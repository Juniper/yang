/*
 * Copyright (c) 2020 Juniper Networks, Inc.
 * All rights reserved.
 */
 module junos-ex-rpc-clear {
   namespace "http://yang.juniper.net/junos-ex/rpc/clear";

   prefix clear;

   import junos-common-ddl-extensions {
     prefix junos;
     revision-date 2019-01-01;
   }

   import junos-common-odl-extensions {
     prefix junos-odl;
     revision-date 2019-01-01;
   }

   import junos-common-types {
     prefix jt;
     revision-date 2019-01-01;
   }

   organization "Juniper Networks, Inc.";

   contact "yang-support@juniper.net";

   description "Junos RPC YANG module for clear command(s)";

   revision 2019-01-01 {
     description "Junos: 20.4R1.12";
   }

   rpc clear-cli-logical-system {
     description "Clear logical system association";
     output {
       choice output_c {
         case output-tag {
           leaf output {
             type string;
           }
         }
         case multichassis-tag {
           anyxml multi-routing-engine-results;
         }
       }
     }
   }
   rpc clear-cli-tenant {
     description "Clear teannt association";
     output {
       choice output_c {
         case output-tag {
           leaf output {
             type string;
           }
         }
         case multichassis-tag {
           anyxml multi-routing-engine-results;
         }
       }
     }
   }
   rpc clear-cli-satellite {
     description "Clear satellite association";
     output {
       choice output_c {
         case output-tag {
           leaf output {
             type string;
           }
         }
         case multichassis-tag {
           anyxml multi-routing-engine-results;
         }
       }
     }
   }
   rpc clear-system-commit {
     description "Clear all pending commit requests";
     input {
       leaf prepared {
         description "Clear prepared commit";
         type empty;
       }
     }
     output {
       choice output_c {
         case output-tag {
           leaf output {
             type string;
           }
         }
         case multichassis-tag {
           anyxml multi-routing-engine-results;
         }
       }
     }
   }
   rpc clear-pending-commit-sync-jobs {
     description "Clear pending commit synchronize jobs";
     output {
       choice output_c {
         case output-tag {
           leaf output {
             type string;
           }
         }
         case multichassis-tag {
           anyxml multi-routing-engine-results;
         }
       }
     }
   }
   rpc clear-system-login-lockout {
     description "Clear login locks on user accounts";
     input {
       choice lockout-choice {
         case all {
           leaf all {
             description "Clear login locks on all user acounts";
             type empty;
           }
         }
         case user {
           leaf user {
             description "Name of user";
             type string;
           }
         }
       }
     }
     output {
       choice output_c {
         case output-tag {
           leaf output {
             type string;
           }
         }
         case actual-tag {
           anyxml clear-system-login-lockout;
         }
         case multichassis-tag {
           anyxml multi-routing-engine-results;
         }
       }
     }
   }
   rpc clear-pfe-multicast-stat {
     description "Clear system packet-forwarding-options";
     input {
       leaf multicast-statistics {
         description "Clear per route multicast counters";
         type empty;
       }
     }
     output {
       choice output_c {
         case output-tag {
           leaf output {
             type string;
           }
         }
         case multichassis-tag {
           anyxml multi-routing-engine-results;
         }
       }
     }
   }
   rpc clear-reboot {
     description "Clear all pending halt or reboot requests";
     input {
       uses command-forwarding;
       leaf both-routing-engines {
         description "Clear halt or reboot on both Routing Engines";
         type empty;
       }
     }
     output {
       choice output_c {
         case output-tag {
           leaf output {
             type string;
           }
         }
         case actual-tag {
           anyxml clear-reboot-status;
         }
         case multichassis-tag {
           anyxml multi-routing-engine-results;
         }
       }
     }
   }
   rpc clear-dhcp-binding-information {
     description "Clear DHCP client binding information";
     input {
       uses command-forwarding;
       leaf address {
         description "Address of DHCP client binding";
         type jt:ipaddr;
       }
     }
     output {
       choice output_c {
         case output-tag {
           leaf output {
             type string;
           }
         }
         case multichassis-tag {
           anyxml multi-routing-engine-results;
         }
       }
     }
   }
   rpc clear-dhcp-conflict-information {
     description "Clear DHCP address conflict";
     input {
       uses command-forwarding;
       leaf address {
         description "DHCP conflict address";
         type jt:ipaddr;
       }
     }
     output {
       choice output_c {
         case output-tag {
           leaf output {
             type string;
           }
         }
         case multichassis-tag {
           anyxml multi-routing-engine-results;
         }
       }
     }
   }
   rpc clear-dhcp-statistics-information {
     description "Clear DHCP statistics";
     output {
       choice output_c {
         case output-tag {
           leaf output {
             type string;
           }
         }
         case multichassis-tag {
           anyxml multi-routing-engine-results;
         }
       }
     }
   }
   rpc clear-subscriber-management-statistics {
     description "Clear subscriber management statistics";
     output {
       choice output_c {
         case output-tag {
           leaf output {
             type string;
           }
         }
         case actual-tag {
           anyxml subscriber-management-statistics;
         }
         case multichassis-tag {
           anyxml multi-routing-engine-results;
         }
       }
     }
   }
   rpc clear-subscriber-management-arp {
     description "Clear subscriber management arp information";
     output {
       choice output_c {
         case output-tag {
           leaf output {
             type string;
           }
         }
         case actual-tag {
           anyxml subscriber-management-arp;
         }
         case multichassis-tag {
           anyxml multi-routing-engine-results;
         }
       }
     }
   }
   rpc clear-subscriber-management-arp-interface {
     description "Name of interface";
     input {
       leaf interface-name {
         description "Name of interface";
         type string;
         mandatory true;
       }
     }
     output {
       choice output_c {
         case output-tag {
           leaf output {
             type string;
           }
         }
         case actual-tag {
           anyxml subscriber-management-arp-interface;
         }
         case multichassis-tag {
           anyxml multi-routing-engine-results;
         }
       }
     }
   }
   rpc clear-subscriber-management-arp-address {
     description "Ipv4 address";
     input {
       leaf ip-address {
         description "Ipv4 address";
         type jt:ipv4addr;
         mandatory true;
       }
     }
     output {
       choice output_c {
         case output-tag {
           leaf output {
             type string;
           }
         }
         case actual-tag {
           anyxml subscriber-management-arp-address;
         }
         case multichassis-tag {
           anyxml multi-routing-engine-results;
         }
       }
     }
   }
   rpc clear-subscriber-management-ipv6-neighbors {
     description "Clear subscriber management ipv6 neighbors information";
     output {
       choice output_c {
         case output-tag {
           leaf output {
             type string;
           }
         }
         case actual-tag {
           anyxml subscriber-management-ipv6-neighbors;
         }
         case multichassis-tag {
           anyxml multi-routing-engine-results;
         }
       }
     }
   }
   rpc clear-subscriber-management-ipv6-neighbor-interface {
     description "Name of interface";
     input {
       leaf interface-name {
         description "Name of interface";
         type string;
         mandatory true;
       }
     }
     output {
       choice output_c {
         case output-tag {
           leaf output {
             type string;
           }
         }
         case actual-tag {
           anyxml subscriber-management-ipv6-neighbor-interface;
         }
         case multichassis-tag {
           anyxml multi-routing-engine-results;
         }
       }
     }
   }
   rpc clear-subscriber-management-ipv6-neighbor-address {
     description "Ipv6 address";
     input {
       leaf interface-name {
         description "Ipv6 address";
         type jt:ipv6addr;
         mandatory true;
       }
     }
     output {
       choice output_c {
         case output-tag {
           leaf output {
             type string;
           }
         }
         case actual-tag {
           anyxml subscriber-management-ipv6-neighbor-address;
         }
         case multichassis-tag {
           anyxml multi-routing-engine-results;
         }
       }
     }
   }
   rpc clear-security-alarm-information {
     description "Clear (acknowledge) security alarms";
     input {
       leaf alarm-id {
         description "Alarm ID filter";
         type union {
           type uint32;
           type string {
             pattern "<.*>|$.*";
           }
         }
       }
       leaf-list alarm-type {
         ordered-by user;
         description "Alarm type filter";
         type enumeration {
           enum "authentication" {
             description "Authentication alarms";
           }
           enum "cryptographic-self-test" {
             description "Cryptographic self-test alarms";
           }
           enum "decryption-failures" {
             description "Decryption failure alarms";
           }
           enum "encryption-failures" {
             description "Encryption failure alarms";
           }
           enum "ike-phase1-failures" {
             description "IKE Phase 1 failure alarms";
           }
           enum "ike-phase2-failures" {
             description "IKE Phase 2 failure alarms";
           }
           enum "key-generation-self-test" {
             description "Key generation self-test alarms";
           }
           enum "non-cryptographic-self-test" {
             description "Non-cryptographic self-test alarms";
           }
           enum "policy" {
             description "Policy alarms";
           }
           enum "replay-attacks" {
             description "Replay attack alarms";
           }
           enum "idp" {
             description "IDP attack alarms";
           }
         }
       }
       leaf newer-than {
         description "Alarms newer than filter (YYYY-MM-DD.HH:MM:SS)";
         type jt:time;
       }
       leaf older-than {
         description "Alarms older than filter (YYYY-MM-DD.HH:MM:SS)";
         type jt:time;
       }
       leaf process {
         description "Process that generated the alarm filter";
         type string;
       }
       leaf severity {
         description "Severity of the alarm filter";
         type enumeration {
           enum "alert" {
             description "Alert severity";
           }
           enum "crit" {
             description "Critical severity";
           }
           enum "debug" {
             description "Debug severity";
           }
           enum "emerg" {
             description "Emergency severity";
           }
           enum "err" {
             description "Error severity";
           }
           enum "info" {
             description "Information severity";
           }
           enum "notice" {
             description "Notice severity";
           }
           enum "warning" {
             description "Warning severity";
           }
         }
       }
       leaf all {
         description "Clear (acknowledge) all security alarms";
         type empty;
       }
     }
     output {
       choice output_c {
         case output-tag {
           leaf output {
             type string;
           }
         }
         case actual-tag {
           anyxml clear-security-alarm-results;
         }
         case multichassis-tag {
           anyxml multi-routing-engine-results;
         }
       }
     }
   }
   rpc clear-security-log-information {
     description "Clear auditable security logs";
     input {
       leaf destination-address {
         description "Destination address and optional prefix length";
         type jt:ipprefix-optional;
       }
       leaf destination-port {
         description "Destination port";
         type union {
           type uint32;
           type string {
             pattern "<.*>|$.*";
           }
         }
       }
       leaf event-id {
         description "Event ID filter";
         type string;
       }
       leaf interface-name {
         description "Name of interface";
         type string;
       }
       leaf older-than {
         description "Events older than filter (YYYY-MM-DD.HH:MM:SS)";
         type jt:time;
       }
       leaf policy-name {
         description "Policy name filter";
         type string;
       }
       leaf process {
         description "Process that generated the event";
         type string;
       }
       leaf protocol {
         description "Protocol filter";
         type string;
       }
       leaf newer-than {
         description "Events newer than filter (YYYY-MM-DD.HH:MM:SS)";
         type jt:time;
       }
       leaf result {
         type enumeration {
           enum "failure" {
             description "Event was a failure";
           }
           enum "success" {
             description "Event was successful";
           }
         }
       }
       leaf severity {
         description "Severity of the event";
         type enumeration {
           enum "alert" {
             description "Alert severity";
           }
           enum "crit" {
             description "Critical severity";
           }
           enum "debug" {
             description "Debug severity";
           }
           enum "emerg" {
             description "Emergency severity";
           }
           enum "err" {
             description "Error severity";
           }
           enum "info" {
             description "Information severity";
           }
           enum "notice" {
             description "Notice severity";
           }
           enum "warning" {
             description "Warning severity";
           }
         }
       }
       leaf source-address {
         description "Source address and optional prefix length";
         type jt:ipprefix-optional;
       }
       leaf source-port {
         description "Source port";
         type union {
           type uint32;
           type string {
             pattern "<.*>|$.*";
           }
         }
       }
       leaf username {
         description "Username filter";
         type string;
       }
       leaf all {
         description "Clear all security log entries";
         type empty;
       }
     }
     output {
       choice output_c {
         case output-tag {
           leaf output {
             type string;
           }
         }
         case actual-tag {
           anyxml clear-security-log-information;
         }
         case multichassis-tag {
           anyxml multi-routing-engine-results;
         }
       }
     }
   }
   rpc clear-pki-certificate-request {
     description "Clear router certificate request";
     input {
       uses command-forwarding;
       choice daemon-select {
         case logical-system {
         }
       }
       choice certificate-request-choice {
         case certificate-id {
           leaf certificate-id {
             description "Certificate identifier";
             type string {
               length "1 .. 32";
               junos:posix-pattern "![/%. ]";
               junos:pattern-message "Must not contain '/', %, '.' or a space";
             }
           }
         }
         case all {
           leaf all {
             description "Clear all certificate requests";
             type empty;
           }
         }
       }
     }
     output {
       choice output_c {
         case output-tag {
           leaf output {
             type string;
           }
         }
         case multichassis-tag {
           anyxml multi-routing-engine-results;
         }
       }
     }
   }
   rpc clear-pki-ca-certificate {
     description "Clear CA/RA certificate";
     input {
       uses command-forwarding;
       choice daemon-select {
         case logical-system {
         }
       }
       choice ca-choice {
         case ca-profile {
           leaf ca-profile {
             description "Certificate authority profile";
             type string {
               length "1 .. 32";
               junos:posix-pattern "![/%. ]";
               junos:pattern-message "Must not contain '/', %, '.' or a space";
             }
           }
         }
         case ca-profile-group {
           leaf ca-profile-group {
             description "Clear CA profile group";
             type string {
               length "1 .. 32";
               junos:posix-pattern "![/%. ]";
               junos:pattern-message "Must not contain '/', %, '.' or a space";
             }
           }
         }
         case all {
           leaf all {
             description "Clear all CA certificates";
             type empty;
           }
         }
       }
     }
     output {
       choice output_c {
         case output-tag {
           leaf output {
             type string;
           }
         }
         case multichassis-tag {
           anyxml multi-routing-engine-results;
         }
       }
     }
   }
   rpc clear-node-local-certificate-request {
     description "Clear router certificate request";
     input {
       uses command-forwarding;
       choice daemon-select {
         case logical-system {
         }
       }
       choice certificate-request-choice {
         case certificate-id {
           leaf certificate-id {
             description "Certificate identifier";
             type string {
               length "1 .. 32";
               junos:posix-pattern "![/%. ]";
               junos:pattern-message "Must not contain '/', %, '.' or a space";
             }
           }
         }
         case all {
           leaf all {
             description "Clear all certificate requests";
             type empty;
           }
         }
       }
     }
     output {
       choice output_c {
         case output-tag {
           leaf output {
             type string;
           }
         }
         case multichassis-tag {
           anyxml multi-routing-engine-results;
         }
       }
     }
   }
   rpc clear-node-local-local-certificate {
     description "Clear local certificate";
     input {
       uses command-forwarding;
       choice daemon-select {
         case logical-system {
         }
       }
       choice certificate-choice {
         case certificate-id {
           leaf certificate-id {
             description "Certificate identifier";
             type string {
               length "1 .. 32";
               junos:posix-pattern "![/%. ]";
               junos:pattern-message "Must not contain '/', %, '.' or a space";
             }
           }
         }
         case system-generated {
           leaf system-generated {
             description "Clear autogenerated self-signed certificate";
             type empty;
           }
         }
         case all {
           leaf all {
             description "Clear all local certificates";
             type empty;
           }
         }
       }
     }
     output {
       choice output_c {
         case output-tag {
           leaf output {
             type string;
           }
         }
         case multichassis-tag {
           anyxml multi-routing-engine-results;
         }
       }
     }
   }
   rpc clear-pki-node-local-key-pair {
     description "Clear key pair";
     input {
       uses command-forwarding;
       choice daemon-select {
         case logical-system {
         }
       }
       choice certificate-choice {
         case certificate-id {
           leaf certificate-id {
             description "Certificate identifier";
             type string {
               length "1 .. 32";
               junos:posix-pattern "![/%. ]";
               junos:pattern-message "Must not contain '/', %, '.' or a space";
             }
           }
         }
         case all {
           leaf all {
             description "Clear all local certificates";
             type empty;
           }
         }
       }
     }
     output {
       choice output_c {
         case output-tag {
           leaf output {
             type string;
           }
         }
         case multichassis-tag {
           anyxml multi-routing-engine-results;
         }
       }
     }
   }
   rpc clear-pki-key-pair {
     description "Clear key pair";
     input {
       uses command-forwarding;
       choice daemon-select {
         case logical-system {
         }
       }
       choice certificate-choice {
         case certificate-id {
           leaf certificate-id {
             description "Certificate identifier";
             type string {
               length "1 .. 32";
               junos:posix-pattern "![/%. ]";
               junos:pattern-message "Must not contain '/', %, '.' or a space";
             }
           }
         }
         case all {
           leaf all {
             description "Clear all local certificates";
             type empty;
           }
         }
       }
     }
     output {
       choice output_c {
         case output-tag {
           leaf output {
             type string;
           }
         }
         case multichassis-tag {
           anyxml multi-routing-engine-results;
         }
       }
     }
   }
   rpc clear-pki-local-certificate {
     description "Clear local certificate";
     input {
       uses command-forwarding;
       choice daemon-select {
         case logical-system {
         }
       }
       choice certificate-choice {
         case certificate-id {
           leaf certificate-id {
             description "Certificate identifier";
             type string {
               length "1 .. 32";
               junos:posix-pattern "![/%. ]";
               junos:pattern-message "Must not contain '/', %, '.' or a space";
             }
           }
         }
         case system-generated {
           leaf system-generated {
             description "Clear autogenerated self-signed certificate";
             type empty;
           }
         }
         case all {
           leaf all {
             description "Clear all local certificates";
             type empty;
           }
         }
       }
     }
     output {
       choice output_c {
         case output-tag {
           leaf output {
             type string;
           }
         }
         case multichassis-tag {
           anyxml multi-routing-engine-results;
         }
       }
     }
   }
   rpc clear-pki-crl {
     description "Clear certificate revocation list";
     input {
       uses command-forwarding;
       choice daemon-select {
         case logical-system {
         }
       }
       choice ca-choice {
         case ca-profile {
           leaf ca-profile {
             description "Certificate authority profile";
             type string {
               length "1 .. 32";
               junos:posix-pattern "![/%. ]";
               junos:pattern-message "Must not contain '/', %, '.' or a space";
             }
           }
         }
         case all {
           leaf all {
             description "Clear all CRLs";
             type empty;
           }
         }
       }
     }
     output {
       choice output_c {
         case output-tag {
           leaf output {
             type string;
           }
         }
         case multichassis-tag {
           anyxml multi-routing-engine-results;
         }
       }
     }
   }
   rpc clear-gvpn-ipsec-security-association {
     description "Clear IPSec dynamic security associations";
     input {
       uses command-forwarding;
       leaf index {
         description "Index of security association";
         type union {
           type string {
             pattern "<.*>|$.*";
           }
           type uint32 {
             range "10001 .. 20000";
           }
         }
       }
       leaf group-id {
         description "Group VPN identification number";
         type union {
           type string {
             pattern "<.*>|$.*";
           }
           type uint32 {
             range "1 .. 4294967295";
           }
         }
       }
       leaf service-set {
         description "Service set name";
         type string {
           junos:posix-pattern "^[A-Za-z0-9][_0-9A-Za-z-]{0,62}$";
           junos:pattern-message "Must be a string beginning with a number or letter and consisting of no more than 63 total letters, numbers, dashes and underscores.";
         }
       }
     }
     output {
       choice output_c {
         case output-tag {
           leaf output {
             type string;
           }
         }
         case multichassis-tag {
           anyxml multi-routing-engine-results;
         }
       }
     }
   }
   rpc clear-gvpn-ipsec-security-association-statistics {
     description "Clear IPSec security associations statistics";
     input {
       leaf group-id {
         description "Group VPN identification number";
         type union {
           type string {
             pattern "<.*>|$.*";
           }
           type uint32 {
             range "1 .. 4294967295";
           }
         }
       }
       leaf service-set {
         description "Service set name";
         type string {
           junos:posix-pattern "^[A-Za-z0-9][_0-9A-Za-z-]{0,62}$";
           junos:pattern-message "Must be a string beginning with a number or letter and consisting of no more than 63 total letters, numbers, dashes and underscores.";
         }
       }
     }
     output {
       choice output_c {
         case output-tag {
           leaf output {
             type string;
           }
         }
         case multichassis-tag {
           anyxml multi-routing-engine-results;
         }
       }
     }
   }
   rpc clear-gvpn-ipsec-statistics {
     description "Clear Group VPN IPSec statistics";
     input {
       uses command-forwarding;
       leaf fpc {
         description "FPC slot number";
         type union {
           type string {
             pattern "<.*>|$.*";
           }
           type uint32;
         }
       }
       leaf pic {
         description "PIC slot number";
         type union {
           type string {
             pattern "<.*>|$.*";
           }
           type uint32;
         }
       }
       leaf index {
         description "Index of security association";
         type union {
           type string {
             pattern "<.*>|$.*";
           }
           type uint32 {
             range "10001 .. 20000";
           }
         }
       }
     }
     output {
       choice output_c {
         case output-tag {
           leaf output {
             type string;
           }
         }
         case multichassis-tag {
           anyxml multi-routing-engine-results;
         }
       }
     }
   }
   rpc clear-group-vpn-ike-security-associations {
     description "Clear group VPN IKE security associations";
     input {
       uses command-forwarding;
       leaf service-set {
         description "Service set name";
         type string {
           junos:posix-pattern "^[A-Za-z0-9][_0-9A-Za-z-]{0,62}$";
           junos:pattern-message "Must be a string beginning with a number or letter and consisting of no more than 63 total letters, numbers, dashes and underscores.";
         }
       }
       leaf peer-address {
         description "IP address of the peer";
         type jt:ipaddr;
       }
       leaf index {
         description "Index of security association";
         default "0";
         type union {
           type uint32;
           type string {
             pattern "<.*>|$.*";
           }
         }
       }
     }
     output {
       choice output_c {
         case output-tag {
           leaf output {
             type string;
           }
         }
         case multichassis-tag {
           anyxml multi-routing-engine-results;
         }
       }
     }
   }
   rpc clear-gvpn-group-information {
     description "Clear IPSec Group VPN";
     input {
       uses command-forwarding;
       leaf group-id {
         description "Group VPN identification number";
         type union {
           type string {
             pattern "<.*>|$.*";
           }
           type uint32 {
             range "1 .. 4294967295";
           }
         }
       }
       leaf vpn {
         description "Group VPN Name";
         type string {
           length "1 .. 32";
         }
       }
       leaf service-set {
         description "Service set name";
         type string {
           junos:posix-pattern "^[A-Za-z0-9][_0-9A-Za-z-]{0,62}$";
           junos:pattern-message "Must be a string beginning with a number or letter and consisting of no more than 63 total letters, numbers, dashes and underscores.";
         }
       }
     }
     output {
       choice output_c {
         case output-tag {
           leaf output {
             type string;
           }
         }
         case multichassis-tag {
           anyxml multi-routing-engine-results;
         }
       }
     }
   }
   rpc clear-mka-statistics {
     description "Clear MKA statistics information";
     output {
       choice output_c {
         case output-tag {
           leaf output {
             type string;
           }
         }
         case actual-tag {
           anyxml mka-statistics;
         }
         case multichassis-tag {
           anyxml multi-routing-engine-results;
         }
       }
     }
   }
   rpc clear-mka-interface-statistics {
     description "Clear MKA statistics information on this interface";
     input {
       choice interface-choice {
         case interface-name {
           leaf interface-name {
             description "Name of interface";
             type union {
               type jt:interface-name;
               type string {
                 pattern "<.*>|$.*";
               }
             }
           }
         }
         case all {
           leaf all {
             description "Clear mka statistics of all interfaces";
             type string;
           }
         }
       }
     }
     output {
       choice output_c {
         case output-tag {
           leaf output {
             type string;
           }
         }
         case actual-tag {
           anyxml mka-statistics;
         }
         case multichassis-tag {
           anyxml multi-routing-engine-results;
         }
       }
     }
   }
   rpc clear-log {
     description "Clear contents of log file";
     input {
       leaf filename {
         description "Name of log file";
         type string {
           junos:posix-pattern "![ =;|(){}]";
           junos:pattern-message "Must not contain any special characters";
         }
         mandatory true;
       }
       leaf all {
         description "Also delete all archive (.gz) files for specified file";
         type empty;
       }
       leaf tenant {
         description "Name of tenant";
         type string {
           junos:posix-pattern "^[a-zA-Z0-9-]{1,63}$";
           junos:pattern-message "Tenant name is a string consisting of up to 63 letters, numbers and dashes";
         }
       }
       leaf logical-system {
         description "Name of logical system";
         type string {
           junos:posix-pattern "^[a-zA-Z0-9_-]{1,63}$";
           junos:pattern-message "Logical-system name is a string consisting of up to 63 letters, numbers, dashes and underscores";
         }
       }
     }
     output {
       choice output_c {
         case output-tag {
           leaf output {
             type string;
           }
         }
         case multichassis-tag {
           anyxml multi-routing-engine-results;
         }
       }
     }
   }
   rpc clear-log-sset {
     description "Name of service-set";
     input {
       leaf filename {
         description "Name of log file";
         type string {
           junos:posix-pattern "![ =;|(){}]";
           junos:pattern-message "Must not contain any special characters [ =;|(){}]";
         }
         mandatory true;
       }
     }
     output {
       choice output_c {
         case output-tag {
           leaf output {
             type string;
           }
         }
         case multichassis-tag {
           anyxml multi-routing-engine-results;
         }
       }
     }
   }
   rpc clear-log-pics {
     description "Name of interface";
     input {
       leaf filename {
         description "Name of log file";
         type string {
           junos:posix-pattern "![ =;|(){}]";
           junos:pattern-message "Must not contain any special characters [ =;|(){}]";
         }
         mandatory true;
       }
     }
     output {
       choice output_c {
         case output-tag {
           leaf output {
             type string;
           }
         }
         case multichassis-tag {
           anyxml multi-routing-engine-results;
         }
       }
     }
   }
   rpc clear-request-response-clients {
     description "Clear client sessions";
     input {
       leaf client-id {
         description "Client ID of session to be terminated";
         type string;
         mandatory true;
       }
     }
     output {
       choice output_c {
         case output-tag {
           leaf output {
             type string;
           }
         }
         case actual-tag {
           anyxml clear-request-response-client-information;
         }
         case multichassis-tag {
           anyxml multi-routing-engine-results;
         }
       }
     }
   }
   rpc clear-rfc2544-information {
     description "Clear rfc2544 information";
     output {
       choice output_c {
         case output-tag {
           leaf output {
             type string;
           }
         }
         case multichassis-tag {
           anyxml multi-routing-engine-results;
         }
       }
     }
   }
   rpc clear-active-tests-information {
     description "Clear rfc2544 active tests";
     input {
       leaf test-id {
         description "Test id";
         type union {
           type uint32;
           type string {
             pattern "<.*>|$.*";
           }
         }
       }
     }
     output {
       choice output_c {
         case output-tag {
           leaf output {
             type string;
           }
         }
         case multichassis-tag {
           anyxml multi-routing-engine-results;
         }
       }
     }
   }
   rpc clear-aborted-tests-information {
     description "Clear rfc2544 aborted tests";
     input {
       leaf test-id {
         description "Test id";
         type union {
           type uint32;
           type string {
             pattern "<.*>|$.*";
           }
         }
       }
     }
     output {
       choice output_c {
         case output-tag {
           leaf output {
             type string;
           }
         }
         case multichassis-tag {
           anyxml multi-routing-engine-results;
         }
       }
     }
   }
   rpc clear-completed-tests-information {
     description "Clear rfc2544 completed tests";
     input {
       leaf test-id {
         description "Test id";
         type union {
           type uint32;
           type string {
             pattern "<.*>|$.*";
           }
         }
       }
     }
     output {
       choice output_c {
         case output-tag {
           leaf output {
             type string;
           }
         }
         case multichassis-tag {
           anyxml multi-routing-engine-results;
         }
       }
     }
   }
   rpc clear-services-ipsec-vpn-security-associations {
     description "Clear IPSec dynamic security associations";
     input {
       leaf service-set {
         description "Name of service set";
         type string {
           junos:posix-pattern "^[A-Za-z0-9][_0-9A-Za-z-]{0,62}$";
           junos:pattern-message "Must be a string beginning with a number or letter and consisting of no more than 63 total letters, numbers, dashes and underscores.";
         }
       }
       leaf tunnel-index {
         description "Tunnel index";
         type union {
           type uint32;
           type string {
             pattern "<.*>|$.*";
           }
         }
       }
       leaf remote-gateway {
         description "Peer address to use as filter";
         type jt:ipaddr;
       }
     }
     output {
       choice output_c {
         case output-tag {
           leaf output {
             type string;
           }
         }
         case multichassis-tag {
           anyxml multi-routing-engine-results;
         }
       }
     }
   }
   rpc clear-ipsec-vpn-statistics {
     description "Clear IPSec statistics";
     input {
       leaf remote-gateway {
         description "Peer address to use as filter";
         type string;
       }
       leaf service-set {
         description "Name of service set";
         type string;
       }
     }
     output {
       choice output_c {
         case output-tag {
           leaf output {
             type string;
           }
         }
         case multichassis-tag {
           anyxml multi-routing-engine-results;
         }
       }
     }
   }
   rpc clear-services-ike-security-associations {
     description "Clear IKE security associations";
     input {
       leaf peer-address {
         description "Name of security association";
         type jt:ipaddr;
       }
       leaf routing-instance {
         description "Name of the local-gateway routing-instance";
         type string;
       }
       leaf service-set {
         description "Name of service set";
         type string {
           junos:posix-pattern "^[A-Za-z0-9][_0-9A-Za-z-]{0,62}$";
           junos:pattern-message "Must be a string beginning with a number or letter and consisting of no more than 63 total letters, numbers, dashes and underscores.";
         }
       }
     }
     output {
       choice output_c {
         case output-tag {
           leaf output {
             type string;
           }
         }
         case multichassis-tag {
           anyxml multi-routing-engine-results;
         }
       }
     }
   }
   rpc clear-services-ike-statistics {
     description "Clear IKE security associations statistics";
     input {
       leaf peer-address {
         description "Name of security association";
         type jt:ipaddr;
       }
       leaf routing-instance {
         description "Name of the local-gateway routing-instance";
         type string;
       }
       leaf service-set {
         description "Name of service set";
         type string {
           junos:posix-pattern "^[A-Za-z0-9][_0-9A-Za-z-]{0,62}$";
           junos:pattern-message "Must be a string beginning with a number or letter and consisting of no more than 63 total letters, numbers, dashes and underscores.";
         }
       }
     }
     output {
       choice output_c {
         case output-tag {
           leaf output {
             type string;
           }
         }
         case multichassis-tag {
           anyxml multi-routing-engine-results;
         }
       }
     }
   }
   rpc clear-ipsec-certificates-service-set {
     description "Clear certificates for one or all service sets";
     input {
       choice specific-or-all-service-set {
         case service-set {
           leaf service-set {
             description "Name of service set for which to clear certificates";
             type string {
               junos:posix-pattern "^[A-Za-z0-9][_0-9A-Za-z-]{0,62}$";
               junos:pattern-message "Must be a string beginning with a number or letter and consisting of no more than 63 total letters, numbers, dashes and underscores.";
             }
           }
         }
         case all {
           leaf all {
             description "Clear all local and remote certificates";
             type empty;
           }
         }
       }
       leaf certificate-cache-entry {
         description "Certificate entry present in the cache";
         type union {
           type int32;
           type string {
             pattern "<.*>|$.*";
           }
         }
       }
     }
     output {
       choice output_c {
         case output-tag {
           leaf output {
             type string;
           }
         }
         case multichassis-tag {
           anyxml multi-routing-engine-results;
         }
       }
     }
   }
   rpc clear-service-accounting-information {
     description "Clear service accouting information";
     output {
       choice output_c {
         case output-tag {
           leaf output {
             type string;
           }
         }
         case multichassis-tag {
           anyxml multi-routing-engine-results;
         }
       }
     }
   }
   rpc clear-service-accounting-statistics {
     description "Clear all statistics";
     output {
       choice output_c {
         case output-tag {
           leaf output {
             type string;
           }
         }
         case multichassis-tag {
           anyxml multi-routing-engine-results;
         }
       }
     }
   }
   rpc clear-service-accouting-flow {
     description "Clear service accouting flows";
     output {
       choice output_c {
         case output-tag {
           leaf output {
             type string;
           }
         }
         case multichassis-tag {
           anyxml multi-routing-engine-results;
         }
       }
     }
   }
   rpc clear-service-video-monitoring-information {
     description "Clear video monitoring service related counters";
     output {
       choice output_c {
         case output-tag {
           leaf output {
             type string;
           }
         }
         case multichassis-tag {
           anyxml multi-routing-engine-results;
         }
       }
     }
   }
   rpc clear-service-video-monitoring-mdi-information {
     description "Clear video monitoring mdi counters";
     output {
       choice output_c {
         case output-tag {
           leaf output {
             type string;
           }
         }
         case multichassis-tag {
           anyxml multi-routing-engine-results;
         }
       }
     }
   }
   rpc clear-service-video-monitoring-mdi-statistics {
     description "Clear all statistics";
     input {
       leaf fpc-slot {
         description "FPC Slot number";
         type union {
           type string {
             pattern "<.*>|$.*";
           }
           type uint32;
         }
         mandatory true;
       }
     }
     output {
       choice output_c {
         case output-tag {
           leaf output {
             type string;
           }
         }
         case multichassis-tag {
           anyxml multi-routing-engine-results;
         }
       }
     }
   }
   rpc clear-service-video-monitoring-mdi-errors {
     description "Clear all error counters";
     input {
       leaf fpc-slot {
         description "FPC Slot number";
         type union {
           type string {
             pattern "<.*>|$.*";
           }
           type uint32;
         }
         mandatory true;
       }
     }
     output {
       choice output_c {
         case output-tag {
           leaf output {
             type string;
           }
         }
         case multichassis-tag {
           anyxml multi-routing-engine-results;
         }
       }
     }
   }
   rpc clear-service-video-monitoring-mdi-alarm-information {
     description "Clear video monitoring mdi alarm counters";
     output {
       choice output_c {
         case output-tag {
           leaf output {
             type string;
           }
         }
         case multichassis-tag {
           anyxml multi-routing-engine-results;
         }
       }
     }
   }
   rpc clear-services-video-monitoring-mdi-alarm-statistics {
     description "Clear all statistics";
     input {
       leaf fpc-slot {
         description "FPC Slot number";
         type union {
           type string {
             pattern "<.*>|$.*";
           }
           type uint32;
         }
         mandatory true;
       }
     }
     output {
       choice output_c {
         case output-tag {
           leaf output {
             type string;
           }
         }
         case multichassis-tag {
           anyxml multi-routing-engine-results;
         }
       }
     }
   }
   rpc clear-services-video-monitoring-mdi-alarm-errors {
     description "Clear all errors";
     input {
       leaf fpc-slot {
         description "FPC Slot number";
         type union {
           type string {
             pattern "<.*>|$.*";
           }
           type uint32;
         }
         mandatory true;
       }
     }
     output {
       choice output_c {
         case output-tag {
           leaf output {
             type string;
           }
         }
         case multichassis-tag {
           anyxml multi-routing-engine-results;
         }
       }
     }
   }
   rpc request-clear-inline-monitoring {
     description "Clear inline-monitoring counters";
     output {
       choice output_c {
         case output-tag {
           leaf output {
             type string;
           }
         }
         case multichassis-tag {
           anyxml multi-routing-engine-results;
         }
       }
     }
   }
   rpc request-clear-inline-monitoring-statistics {
     description "Clear statistics";
     input {
       leaf fpc-slot {
         description "FPC Slot number";
         type union {
           type string {
             pattern "<.*>|$.*";
           }
           type uint32;
         }
         mandatory true;
       }
       leaf instance-name {
         description "Instance name";
         type string;
       }
       leaf collector-name {
         description "Collector name";
         type string;
       }
     }
     output {
       choice output_c {
         case output-tag {
           leaf output {
             type string;
           }
         }
         case multichassis-tag {
           anyxml multi-routing-engine-results;
         }
       }
     }
   }
   rpc clear-service-msp-flow-table-information {
     description "Remove established flows from flow table";
     input {
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf protocol {
         description "IP protocol type to use as filter";
         type string;
       }
       leaf service-set {
         description "Name of service set";
         type string;
       }
       leaf interface {
         description "Name of extension provider interface";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
           enum "pop3" {
             description "Post Office Protocol 3 Protocol";
           }
           enum "smtps" {
             description "Simple Mail Transfer Protocol Over TLS";
           }
           enum "imaps" {
             description "Internet Mail Access Protocol Over TLS";
           }
           enum "pop3s" {
             description "Post Office Protocol 3 Protocol Over TLS";
           }
         }
       }
     }
     output {
       choice output_c {
         case output-tag {
           leaf output {
             type string;
           }
         }
         case actual-tag {
           anyxml service-msp-flow-drain-information;
         }
         case multichassis-tag {
           anyxml multi-routing-engine-results;
         }
       }
     }
   }
   rpc clear-service-msp-session-table-information {
     description "Remove established sessions from sessions table";
     input {
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf protocol {
         description "IP protocol type to use as filter";
         type string;
       }
       leaf service-set {
         description "Name of service set";
         type string;
       }
       leaf interface {
         description "Name of extension provider interface";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
           enum "pop3" {
             description "Post Office Protocol 3 Protocol";
           }
           enum "smtps" {
             description "Simple Mail Transfer Protocol Over TLS";
           }
           enum "imaps" {
             description "Internet Mail Access Protocol Over TLS";
           }
           enum "pop3s" {
             description "Post Office Protocol 3 Protocol Over TLS";
           }
         }
       }
     }
     output {
       choice output_c {
         case output-tag {
           leaf output {
             type string;
           }
         }
         case actual-tag {
           anyxml service-msp-session-drain-information;
         }
         case multichassis-tag {
           anyxml multi-routing-engine-results;
         }
       }
     }
   }
   rpc clear-service-msp-session-analysis-information {
     description "Clear service session analysis counter statistics";
     input {
       leaf interface {
         description "Name of extension provider interface";
         type string;
       }
     }
     output {
       choice output_c {
         case output-tag {
           leaf output {
             type string;
           }
         }
         case actual-tag {
           anyxml clear-service-msp-session-analysis-information;
         }
         case multichassis-tag {
           anyxml multi-routing-engine-results;
         }
       }
     }
   }
   rpc clear-service-msp-subscriber-analyis-counters-information {
     description "Remove established subscriber analysis counters";
     input {
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf protocol {
         description "IP protocol type to use as filter";
         type string;
       }
       leaf service-set {
         description "Name of service set";
         type string;
       }
       leaf interface {
         description "Name of extension provider interface";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
           enum "pop3" {
             description "Post Office Protocol 3 Protocol";
           }
           enum "smtps" {
             description "Simple Mail Transfer Protocol Over TLS";
           }
           enum "imaps" {
             description "Internet Mail Access Protocol Over TLS";
           }
           enum "pop3s" {
             description "Post Office Protocol 3 Protocol Over TLS";
           }
         }
       }
     }
     output {
       choice output_c {
         case output-tag {
           leaf output {
             type string;
           }
         }
         case actual-tag {
           anyxml service-msp-subscriber-analysis-counters-information;
         }
         case multichassis-tag {
           anyxml multi-routing-engine-results;
         }
       }
     }
   }
   rpc clear-service-subscriber-analysis-information {
     description "Clear service subscribers counter statistics";
     input {
       leaf interface {
         description "Name of extension provider interface";
         type string;
       }
     }
     output {
       choice output_c {
         case output-tag {
           leaf output {
             type string;
           }
         }
         case actual-tag {
           anyxml clear-msp-service-subscriber-analysis-information;
         }
         case multichassis-tag {
           anyxml multi-routing-engine-results;
         }
       }
     }
   }
   rpc clear-service-pcp-epoch {
     description "Clear pcp epoch information";
     input {
       leaf interface {
         description "Name of adaptive services interface";
         type string;
       }
       leaf server-name {
         description "Server name";
         type string;
       }
     }
     output {
       choice output_c {
         case output-tag {
           leaf output {
             type string;
           }
         }
         case actual-tag {
           anyxml service-pcp-epoch-information;
         }
         case multichassis-tag {
           anyxml multi-routing-engine-results;
         }
       }
     }
   }
   rpc clear-service-pcp-statistics {
     description "Clear PCP statistics";
     input {
       leaf interface {
         description "Name of adaptive services interface";
         type string;
       }
     }
     output {
       choice output_c {
         case output-tag {
           leaf output {
             type string;
           }
         }
         case actual-tag {
           anyxml service-pcp-statistics-drain-information;
         }
         case multichassis-tag {
           anyxml multi-routing-engine-results;
         }
       }
     }
   }
   rpc clear-dhcp-service-statistics-information {
     description "Clear DHCP service statistics";
     input {
       leaf interface {
         description "Name of interface";
         type union {
           type jt:interface-name;
           type string {
             pattern "<.*>|$.*";
           }
         }
       }
     }
     output {
       choice output_c {
         case output-tag {
           leaf output {
             type string;
           }
         }
         case multichassis-tag {
           anyxml multi-routing-engine-results;
         }
       }
     }
   }
   rpc clear-dhcp-relay-binding-information {
     description "Clear DHCP client binding information";
     input {
       choice binding-clear-choice {
         case address {
           leaf address {
             description "IP address or MAC address or Session Id of DHCP client binding";
             type string;
           }
         }
         case interfaces-wildcard {
           leaf interfaces-wildcard {
             description "Interfaces to clear bindings on (can be '*' wildcard)";
             type string {
               junos:posix-pattern "^( (((ge-)|(mge-)|(xe-)|(et-))( [[:digit:]]+(-([[:digit:]]+))+(-([[:digit:]]+)?)?)?) | (ae))+$";
               junos:pattern-message "Must be an interface wildcard string";
             }
           }
         }
         case interfaces-vlan {
           leaf interfaces-vlan {
             description "Interface VLAN-ID/SVLAN-ID on which to clear bindings";
             type string {
               junos:posix-pattern "^(( (((ge-)|(mge-)|(xe-)|(et-))( [[:digit:]]+(-([[:digit:]]+))+(-([[:digit:]]+)?)?)?) | (ae))(/:)([[:digit:]]+(-[[:digit:]]+))?)+$";
               junos:pattern-message "Must be an interface:VLAN string";
             }
           }
         }
         case all {
           leaf all {
             description "Clear all bindings";
             type empty;
           }
         }
       }
       leaf routing-instance {
         description "Name of routing instance";
         type string;
       }
       leaf bridge-domain {
         description "Name of bridge domain";
         type string;
       }
       choice force_choice {
         case dual-stack {
           leaf dual-stack {
             description "Clear dual stack bindings";
             type empty;
           }
         }
       }
       choice lsys-tenant {
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcp-interface-bindings {
     description "Name of interface on which to clear bindings";
     input {
       leaf interface-name {
         description "Name of interface";
         type string;
         mandatory true;
       }
     }
     output {
       choice output_c {
         case output-tag {
           leaf output {
             type string;
           }
         }
         case multichassis-tag {
           anyxml multi-routing-engine-results;
         }
       }
     }
   }
   rpc clear-dhcp-relay-statistics-information {
     description "Clear DHCP statistics";
     input {
       leaf routing-instance {
         description "Name of routing instance";
         type string;
       }
       leaf bridge-domain {
         description "Name of bridge domain";
         type string;
       }
       choice lsys-tenant {
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcp-relay-leasequery-statistics {
     description "Clear DHCP relay leasequery statistics";
     input {
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcp-relay-bulk-leasequery-conn-statistics {
     description "Clear DHCP relay bulk leasequery conn statistics";
     input {
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcp-relay-lockout-entries-information {
     description "Clear DHCP lockout entries";
     input {
       choice clear-lockout-entry {
         case index {
           leaf index {
             description "Clear lockout entry by index";
             type union {
               type uint32;
               type string {
                 pattern "<.*>|$.*";
               }
             }
           }
         }
         case all {
           leaf all {
             description "Clear all lockout entry";
             type empty;
           }
         }
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcp-relay-alq-information-statistics-peer {
     description "Clear active-leasequery peer statistics";
     input {
       leaf peer-address {
         description "Active-leasequery peer address";
         type jt:ipaddr;
         mandatory true;
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcp-relay-alq-info-statistics-interface {
     description "Clear active-leasequery interface statistics";
     input {
       leaf interface-name {
         description "Active-leasequery interface name";
         type string;
         mandatory true;
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcp-server-binding-information {
     description "Clear DHCP client binding information";
     input {
       choice binding-clear-choice {
         case address {
           leaf address {
             description "IP address or MAC address or Session Id of DHCP client binding";
             type string;
           }
         }
         case interfaces-wildcard {
           leaf interfaces-wildcard {
             description "Interfaces to clear bindings on (can be '*' wildcard)";
             type string {
               junos:posix-pattern "^( (((ge-)|(mge-)|(xe-)|(et-))( [[:digit:]]+(-([[:digit:]]+))+(-([[:digit:]]+)?)?)?) | (ae))+$";
               junos:pattern-message "Must be an interface wildcard string";
             }
           }
         }
         case interfaces-vlan {
           leaf interfaces-vlan {
             description "Interface VLAN-ID/SVLAN-ID on which to clear bindings";
             type string {
               junos:posix-pattern "^(( (((ge-)|(mge-)|(xe-)|(et-))( [[:digit:]]+(-([[:digit:]]+))+(-([[:digit:]]+)?)?)?) | (ae))(/:)([[:digit:]]+(-[[:digit:]]+))?)+$";
               junos:pattern-message "Must be an interface:VLAN string";
             }
           }
         }
         case all {
           leaf all {
             description "Clear all bindings";
             type empty;
           }
         }
       }
       leaf routing-instance {
         description "Name of routing instance";
         type string;
       }
       choice force_choice {
         case dual-stack {
           leaf dual-stack {
             description "Clear dual stack bindings";
             type empty;
           }
         }
       }
       choice lsys-tenant {
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcp-server-binding-interface {
     description "Name of interface on which to clear bindings";
     input {
       leaf interface-name {
         description "Name of interface";
         type string;
         mandatory true;
       }
     }
     output {
       choice output_c {
         case output-tag {
           leaf output {
             type string;
           }
         }
         case multichassis-tag {
           anyxml multi-routing-engine-results;
         }
       }
     }
   }
   rpc clear-server-statistics-information {
     description "Clear DHCP server statistics";
     input {
       leaf routing-instance {
         description "Name of routing instance";
         type string;
       }
       choice lsys-tenant {
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcp-server-bulk-leasequery-statistics {
     description "Show DHCP server bulk leasequeery statistics";
     input {
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcp-server-lockout-entries-information {
     description "Clear DHCP lockout entries";
     input {
       choice clear-lockout-entry {
         case index {
           leaf index {
             description "Clear lockout entry by index";
             type union {
               type uint32;
               type string {
                 pattern "<.*>|$.*";
               }
             }
           }
         }
         case all {
           leaf all {
             description "Clear all lockout entry";
             type empty;
           }
         }
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcp-client-binding-information {
     description "Clear DHCP client binding information";
     input {
       choice binding-clear-choice {
         case interface {
           leaf interface {
             description "Name of interface";
             type string;
           }
         }
         case all {
           leaf all {
             description "Clear all bindings";
             type empty;
           }
         }
       }
       leaf routing-instance {
         description "Name of routing instance";
         type string;
       }
       choice lsys-tenant {
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-client-statistics-information {
     description "Clear DHCP client statistics";
     input {
       leaf routing-instance {
         description "Name of routing instance";
         type string;
       }
       choice lsys-tenant {
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-proxy-client-statistics-information {
     description "Clear DHCP client statistics";
     input {
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcpv6-service-statistics-information {
     description "Clear DHCPv6 service statistics";
     input {
       leaf interface {
         description "Name of interface";
         type union {
           type jt:interface-name;
           type string {
             pattern "<.*>|$.*";
           }
         }
       }
     }
     output {
       choice output_c {
         case output-tag {
           leaf output {
             type string;
           }
         }
         case multichassis-tag {
           anyxml multi-routing-engine-results;
         }
       }
     }
   }
   rpc clear-dhcpv6-relay-binding-information {
     description "Clear DHCPv6 client binding information";
     input {
       choice binding-clear-choice {
         case address {
           leaf address {
             description "IPv6 Prefix, session-id or CID of DHCPv6 client binding";
             type string;
           }
         }
         case interfaces-wildcard {
           leaf interfaces-wildcard {
             description "Interfaces to clear bindings on (can be '*' wildcard)";
             type string {
               junos:posix-pattern "^( (((ge-)|(mge-)|(xe-)|(et-))( [[:digit:]]+(-([[:digit:]]+))+(-([[:digit:]]+)?)?)?) | (ae))+$";
               junos:pattern-message "Must be an interface wildcard string";
             }
           }
         }
         case interfaces-vlan {
           leaf interfaces-vlan {
             description "Interface VLAN-ID/SVLAN-ID on which to clear bindings";
             type string {
               junos:posix-pattern "^(( (((ge-)|(mge-)|(xe-)|(et-))( [[:digit:]]+(-([[:digit:]]+))+(-([[:digit:]]+)?)?)?) | (ae))(/:)([[:digit:]]+(-[[:digit:]]+))?)+$";
               junos:pattern-message "Must be an interface:VLAN string";
             }
           }
         }
         case all {
           leaf all {
             description "Clear all bindings";
             type empty;
           }
         }
       }
       leaf routing-instance {
         description "Name of routing instance";
         type string;
       }
       choice force_choice {
         case dual-stack {
           leaf dual-stack {
             description "Clear dual stack bindings";
             type empty;
           }
         }
       }
       choice lsys-tenant {
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcpv6-relay-binding-interface {
     description "Name of interface on which to clear bindings";
     input {
       leaf interface-name {
         description "Name of interface";
         type string;
         mandatory true;
       }
     }
     output {
       choice output_c {
         case output-tag {
           leaf output {
             type string;
           }
         }
         case multichassis-tag {
           anyxml multi-routing-engine-results;
         }
       }
     }
   }
   rpc clear-dhcpv6-relay-statistics-information {
     description "Clear DHCPv6 relay statistics";
     input {
       leaf routing-instance {
         description "Name of routing instance";
         type string;
       }
       choice lsys-tenant {
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcpv6-relay-leasequery-statistics {
     description "Clear DHCP relay leasequery statistics";
     input {
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcpv6-relay-bulk-leasequery-conn-statistics {
     description "Clear DHCP relay bulk leasequery conn statistics";
     input {
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcpv6-relay-lockout-entries-information {
     description "Clear DHCP lockout entries";
     input {
       choice clear-lockout-entry {
         case index {
           leaf index {
             description "Clear lockout entry by index";
             type union {
               type uint32;
               type string {
                 pattern "<.*>|$.*";
               }
             }
           }
         }
         case all {
           leaf all {
             description "Clear all lockout entry";
             type empty;
           }
         }
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcpv6-relay-alq-info-statistics-peer {
     description "Clear active-leasequery peer statistics";
     input {
       leaf peer-address {
         description "Active-leasequery peer address";
         type jt:ipaddr;
         mandatory true;
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcpv6-relay-alq-info-statistics-interface {
     description "Clear active-leasequery interface statistics";
     input {
       leaf interface-name {
         description "Active-leasequery interface name";
         type string;
         mandatory true;
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcpv6-server-binding-information {
     description "Clear DHCPv6 client binding information";
     input {
       choice binding-clear-choice {
         case address {
           leaf address {
             description "IPv6 Prefix, session-id or CID of DHCPv6 client binding";
             type string;
           }
         }
         case interfaces-wildcard {
           leaf interfaces-wildcard {
             description "Interfaces to clear bindings on (can be '*' wildcard)";
             type string {
               junos:posix-pattern "^( (((ge-)|(mge-)|(xe-)|(et-))( [[:digit:]]+(-([[:digit:]]+))+(-([[:digit:]]+)?)?)?) | (ae))+$";
               junos:pattern-message "Must be an interface wildcard string";
             }
           }
         }
         case interfaces-vlan {
           leaf interfaces-vlan {
             description "Interface VLAN-ID/SVLAN-ID on which to clear bindings";
             type string {
               junos:posix-pattern "^(( (((ge-)|(mge-)|(xe-)|(et-))( [[:digit:]]+(-([[:digit:]]+))+(-([[:digit:]]+)?)?)?) | (ae))(/:)([[:digit:]]+(-[[:digit:]]+))?)+$";
               junos:pattern-message "Must be an interface:VLAN string";
             }
           }
         }
         case all {
           leaf all {
             description "Clear all bindings";
             type empty;
           }
         }
       }
       leaf routing-instance {
         description "Name of routing instance";
         type string;
       }
       choice force_choice {
         case dual-stack {
           leaf dual-stack {
             description "Clear dual stack bindings";
             type empty;
           }
         }
       }
       choice lsys-tenant {
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcpv6-server-binding-interface {
     description "Name of interface on which to clear bindings";
     input {
       leaf interface-name {
         description "Name of interface";
         type string;
         mandatory true;
       }
     }
     output {
       choice output_c {
         case output-tag {
           leaf output {
             type string;
           }
         }
         case multichassis-tag {
           anyxml multi-routing-engine-results;
         }
       }
     }
   }
   rpc clear-dhcpv6-server-statistics-information {
     description "Clear DHCPv6 server statistics";
     input {
       leaf routing-instance {
         description "Name of routing instance";
         type string;
       }
       choice lsys-tenant {
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcpv6-server-bulk-leasequery-statistics {
     description "Show DHCP server bulk leasequeery statistics";
     input {
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcpv6-server-lockout-entries-information {
     description "Clear DHCP lockout entries";
     input {
       choice clear-lockout-entry {
         case index {
           leaf index {
             description "Clear lockout entry by index";
             type union {
               type uint32;
               type string {
                 pattern "<.*>|$.*";
               }
             }
           }
         }
         case all {
           leaf all {
             description "Clear all lockout entry";
             type empty;
           }
         }
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcpv6-client-binding-information {
     description "Clear DHCPV6 client binding information";
     input {
       choice binding-clear-choice {
         case interface {
           leaf interface {
             description "Name of interface";
             type string;
           }
         }
         case all {
           leaf all {
             description "Clear all bindings";
             type empty;
           }
         }
       }
       leaf routing-instance {
         description "Name of routing instance";
         type string;
       }
       choice lsys-tenant {
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcpv6-client-statistics-information {
     description "Clear DHCPV6 client statistics";
     input {
       leaf routing-instance {
         description "Name of routing instance";
         type string;
       }
       choice lsys-tenant {
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcp-security-binding {
     description "Clear dhcp-security bindings";
     output {
       choice output_c {
         case output-tag {
           leaf output {
             type string;
           }
         }
         case multichassis-tag {
           anyxml multi-routing-engine-results;
         }
       }
     }
   }
   rpc clear-dhcp-security-binding-interface {
     description "Name of interface on which to clear bindings";
     input {
       leaf interface-name {
         description "Name of interface";
         type union {
           type jt:interface-name;
           type string {
             pattern "<.*>|$.*";
           }
         }
         mandatory true;
       }
     }
     output {
       choice output_c {
         case output-tag {
           leaf output {
             type string;
           }
         }
         case multichassis-tag {
           anyxml multi-routing-engine-results;
         }
       }
     }
   }
   rpc clear-dhcp-security-binding-vlan {
     description "Name of vlan on which to clear bindings";
     input {
       leaf vlan-name {
         description "Name of vlan";
         type string;
         mandatory true;
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcp-security-binding-ip-address {
     description "Ip-address to clear bindings";
     input {
       leaf ip-address {
         description "Ip-address";
         type jt:ipv4addr;
         mandatory true;
       }
     }
     output {
       choice output_c {
         case output-tag {
           leaf output {
             type string;
           }
         }
         case multichassis-tag {
           anyxml multi-routing-engine-results;
         }
       }
     }
   }
   rpc clear-dhcp-security-binding-statistics {
     description "Clear DHCP snooping statistics";
     output {
       choice output_c {
         case output-tag {
           leaf output {
             type string;
           }
         }
         case multichassis-tag {
           anyxml multi-routing-engine-results;
         }
       }
     }
   }
   rpc clear-dhcp-security-ipv6-binding {
     description "Clear DHCPv6 security bindings";
     input {
       leaf all {
         description "Clear all bindings";
         type empty;
       }
     }
     output {
       choice output_c {
         case output-tag {
           leaf output {
             type string;
           }
         }
         case multichassis-tag {
           anyxml multi-routing-engine-results;
         }
       }
     }
   }
   rpc clear-dhcp-security-ipv6-binding-interface {
     description "Name of interface on which to clear bindings";
     input {
       leaf interface-name {
         description "Name of interface";
         type union {
           type jt:interface-name;
           type string {
             pattern "<.*>|$.*";
           }
         }
         mandatory true;
       }
     }
     output {
       choice output_c {
         case output-tag {
           leaf output {
             type string;
           }
         }
         case multichassis-tag {
           anyxml multi-routing-engine-results;
         }
       }
     }
   }
   rpc clear-dhcp-security-ipv6-binding-vlan {
     description "Name of vlan on which to clear bindings";
     input {
       leaf vlan-name {
         description "Name of vlan";
         type string;
         mandatory true;
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcp-security-binding-ipv6-address {
     description "IPv6 address to clear bindings";
     input {
       leaf ipv6-address {
         description "IPv6 address";
         type jt:ipv6addr;
         mandatory true;
       }
     }
     output {
       choice output_c {
         case output-tag {
           leaf output {
             type string;
           }
         }
         case multichassis-tag {
           anyxml multi-routing-engine-results;
         }
       }
     }
   }
   rpc clear-dhcp-v6-security-statistics {
     description "Clear DHCPv6 security statistics";
     output {
       choice output_c {
         case output-tag {
           leaf output {
             type string;
           }
         }
         case multichassis-tag {
           anyxml multi-routing-engine-results;
         }
       }
     }
   }
   rpc clear-dhcp-security-statistics {
     description "Clear DHCP security statistics";
     output {
       choice output_c {
         case output-tag {
           leaf output {
             type string;
           }
         }
         case multichassis-tag {
           anyxml multi-routing-engine-results;
         }
       }
     }
   }
   rpc clear-lacp-statistics {
     description "Clear LACP statistics";
     output {
       choice output_c {
         case output-tag {
           leaf output {
             type string;
           }
         }
         case multichassis-tag {
           anyxml multi-routing-engine-results;
         }
       }
     }
   }
   rpc clear-lacp-interface-statistics {
     description "Clear LACP interface statistics";
     input {
       leaf interface-name {
         description "Name of interface";
         type union {
           type jt:interface-wildcard;
           type string {
             pattern "<.*>|$.*";
           }
         }
       }
     }
     output {
       choice output_c {
         case output-tag {
           leaf output {
             type string;
           }
         }
         case multichassis-tag {
           anyxml multi-routing-engine-results;
         }
       }
     }
   }
   rpc clear-lacp-timeouts {
     description "Clear LACP timeout information";
     output {
       choice output_c {
         case output-tag {
           leaf output {
             type string;
           }
         }
         case multichassis-tag {
           anyxml multi-routing-engine-results;
         }
       }
     }
   }
   rpc clear-lacp-interface-timeouts {
     description "Clear LACP interface timeouts";
     input {
       leaf interface-name {
         description "Name of interface";
         type union {
           type jt:interface-wildcard;
           type string {
             pattern "<.*>|$.*";
           }
         }
       }
     }
     output {
       choice output_c {
         case output-tag {
           leaf output {
             type string;
           }
         }
         case multichassis-tag {
           anyxml multi-routing-engine-results;
         }
       }
     }
   }
   rpc clear-lfmd-statistics {
     description "Clear link-fault-management statistics";
     input {
       leaf interface-name {
         description "Name of physical interface";
         type union {
           type jt:interface-device;
           type string {
             pattern "<.*>|$.*";
           }
         }
       }
     }
     output {
       choice output_c {
         case output-tag {
           leaf output {
             type string;
           }
         }
         case actual-tag {
           anyxml lfmd-clear-output;
         }
         case multichassis-tag {
           anyxml multi-routing-engine-results;
         }
       }
     }
   }
   rpc clear-lfmd-action-profile-statistics {
     description "Clear link-fault-management action-profile statistics";
     input {
       leaf action-profile-name {
         description "Name of the action profile to clear";
         type string {
           length "1 .. 32";
         }
         mandatory true;
       }
     }
     output {
       choice output_c {
         case output-tag {
           leaf output {
             type string;
           }
         }
         case actual-tag {
           anyxml lfmd-clear-output;
         }
         case multichassis-tag {
           anyxml multi-routing-engine-results;
         }
       }
     }
   }
   rpc clear-lfmd-state {
     description "Clear link-fault-management state and restart discovery";
     input {
       leaf interface-name {
         description "Name of physical interface";
         type union {
           type jt:interface-device;
           type string {
             pattern "<.*>|$.*";
           }
         }
         mandatory true;
       }
     }
     output {
       choice output_c {
         case output-tag {
           leaf output {
             type string;
           }
         }
         case actual-tag {
           anyxml lfmd-clear-output;
         }
         case multichassis-tag {
           anyxml multi-routing-engine-results;
         }
       }
     }
   }
   rpc clear-cfm-continuity-measurement {
     description "Clear continuity-measurement information";
     input {
       leaf maintenance-domain {
         description "Name of maintenance domain";
         type string {
           length "1 .. 45";
         }
         mandatory true;
       }
       leaf maintenance-association {
         description "Name of maintenance association";
         type string {
           length "1 .. 45";
         }
         mandatory true;
       }
       leaf local-mep {
         description "Identifier for local maintenance endpoint";
         type union {
           type string {
             pattern "<.*>|$.*";
           }
           type uint32 {
             range "1 .. 8191";
           }
         }
       }
       leaf remote-mep {
         description "Identifier for remote maintenance endpoint";
         type union {
           type string {
             pattern "<.*>|$.*";
           }
           type uint32 {
             range "1 .. 8191";
           }
         }
       }
     }
     output {
       choice output_c {
         case output-tag {
           leaf output {
             type string;
           }
         }
         case actual-tag {
           anyxml cfmd-clear-continuity-measurement;
         }
         case multichassis-tag {
           anyxml multi-routing-engine-results;
         }
       }
     }
   }
   rpc clear-cfm-delay-statistics {
     description "Clear Ethernet OAM delay statistics";
     input {
       leaf ethdm-type {
         type enumeration {
           enum "one-way" {
             description "One-way delay measurement";
           }
           enum "two-way" {
             description "Two-way delay measurement";
           }
         }
       }
       leaf maintenance-domain {
         description "Name of maintenance domain";
         type string {
           length "1 .. 45";
         }
         mandatory true;
       }
       leaf maintenance-association {
         description "Name of maintenance association";
         type string {
           length "1 .. 45";
         }
         mandatory true;
       }
       leaf local-mep {
         description "Identifier for local maintenance endpoint";
         type union {
           type string {
             pattern "<.*>|$.*";
           }
           type uint32 {
             range "1 .. 8191";
           }
         }
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case actual-tag {
           anyxml cfmd-clear-delay-statistics;
         }
         case multichassis-tag {
           anyxml multi-routing-engine-results;
         }
       }
     }
   }
   rpc clear-cfm-loss-statistics {
     description "Clear Ethernet OAM loss statistics";
     input {
       leaf maintenance-domain {
         description "Name of maintenance domain";
         type string {
           length "1 .. 45";
         }
         mandatory true;
       }
       leaf maintenance-association {
         description "Name of maintenance association";
         type string {
           length "1 .. 45";
         }
         mandatory true;
       }
       leaf local-mep {
         description "Identifier for local maintenance endpoint";
         type union {
           type string {
             pattern "<.*>|$.*";
           }
           type uint32 {
             range "1 .. 8191";
           }
         }
       }
     }
     output {
       choice output_c {
         case output-tag {
           leaf output {
             type string;
           }
         }
         case actual-tag {
           anyxml cfmd-clear-loss-statistics;
         }
         case multichassis-tag {
           anyxml multi-routing-engine-results;
         }
       }
     }
   }
   rpc clear-cfm-slm-statistics {
     description "Clear Ethernet OAM slm statistics";
     input {
       leaf maintenance-domain {
         description "Name of maintenance domain";
         type string {
           length "1 .. 45";
         }
         mandatory true;
       }
       leaf maintenance-association {
         description "Name of maintenance association";
         type string {
           length "1 .. 45";
         }
         mandatory true;
       }
       leaf local-mep {
         description "Identifier for local maintenance endpoint";
         type union {
           type string {
             pattern "<.*>|$.*";
           }
           type uint32 {
             range "1 .. 8191";
           }
         }
       }
     }
     output {
       choice output_c {
         case output-tag {
           leaf output {
             type string;
           }
         }
         case actual-tag {
           anyxml cfmd-clear-slm-statistics;
         }
         case multichassis-tag {
           anyxml multi-routing-engine-results;
         }
       }
     }
   }
   rpc clear-cfm-statistics {
     description "Clear connectivity-fault-management statistics";
     input {
       leaf interface {
         description "Clear the statistics on an interface";
         type string;
       }
       leaf level {
         description "The maintenance-domain level";
         type union {
           type string {
             pattern "<.*>|$.*";
           }
           type int32 {
             range "0 .. 7";
           }
         }
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-cfm-linktrace-path-database {
     description "Clear linktrace path-database entries of a remote host";
     input {
       leaf maintenance-domain {
         description "Name of maintenance domain";
         type string {
           length "1 .. 45";
         }
         mandatory true;
       }
       leaf maintenance-association {
         description "Name of maintenance association";
         type string {
           length "1 .. 45";
         }
         mandatory true;
       }
       leaf host {
         description "MAC address of remote host in xx:xx:xx:xx:xx:xx format";
         type jt:mac-unicast;
         mandatory true;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-cfm-policer-statistics {
     description "Clear policer statistics";
     input {
       leaf maintenance-domain {
         description "Name of maintenance domain";
         type string {
           length "1 .. 45";
         }
       }
       leaf maintenance-association {
         description "Name of maintenance association";
         type string {
           length "1 .. 45";
         }
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-cfm-iterator-statistics {
     description "Clear Ethernet OAM SLA iterator statistics information";
     input {
       leaf sla-iterator {
         description "Name of the iterator profile";
         type string;
         mandatory true;
       }
       leaf maintenance-domain {
         description "Name of maintenance domain";
         type string {
           length "1 .. 45";
         }
         mandatory true;
       }
       leaf maintenance-association {
         description "Name of maintenance association";
         type string {
           length "1 .. 45";
         }
         mandatory true;
       }
       leaf local-mep {
         description "Identifier for local maintenance endpoint";
         type union {
           type string {
             pattern "<.*>|$.*";
           }
           type uint32 {
             range "1 .. 8191";
           }
         }
         mandatory true;
       }
       leaf remote-mep {
         description "MEP identifier of remote host";
         type union {
           type string {
             pattern "<.*>|$.*";
           }
           type int32 {
             range "1 .. 8191";
           }
         }
         mandatory true;
       }
       leaf current-statistics-type {
         type enumeration {
           enum "loss-measurement" {
             description "Show current Frame Loss measurements";
           }
           enum "availability" {
             description "Show current Availability measurements";
           }
           enum "delay-measurement" {
             description "Show current Delay measurement";
           }
           enum "bin" {
             description "Show current Delay measurement bin";
           }
           enum "flap-trap-statistics" {
             description "Show Flap Trap Statistics ";
           }
         }
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
       leaf verbosity {
         default "brief";
         type enumeration {
           enum "brief" {
             description "Display brief output";
           }
           enum "detail" {
             description "Display detail output";
           }
           enum "extensive" {
             description "Display extensive output";
           }
           enum "summary" {
             description "Display summary output";
           }
         }
       }
     }
     output {
       choice output_c {
         case output-tag {
           leaf output {
             type string;
           }
         }
         case multichassis-tag {
           anyxml multi-routing-engine-results;
         }
       }
     }
   }
   rpc clear-cfm-iterator-history {
     description "Clear MEF 36 based Ethernet OAM SLA iterator History statistics information";
     input {
       leaf sla-iterator {
         description "Name of the iterator profile";
         type string;
         mandatory true;
       }
       leaf maintenance-domain {
         description "Name of maintenance domain";
         type string {
           length "1 .. 45";
         }
         mandatory true;
       }
       leaf maintenance-association {
         description "Name of maintenance association";
         type string {
           length "1 .. 45";
         }
         mandatory true;
       }
       leaf local-mep {
         description "Identifier for local maintenance endpoint";
         type union {
           type string {
             pattern "<.*>|$.*";
           }
           type uint32 {
             range "1 .. 8191";
           }
         }
         mandatory true;
       }
       leaf remote-mep {
         description "MEP identifier of remote host";
         type union {
           type string {
             pattern "<.*>|$.*";
           }
           type int32 {
             range "1 .. 8191";
           }
         }
         mandatory true;
       }
       leaf current-statistics-type {
         type enumeration {
           enum "loss-measurement" {
             description "Show current Frame Loss measurements";
           }
           enum "availability" {
             description "Show current Availability measurements";
           }
           enum "delay-measurement" {
             description "Show current Delay measurement";
           }
           enum "bin" {
             description "Show current Delay measurement bin";
           }
           enum "flap-trap-statistics" {
             description "Show Flap Trap Statistics ";
           }
         }
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-cfm-cfmman-conn-statistics {
     description "Clear Ethernet OAM cfmman connection statistics information";
     input {
       leaf fpc-slot {
         description "Fpc slot number";
         type union {
           type string {
             pattern "<.*>|$.*";
           }
           type uint32 {
             range "0 .. 80";
           }
         }
       }
     }
     output {
       choice output_c {
         case output-tag {
           leaf output {
             type string;
           }
         }
         case multichassis-tag {
           anyxml multi-routing-engine-results;
         }
       }
     }
   }
   rpc clear-elmi-statistics {
     description "Clear ethernet local management statistics";
     input {
       leaf interface {
         description "Name of interface";
         type union {
           type jt:interface-device;
           type string {
             pattern "<.*>|$.*";
           }
         }
       }
     }
     output {
       choice output_c {
         case output-tag {
           leaf output {
             type string;
           }
         }
         case multichassis-tag {
           anyxml multi-routing-engine-results;
         }
       }
     }
   }
   rpc clear-arp-table {
     description "Clear address resolution information";
     input {
       leaf hostname {
         description "Name of host";
         type string;
       }
       leaf interface {
         description "Name of the interface";
         type string;
       }
       leaf vpn {
         description "Name of VPN routing table";
         type string;
       }
       leaf logical-system {
         description "Name of logical system";
         type string;
       }
     }
     output {
       choice output_c {
         case output-tag {
           leaf output {
             type string;
           }
         }
         case actual-tag {
           anyxml clear-arp-table-results;
         }
         case multichassis-tag {
           anyxml multi-routing-engine-results;
         }
       }
     }
   }
   rpc clear-arp-table-all {
     description "Clear All ARP entries";
     output {
       choice output_c {
         case output-tag {
           leaf output {
             type string;
           }
         }
         case actual-tag {
           anyxml clear-arp-table-results;
         }
         case multichassis-tag {
           anyxml multi-routing-engine-results;
         }
       }
     }
   }
   rpc clear-interfaces-interval {
     description "Clear interface interval table";
     input {
       leaf interface-name {
         description "Name of physical interface";
         type string;
         mandatory true;
       }
     }
     output {
       choice output_c {
         case output-tag {
           leaf output {
             type string;
           }
         }
         case multichassis-tag {
           anyxml multi-routing-engine-results;
         }
       }
     }
   }
   rpc clear-interface-transport-opt-c-information {
     description "Clear interface transport optics current information";
     input {
       leaf interface-name {
         description "Name of physical interface";
         type string;
         mandatory true;
       }
     }
     output {
       choice output_c {
         case output-tag {
           leaf output {
             type string;
           }
         }
         case actual-tag {
           anyxml interface-transport-opt-c-information;
         }
         case multichassis-tag {
           anyxml multi-routing-engine-results;
         }
       }
     }
   }
   rpc clear-interface-transport-opt-c-all-information {
     description "Clear interface transport optics current information all interfaces";
     output {
       choice output_c {
         case output-tag {
           leaf output {
             type string;
           }
         }
         case actual-tag {
           anyxml interface-transport-opt-c-all-information;
         }
         case multichassis-tag {
           anyxml multi-routing-engine-results;
         }
       }
     }
   }
   rpc clear-interface-transport-opt-cday-information {
     description "Clear interface transport optics current-day information";
     input {
       leaf interface-name {
         description "Name of physical interface";
         type string;
         mandatory true;
       }
     }
     output {
       choice output_c {
         case output-tag {
           leaf output {
             type string;
           }
         }
         case actual-tag {
           anyxml interface-transport-opt-cday-information;
         }
         case multichassis-tag {
           anyxml multi-routing-engine-results;
         }
       }
     }
   }
   rpc clear-interface-transport-opt-cday-all-information {
     description "Clear interface transport optics current-day information all interfaces";
     output {
       choice output_c {
         case output-tag {
           leaf output {
             type string;
           }
         }
         case actual-tag {
           anyxml interface-transport-opt-cday-all-information;
         }
         case multichassis-tag {
           anyxml multi-routing-engine-results;
         }
       }
     }
   }
   rpc clear-interface-transport-opt-all-information {
     description "Clear interface transport optics all information";
     input {
       leaf interface-name {
         description "Name of physical interface";
         type string;
         mandatory true;
       }
     }
     output {
       choice output_c {
         case output-tag {
           leaf output {
             type string;
           }
         }
         case actual-tag {
           anyxml interface-transport-opt-all-information;
         }
         case multichassis-tag {
           anyxml multi-routing-engine-results;
         }
       }
     }
   }
   rpc clear-interface-transport-opt-all-all-information {
     description "Clear interface transport optics all information all interfaces";
     output {
       choice output_c {
         case output-tag {
           leaf output {
             type string;
           }
         }
         case actual-tag {
           anyxml interface-transport-opt-all-all-information;
         }
         case multichassis-tag {
           anyxml multi-routing-engine-results;
         }
       }
     }
   }
   rpc clear-interface-transport-otn-c-information {
     description "Clear interface transport otn current information";
     input {
       leaf interface-name {
         description "Name of physical interface";
         type string;
         mandatory true;
       }
     }
     output {
       choice output_c {
         case output-tag {
           leaf output {
             type string;
           }
         }
         case actual-tag {
           anyxml interface-transport-otn-c-information;
         }
         case multichassis-tag {
           anyxml multi-routing-engine-results;
         }
       }
     }
   }
   rpc clear-interface-transport-otn-c-all-information {
     description "Clear interface transport otn current information all interfaces";
     output {
       choice output_c {
         case output-tag {
           leaf output {
             type string;
           }
         }
         case actual-tag {
           anyxml interface-transport-otn-c-all-information;
         }
         case multichassis-tag {
           anyxml multi-routing-engine-results;
         }
       }
     }
   }
   rpc clear-interface-transport-otn-cday-information {
     description "Clear interface transport otn current-day information";
     input {
       leaf interface-name {
         description "Name of physical interface";
         type string;
         mandatory true;
       }
     }
     output {
       choice output_c {
         case output-tag {
           leaf output {
             type string;
           }
         }
         case actual-tag {
           anyxml interface-transport-otn-cday-information;
         }
         case multichassis-tag {
           anyxml multi-routing-engine-results;
         }
       }
     }
   }
   rpc clear-interface-transport-otn-cday-all-information {
     description "Clear interface transport otn current-day information all interfaces";
     output {
       choice output_c {
         case output-tag {
           leaf output {
             type string;
           }
         }
         case actual-tag {
           anyxml interface-transport-otn-cday-all-information;
         }
         case multichassis-tag {
           anyxml multi-routing-engine-results;
         }
       }
     }
   }
   rpc clear-interface-transport-otn-all-information {
     description "Clear interface transport otn all information";
     input {
       leaf interface-name {
         description "Name of physical interface";
         type string;
         mandatory true;
       }
     }
     output {
       choice output_c {
         case output-tag {
           leaf output {
             type string;
           }
         }
         case actual-tag {
           anyxml interface-transport-otn-all-information;
         }
         case multichassis-tag {
           anyxml multi-routing-engine-results;
         }
       }
     }
   }
   rpc clear-interface-transport-otn-all-all-information {
     description "Clear interface transport otn all information all interfaces";
     output {
       choice output_c {
         case output-tag {
           leaf output {
             type string;
           }
         }
         case actual-tag {
           anyxml interface-transport-otn-all-all-information;
         }
         case multichassis-tag {
           anyxml multi-routing-engine-results;
         }
       }
     }
   }
   rpc clear-interface-transport-all-c-information {
     description "Clear interface transport both otn and optics current information";
     input {
       leaf interface-name {
         description "Name of physical interface";
         type string;
         mandatory true;
       }
     }
     output {
       choice output_c {
         case output-tag {
           leaf output {
             type string;
           }
         }
         case actual-tag {
           anyxml interface-transport-all-c-information;
         }
         case multichassis-tag {
           anyxml multi-routing-engine-results;
         }
       }
     }
   }
   rpc clear-interface-transport-all-c-all-information {
     description "Clear interface transport both otn and optics current information all interfaces";
     output {
       choice output_c {
         case output-tag {
           leaf output {
             type string;
           }
         }
         case actual-tag {
           anyxml interface-transport-all-c-all-information;
         }
         case multichassis-tag {
           anyxml multi-routing-engine-results;
         }
       }
     }
   }
   rpc clear-interface-transport-all-cday-information {
     description "Clear interface transport both otn and optics current-day information";
     input {
       leaf interface-name {
         description "Name of physical interface";
         type string;
         mandatory true;
       }
     }
     output {
       choice output_c {
         case output-tag {
           leaf output {
             type string;
           }
         }
         case actual-tag {
           anyxml interface-transport-all-cday-information;
         }
         case multichassis-tag {
           anyxml multi-routing-engine-results;
         }
       }
     }
   }
   rpc clear-interface-transport-all-cday-all-information {
     description "Clear interface transport both otn and optics current-day information all interfaces";
     output {
       choice output_c {
         case output-tag {
           leaf output {
             type string;
           }
         }
         case actual-tag {
           anyxml interface-transport-all-cday-all-information;
         }
         case multichassis-tag {
           anyxml multi-routing-engine-results;
         }
       }
     }
   }
   rpc clear-interface-transport-all-all-information {
     description "Clear interface transport both otn and optics all information";
     input {
       leaf interface-name {
         description "Name of physical interface";
         type string;
         mandatory true;
       }
     }
     output {
       choice output_c {
         case output-tag {
           leaf output {
             type string;
           }
         }
         case actual-tag {
           anyxml interface-transport-all-all-information;
         }
         case multichassis-tag {
           anyxml multi-routing-engine-results;
         }
       }
     }
   }
   rpc clear-interface-transport-all-all-all-information {
     description "Clear interface transport both otn and optics all information all interfaces";
     output {
       choice output_c {
         case output-tag {
           leaf output {
             type string;
           }
         }
         case actual-tag {
           anyxml interface-transport-all-all-all-information;
         }
         case multichassis-tag {
           anyxml multi-routing-engine-results;
         }
       }
     }
   }
   rpc clear-interfaces-statistics {
     description "Clear interface statistics";
     input {
       leaf interface-name {
         description "Name of physical or logical interface";
         type string;
         mandatory true;
       }
     }
     output {
       choice output_c {
         case output-tag {
           leaf output {
             type string;
           }
         }
         case multichassis-tag {
           anyxml multi-routing-engine-results;
         }
       }
     }
   }
   rpc clear-interfaces-statistics-all {
     description "Clear statistics for all interfaces";
     output {
       choice output_c {
         case output-tag {
           leaf output {
             type string;
           }
         }
         case multichassis-tag {
           anyxml multi-routing-engine-results;
         }
       }
     }
   }
   rpc clear-interface-set-statistics {
     description "Clear interface-set statistics";
     input {
       leaf interface-set-name {
         description "Name of interface set";
         type string;
       }
     }
     output {
       choice output_c {
         case output-tag {
           leaf output {
             type string;
           }
         }
         case multichassis-tag {
           anyxml multi-routing-engine-results;
         }
       }
     }
   }
   rpc clear-interface-set-statistics-all {
     description "Clear statistics for all interfaces";
     output {
       choice output_c {
         case output-tag {
           leaf output {
             type string;
           }
         }
         case multichassis-tag {
           anyxml multi-routing-engine-results;
         }
       }
     }
   }
   rpc clear-interfaces-mac-database {
     description "Clear interface mac entries or statistics from mac database";
     input {
       leaf interface-name {
         description "Name of physical or logical interface";
         type string;
         mandatory true;
       }
       leaf mac-address {
         description "MAC address";
         type string;
       }
     }
     output {
       choice output_c {
         case output-tag {
           leaf output {
             type string;
           }
         }
         case multichassis-tag {
           anyxml multi-routing-engine-results;
         }
       }
     }
   }
   rpc clear-interface-mac-database-statistics {
     description "Clear interface mac-level statistics from mac database";
     input {
       leaf interface-name {
         description "Name of physical or logical Gigabit or 10-Gigabit Ethernet interface";
         type string;
         mandatory true;
       }
     }
     output {
       choice output_c {
         case output-tag {
           leaf output {
             type string;
           }
         }
         case multichassis-tag {
           anyxml multi-routing-engine-results;
         }
       }
     }
   }
   rpc clear-interface-mac-database-statistics-all {
     description "Clear mac level statistics for all interfaces";
     output {
       choice output_c {
         case output-tag {
           leaf output {
             type string;
           }
         }
         case multichassis-tag {
           anyxml multi-routing-engine-results;
         }
       }
     }
   }
   rpc clear-shmlog-entries {
     description "Clear log entries";
     input {
       leaf logname {
         description "Log name(s). Comma delimited list and wildcarding supported";
         type string;
         mandatory true;
       }
     }
     output {
       choice output_c {
         case output-tag {
           leaf output {
             type string;
           }
         }
         case actual-tag {
           anyxml shmlog;
         }
         case multichassis-tag {
           anyxml multi-routing-engine-results;
         }
       }
     }
   }
   rpc clear-shmlog-statistics {
     description "Clear log statistics";
     input {
       leaf logname {
         description "Log name(s). Comma delimited list and wildcarding supported";
         type string;
         mandatory true;
       }
     }
     output {
       choice output_c {
         case output-tag {
           leaf output {
             type string;
           }
         }
         case actual-tag {
           anyxml shmlog;
         }
         case multichassis-tag {
           anyxml multi-routing-engine-results;
         }
       }
     }
   }
   rpc clear-shmlog-all-information {
     description "Clear log stats and entries";
     input {
       leaf logname {
         description "Log name(s). Comma delimited list and wildcarding supported";
         type string;
         mandatory true;
       }
     }
     output {
       choice output_c {
         case output-tag {
           leaf output {
             type string;
           }
         }
         case actual-tag {
           anyxml shmlog;
         }
         case multichassis-tag {
           anyxml multi-routing-engine-results;
         }
       }
     }
   }
   rpc clear-snmp-statistics {
     description "Clear SNMP statistics";
     output {
       choice output_c {
         case output-tag {
           leaf output {
             type string;
           }
         }
         case multichassis-tag {
           anyxml multi-routing-engine-results;
         }
       }
     }
   }
   rpc clear-snmp-subagent-statistics {
     description "Clear statistics for all SNMP subagents";
     output {
       choice output_c {
         case output-tag {
           leaf output {
             type string;
           }
         }
         case multichassis-tag {
           anyxml multi-routing-engine-results;
         }
       }
     }
   }
   rpc clear-stats-response-statistics-information {
     description "Clear statistics for the stats responses from kernel/PFE";
     output {
       choice output_c {
         case output-tag {
           leaf output {
             type string;
           }
         }
         case multichassis-tag {
           anyxml multi-routing-engine-results;
         }
       }
     }
   }
   rpc clear-snmp-history {
     description "Clear all samples of a particular history index";
     input {
       leaf entry {
         type string;
         mandatory true;
       }
     }
     output {
       choice output_c {
         case output-tag {
           leaf output {
             type string;
           }
         }
         case multichassis-tag {
           anyxml multi-routing-engine-results;
         }
       }
     }
   }
   rpc clear-vrrp-information {
     description "Clear Virtual Router Redundancy Protocol statistics";
     input {
       leaf level {
         default "all";
         type enumeration {
           enum "all" {
             description "Clear all statistics";
           }
         }
       }
     }
     output {
       choice output_c {
         case output-tag {
           leaf output {
             type string;
           }
         }
         case actual-tag {
           anyxml vrrp-message;
         }
         case multichassis-tag {
           anyxml multi-routing-engine-results;
         }
       }
     }
   }
   rpc clear-vrrp-interface-statistics {
     description "Name of interface on which to clear statistics";
     input {
       leaf interface-name {
         description "Name of interface";
         type string;
         mandatory true;
       }
     }
     output {
       choice output_c {
         case output-tag {
           leaf output {
             type string;
           }
         }
         case actual-tag {
           anyxml vrrp-message;
         }
         case multichassis-tag {
           anyxml multi-routing-engine-results;
         }
       }
     }
   }
   rpc clear-ipv6-nd-information {
     description "Clear IPv6 neighbor cache information";
     input {
       leaf host {
         description "Neighbor host IPV6 address";
         type string;
       }
       leaf interface {
         description "Name of the interface";
         type string;
       }
       leaf vpn {
         description "Name of VPN routing table";
         type string;
       }
       leaf logical-system {
         description "Name of logical system";
         type string;
       }
     }
     output {
       choice output_c {
         case output-tag {
           leaf output {
             type string;
           }
         }
         case actual-tag {
           anyxml ipv6-modify-nd;
         }
         case multichassis-tag {
           anyxml multi-routing-engine-results;
         }
       }
     }
   }
   rpc clear-ipv6-all-neighbors {
     description "Clear all neighbors";
     output {
       choice output_c {
         case output-tag {
           leaf output {
             type string;
           }
         }
         case actual-tag {
           anyxml ipv6-modify-nd;
         }
         case multichassis-tag {
           anyxml multi-routing-engine-results;
         }
       }
     }
   }
   rpc clear-ipv6-router-advertisement-information {
     description "Clear IPv6 router advertisement information";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf interface {
         description "Name of interface";
         type string;
       }
     }
     output {
       choice output_c {
         case output-tag {
           leaf output {
             type string;
           }
         }
         case multichassis-tag {
           anyxml multi-routing-engine-results;
         }
       }
     }
   }
   rpc clear-ancp-neighbor-connection {
     description "Clear neighbor connection";
     input {
       choice neighbor-opts {
         case ip-address {
           leaf ip-address {
             description "IP address of the neighbor";
             type jt:ipaddr;
           }
         }
         case system-name {
           leaf system-name {
             description "MAC address of the neighbor";
             type string;
           }
         }
       }
     }
     output {
       choice output_c {
         case output-tag {
           leaf output {
             type string;
           }
         }
         case actual-tag {
           anyxml ancp-neighbor-information;
         }
         case multichassis-tag {
           anyxml multi-routing-engine-results;
         }
       }
     }
   }
   rpc clear-ancp-subscriber-connection {
     description "Clear subscriber connections";
     input {
       choice subscriber-opts {
         case identifier {
           leaf identifier {
             description "Agent circuit identifier";
             type string;
           }
         }
         case ip-address {
           leaf ip-address {
             description "IP address of the neighbor";
             type jt:ipaddr;
           }
         }
         case system-name {
           leaf system-name {
             description "MAC address of the neighbor";
             type string;
           }
         }
       }
     }
     output {
       choice output_c {
         case output-tag {
           leaf output {
             type string;
           }
         }
         case actual-tag {
           anyxml ancp-subscriber-information;
         }
         case multichassis-tag {
           anyxml multi-routing-engine-results;
         }
       }
     }
   }
   rpc clear-ancp-statistics {
     description "Clear statistics";
     input {
       choice neighbor-opts {
         case ip-address {
           leaf ip-address {
             description "IP address of the neighbor";
             type jt:ipaddr;
           }
         }
         case system-name {
           leaf system-name {
             description "MAC address of the neighbor";
             type string;
           }
         }
       }
     }
     output {
       choice output_c {
         case output-tag {
           leaf output {
             type string;
           }
         }
         case multichassis-tag {
           anyxml multi-routing-engine-results;
         }
       }
     }
   }
   rpc clear-ancp-access-loop {
     description "Clear access-loop";
     input {
       choice interface-opts {
         case neighbor {
           leaf neighbor {
             description "IP address of the neighbor";
             type jt:ipaddr;
           }
         }
         case subscriber-interface {
           leaf subscriber-interface {
             description "Subscriber-facing interface";
             type string;
           }
         }
       }
       leaf circuit-id {
         description "Access loop circuit id";
         type string {
           junos:posix-pattern "^.{1,63}$";
           junos:pattern-message "Must be a string of 63 characters or less";
         }
       }
       leaf remote-id {
         description "Access loop remote id";
         type string {
           junos:posix-pattern "^.{1,63}$";
           junos:pattern-message "Must be a string of 63 characters or less";
         }
       }
       leaf outer-vlan-id {
         description "Access aggregation circuit id binary";
         type union {
           type string {
             pattern "<.*>|$.*";
           }
           type uint16 {
             range "1 .. 4094";
           }
         }
       }
     }
     output {
       choice output_c {
         case output-tag {
           leaf output {
             type string;
           }
         }
         case multichassis-tag {
           anyxml multi-routing-engine-results;
         }
       }
     }
   }
   rpc clear-authentication-pending-table {
     description "Clear pending authentication requests";
     input {
       uses command-forwarding;
       leaf clear-authentication-pending-table-specific {
         description "Clear information for a specific request";
         type union {
           type string {
             pattern "<.*>|$.*";
           }
           type uint64 {
             range "1 .. 18446744073709551615";
           }
         }
       }
     }
     output {
       choice output_c {
         case output-tag {
           leaf output {
             type string;
           }
         }
         case multichassis-tag {
           anyxml multi-routing-engine-results;
         }
       }
     }
   }
   rpc clear-authentication-statistics {
     description "Clear general authentication statistics";
     output {
       choice output_c {
         case output-tag {
           leaf output {
             type string;
           }
         }
         case multichassis-tag {
           anyxml multi-routing-engine-results;
         }
       }
     }
   }
   rpc clear-aaa-subscriber-table {
     description "Logout the subscriber and clear the session entry";
     output {
       choice output_c {
         case output-tag {
           leaf output {
             type string;
           }
         }
         case multichassis-tag {
           anyxml multi-routing-engine-results;
         }
       }
     }
   }
   rpc clear-aaa-subscriber-by-username {
     description "Logout the subscriber based on username";
     input {
       uses command-forwarding;
       leaf username {
         description "Username";
         type string;
         mandatory true;
       }
       leaf reconnect {
         description "Reconnect subscriber";
         type empty;
       }
     }
     output {
       choice output_c {
         case output-tag {
           leaf output {
             type string;
           }
         }
         case multichassis-tag {
           anyxml multi-routing-engine-results;
         }
       }
     }
   }
   rpc clear-aaa-subscriber-by-session-id {
     description "Logout the subscriber based on session identifier";
     input {
       uses command-forwarding;
       leaf id {
         description "Session id";
         type union {
           type string {
             pattern "<.*>|$.*";
           }
           type uint64 {
             range "1 .. 18446744073709551615";
           }
         }
         mandatory true;
       }
       leaf reconnect {
         description "Reconnect subscriber";
         type empty;
       }
     }
     output {
       choice output_c {
         case output-tag {
           leaf output {
             type string;
           }
         }
         case multichassis-tag {
           anyxml multi-routing-engine-results;
         }
       }
     }
   }
   rpc clear-aaa-subscriber-table-specific-statistics {
     description "Clear subscriber statistics";
     input {
       uses command-forwarding;
       leaf username {
         description "Subscriber session identifier";
         type string;
         mandatory true;
       }
     }
     output {
       choice output_c {
         case output-tag {
           leaf output {
             type string;
           }
         }
         case multichassis-tag {
           anyxml multi-routing-engine-results;
         }
       }
     }
   }
   rpc clear-aaa-statistics-table {
     description "Statistics on subscriber events";
     input {
       leaf statistics-type {
         type enumeration {
           enum "authentication" {
             description "Authentication statistics";
           }
           enum "accounting" {
             description "Accounting statistics";
           }
           enum "dynamic-requests" {
             description "Dynamic requests statistics";
           }
           enum "re-authentication" {
             description "Re-authentication statistics";
           }
           enum "preauthentication" {
             description "Preauthentication statistics";
           }
           enum "terminate-code" {
             description "Terminate-code usage statistics";
           }
           enum "radius" {
             description "RADIUS statistics";
           }
         }
         mandatory true;
       }
     }
     output {
       choice output_c {
         case output-tag {
           leaf output {
             type string;
           }
         }
         case actual-tag {
           anyxml clear-aaa-module-statistics;
         }
         case multichassis-tag {
           anyxml multi-routing-engine-results;
         }
       }
     }
   }
   rpc clear-aaa-address-assignment-pool-statistics {
     description "Show pool information based on pool name";
     input {
       leaf get-address-assignment-pool-table-specific {
         description "Show information for a specific pool";
         type string;
         mandatory true;
       }
       leaf routing-instance {
         description "Name of routing instance";
         type string;
       }
       choice lsys-tenant {
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-aaa-address-assignment-client-statistics {
     description "Show pool information based on client";
     input {
       leaf routing-instance {
         description "Name of routing instance";
         type string;
       }
       choice lsys-tenant {
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-aaa-session-limit-per-username {
     description "Clear session-limit per username related information";
     input {
       leaf username {
         description "Clear blocked-requests statistics for this username";
         type string;
       }
       leaf access-profile {
         description "Clear blocked-requests statistics for this profile";
         type string;
       }
     }
     output {
       choice output_c {
         case output-tag {
           leaf output {
             type string;
           }
         }
         case multichassis-tag {
           anyxml multi-routing-engine-results;
         }
       }
     }
   }
   rpc clear-node-secret-file {
     description "Delete SecurID authentication node secret file";
     output {
       choice output_c {
         case output-tag {
           leaf output {
             type string;
           }
         }
         case multichassis-tag {
           anyxml multi-routing-engine-results;
         }
       }
     }
   }
   rpc clear-gx-plus-statistics-information {
     description "Clear gx-plus statistics";
     output {
       choice output_c {
         case output-tag {
           leaf output {
             type string;
           }
         }
         case multichassis-tag {
           anyxml multi-routing-engine-results;
         }
       }
     }
   }
   rpc clear-gx-plus-replay-information {
     description "Clear gx-plus replay data: request discovery from remote";
     output {
       choice output_c {
         case output-tag {
           leaf output {
             type string;
           }
         }
         case multichassis-tag {
           anyxml multi-routing-engine-results;
         }
       }
     }
   }
   rpc clear-nasreq-statistics-information {
     description "Clear nasreq statistics";
     output {
       choice output_c {
         case output-tag {
           leaf output {
             type string;
           }
         }
         case multichassis-tag {
           anyxml multi-routing-engine-results;
         }
       }
     }
   }
   rpc clear-pcrf-statistics-information {
     description "Clear pcrf statistics information";
     output {
       choice output_c {
         case output-tag {
           leaf output {
             type string;
           }
         }
         case multichassis-tag {
           anyxml multi-routing-engine-results;
         }
       }
     }
   }
   rpc clear-pcrf-subscribers {
     description "Loguout all pcrf subscribers";
     output {
       choice output_c {
         case output-tag {
           leaf output {
             type string;
           }
         }
         case multichassis-tag {
           anyxml multi-routing-engine-results;
         }
       }
     }
   }
   rpc clear-ocs-statistics-information {
     description "Clear ocs statistics information";
     output {
       choice output_c {
         case output-tag {
           leaf output {
             type string;
           }
         }
         case multichassis-tag {
           anyxml multi-routing-engine-results;
         }
       }
     }
   }
   rpc clear-ocs-backup-information {
     description "Clear ocs backup";
     output {
       choice output_c {
         case output-tag {
           leaf output {
             type string;
           }
         }
         case multichassis-tag {
           anyxml multi-routing-engine-results;
         }
       }
     }
   }
   rpc clear-address-assignment-preserved {
     description "Clear preserved addresses";
     input {
       uses command-forwarding;
       leaf key {
         description "Key to identify reservations";
         type string;
         mandatory true;
       }
     }
     output {
       choice output_c {
         case output-tag {
           leaf output {
             type string;
           }
         }
         case multichassis-tag {
           anyxml multi-routing-engine-results;
         }
       }
     }
   }
   rpc clear-radsec-state {
     description "Clear radsec state";
     input {
       uses command-forwarding;
       leaf radsec-state-destination {
         description "Destination to clear";
         type union {
           type uint32;
           type string {
             pattern "<.*>|$.*";
           }
         }
       }
     }
     output {
       choice output_c {
         case output-tag {
           leaf output {
             type string;
           }
         }
         case multichassis-tag {
           anyxml multi-routing-engine-results;
         }
       }
     }
   }
   rpc clear-radsec-statistics-information {
     description "Clear radsec statistics information";
     input {
       uses command-forwarding;
       leaf radsec-statistics-destination {
         description "Destination to clear";
         type union {
           type uint32;
           type string {
             pattern "<.*>|$.*";
           }
         }
       }
     }
     output {
       choice output_c {
         case output-tag {
           leaf output {
             type string;
           }
         }
         case multichassis-tag {
           anyxml multi-routing-engine-results;
         }
       }
     }
   }
   rpc clear-local-cert-statistics-information {
     description "Clear local certificate statistics information";
     input {
       uses command-forwarding;
       leaf verbosity_level {
         default "brief";
         type enumeration {
           enum "brief" {
             description "Show brief output (deafault)";
           }
           enum "detail" {
             description "Show detailed output";
           }
           enum "extensive" {
             description "Show extensive output";
           }
         }
       }
     }
     output {
       choice output_c {
         case output-tag {
           leaf output {
             type string;
           }
         }
         case multichassis-tag {
           anyxml multi-routing-engine-results;
         }
       }
     }
   }
   rpc clear-auto-configuration-interfaces {
     description "Clear interfaces";
     input {
       leaf interface-name {
         description "Name of interface";
         type string;
         mandatory true;
       }
       leaf client-type {
         description "Client type of subscriber";
         type enumeration {
           enum "vlan" {
             description "VLAN clients only";
           }
           enum "vlan-oob" {
             description "VLAN out-of-band clients only";
           }
           enum "dyn-ip" {
             description "Dynamic IP clients only";
           }
           enum "vpls-pw" {
             description "VPLS-PW clients only";
           }
           enum "dot1x" {
             description "Dot1x clients only";
           }
         }
       }
       leaf subscriber-state {
         description "State of subscriber";
         type enumeration {
           enum "init" {
             description "INIT state only";
           }
           enum "configured" {
             description "CONFIGURED state only";
           }
           enum "active" {
             description "ACTIVE state only";
           }
           enum "terminating" {
             description "TERMINATING state only";
           }
           enum "terminated" {
             description "TERMINATED state only";
           }
         }
       }
     }
     output {
       choice output_c {
         case output-tag {
           leaf output {
             type string;
           }
         }
         case multichassis-tag {
           anyxml multi-routing-engine-results;
         }
       }
     }
   }
   rpc clear-auto-configuration-interfaces-interface-set {
     description "Clear interfaces interface-set";
     input {
       leaf interface-set-name {
         description "Name of interface set";
         type string;
         mandatory true;
       }
     }
     output {
       choice output_c {
         case output-tag {
           leaf output {
             type string;
           }
         }
         case multichassis-tag {
           anyxml multi-routing-engine-results;
         }
       }
     }
   }
   rpc clear-bfd-session-information {
     description "Clear BFD sessions";
     input {
       leaf all {
         description "Cleae all BFD sessions";
         type empty;
         mandatory true;
       }
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-bfd-session-discriminator {
     description "Clear a BFD session by discriminator";
     input {
       leaf discr_number {
         description "Local discriminator of session to clear";
         type union {
           type uint32;
           type string {
             pattern "<.*>|$.*";
           }
         }
         mandatory true;
       }
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-bfd-session-address {
     description "Clear a BFD session by address";
     input {
       leaf session_addr {
         description "Address of session to clear";
         type jt:ipaddr;
         mandatory true;
       }
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-bfd-adaptation-information {
     description "Clear BFD adaptation";
     input {
       leaf all {
         description "Clear BFD adaptation for all sessions";
         type empty;
         mandatory true;
       }
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-bfd-adaptation-discriminator {
     description "Clear BFD adaptation by discriminator";
     input {
       leaf discr_number {
         description "Local discriminator of session to clear";
         type union {
           type uint32;
           type string {
             pattern "<.*>|$.*";
           }
         }
         mandatory true;
       }
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-bfd-adaptation-address {
     description "Clear BFD adaptation by address";
     input {
       leaf session_addr {
         description "Address of session to clear";
         type jt:ipaddr;
         mandatory true;
       }
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-synchronous-ethernet-esmc-statistics {
     description "Clear ESMC statistics";
     input {
       leaf interface-name {
         description "Name of interface ";
         type union {
           type jt:interface-device;
           type string {
             pattern "<.*>|$.*";
           }
         }
       }
     }
     output {
       choice output_c {
         case output-tag {
           leaf output {
             type string;
           }
         }
         case actual-tag {
           anyxml clock-synchronization-clear-output;
         }
         case multichassis-tag {
           anyxml multi-routing-engine-results;
         }
       }
     }
   }
   rpc clear-synchronous-ethernet-wait-to-restore {
     description "Clear wait to restore timer";
     input {
       leaf interface {
         description "Name of physical interface";
         type string;
       }
     }
     output {
       choice output_c {
         case output-tag {
           leaf output {
             type string;
           }
         }
         case actual-tag {
           anyxml clear-wait-to-restore;
         }
         case multichassis-tag {
           anyxml multi-routing-engine-results;
         }
       }
     }
   }
   rpc clear-ptp-long-term-counters {
     description "Clear all long-term delay performance entries";
     output {
       choice output_c {
         case output-tag {
           leaf output {
             type string;
           }
         }
         case actual-tag {
           anyxml ptp-clear-long-term-counters;
         }
         case multichassis-tag {
           anyxml multi-routing-engine-results;
         }
       }
     }
   }
   rpc clear-captive-portal-interface-session {
     description "Clear 802.1X session on an interface";
     input {
       leaf interface-name {
         description "Name of interface";
         default "all";
         type union {
           type jt:interface-name;
           type string {
             pattern "<.*>|$.*";
           }
         }
       }
     }
     output {
       choice output_c {
         case output-tag {
           leaf output {
             type string;
           }
         }
         case actual-tag {
           anyxml captive-portal-interface-session;
         }
         case multichassis-tag {
           anyxml multi-routing-engine-results;
         }
       }
     }
   }
   rpc clear-captive-portal-firewall {
     description "Clear captive-portal firewall statistics for a counter";
     input {
       leaf counter-name {
         description "Clear firewall statistics for this counter";
         default "all";
         type string;
       }
     }
     output {
       choice output_c {
         case output-tag {
           leaf output {
             type string;
           }
         }
         case actual-tag {
           anyxml captive-portal-firewall;
         }
         case multichassis-tag {
           anyxml multi-routing-engine-results;
         }
       }
     }
   }
   rpc clear-captive-portal-firewall-interface {
     description "Clear firewall statistics on this interface";
     input {
       leaf interface-name {
         description "Name of interface";
         default "all";
         type union {
           type jt:interface-name;
           type string {
             pattern "<.*>|$.*";
           }
         }
       }
     }
     output {
       choice output_c {
         case output-tag {
           leaf output {
             type string;
           }
         }
         case multichassis-tag {
           anyxml multi-routing-engine-results;
         }
       }
     }
   }
   rpc clear-captive-portal-mac-session {
     description "Clear 802.1X session on a MAC address";
     input {
       leaf session-mac-addr {
         description "MAC address to clear";
         default "all";
         type jt:mac-addr;
       }
     }
     output {
       choice output_c {
         case output-tag {
           leaf output {
             type string;
           }
         }
         case actual-tag {
           anyxml captive-portal-mac-session;
         }
         case multichassis-tag {
           anyxml multi-routing-engine-results;
         }
       }
     }
   }
   rpc clear-dot1x-eapol-block-interface-session {
     description "Clear eapol-block timer for all sessions on an interface";
     input {
       leaf interface-name {
         description "Name of interface";
         default "all";
         type union {
           type jt:interface-wildcard;
           type string {
             pattern "<.*>|$.*";
           }
         }
       }
     }
     output {
       choice output_c {
         case output-tag {
           leaf output {
             type string;
           }
         }
         case actual-tag {
           anyxml dot1x-eapol-block-interface-session;
         }
         case multichassis-tag {
           anyxml multi-routing-engine-results;
         }
       }
     }
   }
   rpc clear-dot1x-eapol-block-mac-session {
     description "Clear eapol-block timer for session on a MAC address";
     input {
       leaf static-mac-addr {
         description "MAC address to clear eapol-block timer";
         default "all";
         type jt:mac-addr;
       }
     }
     output {
       choice output_c {
         case output-tag {
           leaf output {
             type string;
           }
         }
         case actual-tag {
           anyxml dot1x-eapol-block-mac-session;
         }
         case multichassis-tag {
           anyxml multi-routing-engine-results;
         }
       }
     }
   }
   rpc clear-dot1x-interface-session {
     description "Clear 802.1X session on an interface";
     input {
       leaf interface-name {
         description "Name of interface";
         default "all";
         type union {
           type jt:interface-wildcard;
           type string {
             pattern "<.*>|$.*";
           }
         }
       }
     }
     output {
       choice output_c {
         case output-tag {
           leaf output {
             type string;
           }
         }
         case actual-tag {
           anyxml dot1x-interface-session;
         }
         case multichassis-tag {
           anyxml multi-routing-engine-results;
         }
       }
     }
   }
   rpc clear-dot1x-dynamic-vlan {
     description "Clear 802.1X dynamic created vlan";
     output {
       choice output_c {
         case output-tag {
           leaf output {
             type string;
           }
         }
         case actual-tag {
           anyxml dot1x-dynamic-vlan;
         }
         case multichassis-tag {
           anyxml multi-routing-engine-results;
         }
       }
     }
   }
   rpc clear-dot1x-firewall {
     description "Clear dot1x firewall statistics for a counter";
     input {
       leaf counter-name {
         description "Clear firewall statistics for this counter";
         default "all";
         type string;
       }
     }
     output {
       choice output_c {
         case output-tag {
           leaf output {
             type string;
           }
         }
         case actual-tag {
           anyxml dot1x-firewall;
         }
         case multichassis-tag {
           anyxml multi-routing-engine-results;
         }
       }
     }
   }
   rpc clear-dot1x-firewall-interface {
     description "Clear firewall statistics on this interface";
     input {
       leaf interface-name {
         description "Name of interface";
         default "all";
         type union {
           type jt:interface-wildcard;
           type string {
             pattern "<.*>|$.*";
           }
         }
       }
     }
     output {
       choice output_c {
         case output-tag {
           leaf output {
             type string;
           }
         }
         case actual-tag {
           anyxml dot1x-firewall-interface;
         }
         case multichassis-tag {
           anyxml multi-routing-engine-results;
         }
       }
     }
   }
   rpc clear-dot1x-mac-session {
     description "Clear 802.1X session on a MAC address";
     input {
       leaf static-mac-addr {
         description "MAC address to clear";
         default "all";
         type jt:mac-addr;
       }
     }
     output {
       choice output_c {
         case output-tag {
           leaf output {
             type string;
           }
         }
         case actual-tag {
           anyxml dot1x-mac-session;
         }
         case multichassis-tag {
           anyxml multi-routing-engine-results;
         }
       }
     }
   }
   rpc clear-dot1x-statistics {
     description "Clear 802.1X statistics on an interface";
     output {
       choice output_c {
         case output-tag {
           leaf output {
             type string;
           }
         }
         case actual-tag {
           anyxml dot1x-statistics;
         }
         case multichassis-tag {
           anyxml multi-routing-engine-results;
         }
       }
     }
   }
   rpc clear-dot1x-statistics-interface {
     description "Clear 802.1X statistics on this interface";
     input {
       leaf interface-name {
         description "Name of interface";
         default "all";
         type union {
           type jt:interface-wildcard;
           type string {
             pattern "<.*>|$.*";
           }
         }
       }
     }
     output {
       choice output_c {
         case output-tag {
           leaf output {
             type string;
           }
         }
         case actual-tag {
           anyxml dot1x-statistics-interface;
         }
         case multichassis-tag {
           anyxml multi-routing-engine-results;
         }
       }
     }
   }
   rpc clear-dot1x-recovery-timeout {
     description "Clear port error";
     output {
       choice output_c {
         case output-tag {
           leaf output {
             type string;
           }
         }
         case actual-tag {
           anyxml dot1x-recovery-timeout;
         }
         case multichassis-tag {
           anyxml multi-routing-engine-results;
         }
       }
     }
   }
   rpc clear-dot1x-recovery-timeout-interface {
     description "Clear port error for the specified interface";
     input {
       leaf interface-name {
         description "Name of interface";
         default "all";
         type union {
           type jt:interface-wildcard;
           type string {
             pattern "<.*>|$.*";
           }
         }
       }
     }
     output {
       choice output_c {
         case output-tag {
           leaf output {
             type string;
           }
         }
         case actual-tag {
           anyxml dot1x-recovery-timeout-interface;
         }
         case multichassis-tag {
           anyxml multi-routing-engine-results;
         }
       }
     }
   }
   rpc clear-helper-statistics-information {
     description "Clear helper statistics";
     output {
       choice output_c {
         case output-tag {
           leaf output {
             type string;
           }
         }
         case multichassis-tag {
           anyxml multi-routing-engine-results;
         }
       }
     }
   }
   rpc clear-ilmi-statistics {
     description "Clear ILMI statistics";
     output {
       choice output_c {
         case output-tag {
           leaf output {
             type string;
           }
         }
         case multichassis-tag {
           anyxml multi-routing-engine-results;
         }
       }
     }
   }
   rpc clear-ipsec-security-associations {
     description "Clear IPSec dynamic security associations";
     input {
       leaf sa-name {
         description "Name of security association";
         type string {
           length "1 .. 32";
         }
       }
     }
     output {
       choice output_c {
         case output-tag {
           leaf output {
             type string;
           }
         }
         case multichassis-tag {
           anyxml multi-routing-engine-results;
         }
       }
     }
   }
   rpc clear-ike-security-associations {
     description "Clear IKE security associations";
     input {
       leaf peer-address {
         description "Name of security association";
         type jt:ipaddr;
       }
       leaf routing-instance {
         description "Name of the local-gateway routing-instance";
         type string;
       }
       leaf service-set {
         description "Name of service set";
         type string {
           junos:posix-pattern "^[A-Za-z0-9][_0-9A-Za-z-]{0,62}$";
           junos:pattern-message "Must be a string beginning with a number or letter and consisting of no more than 63 total letters, numbers, dashes and underscores.";
         }
       }
     }
     output {
       choice output_c {
         case output-tag {
           leaf output {
             type string;
           }
         }
         case multichassis-tag {
           anyxml multi-routing-engine-results;
         }
       }
     }
   }
   rpc clear-ike-statistics {
     description "Clear IKE security associations statistics";
     input {
       leaf peer-address {
         description "Name of security association";
         type jt:ipaddr;
       }
       leaf routing-instance {
         description "Name of the local-gateway routing-instance";
         type string;
       }
       leaf service-set {
         description "Name of service set";
         type string {
           junos:posix-pattern "^[A-Za-z0-9][_0-9A-Za-z-]{0,62}$";
           junos:pattern-message "Must be a string beginning with a number or letter and consisting of no more than 63 total letters, numbers, dashes and underscores.";
         }
       }
     }
     output {
       choice output_c {
         case output-tag {
           leaf output {
             type string;
           }
         }
         case multichassis-tag {
           anyxml multi-routing-engine-results;
         }
       }
     }
   }
   rpc clear-diameter-peer {
     description "Clear diameter peer information";
     input {
       leaf clear-peer-what {
         default "connection";
         type enumeration {
           enum "connection" {
             description "Clear diameter peer connection(default)";
           }
           enum "statistics" {
             description "Clear diameter peer statistics";
           }
         }
       }
       leaf clear-diameter-peer-name {
         description "Peer name";
         type string;
         mandatory true;
       }
     }
     output {
       choice output_c {
         case output-tag {
           leaf output {
             type string;
           }
         }
         case multichassis-tag {
           anyxml multi-routing-engine-results;
         }
       }
     }
   }
   rpc clear-diameter-function {
     description "Clear diameter function information";
     input {
       leaf clear-function-what {
         type enumeration {
           enum "statistics" {
             description "Clear diameter function statistics";
           }
         }
         mandatory true;
       }
       leaf clear-diameter-function-name {
         description "Function name";
         type enumeration {
           enum "jsrc" {
             description "Function to use SRC application";
           }
           enum "charging-gw" {
             description "Function to use CHARGING application";
           }
           enum "gx-plus" {
             description "Function to use GX-PLUS application";
           }
           enum "sd-3gpp" {
             description "Function to use SD-3GPP application";
           }
           enum "nasreq" {
             description "Function to use NASREQ application";
           }
           enum "pcrf" {
             description "Function to use PCRF(GX) application";
           }
           enum "ocs" {
             description "Function to use OCS(GY) application";
           }
           enum "s6a" {
             description "Function to use S6A application";
           }
         }
         mandatory true;
       }
     }
     output {
       choice output_c {
         case output-tag {
           leaf output {
             type string;
           }
         }
         case multichassis-tag {
           anyxml multi-routing-engine-results;
         }
       }
     }
   }
   rpc clear-auto-bandwidth-history-log-information {
     description "Clear auto-bandwidth history log";
     output {
       choice output_c {
         case output-tag {
           leaf output {
             type string;
           }
         }
         case multichassis-tag {
           anyxml multi-routing-engine-results;
         }
       }
     }
   }
   rpc clear-auto-bandwidth-traffic-information {
     description "Clear auto-bandwidth probe traffic";
     input {
       choice clear-traffic-arg {
         case all {
           leaf all {
             description "Clear all auto-bandwidth probe traffic";
             type empty;
           }
         }
         case probe-name {
           leaf probe-name {
             description "Name of probe";
             type string;
           }
         }
       }
     }
     output {
       choice output_c {
         case output-tag {
           leaf output {
             type string;
           }
         }
         case multichassis-tag {
           anyxml multi-routing-engine-results;
         }
       }
     }
   }
   rpc clear-pgm-negative-acknowledgments {
     description "Clear PGM NAK state information";
     output {
       choice output_c {
         case output-tag {
           leaf output {
             type string;
           }
         }
         case multichassis-tag {
           anyxml multi-routing-engine-results;
         }
       }
     }
   }
   rpc clear-pgm-source-path-messages {
     description "Clear PGM source path message state information";
     output {
       choice output_c {
         case output-tag {
           leaf output {
             type string;
           }
         }
         case multichassis-tag {
           anyxml multi-routing-engine-results;
         }
       }
     }
   }
   rpc clear-pgm-statistics {
     description "Clear PGM statistics information";
     output {
       choice output_c {
         case output-tag {
           leaf output {
             type string;
           }
         }
         case multichassis-tag {
           anyxml multi-routing-engine-results;
         }
       }
     }
   }
   rpc clear-poe-telemetries-information {
     description "Clear PoE telemetries interface information";
     input {
       leaf interface-name {
         description "Name of the interface";
         type union {
           type jt:interface-device;
           type string {
             pattern "<.*>|$.*";
           }
         }
       }
     }
     output {
       choice output_c {
         case output-tag {
           leaf output {
             type string;
           }
         }
         case multichassis-tag {
           anyxml multi-routing-engine-results;
         }
       }
     }
   }
   rpc clear-amt-tunnel {
     description "Clear AMT tunnel";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
     }
     output {
       choice output_c {
         case output-tag {
           leaf output {
             type string;
           }
         }
         case multichassis-tag {
           anyxml multi-routing-engine-results;
         }
       }
     }
   }
   rpc clear-amt-tunnel-interface {
     description "AMT tunnel interface";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
       leaf interface {
         description "Name of the interface";
         type string;
         mandatory true;
       }
     }
     output {
       choice output_c {
         case output-tag {
           leaf output {
             type string;
           }
         }
         case multichassis-tag {
           anyxml multi-routing-engine-results;
         }
       }
     }
   }
   rpc clear-amt-tunnel-gateway-address {
     description "AMT tunnel gateway address";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
       leaf address {
         description "IP address of the gateway";
         type string;
         mandatory true;
       }
       leaf port {
         description "UDP port of the gateway";
         type union {
           type string {
             pattern "<.*>|$.*";
           }
           type uint16 {
             range "1 .. 65535";
           }
         }
       }
     }
     output {
       choice output_c {
         case output-tag {
           leaf output {
             type string;
           }
         }
         case multichassis-tag {
           anyxml multi-routing-engine-results;
         }
       }
     }
   }
   rpc clear-amt-tunnel-statistics {
     description "Clear AMT tunnel message statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
     }
     output {
       choice output_c {
         case output-tag {
           leaf output {
             type string;
           }
         }
         case multichassis-tag {
           anyxml multi-routing-engine-results;
         }
       }
     }
   }
   rpc clear-amt-tunnel-interface-statistics {
     description "AMT tunnel interface";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
       leaf interface {
         description "Name of the interface";
         type string;
         mandatory true;
       }
     }
     output {
       choice output_c {
         case output-tag {
           leaf output {
             type string;
           }
         }
         case multichassis-tag {
           anyxml multi-routing-engine-results;
         }
       }
     }
   }
   rpc clear-amt-tunnel-gateway-address-statistics {
     description "AMT tunnel gateway address";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
       leaf address {
         description "IP address of the gateway";
         type string;
         mandatory true;
       }
       leaf port {
         description "UDP port of the gateway";
         type union {
           type string {
             pattern "<.*>|$.*";
           }
           type uint16 {
             range "1 .. 65535";
           }
         }
       }
     }
     output {
       choice output_c {
         case output-tag {
           leaf output {
             type string;
           }
         }
         case multichassis-tag {
           anyxml multi-routing-engine-results;
         }
       }
     }
   }
   rpc clear-amt-statistics {
     description "Clear AMT statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
     }
     output {
       choice output_c {
         case output-tag {
           leaf output {
             type string;
           }
         }
         case multichassis-tag {
           anyxml multi-routing-engine-results;
         }
       }
     }
   }
   rpc clear-bgp-damping {
     description "Clear damping information";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
         case fabric {
         }
       }
       leaf prefix {
         description "Destination prefix and prefix length";
         type string;
       }
     }
     output {
       choice output_c {
         case output-tag {
           leaf output {
             type string;
           }
         }
         case multichassis-tag {
           anyxml multi-routing-engine-results;
         }
       }
     }
   }
   rpc clear-bgp-neighbor {
     description "Clear BGP neighbors";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
         case fabric {
         }
       }
       leaf disposition {
         type enumeration {
           enum "soft" {
             description "Soft reset outbound state";
           }
           enum "soft-minimum-igp" {
             description "Soft reset outbound state with refresh of minimum igp MED";
           }
           enum "soft-minimum-effective-aigp" {
             description "Soft reset outbound state with refresh of minimum effective aigp MED";
           }
           enum "soft-inbound" {
             description "Soft reset inbound state by issuing Refresh";
           }
           enum "malformed-route" {
             description "Clear malformed routes";
           }
           enum "stale-routes" {
             description "Clear stale routes";
           }
           enum "gracefully" {
             description "Allow peer to start graceful restart receiving-speaker mode, if possible";
           }
         }
       }
       leaf instance {
         description "Name of BGP instance";
         type string;
       }
       leaf as {
         description " Autonomous system number in plain number or 'higher 16bits'.'Lower 16 bits' (asdot notation) format";
         type string {
           junos:posix-pattern "^[0-9]+(.[0-9]+)?$";
           junos:pattern-message "Use format 'x' or 'x.y' to specify number 'x' (Range 1 .. 4294967295) or number with higher 2 bytes 'x' (Range 0 .. 65535) and lower 2 bytes 'y' (Range 0 .. 65535) respectively";
         }
       }
       choice neighbor-choice {
         case neighbor {
           leaf neighbor {
             description "Particular BGP neighbor to clear";
             type string;
           }
         }
         case all {
           leaf all {
             description "Clear All BGP neighbors";
             type empty;
           }
         }
       }
     }
     output {
       choice output_c {
         case output-tag {
           leaf output {
             type string;
           }
         }
         case multichassis-tag {
           anyxml multi-routing-engine-results;
         }
       }
     }
   }
   rpc clear-bgp-table {
     description "Refresh routes in a routing table";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
         case fabric {
         }
       }
       leaf table {
         description "Name of table to clear";
         type string;
         mandatory true;
       }
     }
     output {
       choice output_c {
         case output-tag {
           leaf output {
             type string;
           }
         }
         case multichassis-tag {
           anyxml multi-routing-engine-results;
         }
       }
     }
   }
   rpc clear-esis-adjacency {
     description "Clear ES-IS adjacencies";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of ES-IS instance";
         type string;
       }
       leaf interface {
         description "Name of interface";
         type string;
       }
       leaf neighbor {
         description "Name of neighbor";
         type string;
       }
     }
     output {
       choice output_c {
         case output-tag {
           leaf output {
             type string;
           }
         }
         case multichassis-tag {
           anyxml multi-routing-engine-results;
         }
       }
     }
   }
   rpc clear-esis-statistics {
     description "Clear ES-IS statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of ES-IS instance";
         type string;
       }
     }
     output {
       choice output_c {
         case output-tag {
           leaf output {
             type string;
           }
         }
         case multichassis-tag {
           anyxml multi-routing-engine-results;
         }
       }
     }
   }
   rpc clear-evpn-duplicate-mac-suppression {
     description "Clear duplicate MAC suppression";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Clear duplicate MAC suppression for a specific instance";
         type string;
       }
       leaf l2-domain-id {
         description "Clear duplicate MAC suppression for a specific L2 domain";
         type union {
           type string {
             pattern "<.*>|$.*";
           }
           type int32 {
             range "1 .. 16777214";
           }
         }
       }
       leaf mac-address {
         description "Clear duplicate MAC suppression for a specific MAC address";
         type jt:mac-addr;
       }
     }
     output {
       choice output_c {
         case output-tag {
           leaf output {
             type string;
           }
         }
         case multichassis-tag {
           anyxml multi-routing-engine-results;
         }
       }
     }
   }
   rpc clear-evpn-mac-table {
     description "Clear all learned media access control addresses";
     input {
       leaf instance {
         description "Display information for a specified instance";
         default "all";
         type string;
       }
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf vlan-id {
         description "Clear MAC address learned on a specified VLAN";
         type string;
       }
       leaf isid {
         description "Clear MAC address learned on a specified ISID";
         type string;
       }
       leaf address {
         description "MAC address";
         default "all";
         type jt:mac-addr;
       }
     }
     output {
       choice output_c {
         case output-tag {
           leaf output {
             type string;
           }
         }
         case multichassis-tag {
           anyxml multi-routing-engine-results;
         }
       }
     }
   }
   rpc clear-evpn-interface-mac-table {
     description "Clear media access control table for specified interface";
     input {
       leaf interface-name {
         description "Name of interface for which to clear table";
         type union {
           type jt:interface-unit;
           type string {
             pattern "<.*>|$.*";
           }
         }
         mandatory true;
       }
       leaf vlan-id {
         description "Clear MAC address learned on a specified VLAN";
         type string;
       }
     }
     output {
       choice output_c {
         case output-tag {
           leaf output {
             type string;
           }
         }
         case multichassis-tag {
           anyxml multi-routing-engine-results;
         }
       }
     }
   }
   rpc clear-evpn-mac-ip-table {
     description "Clear IPv4 and IPv6 entries for EVPN instances";
     input {
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf instance {
         description "Display information for a specified vpls";
         default "all";
         type string;
       }
       leaf address {
         description "MAC address";
         default "all";
         type jt:mac-addr;
       }
     }
     output {
       choice output_c {
         case output-tag {
           leaf output {
             type string;
           }
         }
         case multichassis-tag {
           anyxml multi-routing-engine-results;
         }
       }
     }
   }
   rpc clear-evpn-arp-table {
     description "Clear all INET addresses learned via ARP";
     input {
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf instance {
         description "Display information for a specified vpls";
         default "all";
         type string;
       }
       leaf address {
         description "MAC address";
         default "all";
         type jt:mac-addr;
       }
     }
     output {
       choice output_c {
         case output-tag {
           leaf output {
             type string;
           }
         }
         case multichassis-tag {
           anyxml multi-routing-engine-results;
         }
       }
     }
   }
   rpc clear-evpn-nd-table {
     description "Clear all INET6 addresses learned via NDP";
     input {
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf instance {
         description "Display information for a specified vpls";
         default "all";
         type string;
       }
       leaf address {
         description "MAC address";
         default "all";
         type jt:mac-addr;
       }
     }
     output {
       choice output_c {
         case output-tag {
           leaf output {
             type string;
           }
         }
         case multichassis-tag {
           anyxml multi-routing-engine-results;
         }
       }
     }
   }
   rpc clear-exp-segs-all-information {
     description "Clear express segments";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf segment-type {
         default "all";
         type enumeration {
           enum "all" {
             description "Reset 'all' the express-segments originating on this router";
           }
         }
       }
       leaf clear-exp-segs-name-information {
         description "Reset 'name' matching express-segments - Must select 'name' or 'all'";
         type string;
       }
     }
     output {
       choice output_c {
         case output-tag {
           leaf output {
             type string;
           }
         }
         case multichassis-tag {
           anyxml multi-routing-engine-results;
         }
       }
     }
   }
   rpc clear-exp-segs-trafficd-eng-information {
     description "Clear express-segment insertion into TED";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       choice clear-choice {
         case name {
           leaf clear-exp-segs-traffic-eng-name-information {
             description "Name of express-segment - Must select 'name' or 'all'";
             type string;
           }
         }
         case all {
           leaf all {
             description "All matching express-segments - Must select 'name' or 'all'";
             type empty;
           }
         }
       }
     }
     output {
       choice output_c {
         case output-tag {
           leaf output {
             type string;
           }
         }
         case multichassis-tag {
           anyxml multi-routing-engine-results;
         }
       }
     }
   }
   rpc clear-igmp-statistics {
     description "Clear IGMP statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf interface {
         description "Name of interface";
         type string;
       }
     }
     output {
       choice output_c {
         case output-tag {
           leaf output {
             type string;
           }
         }
         case multichassis-tag {
           anyxml multi-routing-engine-results;
         }
       }
     }
   }
   rpc clear-igmp-membership {
     description "Clear IGMP group membership";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf interface {
         description "Name of interface";
         type string;
       }
       choice clear_arg {
         case group {
           leaf group {
             description "IP address range for group";
             type jt:ipv4prefix;
           }
         }
         case all {
           leaf all {
             description "Clear all IGMP group membership";
             type empty;
           }
         }
       }
     }
     output {
       choice output_c {
         case output-tag {
           leaf output {
             type string;
           }
         }
         case multichassis-tag {
           anyxml multi-routing-engine-results;
         }
       }
     }
   }
   rpc clear-igmp-snooping-statistics {
     description "Clear IGMP snooping statistics";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf interface {
         description "Name of interface";
         type string;
       }
       leaf vlan-id {
         description "VLAN ID for a learning domain";
         type union {
           type string {
             pattern "<.*>|$.*";
           }
           type uint32 {
             range "0 .. 4094";
           }
         }
       }
       leaf instance {
         description "Name of routing-instance";
         type string;
       }
       leaf qualified-vlan {
         description "VLAN ID for a Qualified VLAN";
         type union {
           type string {
             pattern "<.*>|$.*";
           }
           type uint32 {
             range "0 .. 4094";
           }
         }
       }
     }
     output {
       choice output_c {
         case output-tag {
           leaf output {
             type string;
           }
         }
         case multichassis-tag {
           anyxml multi-routing-engine-results;
         }
       }
     }
   }
   rpc clear-igmp-snooping-bridge-domain-statistics {
     description "For a particular bridge-domain";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "detail";
         type enumeration {
           enum "brief" {
             description "Display brief output (default)";
           }
           enum "detail" {
             description "Display detailed output";
           }
         }
       }
       leaf virtual-switch {
         description "Name of virtual-switch instance";
         type string;
       }
       leaf domain-name {
         description "Name of bridge-domain";
         type string;
         mandatory true;
       }
       leaf interface {
         description "Name of interface";
         type string;
       }
       leaf vlan-id {
         description "VLAN ID for a learning domain";
         type union {
           type string {
             pattern "<.*>|$.*";
           }
           type uint32 {
             range "0 .. 4094";
           }
         }
       }
     }
     output {
       choice output_c {
         case output-tag {
           leaf output {
             type string;
           }
         }
         case multichassis-tag {
           anyxml multi-routing-engine-results;
         }
       }
     }
   }
   rpc clear-igmp-snooping-vlan-statistics {
     description "For a particular VLAN";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "detail";
         type enumeration {
           enum "brief" {
             description "Display brief output (default)";
           }
           enum "detail" {
             description "Display detailed output";
           }
         }
       }
       leaf virtual-switch {
         description "Name of virtual-switch instance";
         type string;
       }
       leaf vlan-name {
         description "Name of VLAN";
         type string;
         mandatory true;
       }
       leaf interface {
         description "Name of interface";
         type string;
       }
       leaf qualified-vlan {
         description "VLAN ID for a Qualified VLAN";
         type union {
           type string {
             pattern "<.*>|$.*";
           }
           type uint32 {
             range "0 .. 4094";
           }
         }
       }
     }
     output {
       choice output_c {
         case output-tag {
           leaf output {
             type string;
           }
         }
         case multichassis-tag {
           anyxml multi-routing-engine-results;
         }
       }
     }
   }
   rpc clear-igmp-snooping-membership {
     description "Clear IGMP snooping group membership";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf group {
         description "IP address range for group";
         type jt:ipv4prefix;
       }
       leaf interface {
         description "Name of interface";
         type string;
       }
       leaf vlan-id {
         description "VLAN ID for a learning domain";
         type union {
           type string {
             pattern "<.*>|$.*";
           }
           type uint32 {
             range "0 .. 4094";
           }
         }
       }
       leaf instance {
         description "Name of routing-instance";
         type string;
       }
       leaf qualified-vlan {
         description "VLAN ID for a Qualified VLAN";
         type union {
           type string {
             pattern "<.*>|$.*";
           }
           type uint32 {
             range "0 .. 4094";
           }
         }
       }
     }
     output {
       choice output_c {
         case output-tag {
           leaf output {
             type string;
           }
         }
         case multichassis-tag {
           anyxml multi-routing-engine-results;
         }
       }
     }
   }
   rpc clear-igmp-snooping-bridge-domain-membership {
     description "For a particular bridge-domain";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "detail";
         type enumeration {
           enum "brief" {
             description "Display brief output (default)";
           }
           enum "detail" {
             description "Display detailed output";
           }
         }
       }
       leaf virtual-switch {
         description "Name of virtual-switch instance";
         type string;
       }
       leaf domain-name {
         description "Name of bridge-domain";
         type string;
         mandatory true;
       }
       leaf interface {
         description "Name of interface";
         type string;
       }
       leaf vlan-id {
         description "VLAN ID for a learning domain";
         type union {
           type string {
             pattern "<.*>|$.*";
           }
           type uint32 {
             range "0 .. 4094";
           }
         }
       }
       leaf group {
         description "IP address range for group";
         type jt:ipv4prefix;
       }
     }
     output {
       choice output_c {
         case output-tag {
           leaf output {
             type string;
           }
         }
         case multichassis-tag {
           anyxml multi-routing-engine-results;
         }
       }
     }
   }
   rpc clear-igmp-snooping-vlan-membership {
     description "For a particular VLAN";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "detail";
         type enumeration {
           enum "brief" {
             description "Display brief output (default)";
           }
           enum "detail" {
             description "Display detailed output";
           }
         }
       }
       leaf virtual-switch {
         description "Name of virtual-switch instance";
         type string;
       }
       leaf vlan-name {
         description "Name of VLAN";
         type string;
         mandatory true;
       }
       leaf interface {
         description "Name of interface";
         type string;
       }
       leaf qualified-vlan {
         description "VLAN ID for a Qualified VLAN";
         type union {
           type string {
             pattern "<.*>|$.*";
           }
           type uint32 {
             range "0 .. 4094";
           }
         }
       }
       leaf group {
         description "IP address range for group";
         type jt:ipv4prefix;
       }
     }
     output {
       choice output_c {
         case output-tag {
           leaf output {
             type string;
           }
         }
         case multichassis-tag {
           anyxml multi-routing-engine-results;
         }
       }
     }
   }
   rpc clear-dynamic-tunnels-database-statistics {
     description "Clear dynamic-tunnels statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
         case fabric {
         }
       }
       leaf destination {
         description "IP or IP-color<c> address with optional prefix length of destination";
         type string;
       }
       leaf next-hop {
         description "Clear only tunnel nexthop traffic statistics of the tunnels";
         type empty;
       }
       leaf tunnel-type {
         description "Clear traffic statistics of all the tunnels with given tunnel type";
         type enumeration {
           enum "ipoip" {
             description "IPIP tunnel type";
           }
           enum "gre" {
             description "GRE tunnel type";
           }
           enum "udp" {
             description "UDP tunnel type";
           }
         }
       }
       leaf tunnel-id {
         description "Clear traffic statistics of all the tunnels with given tunnel-id";
         type union {
           type uint32;
           type string {
             pattern "<.*>|$.*";
           }
         }
       }
       leaf table {
         description "Clear traffic statistics of all tunnels belonging to this routing table";
         type string;
       }
       leaf chain-type {
         description "Clear traffic statistics of all tunnels with given next-hop type";
         type enumeration {
           enum "v4" {
             description "V4 next-hops";
           }
           enum "v6" {
             description "V6 next-hops";
           }
         }
       }
     }
     output {
       choice output_c {
         case output-tag {
           leaf output {
             type string;
           }
         }
         case multichassis-tag {
           anyxml multi-routing-engine-results;
         }
       }
     }
   }
   rpc clear-isis-adjacency-information {
     description "Clear IS-IS adjacencies";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of IS-IS instance";
         type string;
       }
       leaf interface {
         description "Name of interface";
         type string;
       }
       choice clear-adj-arg {
         case all {
           leaf all {
             description "Clear all IS-IS adjacencies";
             type empty;
           }
         }
         case neighbor {
           leaf neighbor {
             description "Name of neighbor";
             type string;
           }
         }
       }
     }
     output {
       choice output_c {
         case output-tag {
           leaf output {
             type string;
           }
         }
         case multichassis-tag {
           anyxml multi-routing-engine-results;
         }
       }
     }
   }
   rpc clear-isis-database-information {
     description "Clear IS-IS database entries";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of IS-IS instance";
         type string;
       }
       choice clear-db-arg {
         case all {
           leaf all {
             description "Clear all IS-IS database entries";
             type empty;
           }
         }
         case entries {
           leaf entries {
             description "Name of database entry";
             type string;
           }
         }
       }
     }
     output {
       choice output_c {
         case output-tag {
           leaf output {
             type string;
           }
         }
         case multichassis-tag {
           anyxml multi-routing-engine-results;
         }
       }
     }
   }
   rpc clear-isis-layer2-map-information {
     description "Clear IS-IS ARP/ND mapping information";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of IS-IS instance";
         type string;
       }
       leaf destination {
         description "IP address of mapping entry";
         type jt:ipaddr;
       }
     }
     output {
       choice output_c {
         case output-tag {
           leaf output {
             type string;
           }
         }
         case multichassis-tag {
           anyxml multi-routing-engine-results;
         }
       }
     }
   }
   rpc clear-isis-overload-information {
     description "Clear overload bit and regenerate LSPs";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of IS-IS instance";
         type string;
       }
     }
     output {
       choice output_c {
         case output-tag {
           leaf output {
             type string;
           }
         }
         case multichassis-tag {
           anyxml multi-routing-engine-results;
         }
       }
     }
   }
   rpc clear-isis-statistics-information {
     description "Clear IS-IS statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of IS-IS instance";
         type string;
       }
     }
     output {
       choice output_c {
         case output-tag {
           leaf output {
             type string;
           }
         }
         case multichassis-tag {
           anyxml multi-routing-engine-results;
         }
       }
     }
   }
   rpc clear-isis-interface-statistics-information {
     description "Clear ISIS interface statistics information";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of IS-IS instance";
         type string;
       }
       leaf interface-name {
         description "Name of interface";
         type string;
       }
       leaf all {
         description "Clear all interface statistics";
         type empty;
       }
     }
     output {
       choice output_c {
         case output-tag {
           leaf output {
             type string;
           }
         }
         case multichassis-tag {
           anyxml multi-routing-engine-results;
         }
       }
     }
   }
   rpc clear-isis-spring-information {
     description "Clear SPRING information";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-isis-spring-flex-algorithm-information {
     description "Clear SPRING flex-algorithm information";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf flex-algorithm-id {
         description "Flex Algorithm id";
         type union {
           type string {
             pattern "<.*>|$.*";
           }
           type uint32 {
             range "128 .. 255";
           }
         }
       }
       leaf level {
         description "Number of IS-IS level";
         type union {
           type string {
             pattern "<.*>|$.*";
           }
           type uint32 {
             range "1 .. 2";
           }
         }
       }
     }
     output {
       choice output_c {
         case output-tag {
           leaf output {
             type string;
           }
         }
         case multichassis-tag {
           anyxml multi-routing-engine-results;
         }
       }
     }
   }
   rpc clear-isis-spring-traffic-information {
     description "Clear SPRING traffic-statistics-information";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf interface {
         description "Name of interface";
         type string;
       }
       leaf all {
         description "Clear all interface traffic-statistics";
         type empty;
       }
     }
     output {
       choice output_c {
         case output-tag {
           leaf output {
             type string;
           }
         }
         case multichassis-tag {
           anyxml multi-routing-engine-results;
         }
       }
     }
   }
   rpc clear-l2ckt-pw-auto-sensing {
     description "Clear Layer 2 circuit PW auto-sensing state";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf neighbor {
         description "IP address of neighbor";
         default "all";
         type string;
       }
       leaf vc-id {
         description "VC ID";
         default "all";
         type string;
       }
     }
     output {
       choice output_c {
         case output-tag {
           leaf output {
             type string;
           }
         }
         case multichassis-tag {
           anyxml multi-routing-engine-results;
         }
       }
     }
   }
   rpc clear-vpls-mac-address {
     description "Clear a VPLS media access control address";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "VPLS instance name";
         default "all";
         type string;
       }
       leaf address {
         description "MAC address to clear";
         default "all";
         type jt:mac-addr;
       }
     }
     output {
       choice output_c {
         case output-tag {
           leaf output {
             type string;
           }
         }
         case multichassis-tag {
           anyxml multi-routing-engine-results;
         }
       }
     }
   }
   rpc clear-vpls-statistics {
     description "Clear a VPLS statistics information";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "VPLS instance name";
         type string;
         mandatory true;
       }
     }
     output {
       choice output_c {
         case output-tag {
           leaf output {
             type string;
           }
         }
         case multichassis-tag {
           anyxml multi-routing-engine-results;
         }
       }
     }
   }
   rpc clear-vpls-mac-table {
     description "Clear all learned media access control addresses";
     input {
       leaf instance {
         description "Display information for a specified instance";
         default "all";
         type string;
       }
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf vlan-id {
         description "Clear MAC address learned on a specified VLAN";
         type string;
       }
       leaf isid {
         description "Clear MAC address learned on a specified ISID";
         type string;
       }
       leaf address {
         description "MAC address";
         default "all";
         type jt:mac-addr;
       }
     }
     output {
       choice output_c {
         case output-tag {
           leaf output {
             type string;
           }
         }
         case multichassis-tag {
           anyxml multi-routing-engine-results;
         }
       }
     }
   }
   rpc clear-vpls-interface-mac-table {
     description "Clear media access control table for specified interface";
     input {
       leaf interface-name {
         description "Name of interface for which to clear table";
         type union {
           type jt:interface-unit;
           type string {
             pattern "<.*>|$.*";
           }
         }
         mandatory true;
       }
       leaf vlan-id {
         description "Clear MAC address learned on a specified VLAN";
         type string;
       }
     }
     output {
       choice output_c {
         case output-tag {
           leaf output {
             type string;
           }
         }
         case multichassis-tag {
           anyxml multi-routing-engine-results;
         }
       }
     }
   }
   rpc clear-ldp-neighbors {
     description "Clear LDP neighbors";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of LDP routing instance";
         type string;
       }
       choice clear_arg {
         case all {
           leaf all {
             description "Clear all neighbors";
             type empty;
           }
         }
         case neighbor {
           leaf neighbor {
             description "IP address of the neighbor";
             type jt:ipaddr;
           }
         }
         case ldp-family {
           leaf ldp-family {
             type enumeration {
               enum "inet" {
                 description "Clear IPv4 neighbors";
               }
               enum "inet6" {
                 description "Clear IPv6 neighbors";
               }
             }
           }
         }
       }
     }
     output {
       choice output_c {
         case output-tag {
           leaf output {
             type string;
           }
         }
         case multichassis-tag {
           anyxml multi-routing-engine-results;
         }
       }
     }
   }
   rpc clear-ldp-sessions {
     description "Clear LDP sessions";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of LDP routing instance";
         type string;
       }
       choice clear_arg {
         case all {
           leaf all {
             description "Clear all sessions";
             type empty;
           }
         }
         case destination {
           leaf destination {
             description "IP address of session destination";
             type jt:ipaddr;
           }
         }
         case ldp-family {
           leaf ldp-family {
             type enumeration {
               enum "inet" {
                 description "Clear IPv4 sessions";
               }
               enum "inet6" {
                 description "Clear IPv6 sessions";
               }
             }
           }
         }
       }
     }
     output {
       choice output_c {
         case output-tag {
           leaf output {
             type string;
           }
         }
         case multichassis-tag {
           anyxml multi-routing-engine-results;
         }
       }
     }
   }
   rpc clear-ldp-statistics {
     description "Clear LDP statistics counters";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of LDP routing instance";
         type string;
       }
     }
     output {
       choice output_c {
         case output-tag {
           leaf output {
             type string;
           }
         }
         case multichassis-tag {
           anyxml multi-routing-engine-results;
         }
       }
     }
   }
   rpc clear-ldp-interface-hello-statistics {
     description "Clear LDP interface hello statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of LDP routing instance";
         type string;
       }
     }
     output {
       choice output_c {
         case output-tag {
           leaf output {
             type string;
           }
         }
         case multichassis-tag {
           anyxml multi-routing-engine-results;
         }
       }
     }
   }
   rpc clear-mld-statistics {
     description "Clear MLD statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf interface {
         description "Name of interface";
         type string;
       }
     }
     output {
       choice output_c {
         case output-tag {
           leaf output {
             type string;
           }
         }
         case multichassis-tag {
           anyxml multi-routing-engine-results;
         }
       }
     }
   }
   rpc clear-mld-membership {
     description "Clear MLD group membership";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf interface {
         description "Name of interface";
         type string;
       }
       choice clear_arg {
         case group {
           leaf group {
             description "IPv6 address range for group";
             type jt:ipv6prefix;
           }
         }
         case all {
           leaf all {
             description "Clear all MLD group membership";
             type empty;
           }
         }
       }
     }
     output {
       choice output_c {
         case output-tag {
           leaf output {
             type string;
           }
         }
         case multichassis-tag {
           anyxml multi-routing-engine-results;
         }
       }
     }
   }
   rpc clear-mld-snooping-statistics {
     description "Clear MLD snooping statistics";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf interface {
         description "Name of interface";
         type string;
       }
       leaf vlan-id {
         description "VLAN ID for a learning domain";
         type union {
           type string {
             pattern "<.*>|$.*";
           }
           type uint32 {
             range "0 .. 4094";
           }
         }
       }
       leaf instance {
         description "Name of routing-instance";
         type string;
       }
       leaf qualified-vlan {
         description "VLAN ID for a Qualified VLAN";
         type union {
           type string {
             pattern "<.*>|$.*";
           }
           type uint32 {
             range "0 .. 4094";
           }
         }
       }
     }
     output {
       choice output_c {
         case output-tag {
           leaf output {
             type string;
           }
         }
         case multichassis-tag {
           anyxml multi-routing-engine-results;
         }
       }
     }
   }
   rpc clear-mld-snooping-bridge-domain-statistics {
     description "For a particular bridge-domain";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "detail";
         type enumeration {
           enum "brief" {
             description "Display brief output (default)";
           }
           enum "detail" {
             description "Display detailed output";
           }
         }
       }
       leaf virtual-switch {
         description "Name of virtual-switch instance";
         type string;
       }
       leaf domain-name {
         description "Name of bridge-domain";
         type string;
         mandatory true;
       }
       leaf interface {
         description "Name of interface";
         type string;
       }
       leaf vlan-id {
         description "VLAN ID for a learning domain";
         type union {
           type string {
             pattern "<.*>|$.*";
           }
           type uint32 {
             range "0 .. 4094";
           }
         }
       }
     }
     output {
       choice output_c {
         case output-tag {
           leaf output {
             type string;
           }
         }
         case multichassis-tag {
           anyxml multi-routing-engine-results;
         }
       }
     }
   }
   rpc clear-mld-snooping-vlan-statistics {
     description "For a particular VLAN";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "detail";
         type enumeration {
           enum "brief" {
             description "Display brief output (default)";
           }
           enum "detail" {
             description "Display detailed output";
           }
         }
       }
       leaf virtual-switch {
         description "Name of virtual-switch instance";
         type string;
       }
       leaf vlan-name {
         description "Name of VLAN";
         type string;
         mandatory true;
       }
       leaf interface {
         description "Name of interface";
         type string;
       }
       leaf qualified-vlan {
         description "VLAN ID for a Qualified VLAN";
         type union {
           type string {
             pattern "<.*>|$.*";
           }
           type uint32 {
             range "0 .. 4094";
           }
         }
       }
     }
     output {
       choice output_c {
         case output-tag {
           leaf output {
             type string;
           }
         }
         case multichassis-tag {
           anyxml multi-routing-engine-results;
         }
       }
     }
   }
   rpc clear-mld-snooping-membership {
     description "Clear MLD snooping group membership";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf group {
         description "IP address range for group";
         type jt:ipv6prefix;
       }
       leaf interface {
         description "Name of interface";
         type string;
       }
       leaf vlan-id {
         description "VLAN ID for a learning domain";
         type union {
           type string {
             pattern "<.*>|$.*";
           }
           type uint32 {
             range "0 .. 4094";
           }
         }
       }
       leaf instance {
         description "Name of routing-instance";
         type string;
       }
       leaf qualified-vlan {
         description "VLAN ID for a Qualified VLAN";
         type union {
           type string {
             pattern "<.*>|$.*";
           }
           type uint32 {
             range "0 .. 4094";
           }
         }
       }
     }
     output {
       choice output_c {
         case output-tag {
           leaf output {
             type string;
           }
         }
         case multichassis-tag {
           anyxml multi-routing-engine-results;
         }
       }
     }
   }
   rpc clear-mld-snooping-bridge-domain-membership {
     description "For a particular bridge-domain";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "detail";
         type enumeration {
           enum "brief" {
             description "Display brief output (default)";
           }
           enum "detail" {
             description "Display detailed output";
           }
         }
       }
       leaf virtual-switch {
         description "Name of virtual-switch instance";
         type string;
       }
       leaf domain-name {
         description "Name of bridge-domain";
         type string;
         mandatory true;
       }
       leaf interface {
         description "Name of interface";
         type string;
       }
       leaf vlan-id {
         description "VLAN ID for a learning domain";
         type union {
           type string {
             pattern "<.*>|$.*";
           }
           type uint32 {
             range "0 .. 4094";
           }
         }
       }
       leaf group {
         description "IP address range for group";
         type jt:ipv6prefix;
       }
     }
     output {
       choice output_c {
         case output-tag {
           leaf output {
             type string;
           }
         }
         case multichassis-tag {
           anyxml multi-routing-engine-results;
         }
       }
     }
   }
   rpc clear-mld-snooping-vlan-membership {
     description "For a particular VLAN";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "detail";
         type enumeration {
           enum "brief" {
             description "Display brief output (default)";
           }
           enum "detail" {
             description "Display detailed output";
           }
         }
       }
       leaf virtual-switch {
         description "Name of virtual-switch instance";
         type string;
       }
       leaf vlan-name {
         description "Name of VLAN";
         type string;
         mandatory true;
       }
       leaf interface {
         description "Name of interface";
         type string;
       }
       leaf qualified-vlan {
         description "VLAN ID for a Qualified VLAN";
         type union {
           type string {
             pattern "<.*>|$.*";
           }
           type uint32 {
             range "0 .. 4094";
           }
         }
       }
       leaf group {
         description "IP address range for group";
         type jt:ipv6prefix;
       }
     }
     output {
       choice output_c {
         case output-tag {
           leaf output {
             type string;
           }
         }
         case multichassis-tag {
           anyxml multi-routing-engine-results;
         }
       }
     }
   }
   rpc clear-mpls-lsp-information {
     description "Reset nontransit or egress LSPs originating on this router";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of routing instance";
         type string;
       }
       leaf opt {
         type enumeration {
           enum "optimize" {
             description "Perform nonpreemptive optimization computation now";
           }
           enum "optimize-aggressive" {
             description "Perform aggressive optimization computation now";
           }
         }
       }
       leaf stats {
         type enumeration {
           enum "statistics" {
             description "Clear LSP statistics";
           }
           enum "reverse-statistics" {
             description "Clear LSP reverse-statistics for bidirectional LSPs";
           }
           enum "counters" {
             description "Clear LSP Flap/MBB counters";
           }
         }
       }
       leaf autobw {
         type enumeration {
           enum "autobandwidth" {
             description "Clear LSP autobandwidth counters";
           }
         }
       }
       choice clear-arg {
         case name {
           leaf regex {
             description "Regular expression for LSP names to match";
             type string;
           }
         }
         case all {
           leaf all {
             description "Reset 'all' the ingress LSPs originating on this router";
             type empty;
           }
         }
       }
       leaf path {
         description "Regular expression for LSP path to match";
         type string;
       }
     }
     output {
       choice output_c {
         case output-tag {
           leaf output {
             type string;
           }
         }
         case multichassis-tag {
           anyxml multi-routing-engine-results;
         }
       }
     }
   }
   rpc clear-mpls-container-lsp-information {
     description "Reset nontransit or egress container LSP originating on this router";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of routing instance";
         type string;
       }
       leaf opt {
         type enumeration {
           enum "optimize" {
             description "Perform nonpreemptive optimization computation now";
           }
           enum "optimize-aggressive" {
             description "Perform aggressive optimization computation now";
           }
         }
       }
       leaf stats {
         type enumeration {
           enum "statistics" {
             description "Clear LSP statistics";
           }
         }
       }
       leaf autobw {
         type enumeration {
           enum "autobandwidth" {
             description "Clear LSP autobandwidth counters";
           }
         }
       }
       choice clear-arg {
         case name {
           leaf regex {
             description "Name of Container LSP";
             type string;
           }
         }
         case all {
           leaf all {
             description "Reset 'all' the nontransit or egress Container LSPs originating on this router";
             type empty;
           }
         }
       }
       leaf history {
         type enumeration {
           enum "history" {
             description "Clear container LSP samples from the history";
           }
         }
       }
       leaf member {
         description "Regular expression for member LSP names to match";
         type string;
       }
     }
     output {
       choice output_c {
         case output-tag {
           leaf output {
             type string;
           }
         }
         case multichassis-tag {
           anyxml multi-routing-engine-results;
         }
       }
     }
   }
   rpc clear-mpls-label-information {
     description "MPLS label";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf history {
         type enumeration {
           enum "history" {
             description "Clear label history";
           }
         }
         mandatory true;
       }
     }
     output {
       choice output_c {
         case output-tag {
           leaf output {
             type string;
           }
         }
         case multichassis-tag {
           anyxml multi-routing-engine-results;
         }
       }
     }
   }
   rpc clear-mpls-tunnel-manager-statistics-information {
     description "MPLS tunnel manager statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of routing instance";
         type string;
       }
     }
     output {
       choice output_c {
         case output-tag {
           leaf output {
             type string;
           }
         }
         case multichassis-tag {
           anyxml multi-routing-engine-results;
         }
       }
     }
   }
   rpc clear-mpls-static-lsp-information {
     description "Reset static LSP statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of routing instance";
         type string;
       }
       leaf stats {
         type enumeration {
           enum "statistics" {
             description "Clear LSP statistics";
           }
         }
         mandatory true;
       }
       leaf regex {
         description "Regular expression for LSP names to match";
         type string;
       }
     }
     output {
       choice output_c {
         case output-tag {
           leaf output {
             type string;
           }
         }
         case multichassis-tag {
           anyxml multi-routing-engine-results;
         }
       }
     }
   }
   rpc clear-mpls-traceroute-database-ldp {
     description "Clear FECs";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf fec {
         description "IP address and optional prefix length of FEC";
         type jt:ipprefix;
       }
       leaf routing-instance {
         description "Name of routing instance, or 'all'";
         type string {
           junos:posix-pattern "!^((__.*__)|(all)|(.*[ ].*)|(\"\")|(.{129,}))$";
           junos:pattern-message "Must be a non-reserved string of 128 characters or less with no spaces.";
         }
       }
     }
     output {
       choice output_c {
         case output-tag {
           leaf output {
             type string;
           }
         }
         case multichassis-tag {
           anyxml multi-routing-engine-results;
         }
       }
     }
   }
   rpc clear-pm-mpls-lsp-information {
     description "Reset non-transit or egress LSPs originating on this router";
     input {
       leaf regex {
         description "Regular expression for LSP names to match";
         type string;
       }
     }
     output {
       choice output_c {
         case output-tag {
           leaf output {
             type string;
           }
         }
         case multichassis-tag {
           anyxml multi-routing-engine-results;
         }
       }
     }
   }
   rpc clear-msdp-statistics {
     description "Clear MSDP peer statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
       leaf peer {
         description "IP address of peer that provided statistics";
         type jt:ipv4addr;
       }
     }
     output {
       choice output_c {
         case output-tag {
           leaf output {
             type string;
           }
         }
         case multichassis-tag {
           anyxml multi-routing-engine-results;
         }
       }
     }
   }
   rpc clear-msdp-cache {
     description "Clear the MSDP source-active cache";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
       choice clear_arg {
         case peer {
           leaf peer {
             description "IP address of peer that provided cache entries";
             type jt:ipv4addr;
           }
         }
         case all {
           leaf all {
             description "Clear all MSDP source-active cache entries";
             type empty;
           }
         }
       }
     }
     output {
       choice output_c {
         case output-tag {
           leaf output {
             type string;
           }
         }
         case multichassis-tag {
           anyxml multi-routing-engine-results;
         }
       }
     }
   }
   rpc clear-multicast-sessions {
     description "Clear multicast sessions";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf regexp {
         description "Regular expression for sessions to match";
         type string;
       }
     }
     output {
       choice output_c {
         case output-tag {
           leaf output {
             type string;
           }
         }
         case multichassis-tag {
           anyxml multi-routing-engine-results;
         }
       }
     }
   }
   rpc clear-multicast-statistics {
     description "Clear multicast statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
       leaf interface {
         description "Name of interface";
         type string;
       }
       leaf family {
         description "Address family";
         default "inet";
         type enumeration {
           enum "inet" {
             description "Clear IPv4 statistics";
           }
           enum "inet6" {
             description "Clear IPv6 statistics";
           }
         }
       }
     }
     output {
       choice output_c {
         case output-tag {
           leaf output {
             type string;
           }
         }
         case multichassis-tag {
           anyxml multi-routing-engine-results;
         }
       }
     }
   }
   rpc clear-multicast-forwarding-cache {
     description "Clear multicast forwarding cache";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
       leaf family {
         description "Address family";
         default "inet";
         type enumeration {
           enum "inet" {
             description "Clear IPv4 forwarding cache";
           }
           enum "inet6" {
             description "Clear IPv6 forwarding cache";
           }
         }
       }
       leaf all {
         description "Clear all multicast forwarding cache entries";
         type empty;
         mandatory true;
       }
     }
     output {
       choice output_c {
         case output-tag {
           leaf output {
             type string;
           }
         }
         case multichassis-tag {
           anyxml multi-routing-engine-results;
         }
       }
     }
   }
   rpc clear-multicast-scope-statistics {
     description "Clear multicast scope statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf interface {
         description "Name of interface";
         type string;
       }
       leaf family {
         description "Address family";
         default "inet";
         type enumeration {
           enum "inet" {
             description "Clear IPv4 statistics";
           }
           enum "inet6" {
             description "Clear IPv6 statistics";
           }
         }
       }
     }
     output {
       choice output_c {
         case output-tag {
           leaf output {
             type string;
           }
         }
         case multichassis-tag {
           anyxml multi-routing-engine-results;
         }
       }
     }
   }
   rpc clear-multicast-bandwidth-admission {
     description "Re-apply bandwidth admission control";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
       leaf family {
         description "Address family";
         default "inet";
         type enumeration {
           enum "inet" {
             description "For IPv4 ";
           }
           enum "inet6" {
             description "For IPv6 ";
           }
         }
       }
       leaf group {
         description "Destination group address";
         type jt:ipaddr;
       }
       leaf source {
         description "Source address";
         type jt:ipaddr;
       }
       leaf interface {
         description "Name of interface";
         type string;
       }
     }
     output {
       choice output_c {
         case output-tag {
           leaf output {
             type string;
           }
         }
         case multichassis-tag {
           anyxml multi-routing-engine-results;
         }
       }
     }
   }
   rpc clear-ospf-neighbor-information {
     description "Clear OSPF neighbors";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf all {
         description "Clear all Neighbor";
         type empty;
       }
       leaf interface {
         description "Name of logical interface";
         type string;
       }
       leaf neighbor {
         description "Name of neighbor";
         type string;
       }
       leaf area {
         description "OSPF area ID";
         type jt:areaid;
       }
       leaf instance {
         description "Name of OSPF instance";
         type string;
       }
     }
     output {
       choice output_c {
         case output-tag {
           leaf output {
             type string;
           }
         }
         case multichassis-tag {
           anyxml multi-routing-engine-results;
         }
       }
     }
   }
   rpc clear-ospf-database-information {
     description "Clear OSPF database entries";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf all {
         description "Clear All Database";
         type empty;
       }
       leaf area {
         description "OSPF area ID";
         default "all";
         type string;
       }
       leaf instance {
         description "Name of OSPF instance";
         type string;
       }
     }
     output {
       choice output_c {
         case output-tag {
           leaf output {
             type string;
           }
         }
         case multichassis-tag {
           anyxml multi-routing-engine-results;
         }
       }
     }
   }
   rpc clear-ospf-database-protection {
     description "Clear OSPF database protection related state";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of OSPF instance";
         type string;
       }
     }
     output {
       choice output_c {
         case output-tag {
           leaf output {
             type string;
           }
         }
         case multichassis-tag {
           anyxml multi-routing-engine-results;
         }
       }
     }
   }
   rpc clear-ospf-statistics-information {
     description "Clear OSPF statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of OSPF instance";
         type string;
       }
     }
     output {
       choice output_c {
         case output-tag {
           leaf output {
             type string;
           }
         }
         case multichassis-tag {
           anyxml multi-routing-engine-results;
         }
       }
     }
   }
   rpc clear-ospf-io-statistics-information {
     description "Clear OSPF I/O statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-ospf-overload-information {
     description "Clear overload bit and rebuild LSAs";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of OSPF instance";
         type string;
       }
     }
     output {
       choice output_c {
         case output-tag {
           leaf output {
             type string;
           }
         }
         case multichassis-tag {
           anyxml multi-routing-engine-results;
         }
       }
     }
   }
   rpc clear-ospf3-neighbor-information {
     description "Clear OSPFv3 neighbors";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf all {
         description "Clear all Neighbor";
         type empty;
       }
       leaf interface {
         description "Name of logical interface";
         type string;
       }
       leaf neighbor {
         description "Name of OSPFv3 neighbor";
         type string;
       }
       leaf area {
         description "OSPF area ID";
         type jt:areaid;
       }
       leaf instance {
         description "Name of OSPFv3 instance";
         type string;
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
     }
     output {
       choice output_c {
         case output-tag {
           leaf output {
             type string;
           }
         }
         case multichassis-tag {
           anyxml multi-routing-engine-results;
         }
       }
     }
   }
   rpc clear-ospf3-database-information {
     description "Clear OSPFv3 database entries";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf all {
         description "Clear All Database";
         type empty;
       }
       leaf area {
         description "Area ID of OSPFv3 area";
         default "all";
         type string;
       }
       leaf instance {
         description "Name of OSPFv3 instance";
         type string;
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
     }
     output {
       choice output_c {
         case output-tag {
           leaf output {
             type string;
           }
         }
         case multichassis-tag {
           anyxml multi-routing-engine-results;
         }
       }
     }
   }
   rpc clear-ospf3-database-protection-information {
     description "Clear OSPFv3 database protection related state";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of OSPFv3 instance";
         type string;
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
     }
     output {
       choice output_c {
         case output-tag {
           leaf output {
             type string;
           }
         }
         case multichassis-tag {
           anyxml multi-routing-engine-results;
         }
       }
     }
   }
   rpc clear-ospf3-statistics-information {
     description "Clear OSPFv3 statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of OSPFv3 instance";
         type string;
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
     }
     output {
       choice output_c {
         case output-tag {
           leaf output {
             type string;
           }
         }
         case multichassis-tag {
           anyxml multi-routing-engine-results;
         }
       }
     }
   }
   rpc clear-ospf3-io-statistics-information {
     description "Clear OSPFv3 I/O statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-ospf3-overload-information {
     description "Clear overload bit and rebuild LSAs";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of OSPFv3 instance";
         type string;
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
     }
     output {
       choice output_c {
         case output-tag {
           leaf output {
             type string;
           }
         }
         case multichassis-tag {
           anyxml multi-routing-engine-results;
         }
       }
     }
   }
   rpc clear-pim-statistics {
     description "Clear PIM statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
       leaf interface {
         description "Name of interface";
         type string;
       }
       leaf family {
         description "Address family";
         default "inet";
         type enumeration {
           enum "inet" {
             description "Clear IPv4 statistics";
           }
           enum "inet6" {
             description "Clear IPv6 statistics";
           }
         }
       }
     }
     output {
       choice output_c {
         case output-tag {
           leaf output {
             type string;
           }
         }
         case multichassis-tag {
           anyxml multi-routing-engine-results;
         }
       }
     }
   }
   rpc clear-pim-join-state {
     description "Clear PIM join/prune state";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
       choice clear_arg {
         case group {
           leaf group {
             description "IP address and optional prefix length of group";
             type jt:ipprefix;
           }
         }
         case all {
           leaf all {
             description "Clear all PIM join/prune states";
             type empty;
           }
         }
       }
       leaf exact {
         description "Clear only group that matches exactly";
         type empty;
       }
       leaf source {
         description "IP address and optional prefix length of source";
         type jt:ipprefix;
       }
       leaf rp {
         description "IP address and optional prefix length of rendezvous point";
         type jt:ipprefix;
       }
       leaf sparse {
         description "Clear only PIM sparse-mode entries (including SSM)";
         type empty;
       }
       leaf dense {
         description "Clear only PIM dense-mode entries";
         type empty;
       }
       leaf bidirectional {
         description "Clear only bidirectional PIM entries";
         type empty;
       }
       leaf star-g {
         description "Clear only *,G entries";
         type empty;
       }
       leaf sg {
         description "Clear only S,G entries";
         type empty;
       }
       leaf family {
         description "Address family";
         default "inet";
         type enumeration {
           enum "inet" {
             description "Clear IPv4 join/prune state";
           }
           enum "inet6" {
             description "Clear IPv6 join/prune state";
           }
         }
       }
     }
     output {
       choice output_c {
         case output-tag {
           leaf output {
             type string;
           }
         }
         case multichassis-tag {
           anyxml multi-routing-engine-results;
         }
       }
     }
   }
   rpc clear-pim-register-state {
     description "Clear PIM register state";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
       leaf family {
         description "Address family";
         default "inet";
         type enumeration {
           enum "inet" {
             description "Clear IPv4 register state";
           }
           enum "inet6" {
             description "Clear IPv6 register state";
           }
         }
       }
       leaf all {
         description "Clear all PIM register states";
         type empty;
         mandatory true;
       }
     }
     output {
       choice output_c {
         case output-tag {
           leaf output {
             type string;
           }
         }
         case multichassis-tag {
           anyxml multi-routing-engine-results;
         }
       }
     }
   }
   rpc clear-pim-join-distribution {
     description "Redistribute PIM joins";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
       leaf all {
         description "Redistribute all PIM joins";
         type empty;
         mandatory true;
       }
     }
     output {
       choice output_c {
         case output-tag {
           leaf output {
             type string;
           }
         }
         case multichassis-tag {
           anyxml multi-routing-engine-results;
         }
       }
     }
   }
   rpc clear-pim-snooping-join {
     description "Clear PIM snooping join";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf group {
         description "IP address range for group";
         type jt:ipv4prefix;
       }
       leaf vlan-id {
         description "VLAN ID for a learning domain";
         type union {
           type string {
             pattern "<.*>|$.*";
           }
           type uint32 {
             range "0 .. 4094";
           }
         }
       }
       leaf instance {
         description "Name of routing-instance";
         type string;
       }
     }
     output {
       choice output_c {
         case output-tag {
           leaf output {
             type string;
           }
         }
         case multichassis-tag {
           anyxml multi-routing-engine-results;
         }
       }
     }
   }
   rpc clear-pim-snooping-statistics {
     description "Clear PIM snooping statistics";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf interface {
         description "Name of interface";
         type string;
       }
       leaf vlan-id {
         description "VLAN ID for a learning domain";
         type union {
           type string {
             pattern "<.*>|$.*";
           }
           type uint32 {
             range "0 .. 4094";
           }
         }
       }
       leaf instance {
         description "Name of routing-instance";
         type string;
       }
     }
     output {
       choice output_c {
         case output-tag {
           leaf output {
             type string;
           }
         }
         case multichassis-tag {
           anyxml multi-routing-engine-results;
         }
       }
     }
   }
   rpc clear-ripng-statistics {
     description "Clear RIPng statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf neighbor-name {
         description "Name of RIPng neighbor";
         type string;
       }
       leaf instance {
         description "Name of RIPng instance";
         type string;
       }
     }
     output {
       choice output_c {
         case output-tag {
           leaf output {
             type string;
           }
         }
         case multichassis-tag {
           anyxml multi-routing-engine-results;
         }
       }
     }
   }
   rpc clear-ripng-general-statistics {
     description "Clear RIPng general statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-rip-statistics {
     description "Clear RIP statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf neighbor-name {
         description "Name of RIP neighbor";
         type string;
       }
       leaf instance {
         description "Name of RIP instance";
         type string;
       }
     }
     output {
       choice output_c {
         case output-tag {
           leaf output {
             type string;
           }
         }
         case multichassis-tag {
           anyxml multi-routing-engine-results;
         }
       }
     }
   }
   rpc clear-rip-peer-statistics {
     description "Clear peer statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf address {
         description "Ip address of peer";
         type string;
       }
       leaf peer-all {
         description "Clear statistics of all peers";
         type enumeration {
           enum "all" {
             description "Clear statistics of all peers";
           }
         }
       }
     }
     output {
       choice output_c {
         case output-tag {
           leaf output {
             type string;
           }
         }
         case multichassis-tag {
           anyxml multi-routing-engine-results;
         }
       }
     }
   }
   rpc clear-rip-general-statistics {
     description "Clear RIP general statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-validation-database {
     description "Clear the route validation database";
     input {
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
       leaf instance {
         description "Name of route validation instance";
         type string;
       }
     }
     output {
       choice output_c {
         case output-tag {
           leaf output {
             type string;
           }
         }
         case multichassis-tag {
           anyxml multi-routing-engine-results;
         }
       }
     }
   }
   rpc clear-validation-session {
     description "Clear route validation session";
     input {
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
       leaf destination {
         description "IP address of session";
         type jt:ipaddr;
       }
       leaf disposition {
         type enumeration {
           enum "soft-inbound" {
             description "Soft reset inbound state by issuing Reset request";
           }
         }
       }
       leaf instance {
         description "Name of route validation instance";
         type string;
       }
     }
     output {
       choice output_c {
         case output-tag {
           leaf output {
             type string;
           }
         }
         case multichassis-tag {
           anyxml multi-routing-engine-results;
         }
       }
     }
   }
   rpc clear-validation-statistics {
     description "Clear route validation statistics";
     input {
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
       leaf instance {
         description "Name of route validation instance";
         type string;
       }
     }
     output {
       choice output_c {
         case output-tag {
           leaf output {
             type string;
           }
         }
         case multichassis-tag {
           anyxml multi-routing-engine-results;
         }
       }
     }
   }
   rpc clear-rsvp-session-information {
     description "Preempt RSVP session";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       choice clear-choice {
         case name {
           leaf session-name {
             description "Name of session - Must select 'name' or 'all'";
             type string;
           }
         }
         case all {
           leaf all {
             description "All matching sessions - Must select 'name' or 'all'";
             type empty;
           }
         }
       }
       leaf instance {
         description "Name of routing instance";
         type string;
       }
       leaf lsp-id {
         description "LSP ID of the RSVP sender";
         type union {
           type string {
             pattern "<.*>|$.*";
           }
           type uint32 {
             range "1 .. 65535";
           }
         }
       }
       leaf tunnel-id {
         description "Tunnel ID of the RSVP session";
         type union {
           type string {
             pattern "<.*>|$.*";
           }
           type uint32 {
             range "1 .. 65535";
           }
         }
       }
       leaf connection-source {
         description "Source of the label-switched path";
         type jt:ipaddr;
       }
       leaf connection-destination {
         description "Destination of the label-switched path";
         type jt:ipaddr;
       }
       leaf optimize-fast-reroute {
         description "Perform fast-reroute optimization computation now";
         type empty;
       }
       leaf gracefully {
         description "Gracefully tear down RSVP sessions";
         type empty;
       }
     }
     output {
       choice output_c {
         case output-tag {
           leaf output {
             type string;
           }
         }
         case multichassis-tag {
           anyxml multi-routing-engine-results;
         }
       }
     }
   }
   rpc clear-rsvp-counters-information {
     description "Clear RSVP counters";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of routing instance";
         type string;
       }
     }
     output {
       choice output_c {
         case output-tag {
           leaf output {
             type string;
           }
         }
         case multichassis-tag {
           anyxml multi-routing-engine-results;
         }
       }
     }
   }
   rpc clear-l2-learning-mac-move-buffer {
     description "Clear the mac move buffer contents";
     output {
       choice output_c {
         case output-tag {
           leaf output {
             type string;
           }
         }
         case multichassis-tag {
           anyxml multi-routing-engine-results;
         }
       }
     }
   }
   rpc clear-l2-learning-mac-move-buffer-active {
     description "Clear the active mac move buffer entries";
     output {
       choice output_c {
         case output-tag {
           leaf output {
             type string;
           }
         }
         case multichassis-tag {
           anyxml multi-routing-engine-results;
         }
       }
     }
   }
   rpc clear-l2-learning-context-history {
     description "Clear context history";
     output {
       choice output_c {
         case output-tag {
           leaf output {
             type string;
           }
         }
         case multichassis-tag {
           anyxml multi-routing-engine-results;
         }
       }
     }
   }
   rpc clear-l2-learning-remote-backbone-edge-bridges {
     description "Clear remote backbone edge bridges in a PBBN network";
     input {
       leaf remote-beb-mac-address {
         description "Remote backbone edge bridge MAC address";
         default "all";
         type jt:mac-addr;
       }
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf instance {
         description "Display information for a specified instance";
         default "all";
         type string;
       }
     }
     output {
       choice output_c {
         case output-tag {
           leaf output {
             type string;
           }
         }
         case multichassis-tag {
           anyxml multi-routing-engine-results;
         }
       }
     }
   }
   rpc clear-l2-learning-redundancy-group-statistics {
     description "Clear redundancy group statistics counters";
     input {
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
       leaf redundancy-group-id {
         description "Display information for a specified RG";
         default "0";
         type union {
           type string {
             pattern "<.*>|$.*";
           }
           type uint32 {
             range "0 .. 4294967294";
           }
         }
       }
       leaf options {
         description "Clear information for specified RG or all RG(s)";
         type enumeration {
           enum "arp-statistics" {
             description "Show MCAE ARP Synchronization statistics";
           }
           enum "nd-statistics" {
             description "Show MCAE ND synchronization statistics";
           }
         }
       }
     }
     output {
       choice output_c {
         case output-tag {
           leaf output {
             type string;
           }
         }
         case multichassis-tag {
           anyxml multi-routing-engine-results;
         }
       }
     }
   }
   rpc clear-bridge-mac-table {
     description "Clear all learned media access control addresses";
     input {
       leaf instance {
         description "Display information for a specified instance";
         default "all";
         type string;
       }
       leaf bridge-domain {
         description "Name of bridging domain, or 'all'";
         default "all";
         type string;
       }
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf vlan-id {
         description "Clear MAC address learned on a specified VLAN";
         type string;
       }
       leaf isid {
         description "Clear MAC address learned on a specified ISID";
         type string;
       }
       leaf address {
         description "MAC address";
         default "all";
         type jt:mac-addr;
       }
     }
     output {
       choice output_c {
         case output-tag {
           leaf output {
             type string;
           }
         }
         case multichassis-tag {
           anyxml multi-routing-engine-results;
         }
       }
     }
   }
   rpc clear-bridge-interface-mac-table {
     description "Clear media access control table for specified interface";
     input {
       leaf interface-name {
         description "Name of interface for which to clear table";
         type string;
         mandatory true;
       }
       leaf remote-beb-mac-address {
         description "Remote backbone edge bridge MAC address";
         default "all";
         type jt:mac-addr;
       }
       leaf vlan-id {
         description "Clear MAC address learned on a specified VLAN";
         type string;
       }
       leaf isid {
         description "Clear MAC address learned on a specified ISID";
         type string;
       }
     }
     output {
       choice output_c {
         case output-tag {
           leaf output {
             type string;
           }
         }
         case multichassis-tag {
           anyxml multi-routing-engine-results;
         }
       }
     }
   }
   rpc clear-bridge-recovery {
     description "Clear port error";
     output {
       choice output_c {
         case output-tag {
           leaf output {
             type string;
           }
         }
         case multichassis-tag {
           anyxml multi-routing-engine-results;
         }
       }
     }
   }
   rpc clear-bridge-recovery-interface {
     description "Clear port error for specified interface";
     input {
       leaf interface-name {
         description "Name of interface for which to clear table";
         type string;
         mandatory true;
       }
     }
     output {
       choice output_c {
         case output-tag {
           leaf output {
             type string;
           }
         }
         case multichassis-tag {
           anyxml multi-routing-engine-results;
         }
       }
     }
   }
   rpc clear-bridge-statistics {
     description "Clear bridge statistics information";
     input {
       leaf bridge-domain {
         description "Name of bridging domain";
         type string;
         mandatory true;
       }
       leaf instance {
         description "Display information for a specified instance";
         type string;
       }
       leaf logical-system {
         description "Name of logical system";
         type string {
           junos:posix-pattern "^[a-zA-Z0-9_-]{1,63}$";
           junos:pattern-message "Logical-system name is a string consisting of up to 63 letters, numbers, dashes and underscores";
         }
       }
     }
     output {
       choice output_c {
         case output-tag {
           leaf output {
             type string;
           }
         }
         case multichassis-tag {
           anyxml multi-routing-engine-results;
         }
       }
     }
   }
   rpc clear-ethernet-switching-context-history {
     description "Clear context history";
     output {
       choice output_c {
         case output-tag {
           leaf output {
             type string;
           }
         }
         case multichassis-tag {
           anyxml multi-routing-engine-results;
         }
       }
     }
   }
   rpc clear-ethernet-switching-table {
     description "Clear all learned media access control addresses";
     input {
       leaf instance {
         description "Display information for a specified instance";
         default "all";
         type string;
       }
       leaf vlan-name {
         description "Name of VLAN, or 'all'";
         default "all";
         type string;
       }
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf vlan-id {
         description "Clear MAC address learned on a specified VLAN";
         type string;
       }
       leaf isid {
         description "Clear MAC address learned on a specified ISID";
         type string;
       }
       leaf address {
         description "MAC address";
         default "all";
         type jt:mac-addr;
       }
     }
     output {
       choice output_c {
         case output-tag {
           leaf output {
             type string;
           }
         }
         case multichassis-tag {
           anyxml multi-routing-engine-results;
         }
       }
     }
   }
   rpc clear-ethernet-switching-interface-table {
     description "Clear media access control table for specified interface";
     input {
       leaf interface-name {
         description "Name of interface for which to clear table";
         type string;
         mandatory true;
       }
       leaf remote-beb-mac-address {
         description "Remote backbone edge bridge MAC address";
         default "all";
         type jt:mac-addr;
       }
       leaf vlan-id {
         description "Clear MAC address learned on a specified VLAN";
         type string;
       }
       leaf isid {
         description "Clear MAC address learned on a specified ISID";
         type string;
       }
     }
     output {
       choice output_c {
         case output-tag {
           leaf output {
             type string;
           }
         }
         case multichassis-tag {
           anyxml multi-routing-engine-results;
         }
       }
     }
   }
   rpc clear-ethernet-switching-table-persistent-learning {
     description "Clear persistent-mac entries";
     output {
       choice output_c {
         case output-tag {
           leaf output {
             type string;
           }
         }
         case multichassis-tag {
           anyxml multi-routing-engine-results;
         }
       }
     }
   }
   rpc clear-ethernet-switching-table-persistent-learning-interface {
     description "Clear persistent MACs for specified interface";
     input {
       leaf interface-name {
         description "Name of interface for which to clear table";
         type string;
         mandatory true;
       }
     }
     output {
       choice output_c {
         case output-tag {
           leaf output {
             type string;
           }
         }
         case multichassis-tag {
           anyxml multi-routing-engine-results;
         }
       }
     }
   }
   rpc clear-ethernet-switching-table-persistent-learning-mac {
     description "Clear one persitent MAC or all peristent MACs";
     input {
       leaf address {
         description "MAC address";
         default "all";
         type jt:mac-addr;
       }
     }
     output {
       choice output_c {
         case output-tag {
           leaf output {
             type string;
           }
         }
         case multichassis-tag {
           anyxml multi-routing-engine-results;
         }
       }
     }
   }
   rpc clear-ethernet-switching-recovery {
     description "Clear port error";
     output {
       choice output_c {
         case output-tag {
           leaf output {
             type string;
           }
         }
         case multichassis-tag {
           anyxml multi-routing-engine-results;
         }
       }
     }
   }
   rpc clear-ethernet-switching-recovery-interface {
     description "Clear port error for specified interface";
     input {
       leaf interface-name {
         description "Name of interface for which to clear table";
         type union {
           type jt:interface-name;
           type string {
             pattern "<.*>|$.*";
           }
         }
         mandatory true;
       }
       leaf vlan {
         description "VLAN(name or ID)";
         type string;
       }
     }
     output {
       choice output_c {
         case output-tag {
           leaf output {
             type string;
           }
         }
         case multichassis-tag {
           anyxml multi-routing-engine-results;
         }
       }
     }
   }
   rpc clear-ethernet-switching-mac-learning-log {
     description "Clear all MAC address learning log";
     output {
       choice output_c {
         case output-tag {
           leaf output {
             type string;
           }
         }
         case multichassis-tag {
           anyxml multi-routing-engine-results;
         }
       }
     }
   }
   rpc clear-vlans-mac-ip-table {
     description "Clear IPv4 and IPv6 entries for EVPN instances";
     input {
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf instance {
         description "Display information for a specified instance";
         default "all";
         type string;
       }
       leaf vlan-name {
         description "Name of VLAN, or 'all'";
         default "all";
         type string;
       }
       leaf address {
         description "MAC address";
         default "all";
         type jt:mac-addr;
       }
     }
     output {
       choice output_c {
         case output-tag {
           leaf output {
             type string;
           }
         }
         case multichassis-tag {
           anyxml multi-routing-engine-results;
         }
       }
     }
   }
   rpc clear-ethernet-switching-evpn-arp-table {
     description "Clear all INET addresses learned via ARP";
     input {
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf instance {
         description "Display information for a specified instance";
         default "all";
         type string;
       }
       leaf vlan-name {
         description "Name of VLAN, or 'all'";
         default "all";
         type string;
       }
       leaf address {
         description "MAC address";
         default "all";
         type jt:mac-addr;
       }
     }
     output {
       choice output_c {
         case output-tag {
           leaf output {
             type string;
           }
         }
         case multichassis-tag {
           anyxml multi-routing-engine-results;
         }
       }
     }
   }
   rpc clear-ethernet-switching-evpn-nd-table {
     description "Clear all INET6 addresses learned via NDP";
     input {
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf instance {
         description "Display information for a specified instance";
         default "all";
         type string;
       }
       leaf vlan-name {
         description "Name of VLAN, or 'all'";
         default "all";
         type string;
       }
       leaf address {
         description "MAC address";
         default "all";
         type jt:mac-addr;
       }
     }
     output {
       choice output_c {
         case output-tag {
           leaf output {
             type string;
           }
         }
         case multichassis-tag {
           anyxml multi-routing-engine-results;
         }
       }
     }
   }
   rpc clear-mac-vrf-forwarding {
     description "Clear MAC VRF learned Layer 2 MAC address information";
     output {
       choice output_c {
         case output-tag {
           leaf output {
             type string;
           }
         }
         case multichassis-tag {
           anyxml multi-routing-engine-results;
         }
       }
     }
   }
   rpc clear-mac-vrf-mac-table {
     description "Clear all learned media access control addresses";
     input {
       leaf instance {
         description "Display information for a specified instance";
         default "all";
         type string;
       }
       leaf vlan-name {
         description "Name of VLAN, or 'all'";
         default "all";
         type string;
       }
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf vlan-id {
         description "Clear MAC address learned on a specified VLAN";
         type string;
       }
       leaf isid {
         description "Clear MAC address learned on a specified ISID";
         type string;
       }
       leaf address {
         description "MAC address";
         default "all";
         type jt:mac-addr;
       }
     }
     output {
       choice output_c {
         case output-tag {
           leaf output {
             type string;
           }
         }
         case multichassis-tag {
           anyxml multi-routing-engine-results;
         }
       }
     }
   }
   rpc clear-mac-vrf-interface-table {
     description "Clear media access control table for specified interface";
     input {
       leaf interface-name {
         description "Name of interface for which to clear table";
         type string;
         mandatory true;
       }
       leaf remote-beb-mac-address {
         description "Remote backbone edge bridge MAC address";
         default "all";
         type jt:mac-addr;
       }
       leaf vlan-id {
         description "Clear MAC address learned on a specified VLAN";
         type string;
       }
       leaf isid {
         description "Clear MAC address learned on a specified ISID";
         type string;
       }
     }
     output {
       choice output_c {
         case output-tag {
           leaf output {
             type string;
           }
         }
         case multichassis-tag {
           anyxml multi-routing-engine-results;
         }
       }
     }
   }
   rpc clear-mac-vrf-table-persistent-learning {
     description "Clear persistent-mac entries";
     output {
       choice output_c {
         case output-tag {
           leaf output {
             type string;
           }
         }
         case multichassis-tag {
           anyxml multi-routing-engine-results;
         }
       }
     }
   }
   rpc clear-mac-vrf-persistent-learning-interface {
     description "Clear persistent MACs for specified interface";
     input {
       leaf interface-name {
         description "Name of interface for which to clear table";
         type string;
         mandatory true;
       }
     }
     output {
       choice output_c {
         case output-tag {
           leaf output {
             type string;
           }
         }
         case multichassis-tag {
           anyxml multi-routing-engine-results;
         }
       }
     }
   }
   rpc clear-mac-vrf-table-persistent-learning-mac {
     description "Clear one persitent MAC or all peristent MACs";
     input {
       leaf address {
         description "MAC address";
         default "all";
         type jt:mac-addr;
       }
     }
     output {
       choice output_c {
         case output-tag {
           leaf output {
             type string;
           }
         }
         case multichassis-tag {
           anyxml multi-routing-engine-results;
         }
       }
     }
   }
   rpc clear-mac-vrf-recovery {
     description "Clear port error";
     output {
       choice output_c {
         case output-tag {
           leaf output {
             type string;
           }
         }
         case multichassis-tag {
           anyxml multi-routing-engine-results;
         }
       }
     }
   }
   rpc clear-mac-vrf-recovery-interface {
     description "Clear port error for specified interface";
     input {
       leaf interface-name {
         description "Name of interface for which to clear table";
         type union {
           type jt:interface-name;
           type string {
             pattern "<.*>|$.*";
           }
         }
         mandatory true;
       }
       leaf vlan {
         description "VLAN(name or ID)";
         type string;
       }
     }
     output {
       choice output_c {
         case output-tag {
           leaf output {
             type string;
           }
         }
         case multichassis-tag {
           anyxml multi-routing-engine-results;
         }
       }
     }
   }
   rpc clear-mac-vrf-mac-learning-log {
     description "Clear all MAC address learning log";
     output {
       choice output_c {
         case output-tag {
           leaf output {
             type string;
           }
         }
         case multichassis-tag {
           anyxml multi-routing-engine-results;
         }
       }
     }
   }
   rpc clear-mac-vrf-redundancy-group-statistics {
     description "Clear redundancy group statistics counters";
     input {
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
       leaf redundancy-group-id {
         description "Display information for a specified RG";
         default "0";
         type union {
           type string {
             pattern "<.*>|$.*";
           }
           type uint32 {
             range "0 .. 4294967294";
           }
         }
       }
       leaf options {
         description "Clear information for specified RG or all RG(s)";
         type enumeration {
           enum "arp-statistics" {
             description "Show MCAE ARP Synchronization statistics";
           }
           enum "nd-statistics" {
             description "Show MCAE ND synchronization statistics";
           }
         }
       }
     }
     output {
       choice output_c {
         case output-tag {
           leaf output {
             type string;
           }
         }
         case multichassis-tag {
           anyxml multi-routing-engine-results;
         }
       }
     }
   }
   rpc clear-mac-vrf-mac-ip-table {
     description "Clear IPv4 and IPv6 entries for EVPN instances";
     input {
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf instance {
         description "Display information for a specified instance";
         default "all";
         type string;
       }
       leaf vlan-name {
         description "Name of VLAN, or 'all'";
         default "all";
         type string;
       }
       leaf address {
         description "MAC address";
         default "all";
         type jt:mac-addr;
       }
     }
     output {
       choice output_c {
         case output-tag {
           leaf output {
             type string;
           }
         }
         case multichassis-tag {
           anyxml multi-routing-engine-results;
         }
       }
     }
   }
   rpc clear-mac-vrf-mac-ipv4-table {
     description "Clear all INET addresses learned via ARP";
     input {
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf instance {
         description "Display information for a specified instance";
         default "all";
         type string;
       }
       leaf vlan-name {
         description "Name of VLAN, or 'all'";
         default "all";
         type string;
       }
       leaf address {
         description "MAC address";
         default "all";
         type jt:mac-addr;
       }
     }
     output {
       choice output_c {
         case output-tag {
           leaf output {
             type string;
           }
         }
         case multichassis-tag {
           anyxml multi-routing-engine-results;
         }
       }
     }
   }
   rpc clear-mac-vrf-mac-ipv6-table {
     description "Clear all INET6 addresses learned via NDP";
     input {
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf instance {
         description "Display information for a specified instance";
         default "all";
         type string;
       }
       leaf vlan-name {
         description "Name of VLAN, or 'all'";
         default "all";
         type string;
       }
       leaf address {
         description "MAC address";
         default "all";
         type jt:mac-addr;
       }
     }
     output {
       choice output_c {
         case output-tag {
           leaf output {
             type string;
           }
         }
         case multichassis-tag {
           anyxml multi-routing-engine-results;
         }
       }
     }
   }
   rpc clear-lldp-neighbors {
     description "Clear LLDP neighbor information";
     output {
       choice output_c {
         case output-tag {
           leaf output {
             type string;
           }
         }
         case multichassis-tag {
           anyxml multi-routing-engine-results;
         }
       }
     }
   }
   rpc clear-lldp-interface-neighbors {
     description "Clear LLDP interface statistics";
     input {
       leaf interface-device {
         description "Name of interface";
         type union {
           type jt:interface-device;
           type string {
             pattern "<.*>|$.*";
           }
         }
       }
     }
     output {
       choice output_c {
         case output-tag {
           leaf output {
             type string;
           }
         }
         case multichassis-tag {
           anyxml multi-routing-engine-results;
         }
       }
     }
   }
   rpc clear-lldp-statistics {
     description "Clear LLDP statistics";
     output {
       choice output_c {
         case output-tag {
           leaf output {
             type string;
           }
         }
         case multichassis-tag {
           anyxml multi-routing-engine-results;
         }
       }
     }
   }
   rpc clear-lldp-interface-statistics {
     description "Clear LLDP interface statistics";
     input {
       leaf interface-device {
         description "Name of interface";
         type union {
           type jt:interface-device;
           type string {
             pattern "<.*>|$.*";
           }
         }
       }
     }
     output {
       choice output_c {
         case output-tag {
           leaf output {
             type string;
           }
         }
         case multichassis-tag {
           anyxml multi-routing-engine-results;
         }
       }
     }
   }
   rpc clear-passive-monitoring {
     description "Clear passive monitoring statistics";
     output {
       choice output_c {
         case output-tag {
           leaf output {
             type string;
           }
         }
         case multichassis-tag {
           anyxml multi-routing-engine-results;
         }
       }
     }
   }
   rpc clear-passive-monitoring-statistics {
     description "Clear statistics";
     input {
       leaf interface-name {
         description "Name of monitoring interface, wildcard, or 'all'";
         type string;
         mandatory true;
       }
     }
     output {
       choice output_c {
         case output-tag {
           leaf output {
             type string;
           }
         }
         case multichassis-tag {
           anyxml multi-routing-engine-results;
         }
       }
     }
   }
   rpc clear-ppp-statistics-information {
     description "Clear PPP statistics";
     input {
       leaf type {
         description "Type of statistic to clear";
         type enumeration {
           enum "memory" {
             description "Clear PPP process memory statistics";
           }
         }
       }
     }
     output {
       choice output_c {
         case output-tag {
           leaf output {
             type string;
           }
         }
         case multichassis-tag {
           anyxml multi-routing-engine-results;
         }
       }
     }
   }
   rpc clear-database-replication-statistics-information {
     description "Clear database replication statistics";
     output {
       choice output_c {
         case output-tag {
           leaf output {
             type string;
           }
         }
         case multichassis-tag {
           anyxml multi-routing-engine-results;
         }
       }
     }
   }
   rpc clear-firewall-counters {
     description "Clear firewall counters";
     input {
       uses command-forwarding;
       leaf counter {
         description "Counter name";
         type string;
       }
       leaf filter {
         description "Filter name";
         type string;
         mandatory true;
       }
       choice daemon-select {
         case logical-system {
         }
       }
     }
     output {
       choice output_c {
         case output-tag {
           leaf output {
             type string;
           }
         }
         case multichassis-tag {
           anyxml multi-routing-engine-results;
         }
       }
     }
   }
   rpc clear-all-firewall-conters {
     description "Clear all firewall counters";
     input {
       uses command-forwarding;
       choice daemon-select {
         case logical-system {
         }
       }
     }
     output {
       choice output_c {
         case output-tag {
           leaf output {
             type string;
           }
         }
         case multichassis-tag {
           anyxml multi-routing-engine-results;
         }
       }
     }
   }
   rpc clear-firewall-policer-counter-statistics {
     description "Clear policer counter statistics";
     input {
       uses command-forwarding;
       choice daemon-select {
         case logical-system {
         }
       }
       leaf counter-id {
         description "Counter Index";
         type union {
           type string {
             pattern "<.*>|$.*";
           }
           type uint32 {
             range "0 .. 2";
           }
         }
         mandatory true;
       }
     }
     output {
       choice output_c {
         case output-tag {
           leaf output {
             type string;
           }
         }
         case multichassis-tag {
           anyxml multi-routing-engine-results;
         }
       }
     }
   }
   rpc clear-all-firewall-policer-counter-statistics {
     description "Clear all policer counter statistics";
     input {
       uses command-forwarding;
       choice daemon-select {
         case logical-system {
         }
       }
     }
     output {
       choice output_c {
         case output-tag {
           leaf output {
             type string;
           }
         }
         case multichassis-tag {
           anyxml multi-routing-engine-results;
         }
       }
     }
   }
   rpc clear-firewall-log {
     description "Clear all firewall log";
     input {
       uses command-forwarding;
       choice daemon-select {
         case logical-system {
         }
       }
     }
     output {
       choice output_c {
         case output-tag {
           leaf output {
             type string;
           }
         }
         case multichassis-tag {
           anyxml multi-routing-engine-results;
         }
       }
     }
   }
   rpc clear-sflow-collector-statistics {
     description "Clear sFlow collector statistics";
     output {
       choice output_c {
         case output-tag {
           leaf output {
             type string;
           }
         }
         case multichassis-tag {
           anyxml multi-routing-engine-results;
         }
       }
     }
   }
   rpc clear-protection-group-information {
     description "Clear protection group information";
     output {
       choice output_c {
         case output-tag {
           leaf output {
             type string;
           }
         }
         case multichassis-tag {
           anyxml multi-routing-engine-results;
         }
       }
     }
   }
   rpc clear-ethernet-ring-information {
     description "Clear ethernet ring information";
     output {
       choice output_c {
         case output-tag {
           leaf output {
             type string;
           }
         }
         case multichassis-tag {
           anyxml multi-routing-engine-results;
         }
       }
     }
   }
   rpc clear-ethernet-ring-statistics {
     description "Clear ethernet ring statistics";
     input {
       leaf group-name {
         description "Name of protection group";
         type string;
       }
     }
     output {
       choice output_c {
         case output-tag {
           leaf output {
             type string;
           }
         }
         case multichassis-tag {
           anyxml multi-routing-engine-results;
         }
       }
     }
   }
   rpc clear-mvrp-interface-statistics {
     description "Clear MVRP interface statistics";
     input {
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
       leaf routing-instance {
         description "Name of routing instance";
         type string;
       }
       leaf interface {
         description "Name of interface";
         type string;
       }
     }
     output {
       choice output_c {
         case output-tag {
           leaf output {
             type string;
           }
         }
         case multichassis-tag {
           anyxml multi-routing-engine-results;
         }
       }
     }
   }
   rpc clear-stp-interface-statistics {
     description "Clear STP interface statistics";
     input {
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
       leaf interface-name {
         description "Name of interface";
         type union {
           type jt:interface-device;
           type string {
             pattern "<.*>|$.*";
           }
         }
       }
       leaf routing-instance {
         description "Name of routing instance";
         type string;
       }
     }
     output {
       choice output_c {
         case output-tag {
           leaf output {
             type string;
           }
         }
         case actual-tag {
           anyxml stp-interface-statistics;
         }
         case multichassis-tag {
           anyxml multi-routing-engine-results;
         }
       }
     }
   }
   rpc clear-stp-routing-instance-statistics {
     description "Clear STP routing instance statistics";
     input {
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
       leaf routing-instance-name {
         description "Name of routing instance";
         type string;
       }
     }
     output {
       choice output_c {
         case output-tag {
           leaf output {
             type string;
           }
         }
         case actual-tag {
           anyxml stp-routing-instance-statistics;
         }
         case multichassis-tag {
           anyxml multi-routing-engine-results;
         }
       }
     }
   }
   rpc clear-stp-bridge-statistics {
     description "Statistics related to bridge";
     output {
       choice output_c {
         case output-tag {
           leaf output {
             type string;
           }
         }
         case multichassis-tag {
           anyxml multi-routing-engine-results;
         }
       }
     }
   }
   rpc clear-stp-topology-change-counter {
     description "Clear STP topology change counter";
     input {
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
       leaf vlan-id {
         description "VLAN ID";
         type union {
           type string {
             pattern "<.*>|$.*";
           }
           type int32 {
             range "1 .. 4094";
           }
         }
       }
       leaf routing-instance {
         description "Name of routing instance";
         type string;
       }
     }
     output {
       choice output_c {
         case output-tag {
           leaf output {
             type string;
           }
         }
         case actual-tag {
           anyxml stp-topology-change-counter;
         }
         case multichassis-tag {
           anyxml multi-routing-engine-results;
         }
       }
     }
   }
   rpc clear-interface-stp-protocol-migration {
     description "Clear Protocol Migration on an interface";
     input {
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
       leaf interface-name {
         description "Name of interface";
         type union {
           type jt:interface-device;
           type string {
             pattern "<.*>|$.*";
           }
         }
       }
       leaf routing-instance {
         description "Name of routing instance";
         type string;
       }
     }
     output {
       choice output_c {
         case output-tag {
           leaf output {
             type string;
           }
         }
         case actual-tag {
           anyxml interface-stp-protocol-migration;
         }
         case multichassis-tag {
           anyxml multi-routing-engine-results;
         }
       }
     }
   }
   rpc clear-stp-buffer {
     description "Internal buffer for STP";
     output {
       choice output_c {
         case output-tag {
           leaf output {
             type string;
           }
         }
         case multichassis-tag {
           anyxml multi-routing-engine-results;
         }
       }
     }
   }
   rpc clear-loop-detect-statistics-information {
     description "Clear loop detect interface statistics";
     input {
       leaf interface-name {
         type string;
         mandatory true;
       }
     }
     output {
       choice output_c {
         case output-tag {
           leaf output {
             type string;
           }
         }
         case actual-tag {
           anyxml loop-detect-interface-statistics;
         }
         case multichassis-tag {
           anyxml multi-routing-engine-results;
         }
       }
     }
   }
   rpc clear-loop-detect-enhanced-interface-state {
     description "Clear loop detect enhanced interface";
     input {
       leaf interface-name {
         description "Name of interface";
         type union {
           type jt:interface-unit;
           type string {
             pattern "<.*>|$.*";
           }
         }
       }
     }
     output {
       choice output_c {
         case output-tag {
           leaf output {
             type string;
           }
         }
         case actual-tag {
           anyxml ld-clear-loop-detect-enhanced-interface-state;
         }
         case multichassis-tag {
           anyxml multi-routing-engine-results;
         }
       }
     }
   }
   rpc clear-bpdu-error {
     description "Clear BPDU error on an interface (BPDU Protect)";
     input {
       leaf interface-name {
         type string;
         mandatory true;
       }
     }
     output {
       choice output_c {
         case output-tag {
           leaf output {
             type string;
           }
         }
         case actual-tag {
           anyxml bpdu-error;
         }
         case multichassis-tag {
           anyxml multi-routing-engine-results;
         }
       }
     }
   }
   rpc clear-loop-detect-error {
     description "Clear Loop Detect error on an interface";
     input {
       leaf interface-name {
         type string;
         mandatory true;
       }
     }
     output {
       choice output_c {
         case output-tag {
           leaf output {
             type string;
           }
         }
         case actual-tag {
           anyxml loop-detect-error;
         }
         case multichassis-tag {
           anyxml multi-routing-engine-results;
         }
       }
     }
   }
   rpc clear-mac-rewrite-error {
     description "Clear mac-rewrite error on an interface";
     input {
       leaf interface-name {
         description "Name of interface";
         type union {
           type jt:interface-device;
           type string {
             pattern "<.*>|$.*";
           }
         }
       }
     }
     output {
       choice output_c {
         case output-tag {
           leaf output {
             type string;
           }
         }
         case actual-tag {
           anyxml mac-rewrite-error;
         }
         case multichassis-tag {
           anyxml multi-routing-engine-results;
         }
       }
     }
   }
   rpc clear-virtual-chassis-port-statistics {
     description "Clear virtual chassis port statistics";
     input {
       uses command-forwarding;
       leaf interface-name {
         description "Name of virtual chassis port";
         type string;
       }
     }
     output {
       choice output_c {
         case output-tag {
           leaf output {
             type string;
           }
         }
         case actual-tag {
           anyxml clear-virtual-chassis-port-statistics;
         }
         case multichassis-tag {
           anyxml multi-routing-engine-results;
         }
       }
     }
   }
   rpc clear-virtual-chassis-statistics {
     description "Clear virtual chassis statistics";
     output {
       choice output_c {
         case output-tag {
           leaf output {
             type string;
           }
         }
         case actual-tag {
           anyxml clear-virtual-chassis-statistics;
         }
         case multichassis-tag {
           anyxml multi-routing-engine-results;
         }
       }
     }
   }
   rpc clear-fip-snooping-vlan {
     description "Clear FIP snooping database for this VLAN";
     input {
       leaf vlan {
         description "Name of VLAN";
         type string;
         mandatory true;
       }
     }
     output {
       choice output_c {
         case output-tag {
           leaf output {
             type string;
           }
         }
         case multichassis-tag {
           anyxml multi-routing-engine-results;
         }
       }
     }
   }
   rpc clear-fip-snooping-enode {
     description "Clear all FIP snooping session for this Enode";
     input {
       leaf mac {
         description "Enode MAC address";
         type jt:mac-addr;
         mandatory true;
       }
       leaf vlan {
         description "Name of VLAN";
         type string;
       }
     }
     output {
       choice output_c {
         case output-tag {
           leaf output {
             type string;
           }
         }
         case multichassis-tag {
           anyxml multi-routing-engine-results;
         }
       }
     }
   }
   rpc clear-fip-snooping-statistics {
     description "Clear FIP snooping statistics";
     input {
       leaf vlan {
         description "Name of VLAN";
         type string;
       }
     }
     output {
       choice output_c {
         case output-tag {
           leaf output {
             type string;
           }
         }
         case multichassis-tag {
           anyxml multi-routing-engine-results;
         }
       }
     }
   }
   rpc clear-fip-snooping-vlandiscovery-statistics {
     description "Clear FIP vlan discovery statistics";
     output {
       choice output_c {
         case output-tag {
           leaf output {
             type string;
           }
         }
         case multichassis-tag {
           anyxml multi-routing-engine-results;
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member";
           type union {
             type string {
               pattern "<.*>|$.*";
             }
             type uint32;
           }
         }
       }
     }
   }
 }
