/*
 * Copyright (c) 2020 Juniper Networks, Inc.
 * All rights reserved.
 */
 module junos-qfx-conf-routing-options {
   namespace "http://yang.juniper.net/junos-qfx/conf/routing-options";

   prefix jc-routing-options;

   import junos-common-types {
     prefix jt;
     revision-date 2019-01-01;
   }

   import junos-qfx-conf-root {
     prefix jc;
     revision-date 2019-01-01;
   }

   organization "Juniper Networks, Inc.";

   contact "yang-support@juniper.net";

   description "Junos routing-options configuration module";

   revision 2019-01-01 {
     description "Junos: 20.4R1.12";
   }

   augment /jc:configuration {
     uses routing-options-group;
   }
   augment /jc:configuration/jc:groups {
     uses routing-options-group;
   }
   grouping routing-options-group {
     container routing-options {
       description "Protocol-independent routing option configuration";
       uses juniper-routing-options;
     }
   }
   grouping juniper-routing-options {
     uses apply-advanced;
     container rpm-tracking {
       description "RPM static route tracking options";
       uses apply-advanced;
       list route {
         key name;
         ordered-by user;
         description "Static Route";
         leaf name {
           description "IP address of destination";
           type jt:ipprefix;
         }
         uses apply-advanced;
         list next-hop {
           key name;
           ordered-by user;
           description "Next hop to destination";
           uses rpm-next-hop;
         }
         leaf metric {
           description "Metric value";
           type union {
             type string {
               pattern "<.*>|$.*";
             }
             type uint32 {
               range "1 .. 16";
             }
           }
         }
         leaf preference {
           description "Preference value";
           type union {
             type uint32;
             type string {
               pattern "<.*>|$.*";
             }
           }
         }
         leaf tag {
           description "Tag value";
           type union {
             type uint32;
             type string {
               pattern "<.*>|$.*";
             }
           }
         }
         list rpm-probe {
           key name;
           ordered-by user;
           leaf name {
             description "RPM probe to track";
             type string;
           }
           leaf rpm-test {
             description "RPM test to track";
             type string;
           }
         }
       }
     }
     container logical-system-mux {
       description "Logical system control daemon information";
       uses apply-advanced;
       container traceoptions {
         description "Trace options";
         uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "debug" {
                 description "Trace debug-level lrmuxd activities";
               }
               enum "parse" {
                 description "Trace configuration parsing";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
     }
     container backup-selection {
       presence "enable backup-selection";
       description "Backup selection options";
       uses apply-advanced;
       list destination {
         key name;
         description "IP/IPv6 prefix for which backup selection policy is configured";
         leaf name {
           description "IP/IPv6 address (and optional prefix length)";
           type jt:ipprefix-mandatory;
         }
         uses apply-advanced;
         list interface {
           key name;
           description "Primary nexthop interface for which backup selection policy is configured";
           leaf name {
             description "Interface name";
             type union {
               type jt:interface-name;
               type string {
                 pattern "<.*>|$.*";
               }
             }
           }
           uses apply-advanced;
           container admin-group {
             description "Administrative group policies for backup-selection";
             uses apply-advanced;
             leaf-list exclude {
               description "Do not use interface if any admin group available";
               type string;
             }
             leaf-list include-all {
               description "Use interface if admin groups available entirely";
               type string;
             }
             leaf-list include-any {
               description "Use interface if any admin group is available";
               type string;
             }
             leaf-list preference {
               ordered-by user;
               description "Administrative groups in descending preference order";
               type string;
             }
           }
           leaf srlg {
             description "Evaluate Shared Risk Link Group(SRLG) characteristics for backup selection";
             default "loose";
             type enumeration {
               enum "loose" {
                 description "Loose SRLG";
               }
               enum "strict" {
                 description "Strict SRLG";
               }
             }
           }
           leaf protection-type {
             description "Type of protection to be considered";
             type enumeration {
               enum "link" {
                 description "Protect the primary interface from link faults only";
               }
               enum "node" {
                 description "Protect the primary interface from node faults only";
               }
               enum "node-link" {
                 description "Protect the primary interface from either link or node faults; prefer node protection";
               }
             }
           }
           leaf downstream-paths-only {
             description "Choose only the downstream nodes for backup";
             type empty;
           }
           leaf bandwidth-greater-equal-primary {
             description "Use backup nexthop only if bandwidth is >= bandwidth of primary nexthop";
             type empty;
           }
           container backup-neighbor {
             description "Backup Neighbor ID based policies for backup selection";
             uses apply-advanced;
             leaf-list exclude {
               description "List of backup neighbors to be excluded";
               type jt:ipv4addr;
             }
             leaf-list preference {
               ordered-by user;
               description "List of backup neighbors in descending order preference";
               type jt:ipv4addr;
             }
           }
           container node {
             description "Node ID based policies for backup selection";
             uses apply-advanced;
             leaf-list exclude {
               description "List of nodes to be excluded";
               type jt:ipv4addr;
             }
             leaf-list preference {
               ordered-by user;
               description "List of nodes in the descending order of preference";
               type jt:ipv4addr;
             }
           }
           container node-tag {
             description "Node  tag policies";
             uses apply-advanced;
             leaf-list exclude {
               description "The set of node tags to be excluded";
               type union {
                 type uint32;
                 type string {
                   pattern "<.*>|$.*";
                 }
               }
             }
             leaf-list preference {
               ordered-by user;
               description "The set of node tags in the descending order of preference";
               type union {
                 type uint32;
                 type string {
                   pattern "<.*>|$.*";
                 }
               }
             }
           }
           leaf root-metric {
             description "Root metric";
             type enumeration {
               enum "lowest" {
                 description "Choose lowest root metric";
               }
               enum "highest" {
                 description "Choose highest root metric";
               }
             }
           }
           leaf dest-metric {
             description "Destination metric";
             type enumeration {
               enum "lowest" {
                 description "Choose lowest destination metric";
               }
               enum "highest" {
                 description "Choose highest destination metric";
               }
             }
           }
           leaf-list metric-order {
             ordered-by user;
             description "Metric evaluation order";
             type enumeration {
               enum "root" {
               }
               enum "dest" {
               }
             }
             max-elements 2;
           }
           leaf-list evaluation-order {
             ordered-by user;
             description "Interface policy criteria evaluation order";
             type enumeration {
               enum "admin-group" {
                 description "Administrative Group/Link Color";
               }
               enum "srlg" {
                 description "SRLG";
               }
               enum "bandwidth" {
                 description "Bandwidth";
               }
               enum "protection-type" {
                 description "Type of protection";
               }
               enum "backup-neighbor" {
                 description "Backup Neighbor";
               }
               enum "node" {
                 description "Node";
               }
               enum "node-tag" {
                 description "Node tag";
               }
               enum "metric" {
                 description "Metric related parameters";
               }
             }
           }
         }
       }
     }
     list flex-algorithm {
       key name;
       description "Configure flex-algorithms supported by this node.";
       leaf name {
         description "Algorithm id";
         type union {
           type string {
             pattern "<.*>|$.*";
           }
           type uint32 {
             range "128 .. 255";
           }
         }
       }
       uses apply-advanced;
       container definition {
         description "Configure flex-algorithm definition.";
         uses apply-advanced;
         leaf metric-type {
           type enumeration {
             enum "igp-metric" {
               description "Metric configured to be used for IGP";
             }
             enum "te-metric" {
               description "Traffic-engineering metric";
             }
           }
         }
         choice calculation-type {
           case case_1 {
             leaf spf {
               description "Normal SPF of type 0";
               type empty;
             }
           }
           case case_2 {
             leaf strict-spf {
               description "Strict SPF";
               type empty;
             }
           }
         }
         leaf priority {
           description "Priority of the flex-algorithm advertisement.";
           type union {
             type string {
               pattern "<.*>|$.*";
             }
             type uint32 {
               range "0 .. 255";
             }
           }
         }
         container admin-group {
           description "Administrative group policy";
           uses admin_group_include_exclude;
         }
       }
       leaf color {
         description "Color to be associated with this flex-algorithm";
         type union {
           type uint32;
           type string {
             pattern "<.*>|$.*";
           }
         }
       }
     }
     container source-packet-routing {
       description "Source packet routing (SPRING)";
       uses apply-advanced;
       list mapping-server-entry {
         key name;
         ordered-by user;
         description "Mapping server entry";
         leaf name {
           description "Mapping server entry name";
           type string {
             length "1 .. 64";
           }
         }
         uses apply-advanced;
         list prefix-segment {
           key name;
           ordered-by user;
           description "Prefix segment";
           max-elements 64;
           leaf name {
             description "Prefix segment prefix";
             type jt:ipprefix;
           }
           uses apply-advanced;
           leaf index {
             description "Prefix segment index";
             type union {
               type string {
                 pattern "<.*>|$.*";
               }
               type uint32 {
                 range "0 .. 199999";
               }
             }
           }
           leaf attached {
             description "Set attached flag in IS-IS mapping server advertisement";
             type empty;
           }
           leaf domain-wide-flooding {
             description "Set S-flag in IS-IS mapping server advertisement";
             type empty;
           }
           leaf no-node-segment {
             description "Clear node segment flag in mapping server prefix segment";
             type empty;
           }
         }
         list prefix-segment-range {
           key name;
           ordered-by user;
           description "Prefix segment range";
           max-elements 64;
           leaf name {
             description "Prefix segment range name";
             type string {
               length "1 .. 64";
             }
           }
           uses apply-advanced;
           leaf start-prefix {
             description "Start prefix";
             type jt:ipprefix;
           }
           leaf start-index {
             description "Start index";
             type union {
               type string {
                 pattern "<.*>|$.*";
               }
               type uint32 {
                 range "0 .. 199999";
               }
             }
           }
           leaf size {
             description "Size of prefix segment range";
             type union {
               type string {
                 pattern "<.*>|$.*";
               }
               type uint32 {
                 range "1 .. 1024";
               }
             }
           }
           leaf attached {
             description "Set attached flag in IS-IS mapping server advertisement";
             type empty;
           }
           leaf domain-wide-flooding {
             description "Set S-flag in IS-IS mapping server advertisement";
             type empty;
           }
           leaf no-node-segment {
             description "Clear node segment flag in mapping server prefix segment";
             type empty;
           }
         }
       }
       container srv6 {
         description "SRv6 source-packet-routing";
         uses apply-advanced;
         list locator {
           key name;
           ordered-by user;
           leaf name {
             description "Locator entry name";
             type string {
               length "1 .. 64";
             }
           }
           uses apply-advanced;
           leaf algorithm {
             description "Algorithm associated with this locator";
             type union {
               type string {
                 pattern "<.*>|$.*";
               }
               type uint32 {
                 range "0 .. 255";
               }
             }
           }
           leaf address {
             description "Configure Locator Service for SRv6";
             type jt:ipv6prefix;
           }
         }
         leaf no-reduced-srh {
           description "SRv6 Encapsulation mode non reduced SRH";
           type empty;
         }
         leaf transit-srh-insert {
           description "SRv6 SRH insert mode on transit";
           type empty;
         }
       }
     }
     leaf route-distinguisher-id {
       description "Identifier used in route distinguishers for routing instances";
       type jt:ipv4addr;
     }
     list rib {
       key name;
       ordered-by user;
       description "Routing table options";
       leaf name {
         description "Routing table name";
         type string;
       }
       uses apply-advanced;
       container static {
         description "Static routes";
         uses apply-advanced;
         list route {
           key name;
           ordered-by user;
           description "Static route";
           leaf name {
             type jt:ipprefix;
           }
           uses apply-advanced;
           choice next_hop {
             case case_1 {
               leaf-list next-hop {
                 ordered-by user;
                 description "Next hop to destination";
                 type union {
                   type jt:ipaddr-or-interface;
                   type string {
                     pattern "<.*>|$.*";
                   }
                 }
               }
             }
             case case_2 {
               leaf reject {
                 description "Drop packets to destination; send ICMP unreachables";
                 type empty;
               }
             }
             case case_3 {
               leaf discard {
                 description "Drop packets to destination; send no ICMP unreachables";
                 type empty;
               }
             }
             case case_4 {
               leaf receive {
                 description "Install a receive route for the destination";
                 type empty;
               }
             }
             case case_5 {
               leaf next-table {
                 description "Next hop to another table";
                 type string {
                 }
               }
             }
           }
           list qualified-next-hop {
             key name;
             ordered-by user;
             description "Next hop with qualifiers";
             uses qualified_nh_obj;
           }
           leaf backup-pe-group {
             description "Multicast source redundancy group";
             type string;
           }
           container bfd-liveness-detection {
             description "Bidirectional Forwarding Detection (BFD) options";
             uses apply-advanced;
             leaf version {
               description "BFD protocol version number";
               default "automatic";
               type enumeration {
                 enum "0" {
                   description "BFD version 0 (deprecated)";
                 }
                 enum "1" {
                   description "BFD version 1";
                 }
                 enum "automatic" {
                   description "Choose BFD version automatically";
                 }
               }
             }
             leaf minimum-interval {
               description "Minimum transmit and receive interval";
               units "milliseconds";
               type union {
                 type string {
                   pattern "<.*>|$.*";
                 }
                 type uint32 {
                   range "1 .. 255000";
                 }
               }
             }
             leaf minimum-transmit-interval {
               description "Minimum transmit interval";
               status deprecated;
               units "milliseconds";
               type union {
                 type string {
                   pattern "<.*>|$.*";
                 }
                 type uint32 {
                   range "1 .. 255000";
                 }
               }
             }
             leaf minimum-receive-interval {
               description "Minimum receive interval";
               units "milliseconds";
               type union {
                 type string {
                   pattern "<.*>|$.*";
                 }
                 type uint32 {
                   range "1 .. 255000";
                 }
               }
             }
             leaf multiplier {
               description "Detection time multiplier";
               default "3";
               type union {
                 type string {
                   pattern "<.*>|$.*";
                 }
                 type uint32 {
                   range "1 .. 255";
                 }
               }
             }
             choice adaptation-choice {
               case case_1 {
                 leaf no-adaptation {
                   description "Disable adaptation";
                   type empty;
                 }
               }
             }
             container transmit-interval {
               description "Transmit-interval options";
               uses apply-advanced;
               leaf minimum-interval {
                 description "Minimum transmit interval";
                 units "milliseconds";
                 type union {
                   type string {
                     pattern "<.*>|$.*";
                   }
                   type uint32 {
                     range "1 .. 255000";
                   }
                 }
               }
               leaf threshold {
                 description "High transmit interval triggering a trap";
                 units "milliseconds";
                 type union {
                   type uint32;
                   type string {
                     pattern "<.*>|$.*";
                   }
                 }
               }
             }
             container detection-time {
               description "Detection-time options";
               uses apply-advanced;
               leaf threshold {
                 description "High detection-time triggering a trap";
                 units "milliseconds";
                 type union {
                   type uint32;
                   type string {
                     pattern "<.*>|$.*";
                   }
                 }
               }
             }
             container authentication {
               description "Authentication options";
               uses apply-advanced;
               leaf key-chain {
                 description "Key chain name";
                 type string;
               }
               leaf algorithm {
                 description "Algorithm name";
                 type enumeration {
                   enum "simple-password" {
                     description "Simple password";
                   }
                   enum "keyed-md5" {
                     description "Keyed message Digest 5";
                   }
                   enum "meticulous-keyed-md5" {
                     description "Meticulous keyed message Digest 5";
                   }
                   enum "keyed-sha-1" {
                     description "Keyed secure hash algorithm (SHA1) ";
                   }
                   enum "meticulous-keyed-sha-1" {
                     description "Meticulous keyed secure hash algorithm (SHA1) ";
                   }
                 }
               }
               leaf loose-check {
                 description "Verify authentication only if authentication is negotiated";
                 type empty;
               }
             }
             leaf neighbor {
               description "BFD neighbor address";
               type jt:ipaddr;
             }
             leaf local-address {
               description "BFD local address (for multihop only)";
               type jt:ipaddr;
             }
             leaf holddown-interval {
               description "Time to hold the session-UP notification to the client";
               units "milliseconds";
               type union {
                 type string {
                   pattern "<.*>|$.*";
                 }
                 type uint32 {
                   range "0 .. 255000";
                 }
               }
             }
             leaf minimum-receive-ttl {
               description "Minimum receive TTL below which to drop";
               type union {
                 type string {
                   pattern "<.*>|$.*";
                 }
                 type uint8 {
                   range "1 .. 255";
                 }
               }
             }
           }
           choice retain-choice {
             leaf retain {
               description "Always keep route in forwarding table";
               type empty;
             }
             leaf no-retain {
               description "Don't always keep route in forwarding table";
               type empty;
             }
           }
           choice install-choice {
             leaf install {
               description "Install route into forwarding table";
               type empty;
             }
             leaf no-install {
               description "Don't install route into forwarding table";
               type empty;
             }
           }
           choice readvertise-choice {
             leaf readvertise {
               description "Mark route as eligible to be readvertised";
               type empty;
             }
             leaf no-readvertise {
               description "Don't mark route as eligible to be readvertised";
               type empty;
             }
           }
           choice resolve-choice {
             leaf resolve {
               description "Allow resolution of indirectly connected next hops";
               type empty;
             }
             leaf no-resolve {
               description "Don't allow resolution of indirectly connected next hops";
               type empty;
             }
           }
           choice longest-match-choice {
             leaf longest-match {
               description "Always use longest prefix match to resolve next hops";
               type empty;
             }
             leaf no-longest-match {
               description "Don't always use longest prefix match to resolve next hops";
               type empty;
             }
           }
           choice passive_flag {
             case case_1 {
               leaf active {
                 description "Remove inactive route from forwarding table";
                 type empty;
               }
             }
             case case_2 {
               leaf passive {
                 description "Retain inactive route in forwarding table";
                 type empty;
               }
             }
           }
           container metric {
             description "Metric value";
             presence "enable metric";
             uses rib_static_metric_type;
           }
           container metric2 {
             description "Metric value 2";
             presence "enable metric2";
             uses rib_static_metric_type;
           }
           container metric3 {
             description "Metric value 3";
             presence "enable metric3";
             uses rib_static_metric_type;
           }
           container metric4 {
             description "Metric value 4";
             presence "enable metric4";
             uses rib_static_metric_type;
           }
           container tag {
             description "Tag string";
             presence "enable tag";
             uses rib_static_metric_type;
           }
           container tag2 {
             description "Tag string 2";
             presence "enable tag2";
             uses rib_static_metric_type;
           }
           container preference {
             description "Preference value";
             presence "enable preference";
             uses rib_static_metric_type;
           }
           container preference2 {
             description "Preference value 2";
             presence "enable preference2";
             uses rib_static_metric_type;
           }
           container color {
             description "Color (preference) value";
             presence "enable color";
             uses rib_static_metric_type;
           }
           container color2 {
             description "Color (preference) value 2";
             presence "enable color2";
             uses rib_static_metric_type;
           }
           leaf-list community {
             ordered-by user;
             description "BGP community identifier";
             type jt:community;
           }
           container as-path {
             description "Autonomous system path";
             uses apply-advanced;
             leaf path {
               description "Autonomous system path";
               type string;
             }
             leaf origin {
               type enumeration {
                 enum "igp" {
                   description "Path originated in the local IGP";
                 }
                 enum "egp" {
                   description "Path originated in another AS";
                 }
                 enum "incomplete" {
                   description "Path was learned by some other means";
                 }
               }
             }
             leaf atomic-aggregate {
               description "Add ATOMIC_AGGREGATE path attribute to route";
               type empty;
             }
             container aggregator {
               presence "enable aggregator";
               description "Add AGGREGATOR path attribute to route";
             }
             leaf as-number {
               description " Autonomous system number in plain number or 'higher 16bits'.'Lower 16 bits' (asdot notation) format";
               type string {
               }
             }
             leaf address {
               description "Address of BGP system that formed the route";
               type jt:ipv4addr;
             }
           }
           list lsp-next-hop {
             key name;
             ordered-by user;
             description "LSP next hop";
             uses lsp_nh_obj;
           }
           list p2mp-lsp-next-hop {
             key name;
             ordered-by user;
             description "Point-to-multipoint LSP next hop";
             max-elements 1;
             uses lsp_nh_obj;
           }
           container p2mp-ldp-next-hop {
             description "Point-to-multipoint LDP LSP next hop";
             uses p2mp_ldp_lsp_nh_obj;
           }
           list static-lsp-next-hop {
             key name;
             ordered-by user;
             description "Static LSP next hop";
             uses lsp_nh_obj;
           }
         }
         leaf rib-group {
           description "Routing table group";
           type string;
         }
         container defaults {
           description "Global route options";
           uses apply-advanced;
           choice retain-choice {
             leaf retain {
               description "Always keep route in forwarding table";
               type empty;
             }
             leaf no-retain {
               description "Don't always keep route in forwarding table";
               type empty;
             }
           }
           choice install-choice {
             leaf install {
               description "Install route into forwarding table";
               type empty;
             }
             leaf no-install {
               description "Don't install route into forwarding table";
               type empty;
             }
           }
           choice readvertise-choice {
             leaf readvertise {
               description "Mark route as eligible to be readvertised";
               type empty;
             }
             leaf no-readvertise {
               description "Don't mark route as eligible to be readvertised";
               type empty;
             }
           }
           choice resolve-choice {
             leaf resolve {
               description "Allow resolution of indirectly connected next hops";
               type empty;
             }
             leaf no-resolve {
               description "Don't allow resolution of indirectly connected next hops";
               type empty;
             }
           }
           choice longest-match-choice {
             leaf longest-match {
               description "Always use longest prefix match to resolve next hops";
               type empty;
             }
             leaf no-longest-match {
               description "Don't always use longest prefix match to resolve next hops";
               type empty;
             }
           }
           choice passive_flag {
             case case_1 {
               leaf active {
                 description "Remove inactive route from forwarding table";
                 type empty;
               }
             }
             case case_2 {
               leaf passive {
                 description "Retain inactive route in forwarding table";
                 type empty;
               }
             }
           }
           container metric {
             description "Metric value";
             presence "enable metric";
             uses rib_static_metric_type;
           }
           container metric2 {
             description "Metric value 2";
             presence "enable metric2";
             uses rib_static_metric_type;
           }
           container metric3 {
             description "Metric value 3";
             presence "enable metric3";
             uses rib_static_metric_type;
           }
           container metric4 {
             description "Metric value 4";
             presence "enable metric4";
             uses rib_static_metric_type;
           }
           container tag {
             description "Tag string";
             presence "enable tag";
             uses rib_static_metric_type;
           }
           container tag2 {
             description "Tag string 2";
             presence "enable tag2";
             uses rib_static_metric_type;
           }
           container preference {
             description "Preference value";
             presence "enable preference";
             uses rib_static_metric_type;
           }
           container preference2 {
             description "Preference value 2";
             presence "enable preference2";
             uses rib_static_metric_type;
           }
           container color {
             description "Color (preference) value";
             presence "enable color";
             uses rib_static_metric_type;
           }
           container color2 {
             description "Color (preference) value 2";
             presence "enable color2";
             uses rib_static_metric_type;
           }
           leaf-list community {
             ordered-by user;
             description "BGP community identifier";
             type jt:community;
           }
           container as-path {
             description "Autonomous system path";
             uses apply-advanced;
             leaf path {
               description "Autonomous system path";
               type string;
             }
             leaf origin {
               type enumeration {
                 enum "igp" {
                   description "Path originated in the local IGP";
                 }
                 enum "egp" {
                   description "Path originated in another AS";
                 }
                 enum "incomplete" {
                   description "Path was learned by some other means";
                 }
               }
             }
             leaf atomic-aggregate {
               description "Add ATOMIC_AGGREGATE path attribute to route";
               type empty;
             }
             container aggregator {
               presence "enable aggregator";
               description "Add AGGREGATOR path attribute to route";
             }
             leaf as-number {
               description " Autonomous system number in plain number or 'higher 16bits'.'Lower 16 bits' (asdot notation) format";
               type string {
               }
             }
             leaf address {
               description "Address of BGP system that formed the route";
               type jt:ipv4addr;
             }
           }
         }
         container static-route {
           description "Static route Status";
           leaf bfd-admin-down {
             description "Static route State on BFD ADMIN DOWN";
             type enumeration {
               enum "active" {
                 description "Static route will be inactive on bfd-admin-down";
               }
               enum "passive" {
                 description "Static route will remain active on bfd-admin-down";
               }
             }
           }
         }
         list route-target-filter {
           key name;
           ordered-by user;
           description "Route-target-filter route";
           leaf name {
             type string {
               length "1 .. 47";
             }
           }
           uses apply-advanced;
           leaf-list neighbor {
             ordered-by user;
             description "BGP peers for filter";
             type jt:ipaddr-scoped;
           }
           leaf-list group {
             ordered-by user;
             description "BGP groups for filter";
             type string;
           }
           leaf local {
             description "Locally originated filter";
             type empty;
           }
         }
       }
       list martians {
         key "address choice-ident choice-value";
         ordered-by user;
         description "Invalid routes";
         uses martian_type;
       }
       container aggregate {
         description "Coalesced routes";
         uses rib_aggregate_type;
       }
       container generate {
         description "Route of last resort";
         uses rib_aggregate_type;
       }
       choice maximum-paths-type {
         case case_1 {
           container maximum-routes {
             description "Maximum number of routes";
             status deprecated;
             leaf limit {
               description "Maximum number of routes";
               type union {
                 type string {
                   pattern "<.*>|$.*";
                 }
                 type uint32 {
                   range "1 .. 4294967295";
                 }
               }
             }
             choice log_type {
               case case_1 {
                 leaf threshold {
                   description "Percentage of limit at which to start generating warnings";
                   type union {
                     type string {
                       pattern "<.*>|$.*";
                     }
                     type uint32 {
                       range "1 .. 100";
                     }
                   }
                 }
               }
               case case_2 {
                 leaf log-only {
                   description "Generate warning messages only";
                   type empty;
                 }
               }
             }
             leaf log-interval {
               description "Minimum interval between log messages";
               units "seconds";
               type union {
                 type string {
                   pattern "<.*>|$.*";
                 }
                 type uint32 {
                   range "5 .. 86400";
                 }
               }
             }
           }
         }
         case case_2 {
           container maximum-paths {
             description "Maximum number of paths";
             leaf limit {
               description "Maximum number of paths";
               type union {
                 type string {
                   pattern "<.*>|$.*";
                 }
                 type uint32 {
                   range "1 .. 4294967295";
                 }
               }
             }
             choice log_type {
               case case_1 {
                 leaf threshold {
                   description "Percentage of limit at which to start generating warnings";
                   type union {
                     type string {
                       pattern "<.*>|$.*";
                     }
                     type uint32 {
                       range "1 .. 100";
                     }
                   }
                 }
               }
               case case_2 {
                 leaf log-only {
                   description "Generate warning messages only";
                   type empty;
                 }
               }
             }
             leaf log-interval {
               description "Minimum interval between log messages";
               units "seconds";
               type union {
                 type string {
                   pattern "<.*>|$.*";
                 }
                 type uint32 {
                   range "5 .. 86400";
                 }
               }
             }
           }
         }
       }
       container maximum-prefixes {
         description "Maximum number of prefixes";
         leaf limit {
           description "Maximum number of prefixes";
           type union {
             type string {
               pattern "<.*>|$.*";
             }
             type uint32 {
               range "1 .. 4294967295";
             }
           }
         }
         choice log_type {
           case case_1 {
             leaf threshold {
               description "Percentage of limit at which to start generating warnings";
               type union {
                 type string {
                   pattern "<.*>|$.*";
                 }
                 type uint32 {
                   range "1 .. 100";
                 }
               }
             }
           }
           case case_2 {
             leaf log-only {
               description "Generate warning messages only";
               type empty;
             }
           }
         }
         leaf log-interval {
           description "Minimum interval between log messages";
           units "seconds";
           type union {
             type string {
               pattern "<.*>|$.*";
             }
             type uint32 {
               range "5 .. 86400";
             }
           }
         }
       }
       container multipath {
         presence "enable multipath";
         description "Protocol-independent load balancing";
         uses apply-advanced;
         container vpn-unequal-cost {
           presence "enable vpn-unequal-cost";
           description "Include VPN routes with unequal IGP metrics";
           leaf equal-external-internal {
             description "Include external and internal VPN routes";
             type empty;
           }
         }
         leaf as-path-compare {
           description "Compare AS path sequences in addition to AS path length";
           type empty;
         }
         leaf preserve-nexthop-hierarchy {
           description "Force multipath to create List nexthop";
           type empty;
         }
       }
       container policy-multipath {
         description "Policy based multipath";
         uses apply-advanced;
         leaf-list policy {
           ordered-by user;
           description "Import policy to create policy based multipath";
           type jt:policy-algebra;
         }
         container traceoptions {
           description "Trace options";
           uses apply-advanced;
           container file {
             description "Trace file options";
             leaf filename {
               description "Name of file in which to write trace information";
               type string {
                 length "1 .. 1024";
               }
             }
             leaf replace {
               description "Replace trace file rather than appending to it";
               status deprecated;
               type empty;
             }
             leaf size {
               description "Maximum trace file size";
               type string;
             }
             leaf files {
               description "Maximum number of trace files";
               default "10";
               type union {
                 type string {
                   pattern "<.*>|$.*";
                 }
                 type uint32 {
                   range "2 .. 1000";
                 }
               }
             }
             leaf no-stamp {
               description "Do not timestamp trace file";
               status deprecated;
               type empty;
             }
             choice world-readable-choice {
               leaf world-readable {
                 description "Allow any user to read the log file";
                 type empty;
               }
               leaf no-world-readable {
                 description "Don't allow any user to read the log file";
                 type empty;
               }
             }
           }
           list flag {
             key name;
             ordered-by user;
             description "Tracing parameters";
             leaf name {
               type enumeration {
                 enum "route" {
                   description "Policy-multipath route tracing.";
                 }
               }
             }
             leaf send {
               description "Trace transmitted packets";
               type empty;
             }
             leaf receive {
               description "Trace received packets";
               type empty;
             }
             leaf detail {
               description "Trace detailed information";
               type empty;
             }
             leaf disable {
               description "Disable this trace flag";
               type empty;
             }
           }
         }
       }
       container protect {
         description "Protocol-independent protection";
         leaf core {
           description "Protect against unreachability to service-edge router";
           type empty;
         }
       }
       container access {
         description "Access routes";
         uses apply-advanced;
         list route {
           key name;
           ordered-by user;
           description "Access route";
           leaf name {
             description "IP address of destination";
             type jt:ipprefix;
           }
           uses apply-advanced;
           leaf-list next-hop {
             ordered-by user;
             description "Next hop to destination";
             type union {
               type jt:ipaddr-or-interface;
               type string {
                 pattern "<.*>|$.*";
               }
             }
           }
           list qualified-next-hop {
             key name;
             ordered-by user;
             description "Next hop with qualifiers";
             uses qualified_nh_obj;
           }
           leaf metric {
             description "Metric value";
             type union {
               type string {
                 pattern "<.*>|$.*";
               }
               type uint32 {
                 range "1 .. 255";
               }
             }
           }
           leaf preference {
             description "Preference value";
             type union {
               type uint32;
               type string {
                 pattern "<.*>|$.*";
               }
             }
           }
           leaf tag {
             description "Tag string";
             type union {
               type uint32;
               type string {
                 pattern "<.*>|$.*";
               }
             }
           }
           leaf tag2 {
             description "Tag2 string";
             type union {
               type uint32;
               type string {
                 pattern "<.*>|$.*";
               }
             }
           }
         }
       }
       container access-internal {
         description "Access-internal routes";
         uses apply-advanced;
         list route {
           key name;
           ordered-by user;
           description "Access-internal route";
           leaf name {
             description "IP address and optional prefix length of destination";
             type jt:ipprefix;
           }
           uses apply-advanced;
           leaf-list next-hop {
             ordered-by user;
             description "Next hop to destination";
             type union {
               type jt:ipaddr-or-interface;
               type string {
                 pattern "<.*>|$.*";
               }
             }
           }
           list qualified-next-hop {
             key name;
             ordered-by user;
             description "Next hop with qualifiers";
             uses qualified_nh_obj;
           }
         }
       }
       container bgp-static {
         description "Routes for BGP static advertisements";
         uses apply-advanced;
         list route {
           key name;
           ordered-by user;
           description "BGP-static route";
           leaf name {
             description "IP address and optional prefix length of destination";
             type jt:ipprefix;
           }
           uses apply-advanced;
           container metric {
             description "Metric value";
             presence "enable metric";
             uses rib_static_metric_type;
           }
           container metric2 {
             description "Metric value 2";
             presence "enable metric2";
             uses rib_static_metric_type;
           }
           container metric3 {
             description "Metric value 3";
             presence "enable metric3";
             uses rib_static_metric_type;
           }
           container metric4 {
             description "Metric value 4";
             presence "enable metric4";
             uses rib_static_metric_type;
           }
           container tag {
             description "Tag string";
             presence "enable tag";
             uses rib_static_metric_type;
           }
           container tag2 {
             description "Tag string 2";
             presence "enable tag2";
             uses rib_static_metric_type;
           }
           container preference {
             description "Preference value";
             presence "enable preference";
             uses rib_static_metric_type;
           }
           container preference2 {
             description "Preference value 2";
             presence "enable preference2";
             uses rib_static_metric_type;
           }
           container color {
             description "Color (preference) value";
             presence "enable color";
             uses rib_static_metric_type;
           }
           container color2 {
             description "Color (preference) value 2";
             presence "enable color2";
             uses rib_static_metric_type;
           }
           leaf-list community {
             ordered-by user;
             description "BGP community identifier";
             type jt:community;
           }
           container as-path {
             description "Autonomous system path";
             uses apply-advanced;
             leaf path {
               description "Autonomous system path";
               type string;
             }
             leaf origin {
               type enumeration {
                 enum "igp" {
                   description "Path originated in the local IGP";
                 }
                 enum "egp" {
                   description "Path originated in another AS";
                 }
                 enum "incomplete" {
                   description "Path was learned by some other means";
                 }
               }
             }
             leaf atomic-aggregate {
               description "Add ATOMIC_AGGREGATE path attribute to route";
               type empty;
             }
             container aggregator {
               presence "enable aggregator";
               description "Add AGGREGATOR path attribute to route";
             }
             leaf as-number {
               description " Autonomous system number in plain number or 'higher 16bits'.'Lower 16 bits' (asdot notation) format";
               type string {
               }
             }
             leaf address {
               description "Address of BGP system that formed the route";
               type jt:ipv4addr;
             }
           }
         }
       }
       container flow {
         description "Locally defined flow routing information";
         uses apply-advanced;
         container validation {
           description "Flow route validation options";
           presence "enable validation";
           uses flow-validation;
         }
         list route {
           key name;
           ordered-by user;
           description "Flow route";
           uses flow-route-inet6;
         }
         container interface-group {
           description "Interface-group for applying flow-spec filter";
           uses flow-interface-group;
         }
         leaf discard-action-for-unresolved-redir-addr {
           description "For action redirect IP if redirect address is unresolved install discard action filter";
           type empty;
         }
       }
       container label {
         presence "enable label";
         description "Label processing";
         uses apply-advanced;
         leaf-list allocation {
           ordered-by user;
           description "Label allocation policy";
           type jt:policy-algebra;
         }
         leaf-list substitution {
           ordered-by user;
           description "Label substitution policy";
           type jt:policy-algebra;
         }
       }
     }
     container static {
       description "Static routes";
       uses apply-advanced;
       list route {
         key name;
         ordered-by user;
         description "Static route";
         leaf name {
           type jt:ipprefix;
         }
         uses apply-advanced;
         choice next_hop {
           case case_1 {
             leaf-list next-hop {
               ordered-by user;
               description "Next hop to destination";
               type union {
                 type jt:ipaddr-or-interface;
                 type string {
                   pattern "<.*>|$.*";
                 }
               }
             }
           }
           case case_2 {
             leaf reject {
               description "Drop packets to destination; send ICMP unreachables";
               type empty;
             }
           }
           case case_3 {
             leaf discard {
               description "Drop packets to destination; send no ICMP unreachables";
               type empty;
             }
           }
           case case_4 {
             leaf receive {
               description "Install a receive route for the destination";
               type empty;
             }
           }
           case case_5 {
             leaf next-table {
               description "Next hop to another table";
               type string {
               }
             }
           }
         }
         list qualified-next-hop {
           key name;
           ordered-by user;
           description "Next hop with qualifiers";
           uses qualified_nh_obj;
         }
         leaf backup-pe-group {
           description "Multicast source redundancy group";
           type string;
         }
         container bfd-liveness-detection {
           description "Bidirectional Forwarding Detection (BFD) options";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
           container authentication {
             description "Authentication options";
             uses apply-advanced;
             leaf key-chain {
               description "Key chain name";
               type string;
             }
             leaf algorithm {
               description "Algorithm name";
               type enumeration {
                 enum "simple-password" {
                   description "Simple password";
                 }
                 enum "keyed-md5" {
                   description "Keyed message Digest 5";
                 }
                 enum "meticulous-keyed-md5" {
                   description "Meticulous keyed message Digest 5";
                 }
                 enum "keyed-sha-1" {
                   description "Keyed secure hash algorithm (SHA1) ";
                 }
                 enum "meticulous-keyed-sha-1" {
                   description "Meticulous keyed secure hash algorithm (SHA1) ";
                 }
               }
             }
             leaf loose-check {
               description "Verify authentication only if authentication is negotiated";
               type empty;
             }
           }
           leaf neighbor {
             description "BFD neighbor address";
             type jt:ipaddr;
           }
           leaf local-address {
             description "BFD local address (for multihop only)";
             type jt:ipaddr;
           }
           leaf holddown-interval {
             description "Time to hold the session-UP notification to the client";
             units "milliseconds";
             type union {
               type string {
                 pattern "<.*>|$.*";
               }
               type uint32 {
                 range "0 .. 255000";
               }
             }
           }
           leaf minimum-receive-ttl {
             description "Minimum receive TTL below which to drop";
             type union {
               type string {
                 pattern "<.*>|$.*";
               }
               type uint8 {
                 range "1 .. 255";
               }
             }
           }
         }
         choice retain-choice {
           leaf retain {
             description "Always keep route in forwarding table";
             type empty;
           }
           leaf no-retain {
             description "Don't always keep route in forwarding table";
             type empty;
           }
         }
         choice install-choice {
           leaf install {
             description "Install route into forwarding table";
             type empty;
           }
           leaf no-install {
             description "Don't install route into forwarding table";
             type empty;
           }
         }
         choice readvertise-choice {
           leaf readvertise {
             description "Mark route as eligible to be readvertised";
             type empty;
           }
           leaf no-readvertise {
             description "Don't mark route as eligible to be readvertised";
             type empty;
           }
         }
         choice resolve-choice {
           leaf resolve {
             description "Allow resolution of indirectly connected next hops";
             type empty;
           }
           leaf no-resolve {
             description "Don't allow resolution of indirectly connected next hops";
             type empty;
           }
         }
         choice longest-match-choice {
           leaf longest-match {
             description "Always use longest prefix match to resolve next hops";
             type empty;
           }
           leaf no-longest-match {
             description "Don't always use longest prefix match to resolve next hops";
             type empty;
           }
         }
         choice passive_flag {
           case case_1 {
             leaf active {
               description "Remove inactive route from forwarding table";
               type empty;
             }
           }
           case case_2 {
             leaf passive {
               description "Retain inactive route in forwarding table";
               type empty;
             }
           }
         }
         container metric {
           description "Metric value";
           presence "enable metric";
           uses rib_static_metric_type;
         }
         container metric2 {
           description "Metric value 2";
           presence "enable metric2";
           uses rib_static_metric_type;
         }
         container metric3 {
           description "Metric value 3";
           presence "enable metric3";
           uses rib_static_metric_type;
         }
         container metric4 {
           description "Metric value 4";
           presence "enable metric4";
           uses rib_static_metric_type;
         }
         container tag {
           description "Tag string";
           presence "enable tag";
           uses rib_static_metric_type;
         }
         container tag2 {
           description "Tag string 2";
           presence "enable tag2";
           uses rib_static_metric_type;
         }
         container preference {
           description "Preference value";
           presence "enable preference";
           uses rib_static_metric_type;
         }
         container preference2 {
           description "Preference value 2";
           presence "enable preference2";
           uses rib_static_metric_type;
         }
         container color {
           description "Color (preference) value";
           presence "enable color";
           uses rib_static_metric_type;
         }
         container color2 {
           description "Color (preference) value 2";
           presence "enable color2";
           uses rib_static_metric_type;
         }
         leaf-list community {
           ordered-by user;
           description "BGP community identifier";
           type jt:community;
         }
         container as-path {
           description "Autonomous system path";
           uses apply-advanced;
           leaf path {
             description "Autonomous system path";
             type string;
           }
           leaf origin {
             type enumeration {
               enum "igp" {
                 description "Path originated in the local IGP";
               }
               enum "egp" {
                 description "Path originated in another AS";
               }
               enum "incomplete" {
                 description "Path was learned by some other means";
               }
             }
           }
           leaf atomic-aggregate {
             description "Add ATOMIC_AGGREGATE path attribute to route";
             type empty;
           }
           container aggregator {
             presence "enable aggregator";
             description "Add AGGREGATOR path attribute to route";
           }
           leaf as-number {
             description " Autonomous system number in plain number or 'higher 16bits'.'Lower 16 bits' (asdot notation) format";
             type string {
             }
           }
           leaf address {
             description "Address of BGP system that formed the route";
             type jt:ipv4addr;
           }
         }
         list lsp-next-hop {
           key name;
           ordered-by user;
           description "LSP next hop";
           uses lsp_nh_obj;
         }
         list p2mp-lsp-next-hop {
           key name;
           ordered-by user;
           description "Point-to-multipoint LSP next hop";
           max-elements 1;
           uses lsp_nh_obj;
         }
         container p2mp-ldp-next-hop {
           description "Point-to-multipoint LDP LSP next hop";
           uses p2mp_ldp_lsp_nh_obj;
         }
         list static-lsp-next-hop {
           key name;
           ordered-by user;
           description "Static LSP next hop";
           uses lsp_nh_obj;
         }
       }
       leaf rib-group {
         description "Routing table group";
         type string;
       }
       container defaults {
         description "Global route options";
         uses apply-advanced;
         choice retain-choice {
           leaf retain {
             description "Always keep route in forwarding table";
             type empty;
           }
           leaf no-retain {
             description "Don't always keep route in forwarding table";
             type empty;
           }
         }
         choice install-choice {
           leaf install {
             description "Install route into forwarding table";
             type empty;
           }
           leaf no-install {
             description "Don't install route into forwarding table";
             type empty;
           }
         }
         choice readvertise-choice {
           leaf readvertise {
             description "Mark route as eligible to be readvertised";
             type empty;
           }
           leaf no-readvertise {
             description "Don't mark route as eligible to be readvertised";
             type empty;
           }
         }
         choice resolve-choice {
           leaf resolve {
             description "Allow resolution of indirectly connected next hops";
             type empty;
           }
           leaf no-resolve {
             description "Don't allow resolution of indirectly connected next hops";
             type empty;
           }
         }
         choice longest-match-choice {
           leaf longest-match {
             description "Always use longest prefix match to resolve next hops";
             type empty;
           }
           leaf no-longest-match {
             description "Don't always use longest prefix match to resolve next hops";
             type empty;
           }
         }
         choice passive_flag {
           case case_1 {
             leaf active {
               description "Remove inactive route from forwarding table";
               type empty;
             }
           }
           case case_2 {
             leaf passive {
               description "Retain inactive route in forwarding table";
               type empty;
             }
           }
         }
         container metric {
           description "Metric value";
           presence "enable metric";
           uses rib_static_metric_type;
         }
         container metric2 {
           description "Metric value 2";
           presence "enable metric2";
           uses rib_static_metric_type;
         }
         container metric3 {
           description "Metric value 3";
           presence "enable metric3";
           uses rib_static_metric_type;
         }
         container metric4 {
           description "Metric value 4";
           presence "enable metric4";
           uses rib_static_metric_type;
         }
         container tag {
           description "Tag string";
           presence "enable tag";
           uses rib_static_metric_type;
         }
         container tag2 {
           description "Tag string 2";
           presence "enable tag2";
           uses rib_static_metric_type;
         }
         container preference {
           description "Preference value";
           presence "enable preference";
           uses rib_static_metric_type;
         }
         container preference2 {
           description "Preference value 2";
           presence "enable preference2";
           uses rib_static_metric_type;
         }
         container color {
           description "Color (preference) value";
           presence "enable color";
           uses rib_static_metric_type;
         }
         container color2 {
           description "Color (preference) value 2";
           presence "enable color2";
           uses rib_static_metric_type;
         }
         leaf-list community {
           ordered-by user;
           description "BGP community identifier";
           type jt:community;
         }
         container as-path {
           description "Autonomous system path";
           uses apply-advanced;
           leaf path {
             description "Autonomous system path";
             type string;
           }
           leaf origin {
             type enumeration {
               enum "igp" {
                 description "Path originated in the local IGP";
               }
               enum "egp" {
                 description "Path originated in another AS";
               }
               enum "incomplete" {
                 description "Path was learned by some other means";
               }
             }
           }
           leaf atomic-aggregate {
             description "Add ATOMIC_AGGREGATE path attribute to route";
             type empty;
           }
           container aggregator {
             presence "enable aggregator";
             description "Add AGGREGATOR path attribute to route";
           }
           leaf as-number {
             description " Autonomous system number in plain number or 'higher 16bits'.'Lower 16 bits' (asdot notation) format";
             type string {
             }
           }
           leaf address {
             description "Address of BGP system that formed the route";
             type jt:ipv4addr;
           }
         }
       }
       container static-route {
         description "Static route Status";
         leaf bfd-admin-down {
           description "Static route State on BFD ADMIN DOWN";
           type enumeration {
             enum "active" {
               description "Static route will be inactive on bfd-admin-down";
             }
             enum "passive" {
               description "Static route will remain active on bfd-admin-down";
             }
           }
         }
       }
       list route-target-filter {
         key name;
         ordered-by user;
         description "Route-target-filter route";
         leaf name {
           type string {
             length "1 .. 47";
           }
         }
         uses apply-advanced;
         leaf-list neighbor {
           ordered-by user;
           description "BGP peers for filter";
           type jt:ipaddr-scoped;
         }
         leaf-list group {
           ordered-by user;
           description "BGP groups for filter";
           type string;
         }
         leaf local {
           description "Locally originated filter";
           type empty;
         }
       }
     }
     container label {
       presence "enable label";
       description "Label processing";
       uses apply-advanced;
       leaf-list allocation {
         ordered-by user;
         description "Label allocation policy";
         type jt:policy-algebra;
       }
       leaf-list substitution {
         ordered-by user;
         description "Label substitution policy";
         type jt:policy-algebra;
       }
     }
     container access {
       description "Access routes";
       uses apply-advanced;
       list route {
         key name;
         ordered-by user;
         description "Access route";
         leaf name {
           description "IP address of destination";
           type jt:ipprefix;
         }
         uses apply-advanced;
         leaf-list next-hop {
           ordered-by user;
           description "Next hop to destination";
           type union {
             type jt:ipaddr-or-interface;
             type string {
               pattern "<.*>|$.*";
             }
           }
         }
         list qualified-next-hop {
           key name;
           ordered-by user;
           description "Next hop with qualifiers";
           uses qualified_nh_obj;
         }
         leaf metric {
           description "Metric value";
           type union {
             type string {
               pattern "<.*>|$.*";
             }
             type uint32 {
               range "1 .. 255";
             }
           }
         }
         leaf preference {
           description "Preference value";
           type union {
             type uint32;
             type string {
               pattern "<.*>|$.*";
             }
           }
         }
         leaf tag {
           description "Tag string";
           type union {
             type uint32;
             type string {
               pattern "<.*>|$.*";
             }
           }
         }
         leaf tag2 {
           description "Tag2 string";
           type union {
             type uint32;
             type string {
               pattern "<.*>|$.*";
             }
           }
         }
       }
     }
     container access-internal {
       description "Access-internal routes";
       uses apply-advanced;
       list route {
         key name;
         ordered-by user;
         description "Access-internal route";
         leaf name {
           description "IP address and optional prefix length of destination";
           type jt:ipprefix;
         }
         uses apply-advanced;
         leaf-list next-hop {
           ordered-by user;
           description "Next hop to destination";
           type union {
             type jt:ipaddr-or-interface;
             type string {
               pattern "<.*>|$.*";
             }
           }
         }
         list qualified-next-hop {
           key name;
           ordered-by user;
           description "Next hop with qualifiers";
           uses qualified_nh_obj;
         }
       }
     }
     container options {
       description "Miscellaneous options";
       uses apply-advanced;
       leaf no-send {
         description "Listen only; do not send protocol packets";
         status deprecated;
         type empty;
       }
       leaf no-resolve {
         description "Do not use DNS name resolution";
         status deprecated;
         type empty;
       }
       container syslog {
         description "Set system logging level";
         uses apply-advanced;
         container level {
           description "Logging level";
           leaf emergency {
             description "Emergency level";
             type empty;
           }
           leaf alert {
             description "Alert level";
             type empty;
           }
           leaf critical {
             description "Critical level";
             type empty;
           }
           leaf error {
             description "Error level";
             type empty;
           }
           leaf warning {
             description "Warning level";
             type empty;
           }
           leaf notice {
             description "Notice level";
             type empty;
           }
           leaf info {
             description "Informational level";
             type empty;
           }
           leaf debug {
             description "Debugging level";
             type empty;
           }
         }
         leaf upto {
           description "Log up to a particular logging level";
           type enumeration {
             enum "emergency" {
               description "Emergency level";
             }
             enum "alert" {
               description "Alert level";
             }
             enum "critical" {
               description "Critical level";
             }
             enum "error" {
               description "Error level";
             }
             enum "warning" {
               description "Warning level";
             }
             enum "notice" {
               description "Notice level";
             }
             enum "info" {
               description "Informational level";
             }
             enum "debug" {
               description "Debugging level";
             }
           }
         }
       }
       leaf mark {
         description "Periodically mark the trace file";
         units "seconds";
         type union {
           type int32;
           type string {
             pattern "<.*>|$.*";
           }
         }
       }
     }
     container resolution {
       presence "enable resolution";
       description "Route next-hop resolution options";
       uses apply-advanced;
       leaf-list tracefilter {
         ordered-by user;
         description "Filter policy";
         type jt:policy-algebra;
       }
       container traceoptions {
         description "Trace options";
         uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "event" {
                 description "Event processing";
               }
               enum "flash" {
                 description "Flash processing";
               }
               enum "kernel" {
                 description "Kernel communication";
               }
               enum "indirect" {
                 description "Indirect next-hop addition, change, or deletion";
               }
               enum "task" {
                 description "Task or job processing";
               }
               enum "igp-frr" {
                 description "IGP triggered FRR events";
               }
               enum "igp-frr-extensive" {
                 description "IGP triggered FRR Extensive events";
               }
               enum "tunnel" {
                 description "Resolver dynamic tunnel events";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       choice preserve-nexthop-hierarchy-choice {
         leaf preserve-nexthop-hierarchy {
           description "Preserve nexthop hierarchy when installing nexthop to forwarding plane";
           type empty;
         }
         leaf no-preserve-nexthop-hierarchy {
           description "Don't preserve nexthop hierarchy when installing nexthop to forwarding plane";
           type empty;
         }
       }
       list rib {
         key name;
         ordered-by user;
         description "Routing table resolution options";
         leaf name {
           description "Routing table name";
           type string;
         }
         uses apply-advanced;
         leaf-list resolution-family {
           ordered-by user;
           description "Family of resultion tree";
           type string;
         }
         leaf-list resolution-ribs {
           ordered-by user;
           description "Routing tables to use for default routing table family resolution";
           type string;
         }
         leaf-list inet-resolution-ribs {
           ordered-by user;
           description "Routing tables to use for ipv4 family protocol-next-hop resolution";
           type string;
         }
         leaf-list inet6-resolution-ribs {
           ordered-by user;
           description "Routing tables to use for ipv6 family protocol-next-hop resolution";
           type string;
         }
         leaf-list iso-resolution-ribs {
           ordered-by user;
           description "Routing tables to use for iso family protocol-next-hop resolution";
           type string;
         }
         leaf-list import {
           ordered-by user;
           description "Import policy";
           type jt:policy-algebra;
         }
         leaf-list inet-import {
           ordered-by user;
           description "Import policy for IPV4 family resolution tree";
           type jt:policy-algebra;
         }
         leaf-list inet6-import {
           ordered-by user;
           description "Import policy for IPV6 family resolution tree";
           type jt:policy-algebra;
         }
         leaf-list iso-import {
           ordered-by user;
           description "Import policy for ISO family resolution tree";
           type jt:policy-algebra;
         }
         leaf-list inetcolor-import {
           ordered-by user;
           description "Import policy for INETCOLOR family resolution tree";
           type jt:policy-algebra;
         }
         leaf-list inet6color-import {
           ordered-by user;
           description "Import policy for INET6COLOR family resolution tree";
           type jt:policy-algebra;
         }
       }
       choice prefer-recursive-primary-path-choice {
         leaf prefer-recursive-primary-path {
           description "Prefer primary path to resolve nexthop during recursive-resolution";
           type empty;
         }
         leaf no-prefer-recursive-primary-path {
           description "Don't prefer primary path to resolve nexthop during recursive-resolution";
           type empty;
         }
       }
     }
     container interface-routes {
       description "Define routing table groups for interface routes";
       uses apply-advanced;
       container rib-group {
         description "Routing table group";
         uses rib_group_type;
       }
       list family {
         key name;
         ordered-by user;
         description "Address family";
         leaf name {
           type enumeration {
             enum "inet" {
               description "IPv4 family";
             }
             enum "inet6" {
               description "IPv6 family";
             }
           }
         }
         uses apply-advanced;
         leaf-list import {
           ordered-by user;
           description "Import policy";
           type jt:policy-algebra;
         }
         container export {
           description "Control exportability of local routes";
           uses apply-advanced;
           leaf point-to-point {
             description "Make point-to-point routes exportable";
             type empty;
           }
           leaf lan {
             description "Make LAN routes exportable";
             type empty;
           }
         }
       }
     }
     leaf loopback-strict-disable {
       description "Completely disable lo0 host prefix when in admin-down state";
       type empty;
     }
     container traceoptions {
       description "Global routing protocol trace options";
       uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "parse" {
               description "Trace configuration parsing";
             }
             enum "regex-parse" {
               description "Trace regular-expression parsing";
             }
             enum "config-internal" {
               description "Trace configuration internals";
             }
             enum "nsr-synchronization" {
               description "Trace nonstop routing synchronization events";
             }
             enum "condition-manager" {
               description "Trace condition manager events";
             }
             enum "graceful-restart" {
               description "Trace Graceful Restart events";
             }
             enum "session" {
               description "Trace Session ID allocations/deallocations";
             }
             enum "hfrr-fsm" {
               description "Host FRR FSM events tracing";
             }
             enum "hfrr-route" {
               description "Host FRR route events tracing";
             }
             enum "statistics-id-group" {
               description "Trace Statistics ID Group operations";
             }
             enum "route-record" {
               description "Trace route-record server-side events";
             }
             enum "jvision-lsp" {
               description "Trace Jvision events and errors";
             }
             enum "dyn-nh-template" {
               description "Dynamic nexthops template events tracing";
             }
             enum "read-route" {
               description "Read route events tracing";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf disable {
           description "Disable this trace flag";
           type empty;
         }
       }
     }
     container topologies {
       description "Define routing topologies";
       uses apply-advanced;
       list family {
         key name;
         ordered-by user;
         description "Address family";
         leaf name {
           type enumeration {
             enum "inet" {
               description "IPv4 family";
             }
             enum "inet6" {
               description "IPv6 family";
             }
           }
         }
         uses apply-advanced;
         list topology {
           key name;
           ordered-by user;
           description "Topology information";
           leaf name {
             description "Topology name";
             type string {
             }
           }
           uses apply-advanced;
         }
       }
     }
     leaf router-id {
       description "Router identifier";
       type jt:ipv4addr;
     }
     container autonomous-system {
       description "Autonomous system number";
       leaf as-number {
         description " Autonomous system number in plain number or 'higher 16bits'.'Lower 16 bits' (asdot notation) format";
         type string {
         }
       }
       leaf loops {
         description "Maximum number of times this AS can be in an AS path";
         type union {
           type string {
             pattern "<.*>|$.*";
           }
           type int32 {
             range "1 .. 10";
           }
         }
       }
       leaf asdot-notation {
         description "Use AS-Dot notation to display true 4 byte AS numbers";
         type empty;
       }
       container independent-domain {
         presence "enable independent-domain";
         description "Independent autonomous-system domain from master instance";
         container no-attrset {
           presence "enable no-attrset";
           description "Do not tunnel ce bgp attributes across provider network";
         }
       }
     }
     container confederation {
       description "Confederation autonomous system number";
       leaf confederation-as {
         description " Autonomous system number in plain number or 'higher 16bits'.'Lower 16 bits' (asdot notation) format";
         type string {
         }
       }
       leaf-list members {
         ordered-by user;
         description " Autonomous system number in plain number or 'higher 16bits'.'Lower 16 bits' (asdot notation) format";
         type string;
       }
     }
     leaf ipv6-router-id {
       description "IPv6 router identifier";
       type string;
     }
     container graceful-restart {
       presence "enable graceful-restart";
       description "Graceful or hitless routing restart options";
       uses apply-advanced;
       choice enable-disable {
         case case_1 {
           leaf disable {
             description "Disable graceful restart";
             type empty;
           }
         }
       }
       leaf restart-duration {
         description "Maximum time for which router is in graceful restart";
         type union {
           type string {
             pattern "<.*>|$.*";
           }
           type uint32 {
             range "120 .. 10000";
           }
         }
       }
     }
     container flow {
       description "Locally defined flow routing information";
       uses apply-advanced;
       leaf firewall-install-disable {
         description "Disable installing flowspec firewall filters in dfwd ";
         type empty;
       }
       container validation {
         description "Flow route validation options";
         presence "enable validation";
         uses flow-validation;
       }
       container interface-group {
         description "Interface-group for applying flow-spec filter";
         uses flow-interface-group;
       }
       list route {
         key name;
         ordered-by user;
         description "Flow route";
         uses flow-route-inet;
       }
       leaf term-order {
         description "Term evaluation order for flow routes";
         type enumeration {
           enum "legacy" {
             description "Legacy term order (default)";
           }
           enum "standard" {
             description "RFC compliant term order";
           }
         }
       }
       leaf discard-action-for-unresolved-redir-addr {
         description "For action redirect IP if redirect address is unresolved install discard action filter";
         type empty;
       }
     }
     leaf no-soft-core {
       description "Disable soft assert to generate core and just log the event";
       type empty;
     }
     leaf med-igp-update-interval {
       description "Delay (in minutes) in updating MED IGP for bgp groups with 'delay-med-update' ";
       type union {
         type string {
           pattern "<.*>|$.*";
         }
         type uint32 {
           range "10 .. 600";
         }
       }
     }
     container bmp {
       presence "enable bmp";
       description "BGP Monitoring Protocol (BMP) configuration";
       uses apply-advanced;
       leaf authentication-key {
         description "MD5 authentication key";
         type string {
           length "1 .. 126";
         }
       }
       leaf authentication-algorithm {
         description "Authentication algorithm name";
         default "hmac-sha-1-96";
         type enumeration {
           enum "md5" {
             description "Message Digest 5";
           }
           enum "hmac-sha-1-96" {
             description "Hash-based Message Authentication Code (SHA1) (96 bits)";
           }
           enum "aes-128-cmac-96" {
             description "Cipher-based Message Authentication Code (AES128) (96 bits)";
           }
           enum "ao" {
             description "TCP Authentication Option";
           }
         }
       }
       leaf tcpao-handling-with-digest-mismatch {
         description "Drop or continue without TCP-AO with digest mismatch with TCP-AO";
         type enumeration {
           enum "drop-if-no-tcpao" {
             description "Drop the connection if Digest mismatched";
           }
           enum "allow-without-tcpao" {
             description "Allow the connection establishment without TCP-AO";
           }
         }
       }
       leaf authentication-key-chain {
         description "Key chain name";
         type string {
           length "1 .. 128";
         }
       }
       container hold-down {
         presence "enable hold-down";
         leaf hold-down-time {
           description "Prevent re-establishment for this time";
           units "seconds";
           type union {
             type string {
               pattern "<.*>|$.*";
             }
             type uint32 {
               range "30 .. 65535";
             }
           }
         }
         leaf flaps {
           description "Number of flaps before damping";
           type union {
             type string {
               pattern "<.*>|$.*";
             }
             type uint32 {
               range "2 .. 10";
             }
           }
         }
         leaf period {
           description "Time period for flaps";
           units "seconds";
           type union {
             type string {
               pattern "<.*>|$.*";
             }
             type uint32 {
               range "30 .. 65535";
             }
           }
         }
       }
       leaf initiation-message {
         description "User string sent with the initiation message";
         type string {
           length "1 .. 255";
         }
       }
       leaf local-address {
         description "Address of local end of BMP session";
         type jt:ipaddr;
       }
       leaf local-port {
         description "Local port for listening";
         type union {
           type string {
             pattern "<.*>|$.*";
           }
           type uint32 {
             range "1024 .. 65535";
           }
         }
       }
       leaf connection-mode {
         description "Specify active or passive";
         type enumeration {
           enum "active" {
             description "Initiate the connection";
           }
           enum "passive" {
             description "Listen for the connection";
           }
         }
       }
       leaf priority {
         description "Relative dispatch priority";
         type enumeration {
           enum "low" {
             description "Lowest priority";
           }
           enum "medium" {
             description "Medium priority";
           }
           enum "high" {
             description "Highest priority";
           }
         }
       }
       leaf monitor {
         description "Enable/Disable monitoring";
         type enumeration {
           enum "enable" {
             description "Enable monitoring of BGP peer(s)";
           }
           enum "disable" {
             description "Disable monitoring of BGP peer(s)";
           }
         }
       }
       container route-monitoring {
         description "Control route monitoring settings";
         uses apply-advanced;
         leaf none {
           description "Do not send route monitoring messages";
           type empty;
         }
         leaf loc-rib {
           description "Send local-rib route monitoring messages";
           type empty;
         }
         container pre-policy {
           presence "enable pre-policy";
           description "Send pre policy route monitoring messages";
           leaf exclude-non-feasible {
             description "Exclude looped routes, etc";
             type empty;
           }
         }
         container post-policy {
           presence "enable post-policy";
           description "Send post policy route monitoring messages";
           leaf exclude-non-eligible {
             description "Exclude unresolved routes, etc.";
             type empty;
           }
         }
         container rib-out {
           presence "enable rib-out";
           description "Send adj-ribs-out route monitoring messages";
           leaf pre-policy {
             description "Send pre-policy adj-ribs-out route monitoring messages";
             type empty;
           }
           leaf post-policy {
             description "Send post-policy adj-ribs-out route monitoring messages";
             type empty;
           }
         }
       }
       leaf max-loc-rib-buffer-count {
         description "Max number of loc-rib outstanding buffers before blocking";
         type union {
           type string {
             pattern "<.*>|$.*";
           }
           type uint32 {
             range "1 .. 50";
           }
         }
       }
       leaf station-address {
         description "Address/name of monitoring station";
         type jt:ipaddr;
       }
       leaf routing-instance {
         description "Routing-instance through which BMP station is reachable";
         type string;
       }
       leaf station-port {
         description "Port of monitoring station";
         type union {
           type string {
             pattern "<.*>|$.*";
           }
           type uint32 {
             range "1 .. 65535";
           }
         }
       }
       leaf statistics-timeout {
         description "Statistics message timer, 15-65535, or 0 for no messages";
         units "seconds";
         type union {
           type string {
             pattern "<.*>|$.*";
           }
           type uint32 {
             range "0 .. 65535";
           }
         }
       }
       container traceoptions {
         description "Trace options";
         uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Trace flag information";
           leaf name {
             type enumeration {
               enum "packets" {
                 description "Trace all messages";
               }
               enum "up" {
                 description "Trace up messages";
               }
               enum "down" {
                 description "Trace down messages";
               }
               enum "statistics" {
                 description "Trace statistics messages";
               }
               enum "route-monitoring" {
                 description "Trace route monitoring messages";
               }
               enum "event" {
                 description "Trace major events, station establishment, errors, events";
               }
               enum "error" {
                 description "Trace error conditions";
               }
               enum "write" {
                 description "Trace writing of messages";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       list station {
         key name;
         description "Define a BMP station";
         leaf name {
           description "Station name";
           type string;
         }
         uses apply-advanced;
         leaf authentication-key {
           description "MD5 authentication key";
           type string {
             length "1 .. 126";
           }
         }
         leaf authentication-algorithm {
           description "Authentication algorithm name";
           type enumeration {
             enum "md5" {
               description "Message Digest 5";
             }
             enum "hmac-sha-1-96" {
               description "Hash-based Message Authentication Code (SHA1) (96 bits)";
             }
             enum "aes-128-cmac-96" {
               description "Cipher-based Message Authentication Code (AES128) (96 bits)";
             }
             enum "ao" {
               description "TCP Authentication Option";
             }
           }
         }
         leaf tcpao-handling-with-digest-mismatch {
           description "Drop or continue without TCP-AO with digest mismatch with TCP-AO";
           type enumeration {
             enum "drop-if-no-tcpao" {
               description "Drop the connection if Digest mismatched";
             }
             enum "allow-without-tcpao" {
               description "Allow the connection establishment without TCP-AO";
             }
           }
         }
         leaf authentication-key-chain {
           description "Key chain name";
           type string {
             length "1 .. 128";
           }
         }
         container hold-down {
           presence "enable hold-down";
           leaf hold-down-time {
             description "Prevent re-establishment for this time";
             units "seconds";
             type union {
               type string {
                 pattern "<.*>|$.*";
               }
               type uint32 {
                 range "30 .. 65535";
               }
             }
           }
           leaf flaps {
             description "Number of flaps before damping";
             type union {
               type string {
                 pattern "<.*>|$.*";
               }
               type uint32 {
                 range "2 .. 10";
               }
             }
           }
           leaf period {
             description "Time period for flaps";
             units "seconds";
             type union {
               type string {
                 pattern "<.*>|$.*";
               }
               type uint32 {
                 range "30 .. 65535";
               }
             }
           }
         }
         leaf initiation-message {
           description "User string sent with the initiation message";
           type string {
             length "1 .. 255";
           }
         }
         leaf local-address {
           description "Address of local end of BMP session";
           type jt:ipaddr;
         }
         leaf local-port {
           description "Local port for listening";
           type union {
             type string {
               pattern "<.*>|$.*";
             }
             type uint32 {
               range "1024 .. 65535";
             }
           }
         }
         leaf connection-mode {
           description "Specify active or passive";
           type enumeration {
             enum "active" {
               description "Initiate the connection";
             }
             enum "passive" {
               description "Listen for the connection";
             }
           }
         }
         leaf priority {
           description "Relative dispatch priority";
           type enumeration {
             enum "low" {
               description "Lowest priority";
             }
             enum "medium" {
               description "Medium priority";
             }
             enum "high" {
               description "Highest priority";
             }
           }
         }
         leaf monitor {
           description "Enable/Disable monitoring";
           type enumeration {
             enum "enable" {
               description "Enable monitoring of BGP peer(s)";
             }
             enum "disable" {
               description "Disable monitoring of BGP peer(s)";
             }
           }
         }
         container route-monitoring {
           description "Control route monitoring settings";
           uses apply-advanced;
           leaf none {
             description "Do not send route monitoring messages";
             type empty;
           }
           leaf loc-rib {
             description "Send local-rib route monitoring messages";
             type empty;
           }
           container pre-policy {
             presence "enable pre-policy";
             description "Send pre policy route monitoring messages";
             leaf exclude-non-feasible {
               description "Exclude looped routes, etc";
               type empty;
             }
           }
           container post-policy {
             presence "enable post-policy";
             description "Send post policy route monitoring messages";
             leaf exclude-non-eligible {
               description "Exclude unresolved routes, etc.";
               type empty;
             }
           }
           container rib-out {
             presence "enable rib-out";
             description "Send adj-ribs-out route monitoring messages";
             leaf pre-policy {
               description "Send pre-policy adj-ribs-out route monitoring messages";
               type empty;
             }
             leaf post-policy {
               description "Send post-policy adj-ribs-out route monitoring messages";
               type empty;
             }
           }
         }
         leaf max-loc-rib-buffer-count {
           description "Max number of loc-rib outstanding buffers before blocking";
           type union {
             type string {
               pattern "<.*>|$.*";
             }
             type uint32 {
               range "1 .. 50";
             }
           }
         }
         leaf station-address {
           description "Address/name of monitoring station";
           type jt:ipaddr;
         }
         leaf routing-instance {
           description "Routing-instance through which BMP station is reachable";
           type string;
         }
         leaf station-port {
           description "Port of monitoring station";
           type union {
             type string {
               pattern "<.*>|$.*";
             }
             type uint32 {
               range "1 .. 65535";
             }
           }
         }
         leaf statistics-timeout {
           description "Statistics message timer, 15-65535, or 0 for no messages";
           units "seconds";
           type union {
             type string {
               pattern "<.*>|$.*";
             }
             type uint32 {
               range "0 .. 65535";
             }
           }
         }
         container traceoptions {
           description "Trace options";
           uses apply-advanced;
           container file {
             description "Trace file options";
             leaf filename {
               description "Name of file in which to write trace information";
               type string {
                 length "1 .. 1024";
               }
             }
             leaf replace {
               description "Replace trace file rather than appending to it";
               status deprecated;
               type empty;
             }
             leaf size {
               description "Maximum trace file size";
               type string;
             }
             leaf files {
               description "Maximum number of trace files";
               default "10";
               type union {
                 type string {
                   pattern "<.*>|$.*";
                 }
                 type uint32 {
                   range "2 .. 1000";
                 }
               }
             }
             leaf no-stamp {
               description "Do not timestamp trace file";
               status deprecated;
               type empty;
             }
             choice world-readable-choice {
               leaf world-readable {
                 description "Allow any user to read the log file";
                 type empty;
               }
               leaf no-world-readable {
                 description "Don't allow any user to read the log file";
                 type empty;
               }
             }
           }
           list flag {
             key name;
             ordered-by user;
             description "Trace flag information";
             leaf name {
               type enumeration {
                 enum "packets" {
                   description "Trace all messages";
                 }
                 enum "up" {
                   description "Trace up messages";
                 }
                 enum "down" {
                   description "Trace down messages";
                 }
                 enum "statistics" {
                   description "Trace statistics messages";
                 }
                 enum "route-monitoring" {
                   description "Trace route monitoring messages";
                 }
                 enum "event" {
                   description "Trace major events, station establishment, errors, events";
                 }
                 enum "error" {
                   description "Trace error conditions";
                 }
                 enum "write" {
                   description "Trace writing of messages";
                 }
                 enum "route" {
                   description "Trace routing information";
                 }
                 enum "normal" {
                   description "Trace normal events";
                 }
                 enum "general" {
                   description "Trace general events";
                 }
                 enum "state" {
                   description "Trace state transitions";
                 }
                 enum "policy" {
                   description "Trace policy processing";
                 }
                 enum "task" {
                   description "Trace routing protocol task processing";
                 }
                 enum "timer" {
                   description "Trace routing protocol timer processing";
                 }
                 enum "all" {
                   description "Trace everything";
                 }
               }
             }
             leaf send {
               description "Trace transmitted packets";
               type empty;
             }
             leaf receive {
               description "Trace received packets";
               type empty;
             }
             leaf detail {
               description "Trace detailed information";
               type empty;
             }
             leaf disable {
               description "Disable this trace flag";
               type empty;
             }
           }
         }
       }
     }
     leaf bgp-orf-cisco-mode {
       description "Using BGP ORF capability code 130 and Prefix ORF type 128";
       type empty;
     }
     leaf highwatermark-log-interval {
       description "High watermark log interval (default 30 seconds)";
       units "seconds";
       type union {
         type string {
           pattern "<.*>|$.*";
         }
         type uint32 {
           range "5 .. 1200";
         }
       }
     }
     leaf time-averaged-watermark-interval {
       description "For calculating average watermark";
       units "days";
       type union {
         type string {
           pattern "<.*>|$.*";
         }
         type uint32 {
           range "1 .. 15";
         }
       }
     }
     container ppm {
       presence "enable ppm";
       description "Set periodic packet management properties";
       uses apply-advanced;
       leaf delegate-processing {
         description "Enable distribution of PPM sessions";
         status deprecated;
         type empty;
       }
       leaf no-delegate-processing {
         description "Disable PPM sessions distribution";
         type empty;
       }
       leaf inline-processing-enable {
         description "Enable PPM session inline distribution";
         type empty;
       }
       leaf inline-ae-processing-enable {
         description "Enable PPM session inline distribution on AE";
         status deprecated;
         type empty;
       }
       leaf redistribution-timer {
         description "Time to wait after switchover before starting timers";
         type union {
           type string {
             pattern "<.*>|$.*";
           }
           type uint32 {
             range "1 .. 120";
           }
         }
       }
     }
     leaf no-bfd-triggered-local-repair {
       description "Disable bfd triggered local repair";
       type empty;
     }
     container auto-bandwidth {
       presence "enable auto-bandwidth";
       description "Auto bandwidth";
       uses apply-advanced;
       list template {
         key name;
         ordered-by user;
         description "Auto bandwidth template";
         leaf name {
           description "Auto bandwidth template name (Maximum length 64)";
           type string {
             length "1 .. 64";
           }
         }
         uses apply-advanced;
         leaf adjust-interval {
           description "Adjust interval";
           type union {
             type string {
               pattern "<.*>|$.*";
             }
             type uint32 {
               range "30 .. 3600";
             }
           }
         }
         leaf adjust-threshold {
           description "Percentage threshhold";
           type union {
             type string {
               pattern "<.*>|$.*";
             }
             type uint32 {
               range "0 .. 100";
             }
           }
         }
         leaf statistic-collection-interval {
           description "Collection interval";
           type union {
             type string {
               pattern "<.*>|$.*";
             }
             type uint32 {
               range "10 .. 300";
             }
           }
         }
         leaf auto-bandwidth-subscription {
           description "Percentage threshhold for subscription";
           type union {
             type string {
               pattern "<.*>|$.*";
             }
             type uint32 {
               range "0 .. 200";
             }
           }
         }
       }
       container traceoptions {
         description "Trace options for sr stats";
         uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "all" {
                 description "Trace All";
               }
               enum "timer" {
                 description "Trace traffic recv by periodic timer";
               }
               enum "state" {
                 description "Trace state of sensor";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
     }
     leaf enable-sensors {
       description "Enable Sensor for MX/PTX/QFX/EX";
       type empty;
     }
     leaf maximum-ecmp {
       description "Maximum ECMP limit for nexthops";
       type enumeration {
         enum "16" {
           description "Maximum 16 ECMP routes";
         }
         enum "32" {
           description "Maximum 32 ECMP routes";
         }
         enum "64" {
           description "Maximum 64 ECMP routes";
         }
         enum "96" {
           description "Maximum 96 ECMP routes";
         }
         enum "128" {
           description "Maximum 128 ECMP routes";
         }
         enum "160" {
           description "Maximum 160 ECMP routes";
         }
         enum "192" {
           description "Maximum 192 ECMP routes";
         }
         enum "224" {
           description "Maximum 224 ECMP routes";
         }
         enum "256" {
           description "Maximum 256 ECMP routes";
         }
         enum "288" {
           description "Maximum 288 ECMP routes";
         }
         enum "320" {
           description "Maximum 320 ECMP routes";
         }
         enum "352" {
           description "Maximum 352 ECMP routes";
         }
         enum "384" {
           description "Maximum 384 ECMP routes";
         }
         enum "416" {
           description "Maximum 416 ECMP routes";
         }
         enum "448" {
           description "Maximum 448 ECMP routes";
         }
         enum "480" {
           description "Maximum 480 ECMP routes";
         }
         enum "512" {
           description "Maximum 512 ECMP routes";
         }
       }
     }
     list martians {
       key "address choice-ident choice-value";
       ordered-by user;
       description "Invalid routes";
       uses martian_type;
     }
     container aggregate {
       description "Coalesced routes";
       uses rib_aggregate_type;
     }
     container generate {
       description "Route of last resort";
       uses rib_aggregate_type;
     }
     choice maximum-paths-type {
       case case_1 {
         container maximum-routes {
           description "Maximum number of routes";
           status deprecated;
           leaf limit {
             description "Maximum number of routes";
             type union {
               type string {
                 pattern "<.*>|$.*";
               }
               type uint32 {
                 range "1 .. 4294967295";
               }
             }
           }
           choice log_type {
             case case_1 {
               leaf threshold {
                 description "Percentage of limit at which to start generating warnings";
                 type union {
                   type string {
                     pattern "<.*>|$.*";
                   }
                   type uint32 {
                     range "1 .. 100";
                   }
                 }
               }
             }
             case case_2 {
               leaf log-only {
                 description "Generate warning messages only";
                 type empty;
               }
             }
           }
           leaf log-interval {
             description "Minimum interval between log messages";
             units "seconds";
             type union {
               type string {
                 pattern "<.*>|$.*";
               }
               type uint32 {
                 range "5 .. 86400";
               }
             }
           }
         }
       }
       case case_2 {
         container maximum-paths {
           description "Maximum number of paths";
           leaf limit {
             description "Maximum number of paths";
             type union {
               type string {
                 pattern "<.*>|$.*";
               }
               type uint32 {
                 range "1 .. 4294967295";
               }
             }
           }
           choice log_type {
             case case_1 {
               leaf threshold {
                 description "Percentage of limit at which to start generating warnings";
                 type union {
                   type string {
                     pattern "<.*>|$.*";
                   }
                   type uint32 {
                     range "1 .. 100";
                   }
                 }
               }
             }
             case case_2 {
               leaf log-only {
                 description "Generate warning messages only";
                 type empty;
               }
             }
           }
           leaf log-interval {
             description "Minimum interval between log messages";
             units "seconds";
             type union {
               type string {
                 pattern "<.*>|$.*";
               }
               type uint32 {
                 range "5 .. 86400";
               }
             }
           }
         }
       }
     }
     container maximum-prefixes {
       description "Maximum number of prefixes";
       leaf limit {
         description "Maximum number of prefixes";
         type union {
           type string {
             pattern "<.*>|$.*";
           }
           type uint32 {
             range "1 .. 4294967295";
           }
         }
       }
       choice log_type {
         case case_1 {
           leaf threshold {
             description "Percentage of limit at which to start generating warnings";
             type union {
               type string {
                 pattern "<.*>|$.*";
               }
               type uint32 {
                 range "1 .. 100";
               }
             }
           }
         }
         case case_2 {
           leaf log-only {
             description "Generate warning messages only";
             type empty;
           }
         }
       }
       leaf log-interval {
         description "Minimum interval between log messages";
         units "seconds";
         type union {
           type string {
             pattern "<.*>|$.*";
           }
           type uint32 {
             range "5 .. 86400";
           }
         }
       }
     }
     container multipath {
       presence "enable multipath";
       description "Protocol-independent load balancing";
       uses apply-advanced;
       container vpn-unequal-cost {
         presence "enable vpn-unequal-cost";
         description "Include VPN routes with unequal IGP metrics";
         leaf equal-external-internal {
           description "Include external and internal VPN routes";
           type empty;
         }
       }
       leaf as-path-compare {
         description "Compare AS path sequences in addition to AS path length";
         type empty;
       }
       leaf preserve-nexthop-hierarchy {
         description "Force multipath to create List nexthop";
         type empty;
       }
     }
     container policy-multipath {
       description "Policy based multipath";
       uses apply-advanced;
       leaf-list policy {
         ordered-by user;
         description "Import policy to create policy based multipath";
         type jt:policy-algebra;
       }
       container traceoptions {
         description "Trace options";
         uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "route" {
                 description "Policy-multipath route tracing.";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
     }
     container protect {
       description "Protocol-independent protection";
       leaf core {
         description "Protect against unreachability to service-edge router";
         type empty;
       }
     }
     container bgp-static {
       description "Routes for BGP static advertisements";
       uses apply-advanced;
       list route {
         key name;
         ordered-by user;
         description "BGP-static route";
         leaf name {
           description "IP address and optional prefix length of destination";
           type jt:ipprefix;
         }
         uses apply-advanced;
         container metric {
           description "Metric value";
           presence "enable metric";
           uses rib_static_metric_type;
         }
         container metric2 {
           description "Metric value 2";
           presence "enable metric2";
           uses rib_static_metric_type;
         }
         container metric3 {
           description "Metric value 3";
           presence "enable metric3";
           uses rib_static_metric_type;
         }
         container metric4 {
           description "Metric value 4";
           presence "enable metric4";
           uses rib_static_metric_type;
         }
         container tag {
           description "Tag string";
           presence "enable tag";
           uses rib_static_metric_type;
         }
         container tag2 {
           description "Tag string 2";
           presence "enable tag2";
           uses rib_static_metric_type;
         }
         container preference {
           description "Preference value";
           presence "enable preference";
           uses rib_static_metric_type;
         }
         container preference2 {
           description "Preference value 2";
           presence "enable preference2";
           uses rib_static_metric_type;
         }
         container color {
           description "Color (preference) value";
           presence "enable color";
           uses rib_static_metric_type;
         }
         container color2 {
           description "Color (preference) value 2";
           presence "enable color2";
           uses rib_static_metric_type;
         }
         leaf-list community {
           ordered-by user;
           description "BGP community identifier";
           type jt:community;
         }
         container as-path {
           description "Autonomous system path";
           uses apply-advanced;
           leaf path {
             description "Autonomous system path";
             type string;
           }
           leaf origin {
             type enumeration {
               enum "igp" {
                 description "Path originated in the local IGP";
               }
               enum "egp" {
                 description "Path originated in another AS";
               }
               enum "incomplete" {
                 description "Path was learned by some other means";
               }
             }
           }
           leaf atomic-aggregate {
             description "Add ATOMIC_AGGREGATE path attribute to route";
             type empty;
           }
           container aggregator {
             presence "enable aggregator";
             description "Add AGGREGATOR path attribute to route";
           }
           leaf as-number {
             description " Autonomous system number in plain number or 'higher 16bits'.'Lower 16 bits' (asdot notation) format";
             type string {
             }
           }
           leaf address {
             description "Address of BGP system that formed the route";
             type jt:ipv4addr;
           }
         }
       }
     }
     list rib-groups {
       key name;
       ordered-by user;
       description "Group of routing tables";
       uses rpd_rib_group_type;
     }
     leaf route-record {
       description "Enable route recording";
       type empty;
     }
     leaf-list instance-import {
       ordered-by user;
       description "Import policy for instance RIBs";
       type jt:policy-algebra;
     }
     leaf-list instance-export {
       ordered-by user;
       description "Export policy for instance RIBs";
       type jt:policy-algebra;
     }
     container auto-export {
       presence "enable auto-export";
       description "Export routes between routing instances";
       uses apply-advanced;
       choice enable-disable {
         case case_1 {
           leaf disable {
             description "Disable auto-export";
             type empty;
           }
         }
       }
       container traceoptions {
         description "Trace options";
         uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "export" {
                 description "Export processing";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       container family {
         container inet {
           description "IPv4 parameters";
           uses export-af-obj;
         }
         container inet6 {
           description "IPv6 parameters";
           uses export-af-obj;
         }
         container iso {
           description "ISO parameters";
           uses export-af-obj;
         }
       }
     }
     container dynamic-tunnels {
       description "Dynamic tunnel definitions";
       uses apply-advanced;
       list tunnel-attributes {
         key name;
         ordered-by user;
         description "Dynamic tunnel attributes definition";
         leaf name {
           description "Dynamic Tunnel attribute name";
           type string {
           }
         }
         uses apply-advanced;
         leaf dynamic-tunnel-source-prefix {
           description "Tunnel source address";
           type jt:ipaddr;
         }
         leaf dynamic-tunnel-type {
           type enumeration {
             enum "GRE" {
               description "Tunnel type GRE";
             }
             enum "V4oV6" {
               description "Tunnel type is IPV4oIPV6";
             }
             enum "UDP" {
               description "Tunnel type UDP";
             }
             enum "BGP-SIGNAL" {
               description "Tunnel type BGP-SIGNAL";
             }
           }
         }
         leaf dynamic-tunnel-mtu {
           description "Dynamic Tunnel MTU value";
           type union {
             type string {
               pattern "<.*>|$.*";
             }
             type uint32 {
               range "296 .. 9232";
             }
           }
         }
         leaf dynamic-tunnel-anchor-pfe {
           description "Dynamic Tunnel anchor PFE name of format pfe-x/y/z";
           type string {
           }
         }
         leaf dynamic-tunnel-anti-spoof {
           type enumeration {
             enum "on" {
               description "Enable antispoofing check. Default is enabled";
             }
             enum "off" {
               description "Disable antispoofing check";
             }
           }
         }
         leaf dynamic-tunnel-reassembly {
           type enumeration {
             enum "on" {
               description "Enable reassembly check. Default is disabled";
             }
             enum "off" {
               description "Disable reassembly check";
             }
           }
         }
       }
       list forwarding-rib {
         key name;
         ordered-by user;
         description "Forwarding routing table for dynamic-tunnel";
         leaf name {
           description "Routing table name";
           type string;
         }
         uses apply-advanced;
         leaf-list inet-import {
           ordered-by user;
           description "Import policy for V4 dynamic-tunnel";
           type jt:policy-algebra;
         }
       }
       container statistics {
         description "Fetch traffic statistics for  dynamic tunnels";
         uses apply-advanced;
         leaf interval {
           description "Time after which statistics has to be fetched";
           units "seconds";
           type union {
             type string {
               pattern "<.*>|$.*";
             }
             type uint16 {
               range "1 .. 65535";
             }
           }
         }
       }
       container traceoptions {
         description "Trace options";
         uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "kernel" {
                 description "Trace kernel communication";
               }
               enum "tunnel" {
                 description "Trace tunnel addition, change, or deletion";
               }
               enum "task" {
                 description "Trace task or job processing";
               }
               enum "tunnel-event" {
                 description "Trace create, delete, up, down event for nh based tunnel";
               }
               enum "flash-event" {
                 description "Trace flash event for tunnel forwarding route";
               }
               enum "stats-job" {
                 description "Trace taffic statistics job related stuff";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       leaf gre {
         description "Enable dynamic gre tunnel mode";
         type enumeration {
           enum "next-hop-based-tunnel" {
             description "Enable nh base dynamic-tunnel";
           }
         }
       }
       list dynamic-tunnel {
         key name;
         ordered-by user;
         uses dynamic_tunnel_type;
       }
     }
     list interface {
       key name;
       ordered-by user;
       description "Direct/Host route FRR protection";
       leaf name {
         description "Interface name";
         type union {
           type jt:interface-name;
           type string {
             pattern "<.*>|$.*";
           }
         }
       }
       uses apply-advanced;
       leaf arp-prefix-limit {
         description "Max ARP/Host FRR routes allowed";
         type union {
           type string {
             pattern "<.*>|$.*";
           }
           type uint32 {
             range "1 .. 10000";
           }
         }
       }
       leaf supplementary-blackout-timer {
         description "ARP plimit blackout timer = kernel ARP timeout + supplementary-blackout-timer minutes.";
         type union {
           type string {
             pattern "<.*>|$.*";
           }
           type uint32 {
             range "1 .. 15";
           }
         }
       }
       choice protection-type {
         case case_1 {
           leaf link-protection {
             description "Protect interface from link faults only";
             type empty;
           }
         }
       }
     }
     container host-fast-reroute {
       presence "enable host-fast-reroute";
       description "Host Fast Re-route global values. Applies to all host FRR profiles.";
       uses apply-advanced;
       leaf global-arp-prefix-limit {
         description "Max ARP/Host FRR routes allowed per protected IFL";
         type union {
           type string {
             pattern "<.*>|$.*";
           }
           type uint32 {
             range "1 .. 10000";
           }
         }
       }
       leaf global-supplementary-blackout-timer {
         description "ARP plimit global blackout timer = kernel ARP timeout + global-supplementary-blackout-timer minutes.";
         type union {
           type string {
             pattern "<.*>|$.*";
           }
           type uint32 {
             range "1 .. 15";
           }
         }
       }
     }
     leaf warm-standby {
       description "Enable warm-standby";
       type empty;
     }
     leaf nonstop-routing {
       description "Enable nonstop routing";
       type empty;
     }
     container nonstop-routing-options {
       presence "enable nonstop-routing-options";
       description "Nonstop routing options";
       uses apply-advanced;
       leaf precision-timers-max-period {
         description "Set Max period for precision timer support from kernel after switchover";
         type union {
           type string {
             pattern "<.*>|$.*";
           }
           type uint32 {
             range "60 .. 1800";
           }
         }
       }
     }
     leaf nsr-phantom-holdtime {
       description "Set NSR phantom route hold time";
       type union {
         type string {
           pattern "<.*>|$.*";
         }
         type uint32 {
           range "0 .. 10000";
         }
       }
     }
     list srlg {
       key name;
       ordered-by user;
       description "SRLG configuration";
       leaf name {
         description "Group name";
         type string {
           length "1 .. 64";
         }
       }
       uses apply-advanced;
       leaf srlg-value {
         description "Group id";
         type union {
           type string {
             pattern "<.*>|$.*";
           }
           type uint32 {
             range "1 .. 4294967295";
           }
         }
       }
       leaf srlg-cost {
         description "Cost value";
         type union {
           type string {
             pattern "<.*>|$.*";
           }
           type uint32 {
             range "1 .. 65535";
           }
         }
       }
     }
     container admin-groups-extended-range {
       description "Extended administrative groups range";
       uses apply-advanced;
       leaf minimum {
         description "Minimum value of the range for extended administrative groups";
         type union {
           type string {
             pattern "<.*>|$.*";
           }
           type uint32 {
             range "32 .. 4294967295";
           }
         }
       }
       leaf maximum {
         description "Maximum value of the range for extended administrative groups";
         type union {
           type string {
             pattern "<.*>|$.*";
           }
           type uint32 {
             range "32 .. 4294967295";
           }
         }
       }
     }
     list admin-groups-extended {
       key name;
       ordered-by user;
       description "Extended administrative groups";
       leaf name {
         description "Group name (Maximum length 64)";
         type string {
           length "1 .. 64";
         }
       }
       uses apply-advanced;
       leaf group-value {
         description "Group id";
         type union {
           type string {
             pattern "<.*>|$.*";
           }
           type uint32 {
             range "32 .. 4294967295";
           }
         }
       }
     }
     leaf lsp-telemetry {
       description "Turn on Jvision LSP telemetry";
       type empty;
     }
     container source-routing {
       description "Source-routing options";
       uses apply-advanced;
       leaf ip {
         description "Enable IP Source Routing";
         type empty;
       }
       leaf ipv6 {
         description "Enable Type 0 RouteHeader processing";
         type empty;
       }
     }
     container forwarding-table {
       uses forwarding-table-type;
     }
     container fate-sharing {
       description "Fate-sharing links or nodes database";
       uses apply-advanced;
       list group {
         key name;
         ordered-by user;
         description "Group of objects sharing common characteristics";
         leaf name {
           description "Name of object groups sharing the same fate";
           type string {
           }
         }
         uses apply-advanced;
         leaf cost {
           description "Cost value";
           type union {
             type string {
               pattern "<.*>|$.*";
             }
             type uint32 {
               range "1 .. 65535";
             }
           }
         }
         leaf use-for-post-convergence-lfa {
           description "Use this fate-sharing group as a constraint for post-convergence-lfa";
           type empty;
         }
         list from {
           key name;
           uses fate_sharing_links;
         }
       }
     }
     container multicast {
       description "Global multicast options";
       uses apply-advanced;
       container traceoptions {
         description "Global multicast trace options";
         uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "parse" {
                 description "Trace configuration parsing";
               }
               enum "config-internal" {
                 description "Trace configuration internals";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf disable {
             description "Disable this trace flag";
             type empty;
           }
         }
       }
       leaf rpf {
         status deprecated;
         type string;
       }
       list scope {
         key name;
         ordered-by user;
         description "Multicast address scope";
         leaf name {
           description "Name to identify multicast address scope";
           type string;
         }
         uses apply-advanced;
         leaf prefix {
           description "Administratively scoped address";
           type jt:ipprefix;
         }
         leaf-list interface {
           ordered-by user;
           description "Interface on which to configure scoping";
           type union {
             type jt:interface-name;
             type string {
               pattern "<.*>|$.*";
             }
           }
         }
       }
       leaf-list scope-policy {
         ordered-by user;
         description "Scoping policy";
         type jt:policy-algebra;
       }
       list flow-map {
         key name;
         ordered-by user;
         description "Multicast flow map configuration";
         leaf name {
           description "Name of the flow map";
           type string;
         }
         uses apply-advanced;
         leaf-list policy {
           ordered-by user;
           description "Policy for matched flows";
           type jt:policy-algebra;
         }
         container bandwidth {
           presence "enable bandwidth";
           description "Bandwidth properties for matched flows";
           leaf bandwidth-value {
             description "Static or default bandwidth for the matched flows";
             units "bps";
             type string;
           }
           leaf adaptive {
             description "Auto-sense bandwidth for matched flows";
             type empty;
           }
         }
         leaf-list redundant-sources {
           ordered-by user;
           description "Redundant source addresses";
           type jt:ipaddr;
         }
         container forwarding-cache {
           description "Forwarding cache properties for matched flows";
           uses apply-advanced;
           container timeout {
             description "Timeout properties for matched flows";
             choice timeout_choice {
               case case_1 {
                 leaf timeout-value {
                   description "Timeout for forwarding cache entry";
                   units "minutes";
                   type union {
                     type string {
                       pattern "<.*>|$.*";
                     }
                     type uint32 {
                       range "1 .. 720";
                     }
                   }
                 }
               }
               case case_2 {
                 container never {
                   presence "enable never";
                   description "Forwarding cache entries never time out";
                   uses apply-advanced;
                   leaf non-discard-entry-only {
                     description "Apply only to non-discard entries";
                     type empty;
                   }
                 }
               }
             }
           }
         }
       }
       leaf-list resolve-filter {
         ordered-by user;
         description "Multicast resolve policy filter";
         status deprecated;
         type jt:policy-algebra;
       }
       leaf-list ssm-groups {
         ordered-by user;
         description "Source-specific multicast group ranges";
         type jt:ipprefix;
       }
       leaf cont-stats-collection-interval {
         description "IGMP/MLD continuous statistics collection interval";
         default "300";
         type union {
           type string {
             pattern "<.*>|$.*";
           }
           type uint16 {
             range "60 .. 3600";
           }
         }
       }
       leaf asm-override-ssm {
         description "Allow ASM state for SSM group ranges";
         type empty;
       }
       leaf-list rpf-check-policy {
         ordered-by user;
         description "Disable RPF check for a source group pair";
         type jt:policy-algebra;
       }
       container pim-to-igmp-proxy {
         description "PIM-to-IGMP proxy";
         uses apply-advanced;
         leaf-list upstream-interface {
           ordered-by user;
           description "Upstream interface list";
           type union {
             type jt:interface-name;
             type string {
               pattern "<.*>|$.*";
             }
           }
           max-elements 2;
         }
       }
       container pim-to-mld-proxy {
         description "PIM-to-MLD proxy";
         uses apply-advanced;
         leaf-list upstream-interface {
           ordered-by user;
           description "Upstream interface list";
           type union {
             type jt:interface-name;
             type string {
               pattern "<.*>|$.*";
             }
           }
           max-elements 2;
         }
       }
       container forwarding-cache {
         description "Multicast forwarding cache";
         uses apply-advanced;
         leaf allow-maximum {
           description "Allow maximum of global and family level threshold values for suppress and reuse";
           type empty;
         }
         list family {
           key name;
           ordered-by user;
           description "Protocol family";
           leaf name {
             description "Protocol family";
             type enumeration {
               enum "inet" {
                 description "IPv4 family";
               }
               enum "inet6" {
                 description "IPv6 family";
               }
             }
           }
           uses apply-advanced;
           container threshold {
             presence "enable threshold";
             description "Multicast forwarding cache suppress threshold";
             uses apply-advanced;
             leaf suppress {
               description "Suppress threshold";
               type union {
                 type string {
                   pattern "<.*>|$.*";
                 }
                 type uint32 {
                   range "1 .. 200000";
                 }
               }
             }
             leaf reuse {
               description "Reuse threshold";
               type union {
                 type string {
                   pattern "<.*>|$.*";
                 }
                 type uint32 {
                   range "1 .. 200000";
                 }
               }
             }
             leaf mvpn-rpt-suppress {
               description "MVPN RP tree entry suppress threshold";
               type union {
                 type string {
                   pattern "<.*>|$.*";
                 }
                 type uint32 {
                   range "1 .. 200000";
                 }
               }
             }
             leaf mvpn-rpt-reuse {
               description "MVPN RP tree entry reuse threshold";
               type union {
                 type string {
                   pattern "<.*>|$.*";
                 }
                 type uint32 {
                   range "1 .. 200000";
                 }
               }
             }
             leaf log-warning {
               description "Percentage at which to start generating warnings";
               type union {
                 type string {
                   pattern "<.*>|$.*";
                 }
                 type uint32 {
                   range "1 .. 100";
                 }
               }
             }
           }
         }
         container threshold {
           description "Threshold";
           uses apply-advanced;
           leaf suppress {
             description "Suppress threshold";
             type union {
               type string {
                 pattern "<.*>|$.*";
               }
               type uint32 {
                 range "1 .. 200000";
               }
             }
           }
           leaf reuse {
             description "Reuse threshold";
             type union {
               type string {
                 pattern "<.*>|$.*";
               }
               type uint32 {
                 range "1 .. 200000";
               }
             }
           }
           leaf mvpn-rpt-suppress {
             description "MVPN RP tree entry suppress threshold";
             type union {
               type string {
                 pattern "<.*>|$.*";
               }
               type uint32 {
                 range "1 .. 200000";
               }
             }
           }
           leaf mvpn-rpt-reuse {
             description "MVPN RP tree entry reuse threshold";
             type union {
               type string {
                 pattern "<.*>|$.*";
               }
               type uint32 {
                 range "1 .. 200000";
               }
             }
           }
           leaf log-warning {
             description "Percentage at which to start generating warnings";
             type union {
               type string {
                 pattern "<.*>|$.*";
               }
               type uint32 {
                 range "1 .. 100";
               }
             }
           }
         }
         leaf timeout {
           description "Forwarding cache entry timeout in minutes";
           type union {
             type string {
               pattern "<.*>|$.*";
             }
             type uint32 {
               range "1 .. 720";
             }
           }
         }
       }
       list interface {
         key name;
         ordered-by user;
         description "Multicast interface options";
         uses multicast_interface_options_type;
       }
       list ssm-map {
         key name;
         ordered-by user;
         description "SSM map definitions";
         leaf name {
           description "SSM map name";
           type string;
         }
         uses apply-advanced;
         leaf-list policy {
           ordered-by user;
           description "Policy for matching group";
           type jt:policy-algebra;
         }
         leaf-list source {
           ordered-by user;
           description "One or more source addresses";
           type jt:ipaddr;
         }
       }
       container stream-protection {
         presence "enable stream-protection";
         description "Multicast only Fast Re-Route";
         uses apply-advanced;
         leaf mofrr-primary-path-selection-by-routing {
           description "Multicast only Fast Re-Route primary path by Routing";
           type empty;
         }
         leaf mofrr-disjoint-upstream-only {
           description "Multicast only Fast Re-Route disjoint upstream only";
           type empty;
         }
         leaf mofrr-no-backup-join {
           description "Multicast only Fast Re-Route no backup join";
           type empty;
         }
         leaf mofrr-asm-starg {
           description "Multicast only Fast Re-Route asm (*,G)";
           type empty;
         }
         leaf-list policy {
           ordered-by user;
           description "MoFRR Policy";
           type jt:policy-algebra;
         }
       }
       list backup-pe-group {
         key name;
         ordered-by user;
         description "Backup PE group definitions";
         leaf name {
           description "PE group name";
           type string;
         }
         uses apply-advanced;
         leaf-list backups {
           ordered-by user;
           description "One or more IP addresses";
           type jt:ipaddr;
           max-elements 8;
         }
         leaf local-address {
           description "Address to be used as local-address for this group";
           type jt:ipaddr;
         }
       }
       leaf omit-wildcard-address {
         description "Omit wildcard source/group fields in SPMSI AD NLRI";
         type empty;
       }
       leaf local-address {
         description "Local address for PIM and MVPN sessions";
         type jt:ipv4addr;
       }
     }
     container programmable-rpd {
       description "RPD Server module management options";
       uses programmable-rpd-type;
     }
     container validation {
       description "Define Route validation";
       uses apply-advanced;
       container traceoptions {
         description "Trace options for route validation";
         uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "error" {
                 description "Trace errored packets";
               }
               enum "packets" {
                 description "Trace all I/O packets";
               }
               enum "keepalive" {
                 description "Trace keepalive packets";
               }
               enum "update" {
                 description "Trace update packets";
               }
               enum "nsr-synchronization" {
                 description "Trace NSR synchronization events";
               }
               enum "state" {
                 description "Trace state transitions";
               }
               enum "policy" {
                 description "Trace policy processing";
               }
               enum "task" {
                 description "Trace routing protocol task processing";
               }
               enum "timer" {
                 description "Trace routing protocol timer processing";
               }
               enum "client" {
                 description "Trace route validation client events";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       leaf-list notification-rib {
         ordered-by user;
         description "Define routing tables that get notified upon validation state change";
         type string;
       }
       list group {
         key name;
         description "Define a group of sessions";
         leaf name {
           description "Group name";
           type string;
         }
         uses apply-advanced;
         leaf authentication-key {
           description "MD5 authentication key";
           type string {
             length "1 .. 126";
           }
         }
         leaf authentication-algorithm {
           description "Authentication algorithm name";
           default "hmac-sha-1-96";
           type enumeration {
             enum "md5" {
               description "Message Digest 5";
             }
             enum "hmac-sha-1-96" {
               description "Hash-based Message Authentication Code (SHA1) (96 bits)";
             }
             enum "aes-128-cmac-96" {
               description "Cipher-based Message Authentication Code (AES128) (96 bits)";
             }
             enum "ao" {
               description "TCP Authentication Option";
             }
           }
         }
         leaf tcpao-handling-with-digest-mismatch {
           description "Drop or continue without TCP-AO with digest mismatch with TCP-AO";
           type enumeration {
             enum "drop-if-no-tcpao" {
               description "Drop the connection if Digest mismatched";
             }
             enum "allow-without-tcpao" {
               description "Allow the connection establishment without TCP-AO";
             }
           }
         }
         leaf authentication-key-chain {
           description "Key chain name";
           type string {
             length "1 .. 128";
           }
         }
         leaf max-sessions {
           description "Maximum connected session in this group";
           type union {
             type string {
               pattern "<.*>|$.*";
             }
             type uint32 {
               range "1 .. 63";
             }
           }
         }
         list session {
           key name;
           description "Configure a session";
           leaf name {
             type jt:ipaddr;
           }
           uses apply-advanced;
           container traceoptions {
             description "Trace options for route validation";
             uses apply-advanced;
             container file {
               description "Trace file options";
               leaf filename {
                 description "Name of file in which to write trace information";
                 type string {
                   length "1 .. 1024";
                 }
               }
               leaf replace {
                 description "Replace trace file rather than appending to it";
                 status deprecated;
                 type empty;
               }
               leaf size {
                 description "Maximum trace file size";
                 type string;
               }
               leaf files {
                 description "Maximum number of trace files";
                 default "10";
                 type union {
                   type string {
                     pattern "<.*>|$.*";
                   }
                   type uint32 {
                     range "2 .. 1000";
                   }
                 }
               }
               leaf no-stamp {
                 description "Do not timestamp trace file";
                 status deprecated;
                 type empty;
               }
               choice world-readable-choice {
                 leaf world-readable {
                   description "Allow any user to read the log file";
                   type empty;
                 }
                 leaf no-world-readable {
                   description "Don't allow any user to read the log file";
                   type empty;
                 }
               }
             }
             list flag {
               key name;
               ordered-by user;
               description "Tracing parameters";
               leaf name {
                 type enumeration {
                   enum "error" {
                     description "Trace errored packets";
                   }
                   enum "packets" {
                     description "Trace all I/O packets";
                   }
                   enum "keepalive" {
                     description "Trace keepalive packets";
                   }
                   enum "update" {
                     description "Trace update packets";
                   }
                   enum "state" {
                     description "Trace state transitions";
                   }
                   enum "task" {
                     description "Trace routing protocol task processing";
                   }
                   enum "timer" {
                     description "Trace routing protocol timer processing";
                   }
                   enum "all" {
                     description "Trace everything";
                   }
                 }
               }
               leaf send {
                 description "Trace transmitted packets";
                 type empty;
               }
               leaf receive {
                 description "Trace received packets";
                 type empty;
               }
               leaf detail {
                 description "Trace detailed information";
                 type empty;
               }
               leaf disable {
                 description "Disable this trace flag";
                 type empty;
               }
             }
           }
           leaf authentication-key {
             description "MD5 authentication key";
             type string {
               length "1 .. 126";
             }
           }
           leaf authentication-algorithm {
             description "Authentication algorithm name";
             default "hmac-sha-1-96";
             type enumeration {
               enum "md5" {
                 description "Message Digest 5";
               }
               enum "hmac-sha-1-96" {
                 description "Hash-based Message Authentication Code (SHA1) (96 bits)";
               }
               enum "aes-128-cmac-96" {
                 description "Cipher-based Message Authentication Code (AES128) (96 bits)";
               }
               enum "ao" {
                 description "TCP Authentication Option";
               }
             }
           }
           leaf tcpao-handling-with-digest-mismatch {
             description "Drop or continue without TCP-AO with digest mismatch with TCP-AO";
             type enumeration {
               enum "drop-if-no-tcpao" {
                 description "Drop the connection if Digest mismatched";
               }
               enum "allow-without-tcpao" {
                 description "Allow the connection establishment without TCP-AO";
               }
             }
           }
           leaf authentication-key-chain {
             description "Key chain name";
             type string {
               length "1 .. 128";
             }
           }
           leaf refresh-time {
             description "Interval between keepalive packet transmissions";
             units "seconds";
             type union {
               type string {
                 pattern "<.*>|$.*";
               }
               type uint32 {
                 range "1 .. 1800";
               }
             }
           }
           leaf hold-time {
             description "Time after which the session is declared down.";
             units "seconds";
             type union {
               type string {
                 pattern "<.*>|$.*";
               }
               type uint32 {
                 range "10 .. 3600";
               }
             }
           }
           leaf record-lifetime {
             description "Lifetime of route validation records";
             units "seconds";
             type union {
               type string {
                 pattern "<.*>|$.*";
               }
               type uint32 {
                 range "60 .. 604800";
               }
             }
           }
           leaf preference {
             description "Preference for session establishment";
             type union {
               type string {
                 pattern "<.*>|$.*";
               }
               type uint32 {
                 range "1 .. 255";
               }
             }
           }
           leaf port {
             description "Portnumber to connect";
             type union {
               type string {
                 pattern "<.*>|$.*";
               }
               type uint16 {
                 range "1 .. 65535";
               }
             }
           }
           leaf local-address {
             type jt:ipaddr;
           }
         }
       }
       container static {
         description "Define static route validation record";
         uses apply-advanced;
         list record {
           key name;
           description "Static route validation record";
           leaf name {
             type jt:ipprefix;
           }
           uses apply-advanced;
           list maximum-length {
             key name;
             ordered-by user;
             leaf name {
               description "Maximum prefix-length for route validation record";
               type union {
                 type string {
                   pattern "<.*>|$.*";
                 }
                 type uint32 {
                   range "1 .. 128";
                 }
               }
             }
             uses apply-advanced;
             list origin-autonomous-system {
               key name;
               ordered-by user;
               leaf name {
                 description "Legitimate Origin Autonomous System";
                 type union {
                   type uint32;
                   type string {
                     pattern "<.*>|$.*";
                   }
                 }
               }
               uses apply-advanced;
               leaf validation-state {
                 description "Validation state for route validation record";
                 type enumeration {
                   enum "invalid" {
                     description "Invalid route validation state";
                   }
                   enum "valid" {
                     description "Valid route validation state";
                   }
                 }
               }
             }
           }
         }
       }
     }
   }
   grouping admin_group_include_exclude {
     uses apply-advanced;
     choice include-any-choice {
       case case_1 {
         leaf-list include-any {
           ordered-by user;
           description "Groups, one or more of which must be present";
           type string;
         }
       }
     }
     choice include-all-choice {
       case case_1 {
         leaf-list include-all {
           ordered-by user;
           description "Groups, all of which must be present";
           type string;
         }
       }
     }
     choice exclude-choice {
       case case_1 {
         leaf-list exclude {
           ordered-by user;
           description "Groups, all of which must be absent";
           type string;
         }
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping dynamic_tunnel_type {
     description "Dynamic tunnel definition";
     leaf name {
       description "Tunnel name";
       type string {
       }
     }
     uses apply-advanced;
     leaf source-address {
       description "Tunnel source address";
       type jt:ipaddr;
     }
     choice tunnel-type {
       case case_1 {
         list rsvp-te {
           key name;
           ordered-by user;
           description "RSVP-TE point-to-point LSP";
           leaf name {
             description "Configure multiple entries for RSVP tunnel";
             type string;
           }
           uses apply-advanced;
           container label-switched-path-template {
             description "Template for dynamic point-to-point LSP parameters";
             uses apply-advanced;
             choice dynamic-template {
               case case_1 {
                 leaf template-name {
                   description "Name of point-to-point LSP template";
                   type string {
                   }
                 }
               }
               case case_2 {
                 leaf default-template {
                   description "Use default parameters";
                   type empty;
                 }
               }
             }
           }
           list destination-networks {
             key name;
             ordered-by user;
             description "Create tunnels for routes in these destination networks";
             uses app_network_type;
           }
         }
       }
       case case_2 {
         container spring-te {
           description "SPRING-TE LSP's";
           uses apply-advanced;
           list source-routing-path-template {
             key name;
             ordered-by user;
             description "Template color mapping for SPRING-TE dynamic LSP parameters";
             uses spring-te-template-map;
           }
           list destination-networks {
             key name;
             ordered-by user;
             description "Create tunnels for routes in these destination networks";
             uses app_network_type;
           }
         }
       }
       case case_3 {
         leaf gre {
           description "Generic routing encapsulation type for IPv4";
           type empty;
         }
       }
       case case_4 {
         leaf udp {
           description "UDP encapsulation type for IPv4";
           type empty;
         }
       }
       case case_5 {
         leaf bgp-signal {
           description "BGP signals the encapsulation type for IPv4";
           type empty;
         }
       }
       case case_6 {
         leaf ipip {
           description "IPIP encapsulation type for IPv4";
           type empty;
         }
       }
     }
     list destination-networks {
       key name;
       ordered-by user;
       description "Create tunnels for routes in these destination networks";
       uses network_type;
     }
   }
   grouping app_network_type {
     leaf name {
       description "Network prefix";
       type jt:ipprefix;
     }
     uses apply-advanced;
   }
   grouping export-af-obj {
     uses apply-advanced;
     choice enable-disable {
       case case_1 {
         leaf disable {
           description "Disable auto-export for address family";
           type empty;
         }
       }
     }
     container unicast {
       description "Unicast routing information";
       presence "enable unicast";
       uses export-subaf-obj;
     }
     container multicast {
       description "Multicast routing information";
       presence "enable multicast";
       uses export-subaf-obj;
     }
     container flow {
       description "Flow routing information";
       presence "enable flow";
       uses export-subaf-obj;
     }
   }
   grouping export-subaf-obj {
     uses apply-advanced;
     choice enable-disable {
       case case_1 {
         leaf disable {
           description "Disable instance export";
           type empty;
         }
       }
     }
     leaf rib-group {
       description "Auxiliary rib-group of additional RIBs to consider";
       type string;
     }
   }
   grouping fate_sharing_links {
     leaf name {
       description "Router ID or LAN interface address";
       type jt:ipv4addr;
     }
     leaf to {
       description "Point-to-point links";
       type jt:ipv4addr;
     }
   }
   grouping flow-interface-group {
     leaf group {
       description "Interface group ID to match traffic";
       type union {
         type string {
           pattern "<.*>|$.*";
         }
         type uint32 {
           range "1 .. 255";
         }
       }
     }
     leaf exclude {
       description "Don't apply flow-spec filter to traffic on this group";
       type empty;
     }
   }
   grouping flow-route-inet {
     leaf name {
       type string;
     }
     uses apply-advanced;
     leaf no-install {
       description "Don't install firewall filter in forwarding";
       type empty;
     }
     container match {
       description "Flow definition";
       uses flow-route-qualifier-inet;
     }
     container then {
       description "Actions to take for this flow";
       uses flow-route-op;
     }
   }
   grouping flow-route-inet6 {
     leaf name {
       type string;
     }
     uses apply-advanced;
     leaf no-install {
       description "Don't install firewall filter in forwarding";
       type empty;
     }
     container match {
       description "Flow definition";
       uses flow-route-qualifier-inet6;
     }
     container then {
       description "Actions to take for this flow";
       uses flow-route-op;
     }
   }
   grouping flow-route-op {
     uses apply-advanced;
     leaf community {
       description "Name of BGP community";
       type string;
     }
     choice flow_op_action {
       case case_1 {
         leaf accept {
           description "Allow traffic through";
           type empty;
         }
       }
       case case_2 {
         leaf discard {
           description "Discard all traffic for this flow";
           type empty;
         }
       }
       case case_3 {
         leaf rate-limit {
           description "Rate in bits/sec to limit the flow traffic";
           type string;
         }
       }
     }
     leaf routing-instance {
       description "Redirect to instance identified via Route Target community";
       type string {
       }
     }
     leaf sample {
       description "Sample traffic that matches this flow";
       type empty;
     }
     leaf mark {
       description "Set DSCP value for traffic that matches this flow";
       type union {
         type string {
           pattern "<.*>|$.*";
         }
         type uint32 {
           range "0 .. 63";
         }
       }
     }
     leaf next-term {
       description "Continue the filter evaluation after matching this flow";
       type empty;
     }
     choice redirect_op_action {
       case case_1 {
         leaf-list redirect {
           ordered-by user;
           description "Redirect(Tunnel) this flow's traffic to given next-hop address";
           type jt:ipaddr;
         }
       }
     }
   }
   grouping flow-route-qualifier-inet {
     uses apply-advanced;
     leaf-list protocol {
       ordered-by user;
       description "IP protocol value";
       type string;
     }
     leaf-list port {
       ordered-by user;
       type string;
     }
     leaf-list destination-port {
       ordered-by user;
       type string;
     }
     leaf-list source-port {
       ordered-by user;
       type string;
     }
     leaf-list tcp-flags {
       ordered-by user;
       description "TCP flags";
       type string;
     }
     leaf-list packet-length {
       ordered-by user;
       description "Packet length (0-65535)";
       type jt:policy-algebra;
     }
     leaf-list dscp {
       ordered-by user;
       description "Differentiated Services (DiffServ) code point (DSCP) (0-63)";
       type jt:policy-algebra;
     }
     leaf-list fragment {
       ordered-by user;
       type enumeration {
         enum "dont-fragment" {
           description "Don't Fragment flag is set";
         }
         enum "not-a-fragment" {
           description "Not a fragment";
         }
         enum "is-fragment" {
           description "Fragmented packet";
         }
         enum "first-fragment" {
           description "First fragment";
         }
         enum "last-fragment" {
           description "Last fragment";
         }
       }
     }
     leaf destination {
       description "Destination prefix for this traffic flow";
       type jt:ipv4prefix;
     }
     leaf source {
       description "Source prefix for this traffic flow";
       type jt:ipv4prefix;
     }
     leaf-list icmp-code {
       ordered-by user;
       description "ICMP message code";
       type string;
     }
     leaf-list icmp-type {
       ordered-by user;
       description "ICMP message type";
       type string;
     }
   }
   grouping flow-route-qualifier-inet6 {
     uses apply-advanced;
     leaf-list protocol {
       ordered-by user;
       description "IP protocol value";
       type string;
     }
     leaf-list port {
       ordered-by user;
       type string;
     }
     leaf-list destination-port {
       ordered-by user;
       type string;
     }
     leaf-list source-port {
       ordered-by user;
       type string;
     }
     leaf-list tcp-flags {
       ordered-by user;
       description "TCP flags";
       type string;
     }
     leaf-list packet-length {
       ordered-by user;
       description "Packet length (0-65535)";
       type jt:policy-algebra;
     }
     leaf-list dscp {
       ordered-by user;
       description "Differentiated Services (DiffServ) code point (DSCP) (0-63)";
       type jt:policy-algebra;
     }
     leaf-list fragment {
       ordered-by user;
       type enumeration {
         enum "dont-fragment" {
           description "Don't Fragment flag is set";
         }
         enum "not-a-fragment" {
           description "Not a fragment";
         }
         enum "is-fragment" {
           description "Fragmented packet";
         }
         enum "first-fragment" {
           description "First fragment";
         }
         enum "last-fragment" {
           description "Last fragment";
         }
       }
     }
     container destination {
       description "Destination prefix for this traffic flow";
       presence "enable destination";
       uses flow-prefix-with-offset;
     }
     container source {
       description "Source prefix for this traffic flow";
       presence "enable source";
       uses flow-prefix-with-offset;
     }
     leaf-list icmp6-type {
       ordered-by user;
       description "ICMP message type";
       type string;
     }
     leaf-list icmp6-code {
       ordered-by user;
       description "ICMP message code";
       type string;
     }
     leaf-list flow-label {
       ordered-by user;
       description "Flow-label (0-1048575)";
       type jt:policy-algebra;
     }
   }
   grouping flow-prefix-with-offset {
     leaf prefix {
       type jt:ipv6prefix;
     }
     leaf prefix-offset {
       description "Offset from where prefix match will start";
       type union {
         type uint32;
         type string {
           pattern "<.*>|$.*";
         }
       }
     }
   }
   grouping flow-validation {
     uses apply-advanced;
     container traceoptions {
       description "Trace options";
       uses flow-dep-traceoptions;
     }
   }
   grouping flow-dep-traceoptions {
     uses apply-advanced;
     container file {
       description "Trace file options";
       leaf filename {
         description "Name of file in which to write trace information";
         type string {
           length "1 .. 1024";
         }
       }
       leaf replace {
         description "Replace trace file rather than appending to it";
         status deprecated;
         type empty;
       }
       leaf size {
         description "Maximum trace file size";
         type string;
       }
       leaf files {
         description "Maximum number of trace files";
         default "10";
         type union {
           type string {
             pattern "<.*>|$.*";
           }
           type uint32 {
             range "2 .. 1000";
           }
         }
       }
       leaf no-stamp {
         description "Do not timestamp trace file";
         status deprecated;
         type empty;
       }
       choice world-readable-choice {
         leaf world-readable {
           description "Allow any user to read the log file";
           type empty;
         }
         leaf no-world-readable {
           description "Don't allow any user to read the log file";
           type empty;
         }
       }
     }
     list flag {
       key name;
       ordered-by user;
       description "Tracing parameters";
       leaf name {
         type enumeration {
           enum "resolution" {
             description "Trace flow to unicast route resolution";
           }
           enum "flash" {
             description "Trace flash processing";
           }
           enum "route" {
             description "Trace routing information";
           }
           enum "normal" {
             description "Trace normal events";
           }
           enum "general" {
             description "Trace general events";
           }
           enum "state" {
             description "Trace state transitions";
           }
           enum "policy" {
             description "Trace policy processing";
           }
           enum "task" {
             description "Trace routing protocol task processing";
           }
           enum "timer" {
             description "Trace routing protocol timer processing";
           }
           enum "all" {
             description "Trace everything";
           }
         }
       }
       leaf send {
         description "Trace transmitted packets";
         type empty;
       }
       leaf receive {
         description "Trace received packets";
         type empty;
       }
       leaf detail {
         description "Trace detailed information";
         type empty;
       }
       leaf disable {
         description "Disable this trace flag";
         type empty;
       }
       container filter {
         presence "enable filter";
         description "Filter to apply to tracing";
         leaf match-on {
           description "Argument on which to match";
           type enumeration {
             enum "prefix" {
               description "Filter based on prefix";
             }
             enum "route-attribute" {
               description "Filter based on route attributes";
             }
           }
         }
         leaf-list policy {
           ordered-by user;
           description "Filter policy";
           type jt:policy-algebra;
         }
       }
     }
   }
   grouping forwarding-table-type {
     description "Forwarding table management options";
     uses apply-advanced;
     leaf remnant-holdtime {
       description "Time to hold inherited routes from FIB";
       type union {
         type string {
           pattern "<.*>|$.*";
         }
         type uint32 {
           range "0 .. 10000";
         }
       }
     }
     leaf chain-composite-max-label-count {
       description "Maximum labels inside chain composite for the platform.";
       type union {
         type string {
           pattern "<.*>|$.*";
         }
         type uint32 {
           range "1 .. 8";
         }
       }
     }
     leaf krt-nexthop-ack-timeout {
       description "Kernel nexthop ack timeout interval";
       type union {
         type string {
           pattern "<.*>|$.*";
         }
         type uint32 {
           range "1 .. 400";
         }
       }
     }
     container consistency-checking {
       description "RIB/FIB consistency checking";
       status deprecated;
       uses apply-advanced;
       choice enable-disable {
         case case_1 {
           leaf enable {
             description "Enable consistency checking";
             type empty;
           }
         }
         case case_2 {
           leaf disable {
             description "Disable consistency checking";
             type empty;
           }
         }
       }
       leaf period {
         description "Periodicity of scan in seconds";
         type union {
           type string {
             pattern "<.*>|$.*";
           }
           type uint32 {
             range "30 .. 4294967295";
           }
         }
       }
       leaf threshold {
         description "Mismatch threshold until complaint";
         type union {
           type uint32;
           type string {
             pattern "<.*>|$.*";
           }
         }
       }
     }
     leaf-list export {
       ordered-by user;
       description "Export policy";
       type jt:policy-algebra;
     }
     leaf dynamic-list-next-hop {
       description "Dynamic next-hop mode for EVPN";
       type empty;
     }
     container evpn-egress-link-protection {
       presence "enable evpn-egress-link-protection";
       description "EVPN PE-CE egress link failure protection";
       uses apply-advanced;
     }
     container egress-chaining {
       description "Enable egress-chaining";
       uses apply-advanced;
       leaf spring-te {
         description "Enable egress-chaining for SPRING-TE routes";
         type empty;
       }
     }
     choice ecmp-fast-reroute-choice {
       leaf ecmp-fast-reroute {
         description "Enable fast reroute for ECMP next hops";
         type empty;
       }
       leaf no-ecmp-fast-reroute {
         description "Don't enable fast reroute for ECMP next hops";
         type empty;
       }
     }
     choice indirect-next-hop-choice {
       leaf indirect-next-hop {
         description "Install indirect next hops in Packet Forwarding Engine";
         type empty;
       }
       leaf no-indirect-next-hop {
         description "Don't install indirect next hops in Packet Forwarding Engine";
         type empty;
       }
     }
     choice route-ack-converge-choice {
       leaf route-ack-converge {
         description "Enable the route ack convergence feature";
         type empty;
       }
       leaf no-route-ack-converge {
         description "Don't enable the route ack convergence feature";
         type empty;
       }
     }
     choice indirect-next-hop-change-acknowledgements-choice {
       leaf indirect-next-hop-change-acknowledgements {
         description "Request acknowledgements for Indirect next hop changes";
         type empty;
       }
       leaf no-indirect-next-hop-change-acknowledgements {
         description "Don't request acknowledgements for Indirect next hop changes";
         type empty;
       }
     }
     list rib {
       key name;
       ordered-by user;
       status deprecated;
       leaf name {
         type string;
       }
     }
     leaf unicast-reverse-path {
       description "Unicast reverse path (RP) verification";
       type enumeration {
         enum "active-paths" {
           description "Consider active paths when performing RP verification";
         }
         enum "feasible-paths" {
           description "Consider all feasible paths for RP verification";
         }
       }
     }
     container ip-tunnel-rpf-check {
       presence "enable ip-tunnel-rpf-check";
       description "IP tunnel Reverse Path Forwarding Check";
       uses apply-advanced;
       leaf mode {
         default "strict";
         type enumeration {
           enum "strict" {
             description "Strict mode for rpf-check(Default)";
           }
           enum "loose" {
             description "Loose mode for rpf-check";
           }
         }
       }
       leaf fail-filter {
         description "Fail filter name for RPF check(family inet|inet6|any)";
         type string {
         }
       }
     }
     leaf transit-lsp-statistics-from-route {
       description "Enable LSP statistics collection from the route";
       type empty;
     }
     container chained-composite-next-hop {
       description "Next-hop chaining mode";
       uses apply-advanced;
       container ingress {
         description "Ingress LSP nexthop settings";
         uses apply-advanced;
         choice l2vpn-choice {
           leaf l2vpn {
             description "Create composite-chained nexthops for ingress l2vpn LSPs";
             type empty;
           }
           leaf no-l2vpn {
             description "Don't create composite-chained nexthops for ingress l2vpn LSPs";
             type empty;
           }
         }
         choice l2ckt-choice {
           leaf l2ckt {
             description "Create composite-chained nexthops for ingress l2ckt LSPs";
             type empty;
           }
           leaf no-l2ckt {
             description "Don't create composite-chained nexthops for ingress l2ckt LSPs";
             type empty;
           }
         }
         choice fec129-vpws-choice {
           leaf fec129-vpws {
             description "Create composite-chained nexthops for ingress fec129-vpws LSPs";
             type empty;
           }
           leaf no-fec129-vpws {
             description "Don't create composite-chained nexthops for ingress fec129-vpws LSPs";
             type empty;
           }
         }
         choice evpn-choice {
           leaf evpn {
             description "Create composite-chained nexthops for ingress EVPN LSPs";
             type empty;
           }
           leaf no-evpn {
             description "Don't create composite-chained nexthops for ingress EVPN LSPs";
             type empty;
           }
         }
         container labeled-bgp {
           description "Create composite-chained nexthops for ingress labeled-bgp LSPs";
           uses apply-advanced;
           choice inet-choice {
             leaf inet {
               description "Enable inet labeled-bgp composite nexthop creation";
               type empty;
             }
             leaf no-inet {
               description "Don't enable inet labeled-bgp composite nexthop creation";
               type empty;
             }
           }
           choice inet6-choice {
             leaf inet6 {
               description "Enable inet6 labeled-bgp composite nexthop creation";
               type empty;
             }
             leaf no-inet6 {
               description "Don't enable inet6 labeled-bgp composite nexthop creation";
               type empty;
             }
           }
         }
         container l3vpn {
           presence "enable l3vpn";
           description "Create composite-chained nexthops for ingress l3vpn LSPs";
           leaf extended-space {
             description "Allocate in extended-space for scalability";
             type empty;
           }
         }
         choice ldp-choice {
           leaf ldp {
             description "Create chained-composite nexthops to support segmentation LDP tunnels";
             type empty;
           }
           leaf no-ldp {
             description "Don't create chained-composite nexthops to support segmentation LDP tunnels";
             type empty;
           }
         }
       }
       container transit {
         description "Transit LSP nexthops settings";
         uses apply-advanced;
         choice l2vpn-choice {
           leaf l2vpn {
             description "Create composite-chained nexthops for transit l2vpn LSPs";
             type empty;
           }
           leaf no-l2vpn {
             description "Don't create composite-chained nexthops for transit l2vpn LSPs";
             type empty;
           }
         }
         choice l3vpn-choice {
           leaf l3vpn {
             description "Create composite-chained nexthops for transit l3vpn LSPs";
             type empty;
           }
           leaf no-l3vpn {
             description "Don't create composite-chained nexthops for transit l3vpn LSPs";
             type empty;
           }
         }
         choice labeled-bgp-choice {
           leaf labeled-bgp {
             description "Create composite-chained nexthops for transit labeled BGP routes";
             type empty;
           }
           leaf no-labeled-bgp {
             description "Don't create composite-chained nexthops for transit labeled BGP routes";
             type empty;
           }
         }
         choice static-choice {
           leaf static {
             description "Create composite-chained nexthops for static LSPs";
             type empty;
           }
           leaf no-static {
             description "Don't create composite-chained nexthops for static LSPs";
             type empty;
           }
         }
         choice rsvp-choice {
           leaf rsvp {
             description "Create composite-chained nexthops for RSVP LSPs";
             type empty;
           }
           leaf no-rsvp {
             description "Don't create composite-chained nexthops for RSVP LSPs";
             type empty;
           }
         }
         choice rsvp-p2mp-choice {
           leaf rsvp-p2mp {
             description "Create composite-chained nexthops for RSVP p2mp LSPs";
             type empty;
           }
           leaf no-rsvp-p2mp {
             description "Don't create composite-chained nexthops for RSVP p2mp LSPs";
             type empty;
           }
         }
         choice express-segments-choice {
           leaf express-segments {
             description "Create composite-chained nexthops for Express Segments";
             type empty;
           }
           leaf no-express-segments {
             description "Don't create composite-chained nexthops for Express Segments";
             type empty;
           }
         }
         choice ldp-choice {
           leaf ldp {
             description "Create composite-chained nexthops for LDP LSPs";
             type empty;
           }
           leaf no-ldp {
             description "Don't create composite-chained nexthops for LDP LSPs";
             type empty;
           }
         }
         choice ldp-p2mp-choice {
           leaf ldp-p2mp {
             description "Create composite-chained nexthops for LDP P2MP LSPs";
             type empty;
           }
           leaf no-ldp-p2mp {
             description "Don't create composite-chained nexthops for LDP P2MP LSPs";
             type empty;
           }
         }
         choice labeled-isis-choice {
           leaf labeled-isis {
             description "Create composite-chained nexthops for labeled ISIS routes";
             type empty;
           }
           leaf no-labeled-isis {
             description "Don't create composite-chained nexthops for labeled ISIS routes";
             type empty;
           }
         }
       }
     }
     container fib-next-hop-split {
       description "Split nexthop to chain nexthop when installing fom rib to fib";
       uses apply-advanced;
       leaf labeled-isis {
         description "Create composite-chained nexthops for labeled ISIS routes";
         type empty;
       }
     }
   }
   grouping lsp_nh_obj {
     leaf name {
       description "LSP to use to reach destination";
       type string;
     }
     uses apply-advanced;
     leaf preference {
       description "Preference of LSP next hop";
       type union {
         type uint32;
         type string {
           pattern "<.*>|$.*";
         }
       }
     }
     leaf metric {
       description "Metric of LSP next hop";
       type union {
         type uint32;
         type string {
           pattern "<.*>|$.*";
         }
       }
     }
   }
   grouping macro-data-type {
     leaf name {
       description "Keyword part of the keyword-value pair";
       type string;
     }
     leaf value {
       description "Value part of the keyword-value pair";
       type string;
     }
   }
   grouping martian_type {
     description "Invalid routes";
     leaf address {
       description "IP address or hostname";
       type jt:ipprefix;
     }
     leaf choice-ident {
       type enumeration {
         enum "exact" {
         }
         enum "longer" {
         }
         enum "orlonger" {
         }
         enum "upto" {
         }
         enum "through" {
         }
         enum "prefix-length-range" {
         }
         enum "allow" {
         }
       }
     }
     leaf choice-value {
       type string;
     }
     leaf allow {
       type empty;
     }
   }
   grouping multicast_interface_options_type {
     description "Multicast interface options";
     leaf name {
       description "Interface name";
       type union {
         type jt:interface-unit;
         type string {
           pattern "<.*>|$.*";
         }
       }
     }
     uses apply-advanced;
     container maximum-bandwidth {
       presence "enable maximum-bandwidth";
       description "Maximum multicast bandwidth for the interface";
       leaf bandwidth-limit {
         description "Maximum multicast bandwidth on the interface";
         units "bps";
         type string;
       }
     }
     choice enable-disable {
       case case_1 {
         leaf enable {
           description "Enable Multicast";
           status deprecated;
           type empty;
         }
       }
       case case_2 {
         leaf disable {
           description "Disable Multicast";
           status deprecated;
           type empty;
         }
       }
     }
     container reverse-oif-mapping {
       presence "enable reverse-oif-mapping";
       description "Enable reverse OIF mapping on the multicast interface";
       uses apply-advanced;
       leaf no-qos-adjust {
         description "Disable reverse OIF mapping QoS adjustment";
         type empty;
       }
     }
     leaf subscriber-leave-timer {
       description "Timeout in seconds to credit back the bandwidth on the subscriber interface";
       units "seconds";
       type union {
         type string {
           pattern "<.*>|$.*";
         }
         type uint32 {
           range "0 .. 30";
         }
       }
     }
     leaf no-qos-adjust {
       description "Disable QoS adjustment for this interface";
       type empty;
     }
   }
   grouping network_type {
     leaf name {
       description "Network prefix";
       type jt:ipprefix;
     }
     uses apply-advanced;
     leaf-list dyn-tunnel-attribute-policy {
       ordered-by user;
       description "Import policy for dynamic-tunnel under this destination network";
       type jt:policy-algebra;
     }
     leaf preference {
       description "Preference of tunnel route under this destination network";
       type union {
         type uint32;
         type string {
           pattern "<.*>|$.*";
         }
       }
     }
     leaf-list colors {
       ordered-by user;
       description "Set of color list that will be supported for tunnel creation";
       type union {
         type uint32;
         type string {
           pattern "<.*>|$.*";
         }
       }
     }
   }
   grouping p2mp_ldp_lsp_nh_obj {
     uses apply-advanced;
     list root-address {
       key name;
       description "Configure the root address of P2MP LSP";
       leaf name {
         description "Root address of the P2MP LSP";
         type jt:ipaddr;
       }
       uses apply-advanced;
       leaf lsp-id {
         description "Configure the generic LSP identifier";
         type union {
           type string {
             pattern "<.*>|$.*";
           }
           type uint32 {
             range "1 .. 65535";
           }
         }
       }
       list group-address {
         key name;
         description "IPv4/Ipv6 group address for mLDP LSP";
         leaf name {
           description "IPv4/Ipv6 group address";
           type jt:ipaddr;
         }
         uses apply-advanced;
         list source-address {
           key name;
           description "IPv4/Ipv6 source address";
           leaf name {
             description "IPv4/Ipv6 source address for mLDP LSP";
             type jt:ipaddr;
           }
           uses apply-advanced;
         }
       }
     }
   }
   grouping programmable-rpd-type {
     uses apply-advanced;
     container traceoptions {
       description "Trace options";
       uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "client" {
               description "Client events";
             }
             enum "japi" {
               description "JAPI related traces";
             }
             enum "routing-interface" {
               description "Routing interface traces";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
       }
     }
     container purge-timeout {
       presence "enable purge-timeout";
       description "Purge timeout for all programmable-rpd clients in seconds";
       choice purge-parm {
         case case_1 {
           leaf never {
             description "Client programmed objects are never purged";
             type empty;
           }
         }
         case case_2 {
           leaf timeout {
             description "Timeout value, in seconds, for purging client programmed objects";
             units "seconds";
             type union {
               type string {
                 pattern "<.*>|$.*";
               }
               type uint32 {
                 range "1 .. 604800";
               }
             }
           }
         }
       }
     }
     list client {
       key name;
       ordered-by user;
       description "Programmable-rpd client options";
       leaf name {
         description "Client ID";
         type string {
           length "1 .. 255";
         }
       }
       uses apply-advanced;
       list interface-notification {
         key name;
         ordered-by user;
         description "Interfaces for notification";
         leaf name {
           description "Interface";
           type string {
             length "1 .. 32";
           }
         }
         uses apply-advanced;
       }
     }
     container rib-service {
       presence "enable rib-service";
       description "RIB service API options";
       uses apply-advanced;
       container dynamic-next-hop-interface {
         presence "enable dynamic-next-hop-interface";
         description "Update routes for next-hop interface changes";
         uses apply-advanced;
         choice enable-disable {
           case case_1 {
             leaf disable {
               description "Disable dynamic next-hop interface handling";
               type empty;
             }
           }
         }
       }
     }
   }
   grouping qualified_nh_obj {
     leaf name {
       description "Next hop to destination";
       type union {
         type jt:ipaddr-or-interface;
         type string {
           pattern "<.*>|$.*";
         }
       }
     }
     uses apply-advanced;
     leaf preference {
       description "Preference of qualified next hop";
       type union {
         type uint32;
         type string {
           pattern "<.*>|$.*";
         }
       }
     }
     leaf metric {
       description "Metric of qualified next hop";
       type union {
         type uint32;
         type string {
           pattern "<.*>|$.*";
         }
       }
     }
     leaf interface {
       description "Interface of qualified next hop";
       type union {
         type jt:interface-name;
         type string {
           pattern "<.*>|$.*";
         }
       }
     }
     leaf mac-address {
       description "Next-hop Mac Address";
       type jt:mac-unicast;
     }
     leaf tag {
       description "Tag string";
       type union {
         type uint32;
         type string {
           pattern "<.*>|$.*";
         }
       }
     }
     container bfd-liveness-detection {
       description "Bidirectional Forwarding Detection (BFD) options";
       uses apply-advanced;
       leaf version {
         description "BFD protocol version number";
         default "automatic";
         type enumeration {
           enum "0" {
             description "BFD version 0 (deprecated)";
           }
           enum "1" {
             description "BFD version 1";
           }
           enum "automatic" {
             description "Choose BFD version automatically";
           }
         }
       }
       leaf minimum-interval {
         description "Minimum transmit and receive interval";
         units "milliseconds";
         type union {
           type string {
             pattern "<.*>|$.*";
           }
           type uint32 {
             range "1 .. 255000";
           }
         }
       }
       leaf minimum-transmit-interval {
         description "Minimum transmit interval";
         status deprecated;
         units "milliseconds";
         type union {
           type string {
             pattern "<.*>|$.*";
           }
           type uint32 {
             range "1 .. 255000";
           }
         }
       }
       leaf minimum-receive-interval {
         description "Minimum receive interval";
         units "milliseconds";
         type union {
           type string {
             pattern "<.*>|$.*";
           }
           type uint32 {
             range "1 .. 255000";
           }
         }
       }
       leaf multiplier {
         description "Detection time multiplier";
         default "3";
         type union {
           type string {
             pattern "<.*>|$.*";
           }
           type uint32 {
             range "1 .. 255";
           }
         }
       }
       choice adaptation-choice {
         case case_1 {
           leaf no-adaptation {
             description "Disable adaptation";
             type empty;
           }
         }
       }
       container transmit-interval {
         description "Transmit-interval options";
         uses apply-advanced;
         leaf minimum-interval {
           description "Minimum transmit interval";
           units "milliseconds";
           type union {
             type string {
               pattern "<.*>|$.*";
             }
             type uint32 {
               range "1 .. 255000";
             }
           }
         }
         leaf threshold {
           description "High transmit interval triggering a trap";
           units "milliseconds";
           type union {
             type uint32;
             type string {
               pattern "<.*>|$.*";
             }
           }
         }
       }
       container detection-time {
         description "Detection-time options";
         uses apply-advanced;
         leaf threshold {
           description "High detection-time triggering a trap";
           units "milliseconds";
           type union {
             type uint32;
             type string {
               pattern "<.*>|$.*";
             }
           }
         }
       }
       container authentication {
         description "Authentication options";
         uses apply-advanced;
         leaf key-chain {
           description "Key chain name";
           type string;
         }
         leaf algorithm {
           description "Algorithm name";
           type enumeration {
             enum "simple-password" {
               description "Simple password";
             }
             enum "keyed-md5" {
               description "Keyed message Digest 5";
             }
             enum "meticulous-keyed-md5" {
               description "Meticulous keyed message Digest 5";
             }
             enum "keyed-sha-1" {
               description "Keyed secure hash algorithm (SHA1) ";
             }
             enum "meticulous-keyed-sha-1" {
               description "Meticulous keyed secure hash algorithm (SHA1) ";
             }
           }
         }
         leaf loose-check {
           description "Verify authentication only if authentication is negotiated";
           type empty;
         }
       }
       leaf neighbor {
         description "BFD neighbor address";
         type jt:ipaddr;
       }
       leaf local-address {
         description "BFD local address (for multihop only)";
         type jt:ipaddr;
       }
       leaf holddown-interval {
         description "Time to hold the session-UP notification to the client";
         units "milliseconds";
         type union {
           type string {
             pattern "<.*>|$.*";
           }
           type uint32 {
             range "0 .. 255000";
           }
         }
       }
       leaf minimum-receive-ttl {
         description "Minimum receive TTL below which to drop";
         type union {
           type string {
             pattern "<.*>|$.*";
           }
           type uint8 {
             range "1 .. 255";
           }
         }
       }
     }
   }
   grouping rib_aggregate_type {
     uses apply-advanced;
     container defaults {
       description "Global route options";
       uses apply-advanced;
       container metric {
         description "Metric value";
         presence "enable metric";
         uses rib_static_metric_type;
       }
       container metric2 {
         description "Metric value 2";
         presence "enable metric2";
         uses rib_static_metric_type;
       }
       container metric3 {
         description "Metric value 3";
         presence "enable metric3";
         uses rib_static_metric_type;
       }
       container metric4 {
         description "Metric value 4";
         presence "enable metric4";
         uses rib_static_metric_type;
       }
       container tag {
         description "Tag string";
         presence "enable tag";
         uses rib_static_metric_type;
       }
       container tag2 {
         description "Tag string 2";
         presence "enable tag2";
         uses rib_static_metric_type;
       }
       container preference {
         description "Preference value";
         presence "enable preference";
         uses rib_static_metric_type;
       }
       container preference2 {
         description "Preference value 2";
         presence "enable preference2";
         uses rib_static_metric_type;
       }
       container color {
         description "Color (preference) value";
         presence "enable color";
         uses rib_static_metric_type;
       }
       container color2 {
         description "Color (preference) value 2";
         presence "enable color2";
         uses rib_static_metric_type;
       }
       leaf-list community {
         ordered-by user;
         description "BGP community identifier";
         type jt:community;
       }
       container as-path {
         description "Autonomous system path";
         uses apply-advanced;
         leaf path {
           description "Autonomous system path";
           type string;
         }
         leaf origin {
           type enumeration {
             enum "igp" {
               description "Path originated in the local IGP";
             }
             enum "egp" {
               description "Path originated in another AS";
             }
             enum "incomplete" {
               description "Path was learned by some other means";
             }
           }
         }
         leaf atomic-aggregate {
           description "Add ATOMIC_AGGREGATE path attribute to route";
           type empty;
         }
         container aggregator {
           presence "enable aggregator";
           description "Add AGGREGATOR path attribute to route";
         }
         leaf as-number {
           description " Autonomous system number in plain number or 'higher 16bits'.'Lower 16 bits' (asdot notation) format";
           type string {
           }
         }
         leaf address {
           description "Address of BGP system that formed the route";
           type jt:ipv4addr;
         }
       }
       leaf discard {
         description "Drop packets to destination; send no ICMP unreachables";
         type empty;
       }
       leaf next-table {
         description "Next hop to another table";
         type string;
       }
       choice brief_flag {
         case case_1 {
           leaf brief {
             description "Include longest common sequences from contributing paths";
             type empty;
           }
         }
         case case_2 {
           leaf full {
             description "Include all AS numbers from all contributing paths";
             type empty;
           }
         }
       }
       choice passive_flag {
         case case_1 {
           leaf active {
             description "Remove inactive route from forwarding table";
             type empty;
           }
         }
         case case_2 {
           leaf passive {
             description "Retain inactive route in forwarding table";
             type empty;
           }
         }
       }
     }
     list route {
       key name;
       ordered-by user;
       description "Individual route options";
       leaf name {
         description "Destination prefix";
         type jt:ipprefix;
       }
       uses apply-advanced;
       leaf-list policy {
         ordered-by user;
         description "Policy filter";
         type jt:policy-algebra;
       }
       container metric {
         description "Metric value";
         presence "enable metric";
         uses rib_static_metric_type;
       }
       container metric2 {
         description "Metric value 2";
         presence "enable metric2";
         uses rib_static_metric_type;
       }
       container metric3 {
         description "Metric value 3";
         presence "enable metric3";
         uses rib_static_metric_type;
       }
       container metric4 {
         description "Metric value 4";
         presence "enable metric4";
         uses rib_static_metric_type;
       }
       container tag {
         description "Tag string";
         presence "enable tag";
         uses rib_static_metric_type;
       }
       container tag2 {
         description "Tag string 2";
         presence "enable tag2";
         uses rib_static_metric_type;
       }
       container preference {
         description "Preference value";
         presence "enable preference";
         uses rib_static_metric_type;
       }
       container preference2 {
         description "Preference value 2";
         presence "enable preference2";
         uses rib_static_metric_type;
       }
       container color {
         description "Color (preference) value";
         presence "enable color";
         uses rib_static_metric_type;
       }
       container color2 {
         description "Color (preference) value 2";
         presence "enable color2";
         uses rib_static_metric_type;
       }
       leaf-list community {
         ordered-by user;
         description "BGP community identifier";
         type jt:community;
       }
       container as-path {
         description "Autonomous system path";
         uses apply-advanced;
         leaf path {
           description "Autonomous system path";
           type string;
         }
         leaf origin {
           type enumeration {
             enum "igp" {
               description "Path originated in the local IGP";
             }
             enum "egp" {
               description "Path originated in another AS";
             }
             enum "incomplete" {
               description "Path was learned by some other means";
             }
           }
         }
         leaf atomic-aggregate {
           description "Add ATOMIC_AGGREGATE path attribute to route";
           type empty;
         }
         container aggregator {
           presence "enable aggregator";
           description "Add AGGREGATOR path attribute to route";
         }
         leaf as-number {
           description " Autonomous system number in plain number or 'higher 16bits'.'Lower 16 bits' (asdot notation) format";
           type string {
           }
         }
         leaf address {
           description "Address of BGP system that formed the route";
           type jt:ipv4addr;
         }
       }
       leaf discard {
         description "Drop packets to destination; send no ICMP unreachables";
         type empty;
       }
       leaf next-table {
         description "Next hop to another table";
         type string;
       }
       choice brief_flag {
         case case_1 {
           leaf brief {
             description "Include longest common sequences from contributing paths";
             type empty;
           }
         }
         case case_2 {
           leaf full {
             description "Include all AS numbers from all contributing paths";
             type empty;
           }
         }
       }
       choice passive_flag {
         case case_1 {
           leaf active {
             description "Remove inactive route from forwarding table";
             type empty;
           }
         }
         case case_2 {
           leaf passive {
             description "Retain inactive route in forwarding table";
             type empty;
           }
         }
       }
     }
   }
   grouping rib_group_type {
     uses apply-advanced;
     leaf inet-old-style {
       description "Name of the IPv4 routing table group";
       status deprecated;
       type string;
     }
     leaf inet {
       description "Name of the IPv4 routing table group";
       type string;
     }
     leaf inet3 {
       description "Name of the IPv4 inet.3 routing table group";
       type string;
     }
     leaf inet6 {
       description "Name of the IPv6 routing table group";
       type string;
     }
     leaf inet63 {
       description "Name of the IPv6 inet6.3 routing table group";
       type string;
     }
   }
   grouping rib_static_metric_type {
     leaf metric-value {
       description "Metric value";
       type union {
         type uint32;
         type string {
           pattern "<.*>|$.*";
         }
       }
     }
     leaf type {
       description "Metric type";
       type union {
         type string {
           pattern "<.*>|$.*";
         }
         type uint32 {
           range "1 .. 16";
         }
       }
     }
   }
   grouping rpd_rib_group_type {
     description "Routing table group";
     leaf name {
       description "Routing table group";
       type string;
     }
     uses apply-advanced;
     leaf export-rib {
       description "Export routing table";
       type string;
     }
     leaf-list import-rib {
       ordered-by user;
       description "Import routing table";
       type string;
     }
     leaf-list import-policy {
       ordered-by user;
       description "Import policy";
       type jt:policy-algebra;
     }
   }
   grouping rpm-next-hop {
     leaf name {
       description "Next hop to destination";
       type jt:ipaddr;
     }
     uses apply-advanced;
     list rpm-probe {
       key name;
       ordered-by user;
       leaf name {
         description "RPM probe to track";
         type string;
       }
       leaf rpm-test {
         description "RPM test to track";
         type string;
       }
     }
   }
   grouping spring-te-template-map {
     description "SPRING-TE template color map";
     leaf name {
       description "Name of SPRING-TE template";
       type string;
     }
     uses apply-advanced;
     choice colors {
       case case_1 {
         leaf-list color {
           description "Set of color list to be mapped to corresponding SPRING-TE template";
           type union {
             type uint32;
             type string {
               pattern "<.*>|$.*";
             }
           }
         }
       }
       case case_2 {
         leaf color-any {
           description "Map any color to corresponding SPRING-TE template";
           type empty;
         }
       }
     }
   }
 }
