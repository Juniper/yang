/*
 * Copyright (c) 2019 Juniper Networks, Inc.
 * All rights reserved.
 */
 module junos-ex-conf-unified-edge {
   namespace "http://yang.juniper.net/junos-ex/conf/unified-edge";

   prefix jc-unified-edge;

   import junos-common-ddl-extensions {
     prefix junos;
   }

   import junos-common-types {
     prefix jt;
   }

   import junos-ex-conf-root {
     prefix jc;
   }

   organization "Juniper Networks, Inc.";

   contact "yang-support@juniper.net";

   description "Junos unified-edge configuration module";

   revision 2019-01-01 {
     description "Junos: 19.1R1.3";
   }

   augment /jc:configuration {
     uses unified-edge-group;
   }
   augment /jc:configuration/jc:groups {
     uses unified-edge-group;
   }
   grouping unified-edge-group {
     container unified-edge {
       uses apply-advanced;
       container cos-cac {
         description "Unified Edge COS configuration";
         status deprecated;
         uses juniper-unified-edge-cos-options;
       }
       list local-policies {
         key name;
         ordered-by user;
         description "Local policy profiles";
         status deprecated;
         max-elements 8001;
         leaf name {
           description "Local policy profile name";
           type string {
             junos:posix-pattern "^.{1,64}$";
             junos:pattern-message "Must be string of 64 characters or less";
           }
         }
         uses apply-advanced;
         leaf description {
           description "Text description of local policy";
           type string;
         }
         leaf resource-threshold-profile {
           description "Resource threshold profile associated with the local policy";
           type string;
         }
         leaf classifier-profile {
           description "QoS class profile associated with the local policy";
           type string;
         }
         leaf cos-policy-profile {
           description "QoS policy profile associated with the local policy";
           type string;
         }
         leaf roamer-classifier-profile {
           description "QoS classifier profile for roamers";
           type string;
         }
         leaf roamer-cos-policy-profile {
           description "QoS policy profile for roamers";
           type string;
         }
         leaf visitor-classifier-profile {
           description "QoS classifier profile for visitor";
           type string;
         }
         leaf visitor-cos-policy-profile {
           description "QoS policy profile for visitor";
           type string;
         }
         leaf traffic-class-qci-mapping-profile {
           description "Traffic class to qci mapping profile";
           type string {
             length "1 .. 128";
           }
         }
         leaf ul-bandwidth-pool {
           description "Bandwidth pool associated with the local policy";
           type string;
         }
         leaf dl-bandwidth-pool {
           description "Bandwidth pool associated with the local policy";
           type string;
         }
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping juniper-unified-edge-cos-options {
     uses apply-advanced;
     list classifier-profiles {
       key name;
       ordered-by user;
       description "Classifier tables for mobile subscribers (UMTS/EPS)";
       max-elements 8001;
       leaf name {
         description "Classification table name";
         type string {
           junos:posix-pattern "^.{1,64}$";
           junos:pattern-message "Must be string of 64 characters or less";
         }
       }
       uses apply-advanced;
       leaf description {
         description "Text description of classifier profile";
         type string;
       }
       list qos-class-identifier {
         key name;
         ordered-by user;
         description "QCI mapping to forwarding class and loss priority";
         leaf name {
           description "Qci value";
           type union {
             type string {
               pattern "<.*>|$.*";
             }
             type uint32 {
               range "1 .. 9";
             }
           }
         }
         leaf forwarding-class {
           description "Forwarding class";
           type string {
             junos:posix-pattern "^.{1,64}$";
             junos:pattern-message "Must be string of 64 characters or less";
           }
         }
         leaf loss-priority {
           description "Loss priority value";
           type enumeration {
             enum "low" {
               description "Loss priority low";
             }
             enum "high" {
               description "Loss priority high";
             }
           }
         }
       }
     }
     list gbr-bandwidth-pools {
       key name;
       ordered-by user;
       description "GBR bandwith pools configuration";
       max-elements 8001;
       leaf name {
         description "GBR Bandwidth pool name";
         type string {
           junos:posix-pattern "^.{1,64}$";
           junos:pattern-message "Must be string of 64 characters or less";
         }
       }
       uses apply-advanced;
       leaf maximum-bandwidth {
         description "Bandwidth for pool";
         units "mega-bits per second";
         type union {
           type string {
             pattern "<.*>|$.*";
           }
           type uint32 {
             range "50000 .. 500000";
           }
         }
       }
       leaf downgrade-gtp-v1-gbr-bearers {
         description "Downgrade GTPv1 GBR bearer traffic class to background traffic class";
         type empty;
       }
     }
     list resource-threshold-profiles {
       key name;
       ordered-by user;
       description "Resource threshold profiles";
       max-elements 8001;
       leaf name {
         description "Resource threshold profile name";
         type string {
           junos:posix-pattern "^.{1,64}$";
           junos:pattern-message "Must be string of 64 characters or less";
         }
       }
       uses apply-advanced;
       leaf description {
         description "Text description of resource threshold profile";
         type string;
       }
       container bearers-load {
         description "Number of bearers load configurations";
         uses apply-advanced;
         container low {
           description "Low threshold configuration";
           uses apply-advanced;
           leaf percentage {
             description "Low threshold";
             units "Percentage";
             type union {
               type string {
                 pattern "<.*>|$.*";
               }
               type uint32 {
                 range "1 .. 100";
               }
             }
           }
           leaf priority-level {
             description "Priority level - default 10";
             default "10";
             type union {
               type string {
                 pattern "<.*>|$.*";
               }
               type uint32 {
                 range "1 .. 15";
               }
             }
           }
         }
         container high {
           description "High threshold configuration";
           uses apply-advanced;
           leaf percentage {
             description "High threshold";
             units "Percentage";
             type union {
               type string {
                 pattern "<.*>|$.*";
               }
               type uint32 {
                 range "1 .. 100";
               }
             }
           }
           leaf priority-level {
             description "Priority level - default 5";
             default "5";
             type union {
               type string {
                 pattern "<.*>|$.*";
               }
               type uint32 {
                 range "1 .. 15";
               }
             }
           }
         }
       }
       container memory {
         description "Memory load configurations";
         uses apply-advanced;
         container low {
           description "Low threshold configuration";
           uses apply-advanced;
           leaf percentage {
             description "Low threshold";
             units "Percentage";
             type union {
               type string {
                 pattern "<.*>|$.*";
               }
               type uint32 {
                 range "1 .. 100";
               }
             }
           }
           leaf priority-level {
             description "Priority level - default 10";
             default "10";
             type union {
               type string {
                 pattern "<.*>|$.*";
               }
               type uint32 {
                 range "1 .. 15";
               }
             }
           }
         }
         container high {
           description "High threshold configuration";
           uses apply-advanced;
           leaf percentage {
             description "High threshold";
             units "Percentage";
             type union {
               type string {
                 pattern "<.*>|$.*";
               }
               type uint32 {
                 range "1 .. 100";
               }
             }
           }
           leaf priority-level {
             description "Priority level - default 5";
             default "5";
             type union {
               type string {
                 pattern "<.*>|$.*";
               }
               type uint32 {
                 range "1 .. 15";
               }
             }
           }
         }
       }
       container cpu {
         description "CPU load configurations";
         uses apply-advanced;
         container low {
           description "Low threshold configuration";
           uses apply-advanced;
           leaf percentage {
             description "Low threshold";
             units "Percentage";
             type union {
               type string {
                 pattern "<.*>|$.*";
               }
               type uint32 {
                 range "1 .. 100";
               }
             }
           }
           leaf priority-level {
             description "Priority level - default 10";
             default "10";
             type union {
               type string {
                 pattern "<.*>|$.*";
               }
               type uint32 {
                 range "1 .. 15";
               }
             }
           }
         }
         container high {
           description "High threshold configuration";
           uses apply-advanced;
           leaf percentage {
             description "High threshold";
             units "Percentage";
             type union {
               type string {
                 pattern "<.*>|$.*";
               }
               type uint32 {
                 range "1 .. 100";
               }
             }
           }
           leaf priority-level {
             description "Priority level - default 5";
             default "5";
             type union {
               type string {
                 pattern "<.*>|$.*";
               }
               type uint32 {
                 range "1 .. 15";
               }
             }
           }
         }
       }
     }
     list cos-policy-profiles {
       key name;
       ordered-by user;
       description "QoS policy profile";
       max-elements 8001;
       leaf name {
         description "QoS policy profile name";
         type string {
           junos:posix-pattern "^.{1,64}$";
           junos:pattern-message "Must be string of 64 characters or less";
         }
       }
       uses apply-advanced;
       leaf description {
         description "Text description of cos policy";
         type string;
       }
       container default-bearer-qci {
         description "Default bearer qci value";
         leaf qci-value {
           description "Default bearer qci value";
           type union {
             type string {
               pattern "<.*>|$.*";
             }
             type uint8 {
               range "5 .. 9";
             }
           }
         }
         leaf upgrade {
           description "Override qci value";
           type empty;
         }
         leaf reject {
           description "Reject calls with numerially lower qci";
           type empty;
         }
       }
       container allocation-retention-priority {
         description "ARP local policy";
         leaf priority-value {
           description "ARP policy configuration";
           type union {
             type string {
               pattern "<.*>|$.*";
             }
             type uint8 {
               range "1 .. 15";
             }
           }
         }
         leaf reject {
           description "Reject calls with higher priority value";
           type empty;
         }
       }
       container aggregated-qos-control {
         description "Aggregated qos control policy";
         uses apply-advanced;
         container maximum-bit-rate-uplink {
           description "Maximum bit rate uplink";
           leaf mbr-uplink {
             units "kbps";
             type union {
               type string {
                 pattern "<.*>|$.*";
               }
               type uint32 {
                 range "1 .. 1000000";
               }
             }
           }
           leaf upgrade {
             description "Override maximum-bit-rate uplink value";
             type empty;
           }
           leaf reject {
             description "Reject calls with higher uplink maximum-bit-rate";
             type empty;
           }
         }
         container maximum-bit-rate-downlink {
           description "Maximum bit rate downlink";
           leaf mbr-downlink {
             units "kbps";
             type union {
               type string {
                 pattern "<.*>|$.*";
               }
               type uint32 {
                 range "1 .. 1000000";
               }
             }
           }
           leaf upgrade {
             description "Override maximum-bit-rate downlink value";
             type empty;
           }
           leaf reject {
             description "Reject calls with higher downlink maximum-bit-rate";
             type empty;
           }
         }
       }
       container pdp-qos-control {
         description "PDP qos control";
         uses apply-advanced;
         container maximum-bit-rate-uplink {
           description "Maximum bit rate uplink";
           leaf mbr-uplink {
             units "kbps";
             type union {
               type string {
                 pattern "<.*>|$.*";
               }
               type uint32 {
                 range "1 .. 10480000";
               }
             }
           }
           leaf upgrade {
             description "Override maximum-bit-rate uplink value";
             type empty;
           }
           leaf reject {
             description "Reject calls with higher uplink maximum-bit-rate";
             type empty;
           }
         }
         container maximum-bit-rate-downlink {
           description "Maximum bit rate downlink";
           leaf mbr-downlink {
             units "kbps";
             type union {
               type string {
                 pattern "<.*>|$.*";
               }
               type uint32 {
                 range "1 .. 10480000";
               }
             }
           }
           leaf upgrade {
             description "Override maximum-bit-rate downlink value";
             type empty;
           }
           leaf reject {
             description "Reject calls with higher downlink maximum-bit-rate";
             type empty;
           }
         }
         container guaranteed-bit-rate-uplink {
           description "Guaranteed bit rate uplink";
           leaf gbr-uplink {
             units "kbps";
             type union {
               type string {
                 pattern "<.*>|$.*";
               }
               type uint32 {
                 range "1 .. 10480000";
               }
             }
           }
           leaf upgrade {
             description "Override guaranteed-bit-rate uplink value";
             type empty;
           }
           leaf reject {
             description "Reject calls with higher uplink guaranteed-bit-rate";
             type empty;
           }
         }
         container guaranteed-bit-rate-downlink {
           description "Guaranteed bit rate downlink";
           leaf gbr-downlink {
             units "kbps";
             type union {
               type string {
                 pattern "<.*>|$.*";
               }
               type uint32 {
                 range "1 .. 10480000";
               }
             }
           }
           leaf upgrade {
             description "Override guaranteed-bit-rate downlink value";
             type empty;
           }
           leaf reject {
             description "Reject calls with higher downlink guaranteed-bit-rate";
             type empty;
           }
         }
         list qci {
           key name;
           ordered-by user;
           description "PDP qos control per qci";
           leaf name {
             type union {
               type string {
                 pattern "<.*>|$.*";
               }
               type uint8 {
                 range "5 .. 9";
               }
             }
           }
           uses apply-advanced;
           container maximum-bit-rate-uplink {
             description "Maximum bit rate uplink";
             leaf mbr-uplink {
               units "kbps";
               type union {
                 type string {
                   pattern "<.*>|$.*";
                 }
                 type uint32 {
                   range "1 .. 10480000";
                 }
               }
             }
             leaf upgrade {
               description "Override maximum-bit-rate uplink value";
               type empty;
             }
             leaf reject {
               description "Reject calls with higher uplink maximum-bit-rate";
               type empty;
             }
           }
           container maximum-bit-rate-downlink {
             description "Maximum bit rate downlink";
             leaf mbr-downlink {
               units "kbps";
               type union {
                 type string {
                   pattern "<.*>|$.*";
                 }
                 type uint32 {
                   range "1 .. 10480000";
                 }
               }
             }
             leaf upgrade {
               description "Override maximum-bit-rate downlink value";
               type empty;
             }
             leaf reject {
               description "Reject calls with higher downlink maximum-bit-rate";
               type empty;
             }
           }
         }
       }
       container policer-action {
         description "Policer actions";
         uses apply-advanced;
         container non-gbr-bearer {
           description "Policer actions for non gbr bearers";
           uses apply-advanced;
           leaf violate-action {
             description "PDP policer violate action";
             type enumeration {
               enum "set-loss-priority-high" {
                 description "Violate action set loss priority high";
               }
               enum "transmit" {
                 description "Violate action transmit";
               }
             }
           }
         }
         container gbr-bearer {
           description "Policer actions for gbr bearers";
           uses apply-advanced;
           leaf exceed-action {
             description "PDP policer exceed action";
             type enumeration {
               enum "drop" {
                 description "Exceed action drop";
               }
               enum "transmit" {
                 description "Exceed action transmit";
               }
             }
           }
           leaf violate-action {
             description "PDP policer violate action";
             type enumeration {
               enum "set-loss-priority-high" {
                 description "Violate action set loss priority high";
               }
               enum "transmit" {
                 description "Violate action transmit";
               }
             }
           }
         }
       }
     }
   }
   grouping macro-data-type {
     leaf name {
       description "Keyword part of the keyword-value pair";
       type string;
     }
     leaf value {
       description "Value part of the keyword-value pair";
       type string;
     }
   }
 }
