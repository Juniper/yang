/*
 * Copyright (c) 2021 Juniper Networks, Inc.
 * All rights reserved.
 */
 module junos-qfx-conf-security {
   namespace "http://yang.juniper.net/junos-qfx/conf/security";

   prefix jc-security;

   import junos-common-ddl-extensions {
     prefix junos;
     revision-date 2019-01-01;
   }

   import junos-common-types {
     prefix jt;
     revision-date 2019-01-01;
   }

   import junos-qfx-conf-root {
     prefix jc;
     revision-date 2019-01-01;
   }

   organization "Juniper Networks, Inc.";

   contact "yang-support@juniper.net";

   description "Junos security configuration module";

   revision 2019-01-01 {
     description "Junos: 21.3R1.9";
   }

   augment /jc:configuration {
     uses security-group;
   }
   augment /jc:configuration/jc:groups {
     uses security-group;
   }
   grouping security-group {
     container security {
       description "Security configuration";
       uses apply-advanced;
       container alarms {
         description "Configure security alarms";
         uses apply-advanced;
         container audible {
           presence "enable audible";
           description "Beep when new security alarms arrive";
           uses apply-advanced;
           leaf continuous {
             description "Keep beeping until all security alarms have been cleared";
             type empty;
           }
         }
         container potential-violation {
           description "Configure potential security violations";
           uses apply-advanced;
           leaf authentication {
             description "Raise alarm for specified number of authentication failures";
             type union {
               type string {
                 pattern "<.*>|$.*";
               }
               type uint32 {
                 range "2 .. 10";
               }
             }
           }
           leaf cryptographic-self-test {
             description "Raise alarm for cryptographic self test failures";
             type empty;
           }
           leaf key-generation-self-test {
             description "Raise alarm for key generation self test failures";
             type empty;
           }
           leaf non-cryptographic-self-test {
             description "Raise alarm for non-cryptographic self test failures";
             type empty;
           }
           container policy {
             description "Raise alarm for flow policy violations";
           }
           container replay-attacks {
             presence "enable replay-attacks";
             description "No. of Replay attacks before which an alarm needs to be raised";
             uses apply-advanced;
             leaf threshold {
               description "Replay threshold value";
               default "1000";
               type union {
                 type string {
                   pattern "<.*>|$.*";
                 }
                 type uint32 {
                   range "1 .. 1000000000";
                 }
               }
             }
           }
           leaf security-log-percent-full {
             description "Raise alarm when security log exceeds this percent capacity";
             type union {
               type string {
                 pattern "<.*>|$.*";
               }
               type uint8 {
                 range "0 .. 100";
               }
             }
           }
         }
       }
       container log {
         description "Configure auditable security logs";
         uses log-object;
       }
       container certificates {
         description "X.509 certificate configuration";
         uses apply-advanced;
         list local {
           key name;
           ordered-by user;
           description "Local X.509 certificate configuration";
           uses certificate-object;
         }
         leaf path-length {
           description "Maximum certificate path length";
           default "15";
           type union {
             type string {
               pattern "<.*>|$.*";
             }
             type uint32 {
               range "0 .. 15";
             }
           }
         }
         leaf maximum-certificates {
           description "Maximum number of certificates to cache";
           default "1024";
           type union {
             type string {
               pattern "<.*>|$.*";
             }
             type uint32 {
               range "64 .. 4294967295";
             }
           }
         }
         leaf cache-size {
           description "Maximum size of certificate cache";
           units "bytes";
           type string;
         }
         leaf cache-timeout-negative {
           description "Time in seconds to cache negative responses";
           default "20";
           type union {
             type string {
               pattern "<.*>|$.*";
             }
             type uint32 {
               range "10 .. 4294967295";
             }
           }
         }
         leaf enrollment-retry {
           description "Number of retry attempts for an enrollment request";
           type union {
             type string {
               pattern "<.*>|$.*";
             }
             type uint32 {
               range "0 .. 1080";
             }
           }
         }
         list certification-authority {
           key name;
           ordered-by user;
           description "CA X.509 certificate configuration";
           leaf name {
             description "CA profile name";
             type string {
               junos:posix-pattern "^.{1,32}$";
               junos:pattern-message "Must be string of 32 characters or less";
             }
           }
           uses apply-advanced;
           leaf ca-name {
             description "CA name";
             type string;
           }
           leaf file {
             description "File to read certificate from";
             type string;
           }
           leaf crl {
             description "File to read crl from";
             type string;
           }
           leaf enrollment-url {
             description "URL";
             type string;
           }
           leaf ldap-url {
             description "URL";
             type string;
           }
           leaf encoding {
             description "Encoding to use for certificate or CRL on disk";
             default "binary";
             type enumeration {
               enum "binary" {
                 description "DER encoding";
               }
               enum "pem" {
                 description "Privacy-enhanced-mail encoding, base64";
               }
             }
           }
         }
       }
       container authentication-key-chains {
         description "Authentication key chain configuration";
         uses security-authentication-key-chains;
       }
       container ssh-known-hosts {
         description "SSH known host list";
         uses apply-advanced;
         list host {
           key name;
           ordered-by user;
           description "SSH known host entry";
           leaf name {
             description "Host name";
             type string;
           }
           uses apply-advanced;
           leaf rsa1-key {
             description "Base64 encoded RSA key (protocol version 1)";
             type string;
           }
           leaf rsa-key {
             description "Base64 encoded RSA key";
             type string;
           }
           leaf dsa-key {
             description "Base64 encoded DSA key";
             type string;
           }
           leaf ecdsa-key {
             description "Base64 encoded ECDSA key";
             status deprecated;
             type string;
           }
           leaf ecdsa-sha2-nistp256-key {
             description "Base64 encoded ECDSA-SHA2-NIST256 key";
             type string;
           }
           leaf ecdsa-sha2-nistp384-key {
             description "Base64 encoded ECDSA-SHA2-NIST384 key";
             type string;
           }
           leaf ecdsa-sha2-nistp521-key {
             description "Base64 encoded ECDSA-SHA2-NIST521 key";
             type string;
           }
           leaf ed25519-key {
             description "Base64 encoded ED25519 key";
             type string;
           }
         }
       }
       container pki {
         description "PKI service configuration";
         presence "enable pki";
         uses security-pki;
       }
       container group-vpn {
         description "Group VPN configuration";
         uses security-group-vpn;
       }
       container traceoptions {
         description "Trace options for IPSec key management";
         uses security-traceoptions;
       }
       container ipsec {
         description "IPSec configuration";
         uses security-ipsec-vpn;
       }
       container ike {
         description "IKE configuration";
         uses security-ike;
       }
       container idp {
         description "IDP configuration";
         list idp-policy {
           key name;
           ordered-by user;
           description "Configure IDP policy";
           uses idp-policy-type;
         }
         leaf active-policy {
           description "Set active policy";
           status deprecated;
           junos:must "(\"security idp idp-policy $$\")";
           junos:must-message "Policy must be defined under [security idp idp-policy] ";
           type string;
         }
         leaf default-policy {
           description "Set active policy";
           junos:must "(\"security idp idp-policy $$\")";
           junos:must-message "Policy must be defined under [security idp idp-policy] ";
           type string;
         }
         list custom-attack {
           key name;
           ordered-by user;
           description "Configure custom attacks";
           uses custom-attack-type;
         }
         list custom-attack-group {
           key name;
           ordered-by user;
           description "Configure custom attack groups";
           uses custom-attack-group-type;
         }
         list dynamic-attack-group {
           key name;
           ordered-by user;
           description "Configure dynamic attack groups";
           uses dynamic-attack-group-type;
         }
         container traceoptions {
           description "Trace options for idp services";
           uses idpd-traceoptions-type;
         }
         container security-package {
           description "Security package options";
           uses apply-advanced;
           leaf url {
             description "URL of Security package download";
             type string;
           }
           leaf source-address {
             description "Source address to be used for sending download request";
             type jt:ipv4addr;
           }
           leaf proxy-profile {
             description "Proxy profile of security package download";
             junos:must "(\"services proxy profile $$\")";
             junos:must-message "Referenced Proxy profile must be defined under [services proxy profile] path";
             type string {
               length "1 .. 64";
             }
           }
           leaf routing-instance {
             description "Routing instance for security-package download";
             junos:must "(\"routing-instances $$\")";
             junos:must-message "Routing-instance must be defined";
             type string;
           }
           container install {
             presence "enable install";
             description "Configure install command";
             uses apply-advanced;
             leaf ignore-version-check {
               description "Skip version check  when attack database gets installed";
               type empty;
             }
             leaf ignore-appid-failure {
               description "Continue idp installation even if appid installation fails";
               type empty;
             }
           }
           container automatic {
             presence "enable automatic";
             description "Scheduled download and update";
             uses apply-advanced;
             leaf start-time {
               description "Start time (YYYY-MM-DD.HH:MM:SS)";
               type jt:time;
             }
             leaf interval {
               description "Interval";
               units "hours";
               type union {
                 type string {
                   pattern "<.*>|$.*";
                 }
                 type uint32 {
                   range "1 .. 336";
                 }
               }
             }
             leaf download-timeout {
               description "Maximum time for download to complete";
               status deprecated;
               default "1";
               units "minutes";
               type union {
                 type string {
                   pattern "<.*>|$.*";
                 }
                 type uint32 {
                   range "1 .. 60";
                 }
               }
             }
             choice enable-disable {
               case case_1 {
                 leaf enable {
                   description "Enable";
                   type empty;
                 }
               }
             }
           }
         }
         container sensor-configuration {
           description "IDP Sensor Configuration";
           container log {
             description "IDP Log Configuration";
             uses apply-advanced;
             leaf cache-size {
               description "Log cache size";
               type union {
                 type string {
                   pattern "<.*>|$.*";
                 }
                 type uint32;
               }
             }
             container suppression {
               presence "enable suppression";
               description "Log suppression";
               uses apply-advanced;
               choice enable-disable {
                 case case_1 {
                   leaf disable {
                     description "Disable log suppression";
                     type empty;
                   }
                 }
               }
               choice include-destination-address-choice {
                 leaf include-destination-address {
                   description "Include destination address while performing a log suppression";
                   type empty;
                 }
                 leaf no-include-destination-address {
                   description "Don't include destination address while performing a log suppression";
                   type empty;
                 }
               }
               leaf start-log {
                 description "Suppression start log";
                 type union {
                   type string {
                     pattern "<.*>|$.*";
                   }
                   type uint32;
                 }
               }
               leaf max-logs-operate {
                 description "Maximum logs can be operate on";
                 type union {
                   type string {
                     pattern "<.*>|$.*";
                   }
                   type uint32;
                 }
               }
               leaf max-time-report {
                 description "Time after suppressed logs will be reported";
                 type union {
                   type string {
                     pattern "<.*>|$.*";
                   }
                   type uint32;
                 }
               }
             }
           }
           container packet-log {
             description "IDP Packetlog Configuration";
             uses apply-advanced;
             container total-memory {
               description "Total memory unit(%)";
               uses apply-advanced;
               leaf percentage-value {
                 type union {
                   type string {
                     pattern "<.*>|$.*";
                   }
                   type uint32;
                 }
               }
               leaf per-logical-domain {
                 type union {
                   type string {
                     pattern "<.*>|$.*";
                   }
                   type uint32;
                 }
               }
             }
             container max-sessions {
               description "Max num of sessions in unit(%)";
               uses apply-advanced;
               leaf percentage-value {
                 type union {
                   type string {
                     pattern "<.*>|$.*";
                   }
                   type uint32;
                 }
               }
               leaf per-logical-domain {
                 type union {
                   type string {
                     pattern "<.*>|$.*";
                   }
                   type uint32;
                 }
               }
             }
             leaf threshold-logging-interval {
               description "Interval of logs for max limit session/memory reached in minutes";
               type union {
                 type string {
                   pattern "<.*>|$.*";
                 }
                 type uint32;
               }
             }
             leaf source-address {
               description "Source IP address used to transport packetlog to a host";
               type jt:ipv4addr;
             }
             container host {
               description "Destination host to send packetlog to";
               uses apply-advanced;
               leaf ipaddr {
                 description "IP address";
                 type jt:ipv4addr;
               }
               leaf port {
                 description "UDP port number";
                 type union {
                   type uint16;
                   type string {
                     pattern "<.*>|$.*";
                   }
                 }
               }
             }
           }
           container application-identification {
             presence "enable application-identification";
             description "Application identification";
             uses apply-advanced;
             choice enable-disable {
               case case_1 {
                 leaf disable {
                   description "Disable application identification";
                   type empty;
                 }
               }
             }
             leaf max-tcp-session-packet-memory {
               description "Max TCP session memory";
               status deprecated;
               type union {
                 type string {
                   pattern "<.*>|$.*";
                 }
                 type uint32;
               }
             }
             leaf max-udp-session-packet-memory {
               description "Max UDP session memory";
               status deprecated;
               type union {
                 type string {
                   pattern "<.*>|$.*";
                 }
                 type uint32;
               }
             }
             leaf max-packet-memory {
               description "Max packet memory";
               status deprecated;
               type union {
                 type string {
                   pattern "<.*>|$.*";
                 }
                 type uint32;
               }
             }
             leaf max-packet-memory-ratio {
               description "Max packet memory ratio";
               type union {
                 type string {
                   pattern "<.*>|$.*";
                 }
                 type uint32;
               }
             }
             leaf max-reass-packet-memory-ratio {
               description "Max reass packet memory ratio";
               status deprecated;
               type union {
                 type string {
                   pattern "<.*>|$.*";
                 }
                 type uint32;
               }
             }
           }
           container flow {
             description "Flow configuration";
             uses apply-advanced;
             choice log-errors-choice {
               leaf log-errors {
                 description "Flow log errors";
                 type empty;
               }
               leaf no-log-errors {
                 description "Don't flow log errors";
                 type empty;
               }
             }
             choice allow-icmp-without-flow-choice {
               leaf allow-icmp-without-flow {
                 description "Allow icmp without flow";
                 status deprecated;
                 type empty;
               }
               leaf no-allow-icmp-without-flow {
                 description "Don't allow icmp without flow";
                 status deprecated;
                 type empty;
               }
             }
             leaf hash-table-size {
               description "Flow hash table size";
               type union {
                 type string {
                   pattern "<.*>|$.*";
                 }
                 type uint32;
               }
             }
             leaf reject-timeout {
               description "Flow reject timeout";
               type union {
                 type string {
                   pattern "<.*>|$.*";
                 }
                 type uint32;
               }
             }
             leaf max-timers-poll-ticks {
               description "Maximum timers poll ticks";
               type union {
                 type string {
                   pattern "<.*>|$.*";
                 }
                 type uint32;
               }
             }
             leaf fifo-max-size {
               description "Maximum fifo size";
               type union {
                 type string {
                   pattern "<.*>|$.*";
                 }
                 type uint32;
               }
             }
             leaf udp-anticipated-timeout {
               description "Maximum udp anticipated timeout";
               type union {
                 type string {
                   pattern "<.*>|$.*";
                 }
                 type uint32;
               }
             }
             leaf drop-on-limit {
               description "Drop connections on exceeding resource limits";
               type empty;
             }
             leaf drop-on-failover {
               description "Drop traffic on HA failover sessions";
               type empty;
             }
             leaf drop-if-no-policy-loaded {
               description "Drop all traffic till IDP policy gets loaded";
               type empty;
             }
             leaf max-sessions-offset {
               description "Maximum session offset limit percentage";
               type union {
                 type string {
                   pattern "<.*>|$.*";
                 }
                 type uint32;
               }
             }
             leaf min-objcache-limit-lt {
               description "Memory lower threshold limit percentage";
               type union {
                 type string {
                   pattern "<.*>|$.*";
                 }
                 type uint32;
               }
             }
             leaf min-objcache-limit-ut {
               description "Memory upper threshold limit percentage";
               type union {
                 type string {
                   pattern "<.*>|$.*";
                 }
                 type uint32;
               }
             }
             leaf session-steering {
               description "Session steering for session anticipation";
               type empty;
             }
             leaf idp-bypass-cpu-usg-overload {
               description "Enable IDP bypass of sessions/packets on CPU usage overload";
               type empty;
             }
             leaf idp-bypass-cpu-threshold {
               description "Threshold of CPU usage in percentage for IDP bypass";
               default "85";
               type union {
                 type string {
                   pattern "<.*>|$.*";
                 }
                 type uint32;
               }
             }
             leaf idp-bypass-cpu-tolerance {
               description "Tolerance of CPU usage in percentage for IDP bypass";
               default "5";
               type union {
                 type string {
                   pattern "<.*>|$.*";
                 }
                 type uint32;
               }
             }
             leaf intel-inspect-cpu-usg-threshold {
               description "CPU usage threshold percentage for intelligent inspection";
               default "80";
               type union {
                 type string {
                   pattern "<.*>|$.*";
                 }
                 type uint32;
               }
             }
             leaf intel-inspect-cpu-usg-tolerance {
               description "CPU usage tolerance percentage for intelligent inspection";
               default "5";
               type union {
                 type string {
                   pattern "<.*>|$.*";
                 }
                 type uint32;
               }
             }
             leaf intel-inspect-free-mem-threshold {
               description "Free memory threshold percentage for intelligent inspection";
               default "15";
               type union {
                 type string {
                   pattern "<.*>|$.*";
                 }
                 type uint32;
               }
             }
             leaf intel-inspect-mem-tolerance {
               description "Memory tolerance percentage for intelligent inspection";
               default "5";
               type union {
                 type string {
                   pattern "<.*>|$.*";
                 }
                 type uint32;
               }
             }
             leaf-list intel-inspect-protocols {
               ordered-by user;
               description "Protocols to be processed in Intelligent Inspection mode";
               type string;
             }
           }
           container re-assembler {
             description "Re-assembler configuration";
             uses apply-advanced;
             choice drop-on-syn-in-window-choice {
               leaf drop-on-syn-in-window {
                 description "Drop session when SYN is seen in the window";
                 type empty;
               }
               leaf no-drop-on-syn-in-window {
                 description "Don't drop session when SYN is seen in the window";
                 type empty;
               }
             }
             choice ignore-memory-overflow-choice {
               leaf ignore-memory-overflow {
                 description "Ignore memory overflow";
                 type empty;
               }
               leaf no-ignore-memory-overflow {
                 description "Don't ignore memory overflow";
                 type empty;
               }
             }
             choice ignore-reassembly-memory-overflow-choice {
               leaf ignore-reassembly-memory-overflow {
                 description "Ignore packet reassembly memory overflow";
                 type empty;
               }
               leaf no-ignore-reassembly-memory-overflow {
                 description "Don't ignore packet reassembly memory overflow";
                 type empty;
               }
             }
             leaf ignore-reassembly-overflow {
               description "Ignore global reassembly overflow";
               type empty;
             }
             leaf max-packet-mem {
               description "Maximum packet memory";
               status deprecated;
               type union {
                 type string {
                   pattern "<.*>|$.*";
                 }
                 type uint32;
               }
             }
             leaf max-flow-mem {
               description "Maximum flow memory";
               type union {
                 type string {
                   pattern "<.*>|$.*";
                 }
                 type uint32;
               }
             }
             leaf max-packet-mem-ratio {
               description "Maximum packet memory ratio";
               type union {
                 type string {
                   pattern "<.*>|$.*";
                 }
                 type uint32;
               }
             }
             leaf action-on-reassembly-failure {
               description "Select the action on reassembly failures";
               default "drop";
               type enumeration {
                 enum "ignore" {
                   description "No action is taken.";
                 }
                 enum "drop" {
                   description "Drop the packet.";
                 }
                 enum "drop-session" {
                   description "Drop the session.";
                 }
               }
             }
             choice tcp-error-logging-choice {
               leaf tcp-error-logging {
                 description "Enable logging on tcp errors";
                 type empty;
               }
               leaf no-tcp-error-logging {
                 description "Don't enable logging on tcp errors";
                 type empty;
               }
             }
             leaf max-synacks-queued {
               description "Maximum syn-acks queued with different SEQ numbers ";
               type union {
                 type string {
                   pattern "<.*>|$.*";
                 }
                 type uint32;
               }
             }
             choice force-tcp-window-checks-choice {
               leaf force-tcp-window-checks {
                 description "Force TCP window checks if uni-directional policy is configured";
                 type empty;
               }
               leaf no-force-tcp-window-checks {
                 description "Don't force TCP window checks if uni-directional policy is configured";
                 type empty;
               }
             }
           }
           container ips {
             description "Ips configuration";
             uses apply-advanced;
             choice process-override-choice {
               leaf process-override {
                 description "Process override";
                 type empty;
               }
               leaf no-process-override {
                 description "Don't process override";
                 type empty;
               }
             }
             choice detect-shellcode-choice {
               leaf detect-shellcode {
                 description "Detect shellcode";
                 type empty;
               }
               leaf no-detect-shellcode {
                 description "Don't detect shellcode";
                 type empty;
               }
             }
             choice process-ignore-s2c-choice {
               leaf process-ignore-s2c {
                 description "Process ignore s2c";
                 type empty;
               }
               leaf no-process-ignore-s2c {
                 description "Don't process ignore s2c";
                 type empty;
               }
             }
             choice ignore-regular-expression-choice {
               leaf ignore-regular-expression {
                 description "Ignore regular expression";
                 type empty;
               }
               leaf no-ignore-regular-expression {
                 description "Don't ignore regular expression";
                 type empty;
               }
             }
             leaf process-port {
               description "Process port";
               type union {
                 type string {
                   pattern "<.*>|$.*";
                 }
                 type uint32;
               }
             }
             leaf fifo-max-size {
               description "Maximum fifo size";
               type union {
                 type string {
                   pattern "<.*>|$.*";
                 }
                 type uint32;
               }
             }
             leaf log-supercede-min {
               description "Minimum log supercede";
               type union {
                 type string {
                   pattern "<.*>|$.*";
                 }
                 type uint32;
               }
             }
             leaf content-decompression-max-memory-kb {
               description "Maximum memory usage in kilo bytes";
               type union {
                 type string {
                   pattern "<.*>|$.*";
                 }
                 type uint32;
               }
             }
             leaf content-decompression-max-ratio {
               description "Maximum decompression ratio supported";
               type union {
                 type string {
                   pattern "<.*>|$.*";
                 }
                 type uint32;
               }
             }
             leaf session-pkt-depth {
               description "Session pkt scanning depth";
               type union {
                 type string {
                   pattern "<.*>|$.*";
                 }
                 type uint32;
               }
             }
           }
           container global {
             description "Global configuration";
             uses apply-advanced;
             choice enable-packet-pool-choice {
               leaf enable-packet-pool {
                 description "Enable packet pool";
                 type empty;
               }
               leaf no-enable-packet-pool {
                 description "Don't enable packet pool";
                 type empty;
               }
             }
             leaf log-xff-header {
               description "Log xff header";
               type empty;
             }
             choice enable-all-qmodules-choice {
               leaf enable-all-qmodules {
                 description "Enable all qmodules";
                 type empty;
               }
               leaf no-enable-all-qmodules {
                 description "Don't enable all qmodules";
                 type empty;
               }
             }
             choice policy-lookup-cache-choice {
               leaf policy-lookup-cache {
                 description "Policy lookup cache";
                 type empty;
               }
               leaf no-policy-lookup-cache {
                 description "Don't policy lookup cache";
                 type empty;
               }
             }
             leaf memory-limit-percent {
               description "Memory limit percentage";
               type union {
                 type string {
                   pattern "<.*>|$.*";
                 }
                 type uint32;
               }
             }
             leaf disable-idp-processing {
               description "Flag to disable IDP processing";
               type empty;
             }
             leaf intelligent-offload {
               description "Intelligently offload the flow";
               type enumeration {
                 enum "disable" {
                   description "Disable flow offload";
                 }
                 enum "conservative" {
                   description "Increases scrutiny of flows prior to offload";
                 }
               }
             }
           }
           container detector {
             description "Detector Configuration";
             uses apply-advanced;
             list protocol-name {
               key name;
               ordered-by user;
               description "Apropriate help string";
               uses proto-object;
             }
           }
           container high-availability {
             description "High availability configuration";
             uses apply-advanced;
             leaf no-policy-cold-synchronization {
               description "Disable policy cold synchronization";
               type empty;
             }
           }
           container security-configuration {
             description "IDP security configuration";
             uses apply-advanced;
             leaf protection-mode {
               description "Enable security protection mode";
               type enumeration {
                 enum "datacenter" {
                   description "Security protection mode for datacenter";
                 }
                 enum "datacenter-full" {
                   description "Full security protection mode for datacenter";
                 }
                 enum "perimeter" {
                   description "Security protection mode for perimeter";
                 }
                 enum "perimeter-full" {
                   description "Full security protection mode for perimeter";
                 }
               }
             }
           }
         }
         leaf max-sessions {
           description "Max number of IDP sessions";
           type union {
             type uint32;
             type string {
               pattern "<.*>|$.*";
             }
           }
         }
         list logical-system {
           key name;
           ordered-by user;
           description "Configure max IDP sessions for the logial system";
           uses logical-system-type;
         }
         list tenant-system {
           key name;
           ordered-by user;
           description "Configure max IDP sessions for the tenant";
           uses tenant-system-type;
         }
       }
       container macsec {
         description "MAC Security configuration";
         uses security-macsec;
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping certificate-object {
     leaf name {
       description "Simple name to identify this certificate";
       type string;
     }
     uses apply-advanced;
     leaf certificate {
       description "Certificate and private key string";
       type string;
     }
   }
   grouping custom-attack-group-type {
     description "Define custom attack group";
     leaf name {
       description "Custom attack group name";
       type string;
     }
     uses apply-advanced;
     leaf attack-group-description {
       description "Attack group description in xml format";
       status deprecated;
       type string;
     }
     leaf-list group-members {
       ordered-by user;
       description "List of attacks/attack groups belonging to this group";
       type string;
     }
   }
   grouping custom-attack-type {
     description "Define custom attack";
     leaf name {
       description "Custom attack name";
       type string {
         junos:posix-pattern "^.{1,60}$";
         junos:pattern-message "Custom attack name must be a string of 60 characters or less";
       }
     }
     uses apply-advanced;
     leaf-list attack-description {
       ordered-by user;
       description "Attack description";
       type string;
     }
     leaf recommended-action {
       description "Recommended Action";
       type enumeration {
         enum "none" {
           description "No action";
         }
         enum "ignore" {
           description "No further inspection on the flow";
         }
         enum "drop-packet" {
           description "Drop the packet";
         }
         enum "drop" {
           description "Drop the packet and subsequent packets of the flow";
         }
         enum "close-client" {
           description "Reset the client side";
         }
         enum "close-server" {
           description "Reset the server side";
         }
         enum "close" {
           description "Reset both client and server";
         }
       }
     }
     leaf severity {
       description "Select the severity that matches the lethality of this attack on your network";
       type enumeration {
         enum "info" {
           description "Provide information of attack when it matches.";
         }
         enum "warning" {
           description "Issue a warning when attack matches.";
         }
         enum "minor" {
           description "The attack is a  minor one.";
         }
         enum "major" {
           description "The attack is a major one.";
         }
         enum "critical" {
           description "The attack is a critical one.";
         }
       }
     }
     container time-binding {
       description "Time binding params";
       leaf count {
         description "Number of times this attack is to be triggered";
         type union {
           type uint32;
           type string {
             pattern "<.*>|$.*";
           }
         }
       }
       leaf scope {
         description "Scope within which the count occurs";
         junos:must "((!(\".. count 0\") && !(\".. count 1\")))";
         junos:must-message "Scope should be defined if count > 1";
         type enumeration {
           enum "peer" {
             description "If the attack is between a single source and single destination";
           }
           enum "source" {
             description "If the attack is from one source and multiple destination";
           }
           enum "destination" {
             description "If the attack is from multiple sources to one destination";
           }
         }
       }
       leaf interval {
         description "Maximum time-gap between two instances of the attack. Format : MMm-SSs";
         default "01m-00s";
         junos:must "((!(\".. count 0\") && (!(\".. count 1\") && (\".. count\" && \".. scope\"))))";
         junos:must-message "To configure interval, count & scope should be set and count should be greater than or equal to 2";
         type string {
           junos:posix-pattern "^((([0-5][0-9])[m][-]([0-5][0-9])[s])|([6][0][m][-][0][0][s]))$";
           junos:pattern-message "Invalid interval format: Correct format MMm-SSs, with minutes range 00-60, seconds range 00-59";
         }
       }
     }
     container detection-filter {
       junos:must "(!(\".. time-binding\"))";
       junos:must-message "Time-binding and detection-filter will not be allowed together";
       description "Detection filter params";
       leaf count {
         description "Number of matches for this attack to be triggered. Must be greater than 0";
         type union {
           type uint32;
           type string {
             pattern "<.*>|$.*";
           }
         }
       }
       leaf scope {
         description "Scope within which the count occurs";
         type enumeration {
           enum "session" {
             description "If the attack is between a single source and single destination";
           }
           enum "source" {
             description "If the attack is from one source and multiple destination";
           }
           enum "destination" {
             description "If the attack is from multiple sources to one destination";
           }
         }
       }
       leaf interval {
         description "Time period over which count is accrued. Format : MMm-SSs. Minimum value is 1 second";
         type string {
           junos:posix-pattern "^((([0-5][0-9])[m][-]([0-5][0-9])[s])|([6][0][m][-][0][0][s]))$";
           junos:pattern-message "Invalid interval format: Correct format MMm-SSs, with minutes range 00-60, seconds range 00-59";
         }
       }
     }
     container attack-type {
       description "Type of attack";
       uses apply-advanced;
       container signature {
         junos:must "(!((\".. anomaly\" || \".. chain\")))";
         junos:must-message "Only one attack type is permitted";
         description "Signature based attack";
         uses apply-advanced;
         container protocol-binding {
           description "Protocol binding over which attack will be detected";
           uses apply-advanced;
           choice protocol {
             case case_1 {
               container tcp {
                 presence "enable tcp";
                 description "Attack is for TCP packets only";
                 uses apply-advanced;
                 list minimum-port {
                   key name;
                   ordered-by user;
                   description "Multiple sets of (single port/port ranges) can be specified";
                   uses port-range;
                 }
               }
             }
             case case_2 {
               container udp {
                 presence "enable udp";
                 description "Attack is for UDP packets only";
                 uses apply-advanced;
                 list minimum-port {
                   key name;
                   ordered-by user;
                   description "Either single port or port ranges can be specified";
                   uses port-range;
                 }
               }
             }
             case case_3 {
               container rpc {
                 presence "enable rpc";
                 description "Attack is for RPC packets only";
                 uses apply-advanced;
                 leaf program-number {
                   description "RPC Program Number";
                   type union {
                     type uint32;
                     type string {
                       pattern "<.*>|$.*";
                     }
                   }
                 }
               }
             }
             case case_4 {
               leaf icmp {
                 description "Attack is for ICMP packets only";
                 type empty;
               }
             }
             case case_5 {
               leaf icmpv6 {
                 description "Attack is for ICMPv6 packets only";
                 type empty;
               }
             }
             case case_6 {
               container ip {
                 presence "enable ip";
                 description "Attack is for all IP based packets";
                 uses apply-advanced;
                 leaf protocol-number {
                   description "Transport layer protocol number";
                   type union {
                     type string {
                       pattern "<.*>|$.*";
                     }
                     type uint32 {
                       range "0 .. 139";
                     }
                   }
                 }
               }
             }
             case case_7 {
               container ipv6 {
                 presence "enable ipv6";
                 description "Attack is for all IPv6 based packets";
                 uses apply-advanced;
                 leaf protocol-number {
                   description "Transport layer protocol number";
                   type union {
                     type string {
                       pattern "<.*>|$.*";
                     }
                     type uint32 {
                       range "0 .. 139";
                     }
                   }
                 }
               }
             }
             case case_8 {
               leaf application {
                 description "Application name";
                 type string;
               }
             }
             case case_9 {
               leaf nested-application {
                 description "Nested application name";
                 status deprecated;
                 type string;
               }
             }
           }
         }
         leaf context {
           description "Context";
           type string;
         }
         leaf pattern {
           description "Pattern is the signature of the attack you want to detect";
           junos:must "(\".. context\")";
           junos:must-message "Context must be specified";
           type string {
             length "0 .. 511";
           }
         }
         leaf pattern-pcre {
           description "Attack signature pattern in PCRE format";
           junos:must "(\".. context\")";
           junos:must-message "Context must be specified";
           type string {
             length "0 .. 511";
           }
         }
         container content {
           junos:must "(\".. context\")";
           junos:must-message "Context must be specified";
           description "Mention the match-modifire parameters to enhance pattern matching";
           leaf pattern {
             description "Specify match-modifier pattern";
             type string;
           }
           leaf pcre {
             description "PCRE expression";
             type string {
               length "0 .. 511";
             }
           }
           container depth {
             junos:must "(\".. pattern\")";
             junos:must-message "Content pattern must be specified";
             description "Maximum depth to search pattern within a packet. Depth is not relative";
             leaf depth-value {
               description "Specify the value of 'depth'";
               type union {
                 type string {
                   pattern "<.*>|$.*";
                 }
                 type uint16 {
                   range "1 .. 65535";
                 }
               }
             }
             leaf depth-variable {
               description "Specify the variable name from which 'depth' should be extracted";
               type string;
             }
           }
           container offset {
             junos:must "(\".. pattern\")";
             junos:must-message "Content pattern must be specified";
             description "Where to start searching for a pattern within a packet. Offset value is not relative";
             leaf offset-value {
               description "Specify the value of 'offset'";
               type union {
                 type string {
                   pattern "<.*>|$.*";
                 }
                 type uint16 {
                   range "0 .. 65535";
                 }
               }
             }
             leaf offset-variable {
               description "Specify the variable name from which 'offset' should be extracted";
               type string;
             }
           }
           container within {
             junos:must "(\".. pattern\")";
             junos:must-message "Content pattern must be specified";
             description "Maximum Number of bytes present between two conjugative pattern match. within is  relative";
             leaf within-value {
               description "Specify the value of 'within'";
               type union {
                 type string {
                   pattern "<.*>|$.*";
                 }
                 type uint16 {
                   range "1 .. 65535";
                 }
               }
             }
             leaf within-variable {
               description "Specify the variable name from which 'within' should be extracted";
               type string;
             }
           }
           container distance {
             junos:must "(\".. pattern\")";
             junos:must-message "Content pattern must be specified";
             description "Maximum Length to ignore before searching next pattern match. Distance is  relative";
             leaf distance-value {
               description "Specify the value of 'distance'";
               type union {
                 type string {
                   pattern "<.*>|$.*";
                 }
                 type int32 {
                   range "-65535 .. 65535";
                 }
               }
             }
             leaf distance-variable {
               description "Specify the variable name from which 'distance' should be extracted";
               type string;
             }
           }
           container byte-extract {
             junos:must "(\".. pattern\")";
             junos:must-message "Content pattern must be specified";
             description "Mention the byte-extract parameters for signature in length encoded protocols";
             leaf bytes {
               description "Specify the number of bytes to extract from packet";
               type union {
                 type string {
                   pattern "<.*>|$.*";
                 }
                 type uint32 {
                   range "1 .. 10";
                 }
               }
             }
             leaf offset {
               description "Specify the number of bytes in to payload to start processing";
               type union {
                 type int32;
                 type string {
                   pattern "<.*>|$.*";
                 }
               }
             }
             leaf var-name {
               description "Specify the name of the variable to reference in other rule options";
               type string;
             }
             leaf relative {
               description "Specify whether to use an offset relative to last pattern match or not";
               type empty;
             }
             leaf multiplier {
               description "Specify the value to be multiplied against the bytes read";
               type union {
                 type uint16;
                 type string {
                   pattern "<.*>|$.*";
                 }
               }
             }
             leaf endianness {
               description "Specify the endianness with which bytes read should be processed";
               type enumeration {
                 enum "Little" {
                   description "Process data in little endian";
                 }
                 enum "Big" {
                   description "Process data in big endian";
                 }
               }
             }
             leaf align {
               description "Specify the byte alignment";
               type enumeration {
                 enum "2-byte" {
                   description "Round the number of converted bytes to 2-byte boundary";
                 }
                 enum "4-byte" {
                   description "Round the number of converted bytes to 4-byte boundary";
                 }
               }
             }
             leaf string {
               description "Specify the data type in which string data should be parsed";
               type enumeration {
                 enum "hex" {
                   description "Process data in hexadecimal format";
                 }
                 enum "dec" {
                   description "Process data in decimal format";
                 }
                 enum "oct" {
                   description "Process data in octal format";
                 }
               }
             }
             leaf bitmask {
               description "Specify the bitmask (1-4 bytes) for AND operation in hexadecimal format";
               type string;
             }
           }
           container byte-test {
             junos:must "(\".. pattern\")";
             junos:must-message "Content pattern must be specified";
             description "Mention the byte-test parameters for signature in length encoded protocols";
             leaf bytes {
               description "Specify the number of bytes to extract from packet";
               type union {
                 type string {
                   pattern "<.*>|$.*";
                 }
                 type uint32 {
                   range "1 .. 10";
                 }
               }
             }
             container offset {
               description "Mention the offset variable name or offset value to be used";
               leaf offset-value {
                 description "Specify the number of bytes in to payload to start processing";
                 type union {
                   type int32;
                   type string {
                     pattern "<.*>|$.*";
                   }
                 }
               }
               leaf offset-variable {
                 description "Specify the name of the offset variable";
                 type string;
               }
             }
             container rvalue {
               description "Specify the rvalue to test the converted value against";
               leaf rvalue-value {
                 description "Specify the value";
                 type union {
                   type uint32;
                   type string {
                     pattern "<.*>|$.*";
                   }
                 }
               }
               leaf rvalue-variable {
                 description "Specify the variable name";
                 type string;
               }
             }
             leaf relative {
               description "Specify whether to use an offset relative to last pattern match or not";
               type empty;
             }
             leaf operator {
               description "Specify the operation to perform on extracted value";
               type enumeration {
                 enum "less-than" {
                   description "Perform operation 'less than'";
                 }
                 enum "greater-than" {
                   description "Perform operation 'greater than'";
                 }
                 enum "less-than-or-equal" {
                   description "Perform operation 'less than or equal'";
                 }
                 enum "greater-than-or-equal" {
                   description "Perform operation 'greater than or equal'";
                 }
                 enum "equal" {
                   description "Perform operation 'equal'";
                 }
                 enum "bitwise-AND" {
                   description "Perform operation 'bitwise AND'";
                 }
                 enum "bitwise-XOR" {
                   description "Perform operation 'bitwise OR'";
                 }
               }
             }
             leaf negate {
               description "Check if the operator is not true";
               type empty;
             }
             leaf endianness {
               description "Specify the endianness with which bytes read should be processed";
               type enumeration {
                 enum "Little" {
                   description "Process data in little endian";
                 }
                 enum "Big" {
                   description "Process data in big endian";
                 }
               }
             }
             leaf string {
               description "Specify the data type in which string data should be parsed";
               type enumeration {
                 enum "hex" {
                   description "Process data in hexadecimal format";
                 }
                 enum "dec" {
                   description "Process data in decimal format";
                 }
                 enum "oct" {
                   description "Process data in octal format";
                 }
               }
             }
             leaf bitmask {
               description "Specify the bitmask (1-4 bytes) for AND operation in hexadecimal format";
               type string;
             }
           }
           container byte-math {
             junos:must "(\".. pattern\")";
             junos:must-message "Content pattern must be specified";
             description "Mention the byte-math parameters for signature in length encoded protocols";
             leaf bytes {
               description "Specify the number of bytes to extract from packet";
               type union {
                 type string {
                   pattern "<.*>|$.*";
                 }
                 type uint32 {
                   range "1 .. 10";
                 }
               }
             }
             leaf offset {
               description "Specify the number of bytes in to payload to start processing";
               type union {
                 type string {
                   pattern "<.*>|$.*";
                 }
                 type uint16 {
                   range "0 .. 65535";
                 }
               }
             }
             container rvalue {
               description "Specify the value to use mathematical operation against";
               leaf rvalue-value {
                 description "Specify the value";
                 type union {
                   type uint32;
                   type string {
                     pattern "<.*>|$.*";
                   }
                 }
               }
               leaf rvalue-variable {
                 description "Specify the variable name";
                 type string;
               }
             }
             leaf relative {
               description "Specify whether to use an offset relative to last pattern match or not";
               type empty;
             }
             leaf operator {
               description "Specify the operation to perform on extracted value";
               type enumeration {
                 enum "addition" {
                   description "Perform operation 'addition'";
                 }
                 enum "subtraction" {
                   description "Perform operation 'subtraction'";
                 }
                 enum "multiplication" {
                   description "Perform operation 'multiplication'";
                 }
                 enum "division" {
                   description "Perform operation 'division'";
                 }
                 enum "right-shift" {
                   description "Perform operation 'right shift'";
                 }
                 enum "left-shift" {
                   description "Perform operation 'left shift'";
                 }
               }
             }
             leaf endianness {
               description "Specify the endianness with which bytes read should be processed";
               type enumeration {
                 enum "Little" {
                   description "Process data in little endian";
                 }
                 enum "Big" {
                   description "Process data in big endian";
                 }
               }
             }
             leaf string {
               description "Specify the data type in which string data should be parsed";
               type enumeration {
                 enum "hex" {
                   description "Process data in hexadecimal format";
                 }
                 enum "dec" {
                   description "Process data in decimal format";
                 }
                 enum "oct" {
                   description "Process data in octal format";
                 }
               }
             }
             leaf bitmask {
               description "Specify the bitmask (1-4 bytes) for AND operation in hexadecimal format";
               type string;
             }
             leaf result {
               description "Specify the variable name to which result should be stored";
               type string;
             }
           }
           container byte-jump {
             junos:must "(\".. pattern\")";
             junos:must-message "Content pattern must be specified";
             description "Mention the byte-jump parameters for signature in length encoded protocols";
             leaf bytes {
               description "Specify the number of bytes to extract from packet";
               type union {
                 type string {
                   pattern "<.*>|$.*";
                 }
                 type uint32 {
                   range "1 .. 10";
                 }
               }
             }
             container offset {
               description "Mention the offset variable name or offset value to be used";
               leaf offset-value {
                 description "Specify the number of bytes in to payload to start processing";
                 type union {
                   type string {
                     pattern "<.*>|$.*";
                   }
                   type uint16 {
                     range "0 .. 65535";
                   }
                 }
               }
               leaf offset-variable {
                 description "Specify the name of the offset variable";
                 type string;
               }
             }
             leaf relative {
               description "Specify whether to use an offset relative to last pattern match or not";
               type empty;
             }
             leaf multiplier {
               description "Specify the value to be multiplied against the bytes read";
               type union {
                 type uint16;
                 type string {
                   pattern "<.*>|$.*";
                 }
               }
             }
             leaf endianness {
               description "Specify the endianness with which bytes read should be processed";
               type enumeration {
                 enum "Little" {
                   description "Process data in little endian";
                 }
                 enum "Big" {
                   description "Process data in big endian";
                 }
               }
             }
             leaf align {
               description "Specify the endianness with which bytes read should be processed";
               type enumeration {
                 enum "4-byte" {
                   description "Round the number of converted bytes to 4-byte boundary";
                 }
               }
             }
             leaf string {
               description "Specify the data type in which string data should be parsed";
               type enumeration {
                 enum "hex" {
                   description "Process data in hexadecimal format";
                 }
                 enum "dec" {
                   description "Process data in decimal format";
                 }
                 enum "oct" {
                   description "Process data in octal format";
                 }
               }
             }
             leaf bitmask {
               description "Specify the bitmask (1-4 bytes) for AND operation in hexadecimal format";
               type string;
             }
             leaf from-beginning {
               description "Enable jump from the beginning of the payload";
               type empty;
             }
             leaf from-end {
               description "Enable jump from the end of the payload";
               type empty;
             }
             leaf post-offset {
               description "Specify the number of bytes to skip forward or backward";
               type union {
                 type string {
                   pattern "<.*>|$.*";
                 }
                 type int32 {
                   range "-65535 .. 65535";
                 }
               }
             }
           }
           container is-data-at {
             junos:must "(\".. pattern\")";
             junos:must-message "Content pattern must be specified";
             description "Mention the is-data-at parameters for signature in length encoded protocols";
             container offset {
               description "Mention the offset variable name or offset value to be used";
               leaf offset-value {
                 description "Specify the number of bytes in to payload to start processing";
                 type union {
                   type string {
                     pattern "<.*>|$.*";
                   }
                   type uint16 {
                     range "0 .. 65535";
                   }
                 }
               }
               leaf offset-variable {
                 description "Specify the name of the offset variable";
                 type string;
               }
             }
             leaf relative {
               description "Specify whether to use an offset relative to last pattern match or not";
               type empty;
             }
             leaf negate {
               description "Negates the results of the isdataat test";
               type empty;
             }
           }
         }
         container optional-parameters {
           junos:must "(\".. pattern-pcre\")";
           junos:must-message "Applicable only for pattern-pcre defined signatures";
           description "Mention the optional parameters to enhance pattern matching";
           leaf min-offset {
             description "Minimum offset in data at which pattern-match can end";
             type union {
               type uint64;
               type string {
                 pattern "<.*>|$.*";
               }
             }
           }
           leaf max-offset {
             description "Maximum offset in data at which pattern-match can end";
             type union {
               type uint64;
               type string {
                 pattern "<.*>|$.*";
               }
             }
           }
           leaf min-length {
             description "Minimum match length required to match the pattern";
             type union {
               type uint64;
               type string {
                 pattern "<.*>|$.*";
               }
             }
           }
           leaf edit-distance {
             description "Match the pattern within this edit distance";
             type union {
               type uint32;
               type string {
                 pattern "<.*>|$.*";
               }
             }
           }
           leaf hamming-distance {
             description "Match the pattern within this hamming distance";
             type union {
               type uint32;
               type string {
                 pattern "<.*>|$.*";
               }
             }
           }
         }
         leaf regexp {
           description "Regular expression used for matching repetition of patterns";
           junos:must "((\".. pattern\" || \".. pattern-pcre\"))";
           junos:must-message "A pattern or pattern-pcre must be defined ";
           type string {
             length "0 .. 511";
           }
         }
         leaf negate {
           description "Trigger the attack if condition is not met";
           junos:must "(!((\".. context normalized-stream\" || (\".. context normalized-stream256\" || (\".. context normalized-stream1k\" || \".. context normalized-stream8k\")))))";
           junos:must-message "Negation not supported for normalized-stream contexts";
           junos:must "(!((\".. context stream\" || (\".. context stream256\" || (\".. context stream1k\" || \".. context stream8k\")))))";
           junos:must-message "Negation not supported for stream contexts";
           type empty;
         }
         leaf direction {
           description "Connection direction of the attack";
           type enumeration {
             enum "client-to-server" {
               description "Client to Server";
             }
             enum "server-to-client" {
               description "Server to Client";
             }
             enum "any" {
               description "Any direction";
             }
           }
         }
         leaf shellcode {
           description "Specify shellcode flag for this attack";
           type enumeration {
             enum "intel" {
               description "Detect shellcode for intel platforms";
             }
             enum "sparc" {
               description "Detect shellcode for sparc platforms";
             }
             enum "all" {
               description "Detect shellcode for both intel and sparc platforms";
             }
             enum "no-shellcode" {
               description "Do not detect shellcode";
             }
           }
         }
         container protocol {
           description "Protocol header matches";
           uses apply-advanced;
           container ipv4 {
             description "IPv4 protocol parameters";
             uses apply-advanced;
             container tos {
               presence "enable tos";
               description "Type of Service";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container ihl {
               presence "enable ihl";
               description "Header length in words";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 15";
                   }
                 }
               }
             }
             container total-length {
               presence "enable total-length";
               description "Total Length of IP datagram";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container identification {
               presence "enable identification";
               description "Fragment Identification";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container ip-flags {
               presence "enable ip-flags";
               description "IP Flag bits";
               choice rb-choice {
                 leaf rb {
                   description "Reserved bit";
                   type empty;
                 }
                 leaf no-rb {
                   description "Don't reserved bit";
                   type empty;
                 }
               }
               choice mf-choice {
                 leaf mf {
                   description "More Fragment bit";
                   type empty;
                 }
                 leaf no-mf {
                   description "Don't more Fragment bit";
                   type empty;
                 }
               }
               choice df-choice {
                 leaf df {
                   description "Don't Fragment bit";
                   type empty;
                 }
                 leaf no-df {
                   description "Don't don't Fragment bit";
                   type empty;
                 }
               }
             }
             container ttl {
               presence "enable ttl";
               description "Time to live";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container protocol {
               presence "enable protocol";
               description "Transport layer protocol";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container source {
               presence "enable source";
               description "Source IP-address/Hostname";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type jt:ipv4addr;
               }
             }
             container destination {
               presence "enable destination";
               description "Destination IP-address/Hostname";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type jt:ipv4addr;
               }
             }
             container checksum-validate {
               presence "enable checksum-validate";
               description "Validate checksum field against calculated checksum";
               leaf match {
                 description "Match condition";
                 junos:must "(\".. value\")";
                 junos:must-message "Missing mandatory statement: 'value'";
                 type enumeration {
                   enum "equal" {
                     description "Match when checksum field in packet is exact match";
                   }
                   enum "greater-than" {
                     description "Match when checksum field in packet is greater";
                   }
                   enum "less-than" {
                     description "Match when checksum field in packet is less";
                   }
                   enum "not-equal" {
                     description "Match when checksum field in packet is not exact match";
                   }
                 }
               }
               leaf value {
                 description "Match value";
                 default "0";
                 junos:must "(\".. match\")";
                 junos:must-message "Missing mandatory statement: 'match'";
                 type union {
                   type string {
                     pattern "<.*>|$.*";
                   }
                   type uint32 {
                     range "0 .. 65535";
                   }
                 }
               }
             }
           }
           container ipv6 {
             description "IPv6 protocol parameters";
             uses apply-advanced;
             container traffic-class {
               presence "enable traffic-class";
               description "Traffic class. Similar to TOS in IPv4";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container payload-length {
               presence "enable payload-length";
               description "Length of the payload in the IPv6 datagram";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container flow-label {
               presence "enable flow-label";
               description "Flow label identification";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 1048575";
                   }
                 }
               }
             }
             container hop-limit {
               presence "enable hop-limit";
               description "Hop limit";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container next-header {
               presence "enable next-header";
               description "The header following the basic IPv6 header";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container source {
               presence "enable source";
               description "Source IP-address or hostname";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type jt:ipv6addr;
               }
             }
             container destination {
               presence "enable destination";
               description "Destination IP-address or hostname";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type jt:ipv6addr;
               }
             }
             container extension-header {
               description "IPv6 Extension headers";
               uses apply-advanced;
               container routing-header {
                 presence "enable routing-header";
                 description "IPv6 Routing extension header";
                 uses apply-advanced;
                 container header-type {
                   description "Routing header type";
                   uses apply-advanced;
                   leaf match {
                     description "Match condition";
                     type enumeration {
                       enum "equal" {
                         description "Match when value in packet is exact match";
                       }
                       enum "greater-than" {
                         description "Match when value in packet is greater";
                       }
                       enum "less-than" {
                         description "Match when value in packet is less";
                       }
                       enum "not-equal" {
                         description "Match when value in packet is not exact match";
                       }
                     }
                   }
                   leaf value {
                     description "Match value";
                     type union {
                       type string {
                         pattern "<.*>|$.*";
                       }
                       type uint32 {
                         range "0 .. 255";
                       }
                     }
                   }
                 }
               }
               container destination-option {
                 description "IPv6 Destination option extension header";
                 uses apply-advanced;
                 container option-type {
                   description "Destination option header type";
                   uses apply-advanced;
                   leaf match {
                     description "Match condition";
                     type enumeration {
                       enum "equal" {
                         description "Match when value in packet is exact match";
                       }
                       enum "greater-than" {
                         description "Match when value in packet is greater";
                       }
                       enum "less-than" {
                         description "Match when value in packet is less";
                       }
                       enum "not-equal" {
                         description "Match when value in packet is not exact match";
                       }
                     }
                   }
                   leaf value {
                     description "Match value";
                     type union {
                       type string {
                         pattern "<.*>|$.*";
                       }
                       type uint32 {
                         range "0 .. 255";
                       }
                     }
                   }
                 }
                 container home-address {
                   description "IPv6 Home address of the mobile node";
                   uses apply-advanced;
                   leaf match {
                     description "Match condition";
                     type enumeration {
                       enum "equal" {
                         description "Match when value in packet is exact match";
                       }
                       enum "greater-than" {
                         description "Match when value in packet is greater";
                       }
                       enum "less-than" {
                         description "Match when value in packet is less";
                       }
                       enum "not-equal" {
                         description "Match when value in packet is not exact match";
                       }
                     }
                   }
                   leaf value {
                     description "Match value";
                     type jt:ipv6addr;
                   }
                 }
               }
             }
           }
           container tcp {
             junos:must "((!(\".. udp\") && !(\".. icmp\")))";
             junos:must-message "tcp cannot be specified with udp or icmp";
             description "TCP protocol parameters";
             uses apply-advanced;
             container source-port {
               presence "enable source-port";
               description "Source port";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container destination-port {
               presence "enable destination-port";
               description "Destination port";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container sequence-number {
               presence "enable sequence-number";
               description "Sequence Number";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 4294967295";
                   }
                 }
               }
             }
             container ack-number {
               presence "enable ack-number";
               description "Acknowledgement Number";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 4294967295";
                   }
                 }
               }
             }
             container header-length {
               presence "enable header-length";
               description "Header Length in words";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 15";
                   }
                 }
               }
             }
             container reserved {
               presence "enable reserved";
               description "Three reserved bits";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 7";
                   }
                 }
               }
             }
             container window-size {
               presence "enable window-size";
               description "Window Size";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container urgent-pointer {
               presence "enable urgent-pointer";
               description "Urgent Pointer";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container tcp-flags {
               presence "enable tcp-flags";
               description "TCP header flags";
               choice r1-choice {
                 leaf r1 {
                   description "Set Reserverd bit 1";
                   type empty;
                 }
                 leaf no-r1 {
                   description "Don't set Reserverd bit 1";
                   type empty;
                 }
               }
               choice r2-choice {
                 leaf r2 {
                   description "Set Reserved bit 2";
                   type empty;
                 }
                 leaf no-r2 {
                   description "Don't set Reserved bit 2";
                   type empty;
                 }
               }
               choice urg-choice {
                 leaf urg {
                   description "Set Urgent bit";
                   type empty;
                 }
                 leaf no-urg {
                   description "Don't set Urgent bit";
                   type empty;
                 }
               }
               choice ack-choice {
                 leaf ack {
                   description "Set Acknowledge bit";
                   type empty;
                 }
                 leaf no-ack {
                   description "Don't set Acknowledge bit";
                   type empty;
                 }
               }
               choice psh-choice {
                 leaf psh {
                   description "Set Push bit";
                   type empty;
                 }
                 leaf no-psh {
                   description "Don't set Push bit";
                   type empty;
                 }
               }
               choice rst-choice {
                 leaf rst {
                   description "Set Reset bit";
                   type empty;
                 }
                 leaf no-rst {
                   description "Don't set Reset bit";
                   type empty;
                 }
               }
               choice syn-choice {
                 leaf syn {
                   description "Set SYN bit";
                   type empty;
                 }
                 leaf no-syn {
                   description "Don't set SYN bit";
                   type empty;
                 }
               }
               choice fin-choice {
                 leaf fin {
                   description "Set FINish bit";
                   type empty;
                 }
                 leaf no-fin {
                   description "Don't set FINish bit";
                   type empty;
                 }
               }
             }
             container option {
               presence "enable option";
               description "Kind";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container data-length {
               presence "enable data-length";
               description "Size of IP datagram subtracted by TCP header length";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "2 .. 255";
                   }
                 }
               }
             }
             container window-scale {
               presence "enable window-scale";
               description "Window scale";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container mss {
               presence "enable mss";
               description "Maximum Segment Size";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container checksum-validate {
               presence "enable checksum-validate";
               description "Validate checksum field against calculated checksum";
               leaf match {
                 description "Match condition";
                 junos:must "(\".. value\")";
                 junos:must-message "Missing mandatory statement: 'value'";
                 type enumeration {
                   enum "equal" {
                     description "Match when checksum field in packet is exact match";
                   }
                   enum "greater-than" {
                     description "Match when checksum field in packet is greater";
                   }
                   enum "less-than" {
                     description "Match when checksum field in packet is less";
                   }
                   enum "not-equal" {
                     description "Match when checksum field in packet is not exact match";
                   }
                 }
               }
               leaf value {
                 description "Match value";
                 default "0";
                 junos:must "(\".. match\")";
                 junos:must-message "Missing mandatory statement: 'match'";
                 type union {
                   type string {
                     pattern "<.*>|$.*";
                   }
                   type uint32 {
                     range "0 .. 65535";
                   }
                 }
               }
             }
           }
           container udp {
             junos:must "((!(\".. tcp\") && !(\".. icmp\")))";
             junos:must-message "udp cannot be specified with tcp or icmp";
             description "UDP protocol parameters";
             uses apply-advanced;
             container source-port {
               presence "enable source-port";
               description "Source port";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container destination-port {
               presence "enable destination-port";
               description "Destination port";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container data-length {
               presence "enable data-length";
               description "Size of IP datagram subtracted by UDP header length";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container checksum-validate {
               presence "enable checksum-validate";
               description "Validate checksum field against calculated checksum";
               leaf match {
                 description "Match condition";
                 junos:must "(\".. value\")";
                 junos:must-message "Missing mandatory statement: 'value'";
                 type enumeration {
                   enum "equal" {
                     description "Match when checksum field in packet is exact match";
                   }
                   enum "greater-than" {
                     description "Match when checksum field in packet is greater";
                   }
                   enum "less-than" {
                     description "Match when checksum field in packet is less";
                   }
                   enum "not-equal" {
                     description "Match when checksum field in packet is not exact match";
                   }
                 }
               }
               leaf value {
                 description "Match value";
                 default "0";
                 junos:must "(\".. match\")";
                 junos:must-message "Missing mandatory statement: 'match'";
                 type union {
                   type string {
                     pattern "<.*>|$.*";
                   }
                   type uint32 {
                     range "0 .. 65535";
                   }
                 }
               }
             }
           }
           container icmp {
             junos:must "((!(\".. udp\") && (!(\".. tcp\") && !(\".. icmpv6\"))))";
             junos:must-message "icmp cannot be specified with tcp or udp or icmpv6";
             description "ICMP protocol parameters";
             uses apply-advanced;
             container type {
               presence "enable type";
               description "Type";
               uses apply-advanced;
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container code {
               presence "enable code";
               description "Code";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container identification {
               presence "enable identification";
               description "Identifier in echo request/reply";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container sequence-number {
               presence "enable sequence-number";
               description "Sequence Number";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container data-length {
               presence "enable data-length";
               description "Size of IP datagram subtracted by ICMP header length";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container checksum-validate {
               presence "enable checksum-validate";
               description "Validate checksum field against calculated checksum";
               leaf match {
                 description "Match condition";
                 junos:must "(\".. value\")";
                 junos:must-message "Missing mandatory statement: 'value'";
                 type enumeration {
                   enum "equal" {
                     description "Match when checksum field in packet is exact match";
                   }
                   enum "greater-than" {
                     description "Match when checksum field in packet is greater";
                   }
                   enum "less-than" {
                     description "Match when checksum field in packet is less";
                   }
                   enum "not-equal" {
                     description "Match when checksum field in packet is not exact match";
                   }
                 }
               }
               leaf value {
                 description "Match value";
                 default "0";
                 junos:must "(\".. match\")";
                 junos:must-message "Missing mandatory statement: 'match'";
                 type union {
                   type string {
                     pattern "<.*>|$.*";
                   }
                   type uint32 {
                     range "0 .. 65535";
                   }
                 }
               }
             }
           }
           container icmpv6 {
             junos:must "((!(\".. udp\") && (!(\".. tcp\") && !(\".. icmp\"))))";
             junos:must-message "icmpv6 cannot be specified with tcp or udp or icmp";
             description "ICMPv6 protocol parameters";
             uses apply-advanced;
             container type {
               presence "enable type";
               description "Type";
               uses apply-advanced;
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container code {
               presence "enable code";
               description "Code";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container identification {
               presence "enable identification";
               description "Identifier in echo request/reply";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container sequence-number {
               presence "enable sequence-number";
               description "Sequence number";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container data-length {
               presence "enable data-length";
               description "Size of IPv6 datagram subtracted by ICMPv6 header length";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container checksum-validate {
               presence "enable checksum-validate";
               description "Validate checksum field against calculated checksum";
               leaf match {
                 description "Match condition";
                 junos:must "(\".. value\")";
                 junos:must-message "Missing mandatory statement: 'value'";
                 type enumeration {
                   enum "equal" {
                     description "Match when checksum field in packet is exact match";
                   }
                   enum "greater-than" {
                     description "Match when checksum field in packet is greater";
                   }
                   enum "less-than" {
                     description "Match when checksum field in packet is less";
                   }
                   enum "not-equal" {
                     description "Match when checksum field in packet is not exact match";
                   }
                 }
               }
               leaf value {
                 description "Match value";
                 default "0";
                 junos:must "(\".. match\")";
                 junos:must-message "Missing mandatory statement: 'match'";
                 type union {
                   type string {
                     pattern "<.*>|$.*";
                   }
                   type uint32 {
                     range "0 .. 65535";
                   }
                 }
               }
             }
           }
         }
       }
       container anomaly {
         junos:must "(!((\".. signature\" || \".. chain\")))";
         junos:must-message "Only one attack type is permitted";
         description "Protocol anomaly";
         uses apply-advanced;
         leaf service {
           description "Service name";
           type string;
         }
         leaf test {
           description "Protocol anomaly condition to be checked";
           type string;
         }
         leaf direction {
           description "Direction";
           type enumeration {
             enum "client-to-server" {
               description "From Client to Server";
             }
             enum "server-to-client" {
               description "From Server to Client";
             }
             enum "any" {
               description "Any direction";
             }
           }
         }
         leaf shellcode {
           description "Specify shellcode flag for this attack";
           type enumeration {
             enum "intel" {
               description "Detect shellcode for intel platforms";
             }
             enum "sparc" {
               description "Detect shellcode for sparc platforms";
             }
             enum "all" {
               description "Detect shellcode for both intel and sparc platforms";
             }
             enum "no-shellcode" {
               description "Do not detect shellcode";
             }
           }
         }
       }
       container chain {
         junos:must "(!((\".. signature\" || \".. anomaly\")))";
         junos:must-message "Only one attack type is permitted";
         description "Chain attack";
         uses apply-advanced;
         container protocol-binding {
           description "Protocol binding over which attack will be detected";
           uses apply-advanced;
           choice protocol {
             case case_1 {
               container tcp {
                 presence "enable tcp";
                 description "Attack is for TCP packets only";
                 uses apply-advanced;
                 list minimum-port {
                   key name;
                   ordered-by user;
                   description "Multiple sets of (single port/port ranges) can be specified";
                   uses port-range;
                 }
               }
             }
             case case_2 {
               container udp {
                 presence "enable udp";
                 description "Attack is for UDP packets only";
                 uses apply-advanced;
                 list minimum-port {
                   key name;
                   ordered-by user;
                   description "Either single port or port ranges can be specified";
                   uses port-range;
                 }
               }
             }
             case case_3 {
               container rpc {
                 presence "enable rpc";
                 description "Attack is for RPC packets only";
                 uses apply-advanced;
                 leaf program-number {
                   description "RPC Program Number";
                   type union {
                     type uint32;
                     type string {
                       pattern "<.*>|$.*";
                     }
                   }
                 }
               }
             }
             case case_4 {
               leaf icmp {
                 description "Attack is for ICMP packets only";
                 type empty;
               }
             }
             case case_5 {
               leaf icmpv6 {
                 description "Attack is for ICMPv6 packets only";
                 type empty;
               }
             }
             case case_6 {
               container ip {
                 presence "enable ip";
                 description "Attack is for all IP based packets";
                 uses apply-advanced;
                 leaf protocol-number {
                   description "Transport layer protocol number";
                   type union {
                     type string {
                       pattern "<.*>|$.*";
                     }
                     type uint32 {
                       range "0 .. 139";
                     }
                   }
                 }
               }
             }
             case case_7 {
               container ipv6 {
                 presence "enable ipv6";
                 description "Attack is for all IPv6 based packets";
                 uses apply-advanced;
                 leaf protocol-number {
                   description "Transport layer protocol number";
                   type union {
                     type string {
                       pattern "<.*>|$.*";
                     }
                     type uint32 {
                       range "0 .. 139";
                     }
                   }
                 }
               }
             }
             case case_8 {
               leaf application {
                 description "Application name";
                 type string;
               }
             }
             case case_9 {
               leaf nested-application {
                 description "Nested application name";
                 status deprecated;
                 type string;
               }
             }
           }
         }
         leaf scope {
           description "Scope of the attack";
           type enumeration {
             enum "session" {
               description "Allow matches across transactions within the same session";
             }
             enum "transaction" {
               description "Allow matches in single transactions within the same session";
             }
           }
         }
         leaf order {
           description "Attacks should match in the order in which they are defined";
           type empty;
         }
         leaf reset {
           description "Repeat match should generate a new alert";
           type empty;
         }
         leaf expression {
           description "Boolean Expression(or, and, oand). Multiple expressions can be combined using parenthesis.";
           junos:must "(!(\".. order\"))";
           junos:must-message "Boolean Expression cannot be specified with order";
           type string;
         }
         list member {
           key name;
           ordered-by user;
           description "List of member attacks.";
           uses chain-member-type;
         }
       }
     }
   }
   grouping chain-member-type {
     description "Chain member";
     leaf name {
       description "Custom attack name";
       type string;
     }
     uses apply-advanced;
     container attack-type {
       presence "enable attack-type";
       description "Type of attack";
       uses apply-advanced;
       container signature {
         junos:must "(!(\".. anomaly\"))";
         junos:must-message "Only one attack type is permitted";
         description "Signature based attack";
         uses apply-advanced;
         leaf context {
           description "Context";
           type string;
         }
         leaf pattern {
           description "Pattern is the signature of the attack you want to detect";
           junos:must "(\".. context\")";
           junos:must-message "Context must be specified";
           type string {
             length "0 .. 511";
           }
         }
         leaf pattern-pcre {
           description "Attack signature pattern in PCRE format";
           junos:must "(\".. context\")";
           junos:must-message "Context must be specified";
           type string {
             length "0 .. 511";
           }
         }
         container content {
           junos:must "(\".. context\")";
           junos:must-message "Context must be specified";
           description "Mention the match-modifire parameters to enhance pattern matching";
           leaf pattern {
             description "Specify match-modifier pattern";
             type string;
           }
           leaf pcre {
             description "PCRE expression";
             type string {
               length "0 .. 511";
             }
           }
           container depth {
             junos:must "(\".. pattern\")";
             junos:must-message "Content pattern must be specified";
             description "Maximum depth to search pattern within a packet. Depth is not relative";
             leaf depth-value {
               description "Specify the value of 'depth'";
               type union {
                 type string {
                   pattern "<.*>|$.*";
                 }
                 type uint16 {
                   range "1 .. 65535";
                 }
               }
             }
             leaf depth-variable {
               description "Specify the variable name from which 'depth' should be extracted";
               type string;
             }
           }
           container offset {
             junos:must "(\".. pattern\")";
             junos:must-message "Content pattern must be specified";
             description "Where to start searching for a pattern within a packet. Offset value is not relative";
             leaf offset-value {
               description "Specify the value of 'offset'";
               type union {
                 type string {
                   pattern "<.*>|$.*";
                 }
                 type uint16 {
                   range "0 .. 65535";
                 }
               }
             }
             leaf offset-variable {
               description "Specify the variable name from which 'offset' should be extracted";
               type string;
             }
           }
           container within {
             junos:must "(\".. pattern\")";
             junos:must-message "Content pattern must be specified";
             description "Maximum Number of bytes present between two conjugative pattern match. within is  relative";
             leaf within-value {
               description "Specify the value of 'within'";
               type union {
                 type string {
                   pattern "<.*>|$.*";
                 }
                 type uint16 {
                   range "1 .. 65535";
                 }
               }
             }
             leaf within-variable {
               description "Specify the variable name from which 'within' should be extracted";
               type string;
             }
           }
           container distance {
             junos:must "(\".. pattern\")";
             junos:must-message "Content pattern must be specified";
             description "Maximum Length to ignore before searching next pattern match. Distance is  relative";
             leaf distance-value {
               description "Specify the value of 'distance'";
               type union {
                 type string {
                   pattern "<.*>|$.*";
                 }
                 type int32 {
                   range "-65535 .. 65535";
                 }
               }
             }
             leaf distance-variable {
               description "Specify the variable name from which 'distance' should be extracted";
               type string;
             }
           }
           container byte-extract {
             junos:must "(\".. pattern\")";
             junos:must-message "Content pattern must be specified";
             description "Mention the byte-extract parameters for signature in length encoded protocols";
             leaf bytes {
               description "Specify the number of bytes to extract from packet";
               type union {
                 type string {
                   pattern "<.*>|$.*";
                 }
                 type uint32 {
                   range "1 .. 10";
                 }
               }
             }
             leaf offset {
               description "Specify the number of bytes in to payload to start processing";
               type union {
                 type int32;
                 type string {
                   pattern "<.*>|$.*";
                 }
               }
             }
             leaf var-name {
               description "Specify the name of the variable to reference in other rule options";
               type string;
             }
             leaf relative {
               description "Specify whether to use an offset relative to last pattern match or not";
               type empty;
             }
             leaf multiplier {
               description "Specify the value to be multiplied against the bytes read";
               type union {
                 type uint16;
                 type string {
                   pattern "<.*>|$.*";
                 }
               }
             }
             leaf endianness {
               description "Specify the endianness with which bytes read should be processed";
               type enumeration {
                 enum "Little" {
                   description "Process data in little endian";
                 }
                 enum "Big" {
                   description "Process data in big endian";
                 }
               }
             }
             leaf align {
               description "Specify the byte alignment";
               type enumeration {
                 enum "2-byte" {
                   description "Round the number of converted bytes to 2-byte boundary";
                 }
                 enum "4-byte" {
                   description "Round the number of converted bytes to 4-byte boundary";
                 }
               }
             }
             leaf string {
               description "Specify the data type in which string data should be parsed";
               type enumeration {
                 enum "hex" {
                   description "Process data in hexadecimal format";
                 }
                 enum "dec" {
                   description "Process data in decimal format";
                 }
                 enum "oct" {
                   description "Process data in octal format";
                 }
               }
             }
             leaf bitmask {
               description "Specify the bitmask (1-4 bytes) for AND operation in hexadecimal format";
               type string;
             }
           }
           container byte-test {
             junos:must "(\".. pattern\")";
             junos:must-message "Content pattern must be specified";
             description "Mention the byte-test parameters for signature in length encoded protocols";
             leaf bytes {
               description "Specify the number of bytes to extract from packet";
               type union {
                 type string {
                   pattern "<.*>|$.*";
                 }
                 type uint32 {
                   range "1 .. 10";
                 }
               }
             }
             container offset {
               description "Mention the offset variable name or offset value to be used";
               leaf offset-value {
                 description "Specify the number of bytes in to payload to start processing";
                 type union {
                   type int32;
                   type string {
                     pattern "<.*>|$.*";
                   }
                 }
               }
               leaf offset-variable {
                 description "Specify the name of the offset variable";
                 type string;
               }
             }
             container rvalue {
               description "Specify the rvalue to test the converted value against";
               leaf rvalue-value {
                 description "Specify the value";
                 type union {
                   type uint32;
                   type string {
                     pattern "<.*>|$.*";
                   }
                 }
               }
               leaf rvalue-variable {
                 description "Specify the variable name";
                 type string;
               }
             }
             leaf relative {
               description "Specify whether to use an offset relative to last pattern match or not";
               type empty;
             }
             leaf operator {
               description "Specify the operation to perform on extracted value";
               type enumeration {
                 enum "less-than" {
                   description "Perform operation 'less than'";
                 }
                 enum "greater-than" {
                   description "Perform operation 'greater than'";
                 }
                 enum "less-than-or-equal" {
                   description "Perform operation 'less than or equal'";
                 }
                 enum "greater-than-or-equal" {
                   description "Perform operation 'greater than or equal'";
                 }
                 enum "equal" {
                   description "Perform operation 'equal'";
                 }
                 enum "bitwise-AND" {
                   description "Perform operation 'bitwise AND'";
                 }
                 enum "bitwise-XOR" {
                   description "Perform operation 'bitwise OR'";
                 }
               }
             }
             leaf negate {
               description "Check if the operator is not true";
               type empty;
             }
             leaf endianness {
               description "Specify the endianness with which bytes read should be processed";
               type enumeration {
                 enum "Little" {
                   description "Process data in little endian";
                 }
                 enum "Big" {
                   description "Process data in big endian";
                 }
               }
             }
             leaf string {
               description "Specify the data type in which string data should be parsed";
               type enumeration {
                 enum "hex" {
                   description "Process data in hexadecimal format";
                 }
                 enum "dec" {
                   description "Process data in decimal format";
                 }
                 enum "oct" {
                   description "Process data in octal format";
                 }
               }
             }
             leaf bitmask {
               description "Specify the bitmask (1-4 bytes) for AND operation in hexadecimal format";
               type string;
             }
           }
           container byte-math {
             junos:must "(\".. pattern\")";
             junos:must-message "Content pattern must be specified";
             description "Mention the byte-math parameters for signature in length encoded protocols";
             leaf bytes {
               description "Specify the number of bytes to extract from packet";
               type union {
                 type string {
                   pattern "<.*>|$.*";
                 }
                 type uint32 {
                   range "1 .. 10";
                 }
               }
             }
             leaf offset {
               description "Specify the number of bytes in to payload to start processing";
               type union {
                 type string {
                   pattern "<.*>|$.*";
                 }
                 type uint16 {
                   range "0 .. 65535";
                 }
               }
             }
             container rvalue {
               description "Specify the value to use mathematical operation against";
               leaf rvalue-value {
                 description "Specify the value";
                 type union {
                   type uint32;
                   type string {
                     pattern "<.*>|$.*";
                   }
                 }
               }
               leaf rvalue-variable {
                 description "Specify the variable name";
                 type string;
               }
             }
             leaf relative {
               description "Specify whether to use an offset relative to last pattern match or not";
               type empty;
             }
             leaf operator {
               description "Specify the operation to perform on extracted value";
               type enumeration {
                 enum "addition" {
                   description "Perform operation 'addition'";
                 }
                 enum "subtraction" {
                   description "Perform operation 'subtraction'";
                 }
                 enum "multiplication" {
                   description "Perform operation 'multiplication'";
                 }
                 enum "division" {
                   description "Perform operation 'division'";
                 }
                 enum "right-shift" {
                   description "Perform operation 'right shift'";
                 }
                 enum "left-shift" {
                   description "Perform operation 'left shift'";
                 }
               }
             }
             leaf endianness {
               description "Specify the endianness with which bytes read should be processed";
               type enumeration {
                 enum "Little" {
                   description "Process data in little endian";
                 }
                 enum "Big" {
                   description "Process data in big endian";
                 }
               }
             }
             leaf string {
               description "Specify the data type in which string data should be parsed";
               type enumeration {
                 enum "hex" {
                   description "Process data in hexadecimal format";
                 }
                 enum "dec" {
                   description "Process data in decimal format";
                 }
                 enum "oct" {
                   description "Process data in octal format";
                 }
               }
             }
             leaf bitmask {
               description "Specify the bitmask (1-4 bytes) for AND operation in hexadecimal format";
               type string;
             }
             leaf result {
               description "Specify the variable name to which result should be stored";
               type string;
             }
           }
           container byte-jump {
             junos:must "(\".. pattern\")";
             junos:must-message "Content pattern must be specified";
             description "Mention the byte-jump parameters for signature in length encoded protocols";
             leaf bytes {
               description "Specify the number of bytes to extract from packet";
               type union {
                 type string {
                   pattern "<.*>|$.*";
                 }
                 type uint32 {
                   range "1 .. 10";
                 }
               }
             }
             container offset {
               description "Mention the offset variable name or offset value to be used";
               leaf offset-value {
                 description "Specify the number of bytes in to payload to start processing";
                 type union {
                   type string {
                     pattern "<.*>|$.*";
                   }
                   type uint16 {
                     range "0 .. 65535";
                   }
                 }
               }
               leaf offset-variable {
                 description "Specify the name of the offset variable";
                 type string;
               }
             }
             leaf relative {
               description "Specify whether to use an offset relative to last pattern match or not";
               type empty;
             }
             leaf multiplier {
               description "Specify the value to be multiplied against the bytes read";
               type union {
                 type uint16;
                 type string {
                   pattern "<.*>|$.*";
                 }
               }
             }
             leaf endianness {
               description "Specify the endianness with which bytes read should be processed";
               type enumeration {
                 enum "Little" {
                   description "Process data in little endian";
                 }
                 enum "Big" {
                   description "Process data in big endian";
                 }
               }
             }
             leaf align {
               description "Specify the endianness with which bytes read should be processed";
               type enumeration {
                 enum "4-byte" {
                   description "Round the number of converted bytes to 4-byte boundary";
                 }
               }
             }
             leaf string {
               description "Specify the data type in which string data should be parsed";
               type enumeration {
                 enum "hex" {
                   description "Process data in hexadecimal format";
                 }
                 enum "dec" {
                   description "Process data in decimal format";
                 }
                 enum "oct" {
                   description "Process data in octal format";
                 }
               }
             }
             leaf bitmask {
               description "Specify the bitmask (1-4 bytes) for AND operation in hexadecimal format";
               type string;
             }
             leaf from-beginning {
               description "Enable jump from the beginning of the payload";
               type empty;
             }
             leaf from-end {
               description "Enable jump from the end of the payload";
               type empty;
             }
             leaf post-offset {
               description "Specify the number of bytes to skip forward or backward";
               type union {
                 type string {
                   pattern "<.*>|$.*";
                 }
                 type int32 {
                   range "-65535 .. 65535";
                 }
               }
             }
           }
           container is-data-at {
             junos:must "(\".. pattern\")";
             junos:must-message "Content pattern must be specified";
             description "Mention the is-data-at parameters for signature in length encoded protocols";
             container offset {
               description "Mention the offset variable name or offset value to be used";
               leaf offset-value {
                 description "Specify the number of bytes in to payload to start processing";
                 type union {
                   type string {
                     pattern "<.*>|$.*";
                   }
                   type uint16 {
                     range "0 .. 65535";
                   }
                 }
               }
               leaf offset-variable {
                 description "Specify the name of the offset variable";
                 type string;
               }
             }
             leaf relative {
               description "Specify whether to use an offset relative to last pattern match or not";
               type empty;
             }
             leaf negate {
               description "Negates the results of the isdataat test";
               type empty;
             }
           }
         }
         container optional-parameters {
           junos:must "(\".. pattern-pcre\")";
           junos:must-message "Applicable only for pattern-pcre defined signatures";
           description "Mention the optional parameters to enhance pattern matching";
           leaf min-offset {
             description "Minimum offset in data at which pattern-match can end";
             type union {
               type uint64;
               type string {
                 pattern "<.*>|$.*";
               }
             }
           }
           leaf max-offset {
             description "Maximum offset in data at which pattern-match can end";
             type union {
               type uint64;
               type string {
                 pattern "<.*>|$.*";
               }
             }
           }
           leaf min-length {
             description "Minimum match length required to match the pattern";
             type union {
               type uint64;
               type string {
                 pattern "<.*>|$.*";
               }
             }
           }
           leaf edit-distance {
             description "Match the pattern within this edit distance";
             type union {
               type uint32;
               type string {
                 pattern "<.*>|$.*";
               }
             }
           }
           leaf hamming-distance {
             description "Match the pattern within this hamming distance";
             type union {
               type uint32;
               type string {
                 pattern "<.*>|$.*";
               }
             }
           }
         }
         leaf regexp {
           description "Regular expression used for matching repetition of patterns";
           junos:must "((\".. pattern\" || \".. pattern-pcre\"))";
           junos:must-message "A pattern or pattern-pcre must be defined ";
           type string {
             length "0 .. 511";
           }
         }
         leaf negate {
           description "Trigger the attack if condition is not met";
           junos:must "(!((\".. context normalized-stream\" || (\".. context normalized-stream256\" || (\".. context normalized-stream1k\" || \".. context normalized-stream8k\")))))";
           junos:must-message "Negation not supported for normalized-stream contexts";
           junos:must "(!((\".. context stream\" || (\".. context stream256\" || (\".. context stream1k\" || \".. context stream8k\")))))";
           junos:must-message "Negation not supported for stream contexts";
           type empty;
         }
         leaf direction {
           description "Connection direction of the attack";
           type enumeration {
             enum "client-to-server" {
               description "Client to Server";
             }
             enum "server-to-client" {
               description "Server to Client";
             }
             enum "any" {
               description "Any direction";
             }
           }
         }
         leaf shellcode {
           description "Specify shellcode flag for this attack";
           type enumeration {
             enum "intel" {
               description "Detect shellcode for intel platforms";
             }
             enum "sparc" {
               description "Detect shellcode for sparc platforms";
             }
             enum "all" {
               description "Detect shellcode for both intel and sparc platforms";
             }
             enum "no-shellcode" {
               description "Do not detect shellcode";
             }
           }
         }
         container protocol {
           description "Protocol header matches";
           uses apply-advanced;
           container ipv4 {
             description "IPv4 protocol parameters";
             uses apply-advanced;
             container tos {
               presence "enable tos";
               description "Type of Service";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container ihl {
               presence "enable ihl";
               description "Header length in words";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 15";
                   }
                 }
               }
             }
             container total-length {
               presence "enable total-length";
               description "Total Length of IP datagram";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container identification {
               presence "enable identification";
               description "Fragment Identification";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container ip-flags {
               presence "enable ip-flags";
               description "IP Flag bits";
               choice rb-choice {
                 leaf rb {
                   description "Reserved bit";
                   type empty;
                 }
                 leaf no-rb {
                   description "Don't reserved bit";
                   type empty;
                 }
               }
               choice mf-choice {
                 leaf mf {
                   description "More Fragment bit";
                   type empty;
                 }
                 leaf no-mf {
                   description "Don't more Fragment bit";
                   type empty;
                 }
               }
               choice df-choice {
                 leaf df {
                   description "Don't Fragment bit";
                   type empty;
                 }
                 leaf no-df {
                   description "Don't don't Fragment bit";
                   type empty;
                 }
               }
             }
             container ttl {
               presence "enable ttl";
               description "Time to live";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container protocol {
               presence "enable protocol";
               description "Transport layer protocol";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container source {
               presence "enable source";
               description "Source IP-address/Hostname";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type jt:ipv4addr;
               }
             }
             container destination {
               presence "enable destination";
               description "Destination IP-address/Hostname";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type jt:ipv4addr;
               }
             }
             container checksum-validate {
               presence "enable checksum-validate";
               description "Validate checksum field against calculated checksum";
               leaf match {
                 description "Match condition";
                 junos:must "(\".. value\")";
                 junos:must-message "Missing mandatory statement: 'value'";
                 type enumeration {
                   enum "equal" {
                     description "Match when checksum field in packet is exact match";
                   }
                   enum "greater-than" {
                     description "Match when checksum field in packet is greater";
                   }
                   enum "less-than" {
                     description "Match when checksum field in packet is less";
                   }
                   enum "not-equal" {
                     description "Match when checksum field in packet is not exact match";
                   }
                 }
               }
               leaf value {
                 description "Match value";
                 default "0";
                 junos:must "(\".. match\")";
                 junos:must-message "Missing mandatory statement: 'match'";
                 type union {
                   type string {
                     pattern "<.*>|$.*";
                   }
                   type uint32 {
                     range "0 .. 65535";
                   }
                 }
               }
             }
           }
           container ipv6 {
             description "IPv6 protocol parameters";
             uses apply-advanced;
             container traffic-class {
               presence "enable traffic-class";
               description "Traffic class. Similar to TOS in IPv4";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container payload-length {
               presence "enable payload-length";
               description "Length of the payload in the IPv6 datagram";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container flow-label {
               presence "enable flow-label";
               description "Flow label identification";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 1048575";
                   }
                 }
               }
             }
             container hop-limit {
               presence "enable hop-limit";
               description "Hop limit";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container next-header {
               presence "enable next-header";
               description "The header following the basic IPv6 header";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container source {
               presence "enable source";
               description "Source IP-address or hostname";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type jt:ipv6addr;
               }
             }
             container destination {
               presence "enable destination";
               description "Destination IP-address or hostname";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type jt:ipv6addr;
               }
             }
             container extension-header {
               description "IPv6 Extension headers";
               uses apply-advanced;
               container routing-header {
                 presence "enable routing-header";
                 description "IPv6 Routing extension header";
                 uses apply-advanced;
                 container header-type {
                   description "Routing header type";
                   uses apply-advanced;
                   leaf match {
                     description "Match condition";
                     type enumeration {
                       enum "equal" {
                         description "Match when value in packet is exact match";
                       }
                       enum "greater-than" {
                         description "Match when value in packet is greater";
                       }
                       enum "less-than" {
                         description "Match when value in packet is less";
                       }
                       enum "not-equal" {
                         description "Match when value in packet is not exact match";
                       }
                     }
                   }
                   leaf value {
                     description "Match value";
                     type union {
                       type string {
                         pattern "<.*>|$.*";
                       }
                       type uint32 {
                         range "0 .. 255";
                       }
                     }
                   }
                 }
               }
               container destination-option {
                 description "IPv6 Destination option extension header";
                 uses apply-advanced;
                 container option-type {
                   description "Destination option header type";
                   uses apply-advanced;
                   leaf match {
                     description "Match condition";
                     type enumeration {
                       enum "equal" {
                         description "Match when value in packet is exact match";
                       }
                       enum "greater-than" {
                         description "Match when value in packet is greater";
                       }
                       enum "less-than" {
                         description "Match when value in packet is less";
                       }
                       enum "not-equal" {
                         description "Match when value in packet is not exact match";
                       }
                     }
                   }
                   leaf value {
                     description "Match value";
                     type union {
                       type string {
                         pattern "<.*>|$.*";
                       }
                       type uint32 {
                         range "0 .. 255";
                       }
                     }
                   }
                 }
                 container home-address {
                   description "IPv6 Home address of the mobile node";
                   uses apply-advanced;
                   leaf match {
                     description "Match condition";
                     type enumeration {
                       enum "equal" {
                         description "Match when value in packet is exact match";
                       }
                       enum "greater-than" {
                         description "Match when value in packet is greater";
                       }
                       enum "less-than" {
                         description "Match when value in packet is less";
                       }
                       enum "not-equal" {
                         description "Match when value in packet is not exact match";
                       }
                     }
                   }
                   leaf value {
                     description "Match value";
                     type jt:ipv6addr;
                   }
                 }
               }
             }
           }
           container tcp {
             junos:must "((!(\".. udp\") && !(\".. icmp\")))";
             junos:must-message "tcp cannot be specified with udp or icmp";
             description "TCP protocol parameters";
             uses apply-advanced;
             container source-port {
               presence "enable source-port";
               description "Source port";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container destination-port {
               presence "enable destination-port";
               description "Destination port";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container sequence-number {
               presence "enable sequence-number";
               description "Sequence Number";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 4294967295";
                   }
                 }
               }
             }
             container ack-number {
               presence "enable ack-number";
               description "Acknowledgement Number";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 4294967295";
                   }
                 }
               }
             }
             container header-length {
               presence "enable header-length";
               description "Header Length in words";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 15";
                   }
                 }
               }
             }
             container reserved {
               presence "enable reserved";
               description "Three reserved bits";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 7";
                   }
                 }
               }
             }
             container window-size {
               presence "enable window-size";
               description "Window Size";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container urgent-pointer {
               presence "enable urgent-pointer";
               description "Urgent Pointer";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container tcp-flags {
               presence "enable tcp-flags";
               description "TCP header flags";
               choice r1-choice {
                 leaf r1 {
                   description "Set Reserverd bit 1";
                   type empty;
                 }
                 leaf no-r1 {
                   description "Don't set Reserverd bit 1";
                   type empty;
                 }
               }
               choice r2-choice {
                 leaf r2 {
                   description "Set Reserved bit 2";
                   type empty;
                 }
                 leaf no-r2 {
                   description "Don't set Reserved bit 2";
                   type empty;
                 }
               }
               choice urg-choice {
                 leaf urg {
                   description "Set Urgent bit";
                   type empty;
                 }
                 leaf no-urg {
                   description "Don't set Urgent bit";
                   type empty;
                 }
               }
               choice ack-choice {
                 leaf ack {
                   description "Set Acknowledge bit";
                   type empty;
                 }
                 leaf no-ack {
                   description "Don't set Acknowledge bit";
                   type empty;
                 }
               }
               choice psh-choice {
                 leaf psh {
                   description "Set Push bit";
                   type empty;
                 }
                 leaf no-psh {
                   description "Don't set Push bit";
                   type empty;
                 }
               }
               choice rst-choice {
                 leaf rst {
                   description "Set Reset bit";
                   type empty;
                 }
                 leaf no-rst {
                   description "Don't set Reset bit";
                   type empty;
                 }
               }
               choice syn-choice {
                 leaf syn {
                   description "Set SYN bit";
                   type empty;
                 }
                 leaf no-syn {
                   description "Don't set SYN bit";
                   type empty;
                 }
               }
               choice fin-choice {
                 leaf fin {
                   description "Set FINish bit";
                   type empty;
                 }
                 leaf no-fin {
                   description "Don't set FINish bit";
                   type empty;
                 }
               }
             }
             container option {
               presence "enable option";
               description "Kind";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container data-length {
               presence "enable data-length";
               description "Size of IP datagram subtracted by TCP header length";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "2 .. 255";
                   }
                 }
               }
             }
             container window-scale {
               presence "enable window-scale";
               description "Window scale";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container mss {
               presence "enable mss";
               description "Maximum Segment Size";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container checksum-validate {
               presence "enable checksum-validate";
               description "Validate checksum field against calculated checksum";
               leaf match {
                 description "Match condition";
                 junos:must "(\".. value\")";
                 junos:must-message "Missing mandatory statement: 'value'";
                 type enumeration {
                   enum "equal" {
                     description "Match when checksum field in packet is exact match";
                   }
                   enum "greater-than" {
                     description "Match when checksum field in packet is greater";
                   }
                   enum "less-than" {
                     description "Match when checksum field in packet is less";
                   }
                   enum "not-equal" {
                     description "Match when checksum field in packet is not exact match";
                   }
                 }
               }
               leaf value {
                 description "Match value";
                 default "0";
                 junos:must "(\".. match\")";
                 junos:must-message "Missing mandatory statement: 'match'";
                 type union {
                   type string {
                     pattern "<.*>|$.*";
                   }
                   type uint32 {
                     range "0 .. 65535";
                   }
                 }
               }
             }
           }
           container udp {
             junos:must "((!(\".. tcp\") && !(\".. icmp\")))";
             junos:must-message "udp cannot be specified with tcp or icmp";
             description "UDP protocol parameters";
             uses apply-advanced;
             container source-port {
               presence "enable source-port";
               description "Source port";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container destination-port {
               presence "enable destination-port";
               description "Destination port";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container data-length {
               presence "enable data-length";
               description "Size of IP datagram subtracted by UDP header length";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container checksum-validate {
               presence "enable checksum-validate";
               description "Validate checksum field against calculated checksum";
               leaf match {
                 description "Match condition";
                 junos:must "(\".. value\")";
                 junos:must-message "Missing mandatory statement: 'value'";
                 type enumeration {
                   enum "equal" {
                     description "Match when checksum field in packet is exact match";
                   }
                   enum "greater-than" {
                     description "Match when checksum field in packet is greater";
                   }
                   enum "less-than" {
                     description "Match when checksum field in packet is less";
                   }
                   enum "not-equal" {
                     description "Match when checksum field in packet is not exact match";
                   }
                 }
               }
               leaf value {
                 description "Match value";
                 default "0";
                 junos:must "(\".. match\")";
                 junos:must-message "Missing mandatory statement: 'match'";
                 type union {
                   type string {
                     pattern "<.*>|$.*";
                   }
                   type uint32 {
                     range "0 .. 65535";
                   }
                 }
               }
             }
           }
           container icmp {
             junos:must "((!(\".. udp\") && (!(\".. tcp\") && !(\".. icmpv6\"))))";
             junos:must-message "icmp cannot be specified with tcp or udp or icmpv6";
             description "ICMP protocol parameters";
             uses apply-advanced;
             container type {
               presence "enable type";
               description "Type";
               uses apply-advanced;
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container code {
               presence "enable code";
               description "Code";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container identification {
               presence "enable identification";
               description "Identifier in echo request/reply";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container sequence-number {
               presence "enable sequence-number";
               description "Sequence Number";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container data-length {
               presence "enable data-length";
               description "Size of IP datagram subtracted by ICMP header length";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container checksum-validate {
               presence "enable checksum-validate";
               description "Validate checksum field against calculated checksum";
               leaf match {
                 description "Match condition";
                 junos:must "(\".. value\")";
                 junos:must-message "Missing mandatory statement: 'value'";
                 type enumeration {
                   enum "equal" {
                     description "Match when checksum field in packet is exact match";
                   }
                   enum "greater-than" {
                     description "Match when checksum field in packet is greater";
                   }
                   enum "less-than" {
                     description "Match when checksum field in packet is less";
                   }
                   enum "not-equal" {
                     description "Match when checksum field in packet is not exact match";
                   }
                 }
               }
               leaf value {
                 description "Match value";
                 default "0";
                 junos:must "(\".. match\")";
                 junos:must-message "Missing mandatory statement: 'match'";
                 type union {
                   type string {
                     pattern "<.*>|$.*";
                   }
                   type uint32 {
                     range "0 .. 65535";
                   }
                 }
               }
             }
           }
           container icmpv6 {
             junos:must "((!(\".. udp\") && (!(\".. tcp\") && !(\".. icmp\"))))";
             junos:must-message "icmpv6 cannot be specified with tcp or udp or icmp";
             description "ICMPv6 protocol parameters";
             uses apply-advanced;
             container type {
               presence "enable type";
               description "Type";
               uses apply-advanced;
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container code {
               presence "enable code";
               description "Code";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container identification {
               presence "enable identification";
               description "Identifier in echo request/reply";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container sequence-number {
               presence "enable sequence-number";
               description "Sequence number";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container data-length {
               presence "enable data-length";
               description "Size of IPv6 datagram subtracted by ICMPv6 header length";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container checksum-validate {
               presence "enable checksum-validate";
               description "Validate checksum field against calculated checksum";
               leaf match {
                 description "Match condition";
                 junos:must "(\".. value\")";
                 junos:must-message "Missing mandatory statement: 'value'";
                 type enumeration {
                   enum "equal" {
                     description "Match when checksum field in packet is exact match";
                   }
                   enum "greater-than" {
                     description "Match when checksum field in packet is greater";
                   }
                   enum "less-than" {
                     description "Match when checksum field in packet is less";
                   }
                   enum "not-equal" {
                     description "Match when checksum field in packet is not exact match";
                   }
                 }
               }
               leaf value {
                 description "Match value";
                 default "0";
                 junos:must "(\".. match\")";
                 junos:must-message "Missing mandatory statement: 'match'";
                 type union {
                   type string {
                     pattern "<.*>|$.*";
                   }
                   type uint32 {
                     range "0 .. 65535";
                   }
                 }
               }
             }
           }
         }
       }
       container anomaly {
         junos:must "(!(\".. signature\"))";
         junos:must-message "Only one attack type is permitted";
         description "Protocol anomaly";
         uses apply-advanced;
         leaf test {
           description "Protocol anomaly condition to be checked";
           type string;
         }
         leaf direction {
           description "Direction";
           type enumeration {
             enum "client-to-server" {
               description "From Client to Server";
             }
             enum "server-to-client" {
               description "From Server to Client";
             }
             enum "any" {
               description "Any direction";
             }
           }
         }
         leaf shellcode {
           description "Specify shellcode flag for this attack";
           type enumeration {
             enum "intel" {
               description "Detect shellcode for intel platforms";
             }
             enum "sparc" {
               description "Detect shellcode for sparc platforms";
             }
             enum "all" {
               description "Detect shellcode for both intel and sparc platforms";
             }
             enum "no-shellcode" {
               description "Do not detect shellcode";
             }
           }
         }
       }
     }
   }
   grouping dynamic-attack-group-type {
     description "Define dynamic attack group";
     leaf name {
       description "Name of the dynamic attack group";
       type string;
     }
     uses apply-advanced;
     leaf attack-group-description {
       description "Filter name/value in xml format";
       status deprecated;
       type string;
     }
     container filters {
       description "Configure filters";
       uses apply-advanced;
       container direction {
         presence "enable direction";
         description "Direction of attack";
         uses apply-advanced;
         leaf expression {
           description "Boolean AND/OR to be used for values";
           default "or";
           type enumeration {
             enum "and" {
               description "AND values together (recommended if 'exclude-*' values are set)";
             }
             enum "or" {
               description "OR values together";
             }
           }
         }
         leaf-list values {
           ordered-by user;
           description "Values for direction field";
           type enumeration {
             enum "client-to-server" {
               description "Select attacks from client to server";
             }
             enum "server-to-client" {
               description "Select attacks from server to client";
             }
             enum "any" {
               description "Select attacks which can occur in either direction";
             }
             enum "exclude-client-to-server" {
               description "Filter out attacks from client to server";
             }
             enum "exclude-server-to-client" {
               description "Filter out attacks from server to client";
             }
             enum "exclude-any" {
               description "Filter out attacks which occur in either direction";
             }
           }
         }
       }
       container severity {
         presence "enable severity";
         description "Severity of attack";
         uses apply-advanced;
         leaf-list values {
           ordered-by user;
           description "Values for severity field";
           type enumeration {
             enum "info" {
               description "Provide information of attack when it matches.";
             }
             enum "warning" {
               description "Issue a warning when attack matches.";
             }
             enum "minor" {
               description "The attack is a minor one.";
             }
             enum "major" {
               description "The attack is a major one.";
             }
             enum "critical" {
               description "The attack is a critical one.";
             }
           }
         }
       }
       container type {
         presence "enable type";
         description "Type of attack";
         uses apply-advanced;
         leaf-list values {
           ordered-by user;
           description "Values for type field";
           type enumeration {
             enum "signature" {
               description "Signature based attacks";
             }
             enum "anomaly" {
               description "Protocol anomalies";
             }
           }
         }
       }
       choice recommended-choice {
         leaf recommended {
           description "Recommended flag";
           type empty;
         }
         leaf no-recommended {
           description "Don't recommended flag";
           type empty;
         }
       }
       container performance {
         presence "enable performance";
         description "Performance of attack";
         uses apply-advanced;
         leaf-list values {
           ordered-by user;
           description "Values for performance field";
           type enumeration {
             enum "unknown" {
               description "Performance level unknown";
             }
             enum "fast" {
               description "Fast performance";
             }
             enum "normal" {
               description "Normal performance";
             }
             enum "slow" {
               description "Slow performance";
             }
           }
         }
       }
       container category {
         presence "enable category";
         description "Category of attack";
         uses apply-advanced;
         leaf-list values {
           ordered-by user;
           description "Values for category field";
           type string;
         }
       }
       container service {
         presence "enable service";
         description "Service/Application of attack";
         uses apply-advanced;
         leaf-list values {
           ordered-by user;
           description "Values for service field";
           type string;
         }
       }
       container false-positives {
         presence "enable false-positives";
         description "False positive field in attack";
         uses apply-advanced;
         leaf-list values {
           ordered-by user;
           description "Values for false-positives field";
           type enumeration {
             enum "unknown" {
               description "Unknown information";
             }
             enum "rarely" {
               description "Rare false positives occurrence";
             }
             enum "occasionally" {
               description "Ocassional false positives occurrence";
             }
             enum "frequently" {
               description "Frequent false positives occurrence";
             }
           }
         }
       }
       list vendor {
         key name;
         ordered-by user;
         description "Vendor/Product the attack belongs to";
         uses vendor-object;
       }
       container file-type {
         presence "enable file-type";
         description "File type the attack is valid for";
         uses apply-advanced;
         leaf-list values {
           ordered-by user;
           description "Values for file-type field";
           type string;
         }
       }
       container vulnerability-type {
         presence "enable vulnerability-type";
         description "Vulnariability type of attack";
         uses apply-advanced;
         leaf-list values {
           ordered-by user;
           description "Values for vulnariability-type field";
           type string;
         }
       }
       choice excluded-choice {
         leaf excluded {
           description "Excluded Attacks";
           type empty;
         }
         leaf no-excluded {
           description "Don't excluded Attacks";
           type empty;
         }
       }
       container attack-prefix {
         presence "enable attack-prefix";
         description "Prefix match for attack names";
         uses apply-advanced;
         leaf-list values {
           ordered-by user;
           description "Values for attack name prefix match";
           type string;
         }
       }
       list cvss-score {
         key name;
         ordered-by user;
         description "CVSS score of Attack ";
         leaf name {
           description "Match condition of CVSS score";
           type enumeration {
             enum "greater-than" {
               description "Match when cvss score is greater";
             }
             enum "less-than" {
               description "Match when cvss score is less";
             }
           }
         }
         uses apply-advanced;
         leaf value {
           description "Match value";
           junos:must "(\".. value\")";
           junos:must-message "Missing mandatory statement: 'value'";
           type decimal64 {
             fraction-digits 9;
             range "0 .. 10";
           }
         }
       }
       list age-of-attack {
         key name;
         ordered-by user;
         description "Age of an Attack ";
         leaf name {
           description "Match condition of Age of Attack";
           type enumeration {
             enum "greater-than" {
               description "Match when Age of Attack is greater";
             }
             enum "less-than" {
               description "Match when Age of Attack is less";
             }
           }
         }
         uses apply-advanced;
         leaf value {
           description "Match value";
           junos:must "(\".. value\")";
           junos:must-message "Missing mandatory statement: 'value'";
           type union {
             type string {
               pattern "<.*>|$.*";
             }
             type uint32 {
               range "1 .. 100";
             }
           }
         }
       }
     }
   }
   grouping idp-policy-type {
     leaf name {
       description "IDP policy name";
       type string;
     }
     container rulebase-ips {
       description "IPS rulebase";
       uses apply-advanced;
       list rule {
         key name;
         ordered-by user;
         description "Configure IPS rule";
         leaf name {
           description "Rule name";
           type string;
         }
         uses apply-advanced;
         leaf description {
           description "Rule description";
           type string;
         }
         container match {
           description "Rule match criteria";
           uses apply-advanced;
           leaf from-zone {
             description "Match from zone";
             default "any";
             junos:must "((\".. from-zone any\" || \"security zones security-zone $$\"))";
             junos:must-message "from-zone should be 'any' or configured under [security zones security-zone]";
             type string;
           }
           choice source {
             case case_1 {
               leaf-list source-address {
                 ordered-by user;
                 description "Match source address";
                 type string;
               }
             }
             case case_2 {
               leaf-list source-except {
                 ordered-by user;
                 description "Don't match source address";
                 type string;
               }
             }
             case case_3 {
             }
             case case_4 {
             }
           }
           leaf to-zone {
             description "Match to zone";
             default "any";
             junos:must "((\".. to-zone any\" || \"security zones security-zone $$\"))";
             junos:must-message "to-zone should be 'any' or configured under [security zones security-zone]";
             type string;
           }
           choice destination {
             case case_1 {
               leaf-list destination-address {
                 ordered-by user;
                 description "Match destination address";
                 type string;
               }
             }
             case case_2 {
               leaf-list destination-except {
                 ordered-by user;
                 description "Don't match destination address";
                 type string;
               }
             }
             case case_3 {
             }
             case case_4 {
             }
           }
           leaf application {
             description "Specify application or application-set name to match";
             type string;
           }
           container attacks {
             description "Match attack objects";
             uses apply-advanced;
             leaf-list custom-attacks {
               ordered-by user;
               description "Custom attacks";
               type string;
             }
             leaf-list custom-attack-groups {
               ordered-by user;
               description "Custom attack groups";
               type string;
             }
             leaf-list dynamic-attack-groups {
               ordered-by user;
               description "Dynamic attack groups";
               type string;
             }
             leaf-list predefined-attacks {
               ordered-by user;
               description "Predefined attacks";
               type string;
             }
             leaf-list predefined-attack-groups {
               ordered-by user;
               description "Predefined attack groups";
               type string;
             }
           }
         }
         container then {
           uses apply-advanced;
           container action {
             choice action {
               case case_1 {
                 leaf no-action {
                   description "No action";
                   type empty;
                 }
               }
               case case_2 {
                 leaf ignore-connection {
                   description "Ignore";
                   type empty;
                 }
               }
               case case_3 {
                 container mark-diffserv {
                   description "Mark differentiated services codepoint (DSCP)";
                   uses apply-advanced;
                   leaf codepoint {
                     description "Codepoint value";
                     type union {
                       type string {
                         pattern "<.*>|$.*";
                       }
                       type uint32 {
                         range "0 .. 63";
                       }
                     }
                   }
                 }
               }
               case case_4 {
                 container class-of-service {
                   description "Classification of traffic based on class-of-service";
                   uses apply-advanced;
                   leaf forwarding-class {
                     description "Forwarding class for outgoing packets";
                     type string {
                       junos:posix-pattern "^.{1,64}$";
                       junos:pattern-message "Must be string of 64 characters or less";
                     }
                   }
                   leaf dscp-code-point {
                     description "Differentiated services code point value";
                     type union {
                       type string {
                         pattern "<.*>|$.*";
                       }
                       type uint32 {
                         range "0 .. 63";
                       }
                     }
                   }
                 }
               }
               case case_5 {
                 leaf drop-packet {
                   description "Drop packet";
                   type empty;
                 }
               }
               case case_6 {
                 leaf drop-connection {
                   description "Drop connection";
                   type empty;
                 }
               }
               case case_7 {
                 leaf close-client {
                   description "Close client";
                   type empty;
                 }
               }
               case case_8 {
                 leaf close-server {
                   description "Close server";
                   type empty;
                 }
               }
               case case_9 {
                 leaf close-client-and-server {
                   description "Close client and server";
                   type empty;
                 }
               }
               case case_10 {
                 leaf recommended {
                   description "Recommended";
                   junos:must "(\".. .. .. match attacks\")";
                   junos:must-message "attacks must also be configured.";
                   type empty;
                 }
               }
             }
           }
           container ip-action {
             uses apply-advanced;
             choice ip-action {
               case case_1 {
                 leaf ip-notify {
                   description "Notify about future traffic";
                   type empty;
                 }
               }
               case case_2 {
                 leaf ip-close {
                   description "Close future connections";
                   type empty;
                 }
               }
               case case_3 {
                 leaf ip-block {
                   description "Block future connections";
                   type empty;
                 }
               }
             }
             leaf target {
               type enumeration {
                 enum "service" {
                   description "Match source, destination, dst-port and protocol";
                 }
                 enum "source-zone-address" {
                   description "Match source-zone and source-address";
                 }
                 enum "source-address" {
                   description "Match source";
                 }
                 enum "destination-address" {
                   description "Match destination";
                 }
                 enum "zone-service" {
                   description "Match source-zone, destination, dst-port, protocol";
                 }
                 enum "source-zone" {
                   description "Match source-zone";
                 }
               }
             }
             leaf log {
               description "Log IP action taken";
               type empty;
             }
             leaf log-create {
               description "Log IP action creation";
               type empty;
             }
             leaf timeout {
               description "Number of seconds IP action should remain effective";
               type union {
                 type string {
                   pattern "<.*>|$.*";
                 }
                 type uint32 {
                   range "0 .. 64800";
                 }
               }
             }
             leaf refresh-timeout {
               description "Refresh timeout when future connections match installed ip-action filter";
               junos:must "(\".. timeout\")";
               junos:must-message "timeout must be specified";
               type empty;
             }
           }
           container notification {
             presence "enable notification";
             description "Configure notification/logging options";
             uses apply-advanced;
             container log-attacks {
               presence "enable log-attacks";
               description "Enable attack logging";
               uses apply-advanced;
               leaf alert {
                 description "Set alert flag in attack log";
                 type empty;
               }
             }
             container packet-log {
               presence "enable packet-log";
               uses apply-advanced;
               leaf pre-attack {
                 description "No of packets to capture before attack";
                 default "1";
                 type union {
                   type string {
                     pattern "<.*>|$.*";
                   }
                   type uint32 {
                     range "1 .. 255";
                   }
                 }
               }
               leaf post-attack {
                 description "No of packets to capture after attack";
                 type union {
                   type string {
                     pattern "<.*>|$.*";
                   }
                   type uint32 {
                     range "0 .. 255";
                   }
                 }
               }
               leaf post-attack-timeout {
                 description "Timeout (seconds) after attack before stopping packet capture";
                 default "5";
                 type union {
                   type string {
                     pattern "<.*>|$.*";
                   }
                   type uint32 {
                     range "0 .. 1800";
                   }
                 }
               }
             }
           }
           leaf severity {
             description "Set rule severity level";
             type enumeration {
               enum "info" {
               }
               enum "warning" {
               }
               enum "minor" {
               }
               enum "major" {
               }
               enum "critical" {
               }
             }
           }
           container application-services {
             description "Enable application services for this rule";
             container security-intelligence {
               description "Generate security intellegence feeds";
               leaf add-attacker-ip-to-feed {
                 description "Specify the desired feed-name";
                 type string {
                   length "1 .. 64";
                 }
               }
               leaf add-target-ip-to-feed {
                 description "Specify the desired feed-name";
                 type string {
                   length "1 .. 64";
                 }
               }
             }
           }
         }
         leaf terminal {
           description "Set/Unset terminal flag";
           type empty;
         }
       }
     }
     container rulebase-exempt {
       description "Exempt rulebase";
       uses apply-advanced;
       list rule {
         key name;
         ordered-by user;
         description "Configure exempt rule";
         leaf name {
           description "Rule name";
           type string;
         }
         uses apply-advanced;
         leaf description {
           description "Rule description";
           type string;
         }
         container match {
           description "Rule match criteria";
           uses apply-advanced;
           leaf from-zone {
             description "Match from zone";
             default "any";
             junos:must "((\".. from-zone any\" || \"security zones security-zone $$\"))";
             junos:must-message "from-zone should be 'any' or configured under [security zones security-zone]";
             type string;
           }
           choice source {
             case case_1 {
               leaf-list source-address {
                 ordered-by user;
                 description "Match source address";
                 type string;
               }
             }
             case case_2 {
               leaf-list source-except {
                 ordered-by user;
                 description "Don't match source address";
                 type string;
               }
             }
             case case_3 {
             }
             case case_4 {
             }
           }
           leaf to-zone {
             description "Match to zone";
             default "any";
             junos:must "((\".. to-zone any\" || \"security zones security-zone $$\"))";
             junos:must-message "to-zone should be 'any' or configured under [security zones security-zone]";
             type string;
           }
           choice destination {
             case case_1 {
               leaf-list destination-address {
                 ordered-by user;
                 description "Match destination address";
                 type string;
               }
             }
             case case_2 {
               leaf-list destination-except {
                 ordered-by user;
                 description "Don't match destination address";
                 type string;
               }
             }
             case case_3 {
             }
             case case_4 {
             }
           }
           container attacks {
             description "Match attack objects";
             uses apply-advanced;
             leaf-list custom-attacks {
               ordered-by user;
               description "Custom attacks";
               type string;
             }
             leaf-list custom-attack-groups {
               ordered-by user;
               description "Custom attack groups";
               type string;
             }
             leaf-list dynamic-attack-groups {
               ordered-by user;
               description "Dynamic attack groups";
               type string;
             }
             leaf-list predefined-attacks {
               ordered-by user;
               description "Predefined attacks";
               type string;
             }
             leaf-list predefined-attack-groups {
               ordered-by user;
               description "Predefined attack groups";
               type string;
             }
           }
         }
       }
     }
   }
   grouping idpd-traceoptions-type {
     description "Trace options for idpd";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Events and other information to include in trace output";
       leaf name {
         description "Flag name to include in trace output";
         type enumeration {
           enum "all" {
             description "All events";
           }
         }
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
   }
   grouping log-object {
     description "Configure auditable security logs";
     uses apply-advanced;
     list exclude {
       key name;
       ordered-by user;
       description "List of security log criteria to exclude from the audit log";
       status deprecated;
       leaf name {
         description "Exclude criteria name";
         type string;
       }
       uses apply-advanced;
       leaf destination-address {
         description "Destination address";
         type jt:ipaddr;
       }
       leaf destination-port {
         description "Destination port";
         type union {
           type uint32;
           type string {
             pattern "<.*>|$.*";
           }
         }
       }
       leaf event-id {
         description "Event ID filter";
         type string;
       }
       leaf failure {
         description "Event was a failure";
         type empty;
       }
       leaf interface-name {
         description "Name of interface";
         type string;
       }
       leaf policy-name {
         description "Policy name filter";
         type string;
       }
       leaf process {
         description "Process that generated the event";
         type string;
       }
       leaf protocol {
         description "Protocol filter";
         type string;
       }
       leaf source-address {
         description "Source address";
         type jt:ipaddr;
       }
       leaf source-port {
         description "Source port";
         type union {
           type uint32;
           type string {
             pattern "<.*>|$.*";
           }
         }
       }
       leaf success {
         description "Event was successful";
         type empty;
       }
       leaf username {
         description "Username filter";
         type string;
       }
     }
     leaf limit {
       description "Limit number of security log entries to keep in memory";
       status deprecated;
       default "10000";
       type union {
         type uint32;
         type string {
           pattern "<.*>|$.*";
         }
       }
     }
     container cache {
       presence "enable cache";
       description "Cache security log events in the audit log buffer";
       uses apply-advanced;
       list exclude {
         key name;
         ordered-by user;
         description "List of security log criteria to exclude from the audit log";
         junos:must "(!(\".. .. exclude\"))";
         junos:must-message "'security log cache exclude' and 'security log exclude' are mutually exclusive";
         leaf name {
           description "Exclude criteria name";
           type string;
         }
         uses apply-advanced;
         leaf destination-address {
           description "Destination address";
           type jt:ipaddr;
         }
         leaf destination-port {
           description "Destination port";
           type union {
             type uint32;
             type string {
               pattern "<.*>|$.*";
             }
           }
         }
         leaf event-id {
           description "Event ID filter";
           type string;
         }
         leaf failure {
           description "Event was a failure";
           type empty;
         }
         leaf interface-name {
           description "Name of interface";
           type string;
         }
         leaf policy-name {
           description "Policy name filter";
           type string;
         }
         leaf process {
           description "Process that generated the event";
           type string;
         }
         leaf protocol {
           description "Protocol filter";
           type string;
         }
         leaf source-address {
           description "Source address";
           type jt:ipaddr;
         }
         leaf source-port {
           description "Source port";
           type union {
             type uint32;
             type string {
               pattern "<.*>|$.*";
             }
           }
         }
         leaf success {
           description "Event was successful";
           type empty;
         }
         leaf username {
           description "Username filter";
           type string;
         }
       }
       leaf limit {
         description "Limit number of security log entries to keep in memory";
         default "10000";
         junos:must "(!(\".. .. limit\"))";
         junos:must-message "'security log cache limit' and 'security log limit' are mutually exclusive";
         type union {
           type uint32;
           type string {
             pattern "<.*>|$.*";
           }
         }
       }
     }
   }
   grouping logical-system-type {
     description "Logical system name";
     leaf name {
       description "Logical system name";
       junos:must "(\"logical-systems $$\")";
       junos:must-message "Logical systems must be defined under [logical-systems] ";
       type string;
     }
     uses apply-advanced;
     leaf max-sessions {
       description "Max number of IDP sessions";
       type union {
         type uint32;
         type string {
           pattern "<.*>|$.*";
         }
       }
     }
   }
   grouping macro-data-type {
     leaf name {
       description "Keyword part of the keyword-value pair";
       type string;
     }
     leaf value {
       description "Value part of the keyword-value pair";
       type string;
     }
   }
   grouping port-range {
     description "Port ranges";
     leaf name {
       description "Single port/minimum port in the port range";
       type union {
         type string {
           pattern "<.*>|$.*";
         }
         type uint32 {
           range "0 .. 65535";
         }
       }
     }
     leaf maximum-port {
       description "Maximum port in the port range";
       type union {
         type string {
           pattern "<.*>|$.*";
         }
         type uint32 {
           range "0 .. 65535";
         }
       }
     }
   }
   grouping proto-object {
     leaf name {
       type string;
     }
     uses apply-advanced;
     list tunable-name {
       key name;
       ordered-by user;
       description "Protocol tunable name";
       uses tunable-object;
     }
   }
   grouping security-authentication-key-chains {
     uses apply-advanced;
     list key-chain {
       key name;
       description "Key chain configuration";
       leaf name {
         description "Name of authentication key chain";
         type string {
           junos:posix-pattern "!^((__.*__)|(.*[ ].*)|(.{33,}))$";
           junos:pattern-message "Must be string of 32 characters or less with no spaces";
         }
       }
       uses apply-advanced;
       leaf description {
         description "Text description of this authentication-key-chain";
         type string {
           length "1 .. 80";
         }
       }
       leaf tolerance {
         description "Clock skew tolerance";
         default "3600";
         units "seconds";
         type union {
           type string {
             pattern "<.*>|$.*";
           }
           type uint32 {
             range "0 .. 4294967295";
           }
         }
       }
       list key {
         key name;
         description "Authentication element configuration";
         leaf name {
           description "Authentication element identifier";
           type union {
             type string {
               pattern "<.*>|$.*";
             }
             type uint32 {
               range "0 .. 63";
             }
           }
         }
         uses apply-advanced;
         leaf secret {
           description "Authentication key";
           type string {
             length "1 .. 126";
           }
         }
         leaf key-name {
           description "Key name in hexadecimal format used for macsec";
           type string {
             length "2 .. 64";
             junos:posix-pattern "^([0-9a-fA-F][0-9a-fA-F]){1,32}$";
             junos:pattern-message "Must be an even-length string up to 64 hexadecimal digits (0-9, a-f, A-F)";
           }
         }
         leaf start-time {
           description "Start time for key transmission (YYYY-MM-DD.HH:MM)";
           type jt:time;
         }
         leaf algorithm {
           description "Authentication algorithm";
           default "md5";
           type enumeration {
             enum "md5" {
               description "Message Digest 5";
             }
             enum "hmac-sha-1" {
               description "Hash-based Message Authentication Code (SHA1) (96 bits)";
               junos:must "(\".. options isis-enhanced\")";
               junos:must-message "sha algorithm required isis-enhanced";
             }
             enum "ao" {
               description "TCP Authentication Option";
             }
           }
         }
         leaf options {
           description "Protocol's transmission encoding format";
           default "basic";
           type enumeration {
             enum "basic" {
               description "Rudimentary encoding format";
             }
             enum "isis-enhanced" {
               description "RFC 5310 based encoding";
             }
           }
         }
         container ao-attribute {
           junos:must "(!(\".. authentication-key\"))";
           junos:must-message "Cannot be configured with authentication-key";
           junos:must "(\".. algorithm ao\")";
           junos:must-message "Can only be configured with authentication-algorithm ao";
           description "TCP Authentication option attributes";
           uses apply-advanced;
           leaf send-id {
             description "Send id for TCP-AO entry";
             type union {
               type string {
                 pattern "<.*>|$.*";
               }
               type uint32 {
                 range "0 .. 255";
               }
             }
           }
           leaf recv-id {
             description "Recv id for TCP-AO entry";
             type union {
               type string {
                 pattern "<.*>|$.*";
               }
               type uint32 {
                 range "0 .. 255";
               }
             }
           }
           leaf tcp-ao-option {
             description "Include TCP-AO option within message header";
             default "disabled";
             type enumeration {
               enum "enabled" {
                 description "Include the TCP-AO option";
               }
               enum "disabled" {
                 description "Not include the TCP-AO option";
               }
             }
           }
           leaf cryptographic-algorithm {
             description "Cryptographic algorithm for TCP-AO Traffic key and MAC digest generation";
             default "hmac-sha-1-96";
             type enumeration {
               enum "hmac-sha-1-96" {
                 description "Hash-based Message Authentication Code (SHA1) (96 bits)";
               }
               enum "aes-128-cmac-96" {
                 description "Cipher-based Message Authentication Code (AES128) (96 bits)";
               }
             }
           }
         }
       }
     }
   }
   grouping security-group-vpn {
     uses apply-advanced;
     container member {
       description "Group VPN member configuration";
       uses gvpn-member;
     }
   }
   grouping gvpn-member {
     uses apply-advanced;
     container ike {
       description "Group VPN IKE configuration";
       uses gvpn-member-ike;
     }
     container ipsec {
       description "Group VPN IPsec configuration";
       uses gvpn-member-ipsec-vpn;
     }
   }
   grouping gvpn-member-ike {
     uses apply-advanced;
     container traceoptions {
       description "Trace options for Group VPN Member";
       uses apply-advanced;
       leaf no-remote-trace {
         description "Disable remote tracing";
         junos:must "(\"system tracing\")";
         junos:must-message "'no-remote-trace' is valid only when [system tracing] is configured";
         type empty;
       }
       container file {
         description "Trace file information";
         leaf filename {
           description "Name of file in which to write trace information";
           type string {
             length "1 .. 1024";
             junos:posix-pattern "![/ %]";
             junos:pattern-message "Must not contain '/', % or a space";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       leaf level {
         description "Level of debugging output";
         default "error";
         type enumeration {
           enum "error" {
             description "Match error conditions";
           }
           enum "warning" {
             description "Match warning messages";
           }
           enum "notice" {
             description "Match conditions that should be handled specially";
           }
           enum "info" {
             description "Match informational messages";
           }
           enum "verbose" {
             description "Match verbose messages";
           }
           enum "all" {
             description "Match all levels";
           }
         }
       }
       list flag {
         key name;
         ordered-by user;
         description "Tracing parameters";
         leaf name {
           type enumeration {
             enum "timer" {
               description "Trace internal timer events";
             }
             enum "routing-socket" {
               description "Trace routing socket messages";
             }
             enum "parse" {
               description "Trace configuration processing";
             }
             enum "config" {
               description "Trace configuration download processing";
             }
             enum "ike" {
               description "Trace IKE module processing";
             }
             enum "policy-manager" {
               description "Trace policy manager processing";
             }
             enum "general" {
               description "Trace general events";
             }
             enum "database" {
               description "Trace security associations database events";
             }
             enum "certificates" {
               description "Trace certificate events";
             }
             enum "snmp" {
               description "Trace SNMP operations";
             }
             enum "thread" {
               description "Trace thread processing";
             }
             enum "high-availability" {
               description "Trace high-availability operations";
             }
             enum "next-hop-tunnels" {
               description "Trace next-hop-tunnels operations";
             }
             enum "all" {
               description "Trace everything";
             }
           }
         }
       }
       container gateway-filter {
         description "Set gateway filter for trace";
         uses apply-advanced;
         leaf local-address {
           description "Use an IP address to identify the local gateway";
           type jt:ipv4addr;
         }
         leaf remote-address {
           description "Use an IP address to identify the remote gateway";
           type jt:ipv4addr;
         }
       }
     }
     list proposal {
       key name;
       ordered-by user;
       description "Define an IKE proposal";
       uses gvpn-member-ike-proposal;
     }
     list policy {
       key name;
       ordered-by user;
       description "Define an IKE policy";
       uses gvpn-ike-policy;
     }
     list gateway {
       key name;
       ordered-by user;
       description "Define an IKE gateway";
       leaf name {
         description "Label for the remote (peer) gateway";
         junos:must "(!(\"security ike gateway $$\"))";
         junos:must-message "Gateway already defined under [security ike]";
         type string {
           length "1 .. 32";
         }
       }
       uses apply-advanced;
       leaf ike-policy {
         description "Name of the IKE policy";
         junos:must "(!(\"security ike policy $$\"))";
         junos:must-message "Policy already defined under [security ike]";
         junos:must "(\"security group-vpn member ike policy $$\")";
         junos:must-message "Referenced IKE policy must be defined under [edit security group-vpn member ike policy]";
         type string {
           length "1 .. 32";
         }
       }
       container local-identity {
         description "Set the local IKE identity";
         choice identity-type {
           case case_1 {
             container inet {
               description "Use an IPv4 address";
               uses apply-advanced;
               leaf identity-ipv4 {
                 description "The local IPv4 identity";
                 type jt:ipv4addr;
               }
             }
           }
           case case_2 {
             container hostname {
               description "Use a fully-qualified domain name";
               uses apply-advanced;
               leaf identity-hostname {
                 description "The local hostname";
                 type string;
               }
             }
           }
           case case_3 {
             container user-at-hostname {
               description "Use an e-mail address";
               uses apply-advanced;
               leaf identity-user {
                 description "The local user-FQDN";
                 type string;
               }
             }
           }
           case case_4 {
             leaf distinguished-name {
               description "Use a distinguished name specified in local certificate";
               type empty;
             }
           }
         }
       }
       leaf local-address {
         description "Local IPv4 address for group member";
         junos:must "(!(any \"security group-vpn member ike gateway <*> server-address $$\"))";
         junos:must-message "Member can not have the same local address as server";
         type jt:ipv4addr;
       }
       leaf routing-instance {
         description "Name of routing instance that hosts local address";
         default "default";
         junos:must "(\"routing-instances $$\")";
         junos:must-message "Referenced routing-instance must be defined";
         type string;
       }
     }
   }
   grouping gvpn-ike-policy {
     leaf name {
       description "Name of policy";
       junos:must "((\".. proposals\" || \".. proposal-set\"))";
       junos:must-message "IKE policy must have either proposals or proposal-set configured";
       junos:must "(((\".. certificate local-certificate\" || \".. pre-shared-key\") && !((\".. certificate local-certificate\" && \".. pre-shared-key\"))))";
       junos:must-message "IKE policy must have either local certificate or pre-shared key configured";
       junos:must "(!(\"security ike policy $$\"))";
       junos:must-message "Policy already defined under [security ike policy]";
       type string {
         length "1 .. 32";
       }
     }
     uses apply-advanced;
     leaf mode {
       description "Define the IKE mode for Phase 1";
       default "main";
       type enumeration {
         enum "main" {
           description "Main mode";
         }
         enum "aggressive" {
           description "Aggressive mode";
         }
       }
     }
     leaf description {
       description "Text description of IKE policy";
       type string {
         length "1 .. 80";
       }
     }
     leaf-list proposals {
       ordered-by user;
       description "Name of the proposal";
       junos:must "(\".. .. .. proposal $$\")";
       junos:must-message "Referenced proposal is not defined";
       type string {
         length "1 .. 32";
         junos:posix-pattern "^[[:alnum:]][[:alnum:]_-]*$";
         junos:pattern-message "Must be a string beginning with a number or letter and consisting of letters, numbers, dashes and underscores.";
       }
     }
     container certificate {
       description "Certificate configuration";
       uses apply-advanced;
       leaf local-certificate {
         description "Local certificate identifier";
         type string {
           junos:posix-pattern "^.{1,32}$";
           junos:pattern-message "Must be string of 32 characters or less";
         }
       }
       container trusted-ca {
         description "Specify the CA to use";
         status deprecated;
         choice ca {
           case case_1 {
             leaf ca-index {
               description "Index of the preferred CA to use";
               type union {
                 type uint32;
                 type string {
                   pattern "<.*>|$.*";
                 }
               }
             }
           }
           case case_2 {
             leaf use-all {
               description "Use all configured CAs";
               type empty;
             }
           }
         }
       }
       leaf peer-certificate-type {
         description "Preferred type of certificate from peer";
         default "x509-signature";
         type enumeration {
           enum "pkcs7" {
             description "PKCS7 encoding";
           }
           enum "x509-signature" {
             description "X509 signature encoding";
           }
         }
       }
     }
     leaf proposal-set {
       description "Types of default IKE proposal-set";
       type enumeration {
         enum "basic" {
           description "IKE proposal-set for basic";
           junos:must "(!(\".. proposals\"))";
           junos:must-message "IKE policy must not have both proposals and proposal-set configured";
         }
         enum "compatible" {
           description "IKE proposal-set for compatible";
           junos:must "(!(\".. proposals\"))";
           junos:must-message "IKE policy must not have both proposals and proposal-set configured";
         }
         enum "standard" {
           description "IKE proposal-set for standard";
           junos:must "(!(\".. proposals\"))";
           junos:must-message "IKE policy must not have both proposals and proposal-set configured";
         }
       }
     }
     container pre-shared-key {
       description "Define a preshared key";
       choice key-choice {
         case case_1 {
           leaf ascii-text {
             description "Format as text";
             type string {
               length "1 .. 255";
             }
           }
         }
         case case_2 {
           leaf hexadecimal {
             description "Format as hexadecimal";
             type string {
               length "1 .. 255";
               junos:posix-pattern "^[[:xdigit:]]+$";
               junos:pattern-message "Must be hexadecimal digits (0-9, a-f, A-F)";
             }
           }
         }
       }
     }
   }
   grouping gvpn-member-ike-proposal {
     leaf name {
       description "Name of the IKE proposal";
       junos:must "(!(\"security ike proposal $$\"))";
       junos:must-message "Proposal already defined under [security ike proposal]";
       type string {
         length "1 .. 32";
       }
     }
     uses apply-advanced;
     leaf description {
       description "Text description of IKE proposal";
       type string {
         length "1 .. 80";
       }
     }
     leaf authentication-method {
       description "Define authentication method";
       type enumeration {
         enum "pre-shared-keys" {
           description "Preshared keys";
         }
         enum "rsa-signatures" {
           description "RSA signatures";
         }
         enum "dsa-signatures" {
           description "DSA signatures";
         }
       }
     }
     leaf dh-group {
       description "Define Diffie-Hellman group";
       type enumeration {
         enum "group1" {
           description "Diffie-Hellman Group 1";
         }
         enum "group2" {
           description "Diffie-Hellman Group 2";
         }
         enum "group5" {
           description "Diffie-Hellman Group 5";
         }
         enum "group14" {
           description "Diffie-Hellman Group 14";
         }
       }
     }
     leaf authentication-algorithm {
       description "Define authentication algorithm";
       type enumeration {
         enum "md5" {
           description "MD5 authentication algorithm";
         }
         enum "sha1" {
           description "SHA1 authentication algorithm";
         }
         enum "sha-256" {
           description "SHA 256-bit authentication algorithm";
         }
       }
     }
     leaf encryption-algorithm {
       description "Define encryption algorithm";
       type enumeration {
         enum "des-cbc" {
           description "DES-CBC encryption algorithm";
         }
         enum "3des-cbc" {
           description "3DES-CBC encryption algorithm";
         }
         enum "aes-128-cbc" {
           description "AES-CBC 128-bit encryption algorithm";
         }
         enum "aes-192-cbc" {
           description "AES-CBC 192-bit encryption algorithm";
         }
         enum "aes-256-cbc" {
           description "AES-CBC 256-bit encryption algorithm";
         }
       }
     }
     leaf lifetime-seconds {
       description "Lifetime, in seconds";
       default "180";
       units "seconds";
       type union {
         type string {
           pattern "<.*>|$.*";
         }
         type uint32 {
           range "180 .. 86400";
         }
       }
     }
   }
   grouping gvpn-member-ipsec-vpn {
     uses apply-advanced;
     list vpn {
       key name;
       ordered-by user;
       description "Define an IPSec VPN";
       uses ipsec-gvpn-member-template;
     }
   }
   grouping ipsec-gvpn-member-template {
     description "Configure a Group VPN";
     leaf name {
       description "Name of the VPN";
       junos:must "(!(\"security ipsec vpn $$\"))";
       junos:must-message "VPN already defined under [security ipsec]";
       type string {
         length "1 .. 32";
       }
     }
     uses apply-advanced;
     leaf ike-gateway {
       description "Name of IKE gateway";
       junos:must "(\"security group-vpn member ike gateway $$\")";
       junos:must-message "Referenced IKE gateway must be defined under [edit security group-vpn member ike gateway]";
       type string {
         length "1 .. 32";
       }
     }
     leaf group {
       description "Enable Group VPN by defining group id";
       junos:must "((\".. no-group-check\" || unique \"security group-vpn member ipsec vpn <*> group $$\"))";
       junos:must-message "Group id must be unique among group vpns";
       type union {
         type string {
           pattern "<.*>|$.*";
         }
         type uint32 {
           range "1 .. 65535";
         }
       }
     }
     leaf match-direction {
       description "Direction for which the rule match is applied";
       type enumeration {
         enum "input" {
           description "Match on input to interface";
         }
         enum "output" {
           description "Match on output from interface";
         }
       }
     }
     leaf tunnel-mtu {
       description "Maximum transmit packet size";
       default "1500";
       type union {
         type string {
           pattern "<.*>|$.*";
         }
         type uint32 {
           range "256 .. 9192";
         }
       }
     }
     leaf df-bit {
       description "Specifies how to handle the Don't Fragment bit";
       default "clear";
       type enumeration {
         enum "clear" {
           description "Clear DF bit of outer header";
         }
         enum "set" {
           description "Set DF bit of outer header";
         }
         enum "copy" {
           description "Copy DF bit from inner header";
         }
       }
     }
     leaf forward-policy-mismatch {
       description "Enables forwarding of policy mismatch packets";
       type empty;
     }
     container fail-open {
       description "List of fail open rules";
       uses ipsec_gvpn_fail_open_rule_object;
     }
   }
   grouping ipsec_gvpn_fail_open_rule_object {
     uses apply-advanced;
     list rule {
       key name;
       ordered-by user;
       description "Define fail open rules upto 10";
       max-elements 10;
       uses ipsec_gvpn_rule_address_object;
     }
   }
   grouping ipsec_gvpn_rule_address_object {
     leaf name {
       description "Rule name";
       type string {
         length "1 .. 63";
         junos:posix-pattern "^[[:alnum:]][[:alnum:]_-]*$";
         junos:pattern-message "Must be a string beginning with a number or letter and consisting of letters, numbers, dashes and underscores.";
       }
     }
     uses apply-advanced;
     container source-address {
       description "Match IP source address";
       presence "enable source-address";
       uses ipsec_gvpn_addr_object;
     }
     container destination-address {
       description "Match IP destination address";
       presence "enable destination-address";
       uses ipsec_gvpn_addr_object;
     }
   }
   grouping ipsec_gvpn_addr_object {
     uses apply-advanced;
     leaf address {
       description "Prefix to match";
       type jt:ipv4prefix-only;
     }
   }
   grouping security-ike {
     uses apply-advanced;
     container traceoptions {
       description "Trace options for IPSec key management";
       uses security-traceoptions;
     }
     container respond-bad-spi {
       presence "enable respond-bad-spi";
       description "Respond to IPSec packets with bad SPI values";
       leaf max-responses {
         description "Maximum number of times to respond";
         default "5";
         type union {
           type string {
             pattern "<.*>|$.*";
           }
           type uint32 {
             range "1 .. 30";
           }
         }
       }
     }
     list proposal {
       key name;
       ordered-by user;
       description "Define an IKE proposal";
       uses ike-proposal;
     }
     list policy {
       key name;
       ordered-by user;
       description "Define an IKE policy";
       uses ike-policy;
     }
     list gateway {
       key name;
       ordered-by user;
       description "Define an IKE gateway";
       leaf name {
         description "Label for the remote (peer) gateway";
         type string {
           length "1 .. 32";
         }
       }
       uses apply-advanced;
       leaf ike-policy {
         description "Name of the IKE policy";
         junos:must "(!((\"security ike policy $$ mode main\" && (\"security ike policy $$ pre-shared-key\" && \".. dynamic\"))))";
         junos:must-message "Main mode for dynamic peer with Preshared key based authentication is not allowed";
         junos:must "(\"security ike policy $$\")";
         junos:must-message "Referenced IKE policy must be defined under [edit security ike policy]";
         type string {
           length "1 .. 32";
         }
       }
       choice remote-identifier {
         case case_1 {
           leaf-list address {
             ordered-by user;
             description "Addresses or hostnames of peer:1 primary, upto 4 backups";
             type string;
           }
         }
         case case_2 {
           container dynamic {
             description "Site to site peer with dynamic IP address";
             uses apply-advanced;
             choice remote-id-type {
               case case_1 {
                 container distinguished-name {
                   presence "enable distinguished-name";
                   description "Use a distinguished name: ";
                   uses apply-advanced;
                   choice name-type {
                     case case_1 {
                       leaf container {
                         description "Specify the container string";
                         type string;
                       }
                     }
                     case case_2 {
                       leaf wildcard {
                         description "Specify the wildcard string";
                         type string;
                       }
                     }
                   }
                 }
               }
               case case_2 {
                 leaf hostname {
                   description "Use a fully-qualified domain name";
                   type string;
                 }
               }
               case case_3 {
                 leaf inet {
                   description "Use an IPV4 address to identify the dynamic peer";
                   type jt:ipv4addr;
                 }
               }
               case case_4 {
                 leaf inet6 {
                   description "Use an IPV6 address to identify the dynamic peer";
                   type jt:ipv6addr;
                 }
               }
               case case_5 {
                 leaf user-at-hostname {
                   description "Use an e-mail address";
                   type string;
                 }
               }
             }
             leaf connections-limit {
               description "Maximum number of users connected to gateway";
               type union {
                 type uint32;
                 type string {
                   pattern "<.*>|$.*";
                 }
               }
             }
             leaf ike-user-type {
               description "Type of the IKE ID";
               type enumeration {
                 enum "group-ike-id" {
                   description "Email address or FQDN shared as IKED ID by multiple users";
                 }
                 enum "shared-ike-id" {
                   description "Email address shared as IKED ID by multiple users";
                   junos:must "(\" .. .. xauth\")";
                   junos:must-message "Need to configure xauth at [edit security ike gateway]";
                 }
               }
             }
           }
         }
       }
       container dead-peer-detection {
         presence "enable dead-peer-detection";
         description "Enable RFC-3706 DPD";
         uses apply-advanced;
         leaf always-send {
           description "Send DPD messages periodically, regardless of traffic";
           type empty;
         }
         leaf interval {
           description "The interval at which to send DPD messages";
           default "10";
           units "seconds";
           type union {
             type string {
               pattern "<.*>|$.*";
             }
             type uint32 {
               range "10 .. 60";
             }
           }
         }
         leaf threshold {
           description "Maximum number of DPD retransmissions";
           default "5";
           type union {
             type string {
               pattern "<.*>|$.*";
             }
             type uint32 {
               range "1 .. 5";
             }
           }
         }
       }
       leaf no-nat-traversal {
         description "Disable IPSec NAT traversal";
         type empty;
       }
       leaf nat-keepalive {
         description "Interval at which to send NAT keepalives";
         default "5";
         units "seconds";
         type union {
           type string {
             pattern "<.*>|$.*";
           }
           type uint32 {
             range "1 .. 300";
           }
         }
       }
       container local-identity {
         description "Set the local IKE identity";
         choice identity-type {
           case case_1 {
             container inet {
               description "Use an IPv4 address";
               uses apply-advanced;
               leaf identity-ipv4 {
                 description "The local IPv4 identity";
                 type jt:ipv4addr;
               }
             }
           }
           case case_2 {
             container inet6 {
               description "Use an IPv6 address";
               uses apply-advanced;
               leaf identity-ipv6 {
                 description "The local IPv6 identity";
                 type jt:ipv6addr;
               }
             }
           }
           case case_3 {
             container hostname {
               description "Use a fully-qualified domain name";
               uses apply-advanced;
               leaf identity-hostname {
                 description "The local hostname";
                 type string;
               }
             }
           }
           case case_4 {
             container user-at-hostname {
               description "Use an e-mail address";
               uses apply-advanced;
               leaf identity-user {
                 description "The local user-FQDN";
                 type string;
               }
             }
           }
           case case_5 {
             leaf distinguished-name {
               description "Use a distinguished name specified in local certificate";
               type empty;
             }
           }
         }
       }
       container remote-identity {
         junos:must "(!(\".. dynamic\"))";
         junos:must-message "Since the remote gateway is dynamic, Define remote identity under dynamic";
         description "Set the remote IKE identity";
         choice identity-type {
           case case_1 {
             container inet {
               description "Use an IPv4 address";
               uses apply-advanced;
               leaf identity-ipv4 {
                 description "The remote IPv4 identity";
                 type jt:ipv4addr;
               }
             }
           }
           case case_2 {
             container inet6 {
               description "Use an IPv6 address";
               uses apply-advanced;
               leaf identity-ipv6 {
                 description "The remote IPv6 identity";
                 type jt:ipv6addr;
               }
             }
           }
           case case_3 {
             container hostname {
               description "Use a fully-qualified domain name";
               uses apply-advanced;
               leaf identity-hostname {
                 description "The remote hostname";
                 type string;
               }
             }
           }
           case case_4 {
             container user-at-hostname {
               description "Use an e-mail address";
               uses apply-advanced;
               leaf identity-user {
                 description "The remote user-FQDN";
                 type string;
               }
             }
           }
           case case_5 {
             container distinguished-name {
               presence "enable distinguished-name";
               description "Use a distinguished name: ";
               uses apply-advanced;
               leaf container {
                 description "Specify the container string";
                 type string;
               }
               leaf wildcard {
                 description "Specify the wildcard string";
                 type string;
               }
             }
           }
         }
       }
       leaf external-interface {
         description "External interface for IKE negotiations";
         junos:must "(!(\"interfaces $$ family bridge\"))";
         junos:must-message "Bridge interface is not allowed as external-interface";
         junos:must "(\"interfaces $$-IFL\")";
         junos:must-message "Referenced interface must be configured under [edit interfaces] hierarchy";
         type union {
           type jt:interface-unit;
           type string {
             pattern "<.*>|$.*";
           }
         }
       }
       container xauth {
         description "Use extended authentication";
         leaf access-profile {
           description "Access profile that contains authentication information";
           junos:must "(\"access profile $$\")";
           junos:must-message "profile needs to be configured";
           type string;
         }
       }
       leaf general-ikeid {
         description "Accept peer IKE-ID in general";
         junos:must "(!(\".. remote-identity\"))";
         junos:must-message "general-ikeid option is not allowed when remote-identity is configured";
         junos:must "(!(\".. dynamic\"))";
         junos:must-message "general-ikd-id option is not available for dynamic peer.";
         type empty;
       }
       leaf version {
         description "Negotiate using either IKE v1 or IKE v2 protocol";
         default "v1-only";
         type enumeration {
           enum "v1-only" {
             description "The connection must be initiated using IKE version 1";
           }
           enum "v2-only" {
             description "The connection must be initiated using IKE version 2";
           }
         }
       }
     }
   }
   grouping ike-policy {
     leaf name {
       description "IKE peer address";
       junos:must "((\"security ike policy $$ pre-shared-key\" || \"security ike policy $$ local-certificate\"))";
       junos:must-message "Either pre-shared-key or local-certificate must be configured in ike policy";
       type jt:ipv4addr;
     }
     uses apply-advanced;
     leaf mode {
       description "Define the IKE first phase mode";
       type enumeration {
         enum "main" {
           description "Main mode";
         }
         enum "aggressive" {
           description "Aggressive mode";
         }
       }
     }
     leaf description {
       description "Text description of IKE policy";
       type string {
         length "1 .. 80";
       }
     }
     leaf-list proposals {
       ordered-by user;
       description "Name of the proposal";
       junos:must "(\".. .. .. proposal $$\")";
       junos:must-message "Referenced proposal is not defined";
       type string {
         length "1 .. 32";
         junos:posix-pattern "^[[:alnum:]][[:alnum:]_-]*$";
         junos:pattern-message "Must be a string beginning with a number or letter and consisting of letters, numbers, dashes and underscores.";
       }
     }
     leaf local-certificate {
       description "File to read certificate from";
       junos:must "(!(\".. local-key-pair $$\"))";
       junos:must-message "Local certificate and local key pair files must be different";
       type string {
         length "1 .. 255";
       }
     }
     leaf local-key-pair {
       description "File to read key-pair from";
       type string {
         length "1 .. 255";
       }
     }
     leaf encoding {
       description "Encoding to use for certificate or CRL on disk";
       default "binary";
       type enumeration {
         enum "binary" {
           description "DER encoding";
         }
         enum "pem" {
           description "Privacy-enhanced-mail encoding, base64";
         }
       }
     }
     leaf identity {
       description "Define the remote certificate name";
       type string {
         length "1 .. 32";
       }
     }
     container pre-shared-key {
       description "Define a preshared key";
       choice key-choice {
         case case_1 {
           leaf ascii-text {
             description "Format as text";
             type string {
               length "1 .. 255";
             }
           }
         }
         case case_2 {
           leaf hexadecimal {
             description "Format as hexadecimal";
             type string {
               length "1 .. 255";
               junos:posix-pattern "^[[:xdigit:]]+$";
               junos:pattern-message "Must be hexadecimal digits (0-9, a-f, A-F)";
             }
           }
         }
       }
     }
   }
   grouping ike-proposal {
     leaf name {
       description "Name of the IKE proposal";
       junos:must "(((\"services ipsec-vpn ike proposal $$\" && !(\"security ike proposal $$\")) || (\"security ike proposal $$\" && !(\"services ipsec-vpn ike proposal $$\"))))";
       junos:must-message "Referenced IKE proposal must not be defined both under [edit security ike proposal] and [edit services ipsec-vpn ike proposal]";
       type string {
         length "1 .. 32";
         junos:posix-pattern "^[[:alnum:]][[:alnum:]_-]*$";
         junos:pattern-message "Must be a string beginning with a number or letter and consisting of letters, numbers, dashes and underscores.";
       }
     }
     uses apply-advanced;
     leaf description {
       description "Text description of IKE proposal";
       type string {
         length "1 .. 80";
       }
     }
     leaf authentication-method {
       description "Define authentication method";
       type enumeration {
         enum "pre-shared-keys" {
           description "Preshared keys";
         }
         enum "rsa-signatures" {
           description "RSA signatures";
         }
         enum "dsa-signatures" {
           description "DSA signatures";
         }
         enum "ecdsa-signatures-256" {
           description "ECDSA signatures (254 bit modulus)";
         }
         enum "ecdsa-signatures-384" {
           description "ECDSA signatures (384 bit modulus)";
         }
       }
     }
     leaf dh-group {
       description "Define Diffie-Hellman group";
       type enumeration {
         enum "group1" {
           description "Diffie-Hellman Group1";
         }
         enum "group2" {
           description "Diffie-Hellman Group2";
         }
         enum "group5" {
           description "Diffie-Hellman Group5";
         }
         enum "group14" {
           description "Diffie-Hellman Group14";
         }
         enum "group15" {
           description "Diffie-Hellman Group15";
         }
         enum "group16" {
           description "Diffie-Hellman Group16";
         }
         enum "group19" {
           description "Diffie-Hellman Group19";
         }
         enum "group20" {
           description "Diffie-Hellman Group20";
         }
         enum "group24" {
           description "Diffie-Hellman Group24";
         }
       }
     }
     leaf authentication-algorithm {
       description "Define authentication algorithm";
       type enumeration {
         enum "md5" {
           description "MD5 authentication algorithm";
         }
         enum "sha1" {
           description "SHA1 authentication algorithm";
         }
         enum "sha-256" {
           description "SHA 256-bit authentication algorithm";
         }
         enum "sha-384" {
           description "SHA 384-bit authentication algorithm";
         }
       }
     }
     leaf encryption-algorithm {
       description "Define encryption algorithm";
       type enumeration {
         enum "des-cbc" {
           description "DES-CBC encryption algorithm";
         }
         enum "3des-cbc" {
           description "3DES-CBC encryption algorithm";
         }
         enum "aes-128-cbc" {
           description "AES-CBC 128-bit encryption algorithm";
         }
         enum "aes-192-cbc" {
           description "AES-CBC 192-bit encryption algorithm";
         }
         enum "aes-256-cbc" {
           description "AES-CBC 256-bit encryption algorithm";
         }
       }
     }
     leaf lifetime-seconds {
       description "Lifetime, in seconds";
       units "seconds";
       type union {
         type string {
           pattern "<.*>|$.*";
         }
         type uint32 {
           range "180 .. 86400";
         }
       }
     }
   }
   grouping security-ipsec-vpn {
     uses apply-advanced;
     container traceoptions {
       description "Trace options for IPSec data-plane debug";
       uses ipsec-traceoptions;
     }
     container vpn-monitor-options {
       description "Global options for VPN liveliness monitoring";
       presence "enable vpn-monitor-options";
       uses ipsec-vpn-monitor;
     }
     list proposal {
       key name;
       ordered-by user;
       description "Define an IPSec proposal";
       uses ipsec-proposal;
     }
     list policy {
       key name;
       ordered-by user;
       description "Define an IPSec policy";
       uses ipsec-policy;
     }
     list vpn {
       key name;
       ordered-by user;
       description "Define an IPSec VPN";
       uses ipsec-vpn-template;
     }
     list security-association {
       key name;
       ordered-by user;
       description "Define an IPSec security association";
       uses ipsec-sa;
     }
     container internal {
       presence "enable internal";
       description "Define an IPSec SA for internal RE-RE communication";
       uses apply-advanced;
       container security-association {
         description "Define an IPSec security association";
         presence "enable security-association";
         uses ipsec-internal-sa;
       }
     }
     container trusted-channel {
       presence "enable trusted-channel";
       junos:must "(\"security ipsec trusted-channel security-association\")";
       junos:must-message "Must configure trusted-channel security-association";
       description "Define an IPSec SA for trusted-channel communication";
       uses apply-advanced;
       container security-association {
         description "Define an IPSec security association";
         presence "enable security-association";
         uses ipsec-trusted-channel-sa;
       }
       leaf-list port-exclusion-list {
         ordered-by user;
         description "Define port exlusion list";
         junos:must "(\"security ipsec trusted-channel security-association\")";
         junos:must-message "Must configure trusted-channel security-association";
         type union {
           type string {
             pattern "<.*>|$.*";
           }
           type uint32 {
             range "1 .. 65535";
           }
         }
       }
     }
   }
   grouping ipsec-internal-sa {
     uses apply-advanced;
     leaf description {
       description "Text description of internal security association";
       type string {
         length "1 .. 80";
       }
     }
     container manual {
       description "Define a manual security association";
       uses apply-advanced;
       list direction {
         key name;
         ordered-by user;
         description "Define the direction of the security association";
         leaf name {
           type enumeration {
             enum "inbound" {
               description "Inbound security association";
               junos:must "(\".. .. direction $$={outbound}\")";
               junos:must-message "Outbound block must be configured";
             }
             enum "outbound" {
               description "Outbound security association";
               junos:must "(\".. .. direction $$={inbound}\")";
               junos:must-message "Inbound block must be configured";
             }
             enum "bidirectional" {
               description "Bidirectional security association";
               junos:must "((!(\".. .. direction $$={inbound}\") && !(\".. .. direction $$={outbound}\")))";
               junos:must-message "Outbound or inbound blocks must not be configured";
             }
           }
         }
         uses apply-advanced;
         leaf protocol {
           description "Define an IPSec protocol for the security association";
           type enumeration {
             enum "ah" {
               description "Authentication header";
               junos:must "(!(\".. encryption\"))";
               junos:must-message "Encryption must not be defined for AH";
               junos:must "(\".. authentication\")";
               junos:must-message "Authentication must be defined for AH";
             }
             enum "esp" {
               description "Encapsulated Security Payload header";
               junos:must "((\".. authentication\" || \".. encryption\"))";
               junos:must-message "Either authentication or encryption must be defined for ESP";
             }
             enum "bundle" {
               description "Bundle (AH authentication plus ESP encryption)";
               junos:must "(\".. auxiliary-spi\")";
               junos:must-message "Auxiliary SPI must be defined for AH plus ESP bundle";
               junos:must "(\".. encryption\")";
               junos:must-message "Encryption must be defined for AH plus ESP bundle";
               junos:must "(\".. authentication\")";
               junos:must-message "Authentication must be defined for AH plus ESP bundle";
             }
           }
         }
         leaf spi {
           description "Define security parameter index";
           type union {
             type string {
               pattern "<.*>|$.*";
             }
             type uint32 {
               range "256 .. 16639";
             }
           }
         }
         leaf auxiliary-spi {
           description "ESP security parameter index for IPSec SA bundle";
           junos:must "(\".. protocol bundle\")";
           junos:must-message "Auxiliary SPI must be configured with protocol bundle only";
           type union {
             type string {
               pattern "<.*>|$.*";
             }
             type uint32 {
               range "256 .. 16639";
             }
           }
         }
         container authentication {
           description "Define authentication parameters";
           uses apply-advanced;
           leaf algorithm {
             description "Define authentication algorithm";
             type enumeration {
               enum "hmac-md5-96" {
                 description "HMAC-MD5-96 authentication algorithm";
               }
               enum "hmac-sha1-96" {
                 description "HMAC-SHA1-96 authentication algorithm";
               }
               enum "hmac-sha2-256" {
                 description "HMAC-SHA2-256 authentication algorithm";
               }
               enum "hmac-sha-256-128" {
                 description "HMAC-SHA-256-128 authentication algorithm";
               }
             }
           }
           container key {
             description "Define an authentication key";
             choice key-choice {
               case case_1 {
                 leaf ascii-text {
                   description "Format as text";
                   type string {
                     length "1 .. 255";
                   }
                 }
               }
               case case_2 {
                 leaf hexadecimal {
                   description "Format as hexadecimal";
                   type string {
                     length "1 .. 255";
                     junos:posix-pattern "^[[:xdigit:]]+$";
                     junos:pattern-message "Must be hexadecimal digits (0-9, a-f, A-F)";
                   }
                 }
               }
             }
           }
         }
         container encryption {
           description "Define encryption parameters";
           uses apply-advanced;
           leaf algorithm {
             description "Define encryption algorithm";
             type enumeration {
               enum "des-cbc" {
                 description "DES-CBC encryption algorithm";
               }
               enum "3des-cbc" {
                 description "3DES-CBC encryption algorithm";
               }
               enum "aes-128-cbc" {
                 description "AES-CBC 128-bit encryption algorithm";
               }
               enum "aes-192-cbc" {
                 description "AES-CBC 192-bit encryption algorithm";
               }
               enum "aes-256-cbc" {
                 description "AES-CBC 256-bit encryption algorithm";
               }
             }
           }
           container key {
             description "Define an encryption key";
             choice key-choice {
               case case_1 {
                 leaf ascii-text {
                   description "Format as text";
                   type string {
                     length "1 .. 255";
                   }
                 }
               }
               case case_2 {
                 leaf hexadecimal {
                   description "Format as hexadecimal";
                   type string {
                     length "1 .. 255";
                     junos:posix-pattern "^[[:xdigit:]]+$";
                     junos:pattern-message "Must be hexadecimal digits (0-9, a-f, A-F)";
                   }
                 }
               }
             }
           }
         }
       }
     }
   }
   grouping ipsec-policy {
     leaf name {
       description "Name of the IPSec policy";
       junos:must "(((\"services ipsec-vpn ipsec policy $$\" && !(\"security ipsec policy $$\")) || (\"security ipsec policy $$\" && !(\"services ipsec-vpn ipsec policy $$\"))))";
       junos:must-message "Referenced IPSec policy must not be defined both under [edit security ipsec policy] and [edit services ipsec-vpn ipsec policy]";
       type string {
         length "1 .. 32";
         junos:posix-pattern "^[[:alnum:]][[:alnum:]_-]*$";
         junos:pattern-message "Must be a string beginning with a number or letter and consisting of letters, numbers, dashes and underscores.";
       }
     }
     uses apply-advanced;
     leaf description {
       description "Text description of IPSec policy";
       type string {
         length "1 .. 80";
       }
     }
     container perfect-forward-secrecy {
       description "Define perfect forward secrecy";
       uses apply-advanced;
       leaf keys {
         description "Define Diffie-Hellman group";
         type enumeration {
           enum "group1" {
             description "Diffie-Hellman Group1";
           }
           enum "group2" {
             description "Diffie-Hellman Group2";
           }
           enum "group5" {
             description "Diffie-Hellman Group5";
           }
           enum "group14" {
             description "Diffie-Hellman Group14";
           }
           enum "group15" {
             description "Diffie-Hellman Group15";
           }
           enum "group16" {
             description "Diffie-Hellman Group16";
           }
           enum "group19" {
             description "Diffie-Hellman Group19";
           }
           enum "group20" {
             description "Diffie-Hellman Group20";
           }
           enum "group24" {
             description "Diffie-Hellman Group24";
           }
         }
       }
     }
     leaf-list proposals {
       ordered-by user;
       description "Name of the proposal";
       junos:must "(\".. .. .. proposal $$\")";
       junos:must-message "Referenced proposal is not defined";
       type string {
         length "1 .. 32";
         junos:posix-pattern "^[[:alnum:]][[:alnum:]_-]*$";
         junos:pattern-message "Must be a string beginning with a number or letter and consisting of letters, numbers, dashes and underscores.";
       }
     }
     leaf proposal-set {
       description "Types of default IPSEC proposal-set";
       type enumeration {
         enum "basic" {
           description "IPSEC basic proposal-set";
           junos:must "(!(\".. proposals\"))";
           junos:must-message "IPSec policy must not have both proposals and proposal-set configured";
         }
         enum "compatible" {
           description "IPSEC compatible proposal-set";
           junos:must "(!(\".. proposals\"))";
           junos:must-message "IPSec policy must not have both proposals and proposal-set configured";
         }
         enum "standard" {
           description "IPSEC standard proposal-set";
           junos:must "(!(\".. proposals\"))";
           junos:must-message "IPSec policy must not have both proposals and proposal-set configured";
         }
       }
     }
   }
   grouping ipsec-proposal {
     leaf name {
       description "Name of the IPSec proposal";
       junos:must "(((\"services ipsec-vpn ipsec proposal $$\" && !(\"security ipsec proposal $$\")) || (\"security ipsec proposal $$\" && !(\"services ipsec-vpn ipsec proposal $$\"))))";
       junos:must-message "Referenced IPSec proposal must not be defined both under [edit security ipsec proposal] and [edit services ipsec-vpn ipsec proposal]";
       type string {
         length "1 .. 32";
         junos:posix-pattern "^[[:alnum:]][[:alnum:]_-]*$";
         junos:pattern-message "Must be a string beginning with a number or letter and consisting of letters, numbers, dashes and underscores.";
       }
     }
     uses apply-advanced;
     leaf description {
       description "Text description of IPSec proposal";
       type string {
         length "1 .. 80";
       }
     }
     leaf protocol {
       description "Define an IPSec protocol for the proposal";
       type enumeration {
         enum "ah" {
           description "Authentication header";
           junos:must "(!(\".. encryption-algorithm\"))";
           junos:must-message "Encryption algorithm must not be defined for AH";
         }
         enum "esp" {
           description "Encapsulated Security Payload header";
         }
         enum "bundle" {
           description "Bundle (AH authentication plus ESP encryption)";
         }
       }
     }
     leaf authentication-algorithm {
       description "Define authentication algorithm";
       type enumeration {
         enum "hmac-md5-96" {
           description "HMAC-MD5-96 authentication algorithm";
         }
         enum "hmac-sha1-96" {
           description "HMAC-SHA1-96 authentication algorithm";
         }
         enum "hmac-sha-256-128" {
           description "HMAC-SHA-256-128 authentication algorithm";
           junos:must "(\".. .. .. .. ipsec-vpn\")";
           junos:must-message "hmac-sha-256-128 algorithm is not supported for IKE and IPSec configuration in security hierarchy";
         }
         enum "hmac-sha-256-96" {
           description "HMAC-SHA-256-96 authentication algorithm (non-RFC compliant)";
         }
         enum "hmac-sha2-256" {
           description "HMAC-SHA2-256 authentication algorithm";
         }
       }
     }
     leaf encryption-algorithm {
       description "Define encryption algorithm";
       type enumeration {
         enum "des-cbc" {
           description "DES-CBC encryption algorithm";
         }
         enum "3des-cbc" {
           description "3DES-CBC encryption algorithm";
         }
         enum "aes-128-cbc" {
           description "AES-CBC 128-bit encryption algorithm";
         }
         enum "aes-192-cbc" {
           description "AES-CBC 192-bit encryption algorithm";
         }
         enum "aes-256-cbc" {
           description "AES-CBC 256-bit encryption algorithm";
         }
         enum "aes-128-gcm" {
           description "AES-GCM 128-bit encryption algorithm with 16 octet ICV";
           junos:must "(!(\".. authentication-algorithm\"))";
           junos:must-message "HMAC Authentication is not compatible with AES-GCM";
         }
         enum "aes-192-gcm" {
           description "AES-GCM 192-bit encryption algorithm with 16 octet ICV";
           junos:must "(!(\".. authentication-algorithm\"))";
           junos:must-message "HMAC Authentication is not compatible with AES-GCM";
         }
         enum "aes-256-gcm" {
           description "AES-GCM 256-bit encryption algorithm with 16 octet ICV";
           junos:must "(!(\".. authentication-algorithm\"))";
           junos:must-message "HMAC Authentication is not compatible with AES-GCM";
         }
       }
     }
     leaf lifetime-seconds {
       description "Lifetime, in seconds";
       units "seconds";
       type union {
         type string {
           pattern "<.*>|$.*";
         }
         type uint32 {
           range "180 .. 86400";
         }
       }
     }
   }
   grouping ipsec-sa {
     leaf name {
       description "Name of IPSec security association";
       type string {
         length "1 .. 32";
         junos:posix-pattern "^[[:alnum:]][[:alnum:]_-]*$";
         junos:pattern-message "Must be a string beginning with a number or letter and consisting of letters, numbers, dashes and underscores.";
       }
     }
     uses apply-advanced;
     leaf description {
       description "Text description of security association";
       type string {
         length "1 .. 80";
       }
     }
     leaf mode {
       description "Define security association mode";
       default "tunnel";
       type enumeration {
         enum "transport" {
           description "Transport mode";
           junos:must "(!(\".. dynamic\"))";
           junos:must-message "Dynamic security associations are not supported in transport mode";
           junos:must "(\".. manual\")";
           junos:must-message "Manual block must be configured for transport mode security association";
         }
         enum "tunnel" {
           description "Tunnel mode";
         }
       }
     }
     choice sa_choice {
       case case_1 {
         container manual {
           description "Define a manual security association";
           uses apply-advanced;
           list direction {
             key name;
             ordered-by user;
             description "Define the direction of the security association";
             leaf name {
               type enumeration {
                 enum "inbound" {
                   description "Inbound security association";
                   junos:must "(\".. .. direction $$={outbound}\")";
                   junos:must-message "Outbound block must be configured";
                 }
                 enum "outbound" {
                   description "Outbound security association";
                   junos:must "(\".. .. direction $$={inbound}\")";
                   junos:must-message "Inbound block must be configured";
                 }
                 enum "bidirectional" {
                   description "Bidirectional security association";
                   junos:must "((!(\".. .. direction $$={inbound}\") && !(\".. .. direction $$={outbound}\")))";
                   junos:must-message "Outbound or inbound blocks must not be configured";
                 }
               }
             }
             uses apply-advanced;
             leaf protocol {
               description "Define an IPSec protocol for the security association";
               type enumeration {
                 enum "ah" {
                   description "Authentication header";
                   junos:must "(!(\".. encryption\"))";
                   junos:must-message "Encryption must not be defined for AH";
                   junos:must "(\".. authentication\")";
                   junos:must-message "Authentication must be defined for AH";
                 }
                 enum "esp" {
                   description "Encapsulated Security Payload header";
                   junos:must "((\".. authentication\" || \".. encryption\"))";
                   junos:must-message "Either authentication or encryption must be defined for ESP";
                 }
                 enum "bundle" {
                   description "Bundle (AH authentication plus ESP encryption)";
                   junos:must "(\".. auxiliary-spi\")";
                   junos:must-message "Auxiliary SPI must be defined for AH plus ESP bundle";
                   junos:must "(\".. encryption\")";
                   junos:must-message "Encryption must be defined for AH plus ESP bundle";
                   junos:must "(\".. authentication\")";
                   junos:must-message "Authentication must be defined for AH plus ESP bundle";
                 }
               }
             }
             leaf spi {
               description "Define security parameter index";
               type union {
                 type string {
                   pattern "<.*>|$.*";
                 }
                 type uint32 {
                   range "256 .. 16639";
                 }
               }
             }
             leaf auxiliary-spi {
               description "ESP security parameter index for IPSec SA bundle";
               junos:must "(\".. protocol bundle\")";
               junos:must-message "Auxiliary SPI must be configured with protocol bundle only";
               type union {
                 type string {
                   pattern "<.*>|$.*";
                 }
                 type uint32 {
                   range "256 .. 16639";
                 }
               }
             }
             container authentication {
               description "Define authentication parameters";
               uses apply-advanced;
               leaf algorithm {
                 description "Define authentication algorithm";
                 type enumeration {
                   enum "hmac-md5-96" {
                     description "HMAC-MD5-96 authentication algorithm";
                   }
                   enum "hmac-sha1-96" {
                     description "HMAC-SHA1-96 authentication algorithm";
                   }
                   enum "hmac-sha2-256" {
                     description "HMAC-SHA2-256 authentication algorithm";
                   }
                   enum "hmac-sha-256-128" {
                     description "HMAC-SHA-256-128 authentication algorithm";
                   }
                 }
               }
               container key {
                 description "Define an authentication key";
                 choice key-choice {
                   case case_1 {
                     leaf ascii-text {
                       description "Format as text";
                       type string {
                         length "1 .. 255";
                       }
                     }
                   }
                   case case_2 {
                     leaf hexadecimal {
                       description "Format as hexadecimal";
                       type string {
                         length "1 .. 255";
                         junos:posix-pattern "^[[:xdigit:]]+$";
                         junos:pattern-message "Must be hexadecimal digits (0-9, a-f, A-F)";
                       }
                     }
                   }
                 }
               }
             }
             container encryption {
               description "Define encryption parameters";
               uses apply-advanced;
               leaf algorithm {
                 description "Define encryption algorithm";
                 type enumeration {
                   enum "des-cbc" {
                     description "DES-CBC encryption algorithm";
                   }
                   enum "3des-cbc" {
                     description "3DES-CBC encryption algorithm";
                   }
                   enum "aes-128-cbc" {
                     description "AES-CBC 128-bit encryption algorithm";
                   }
                   enum "aes-192-cbc" {
                     description "AES-CBC 192-bit encryption algorithm";
                   }
                   enum "aes-256-cbc" {
                     description "AES-CBC 256-bit encryption algorithm";
                   }
                 }
               }
               container key {
                 description "Define an encryption key";
                 choice key-choice {
                   case case_1 {
                     leaf ascii-text {
                       description "Format as text";
                       type string {
                         length "1 .. 255";
                       }
                     }
                   }
                   case case_2 {
                     leaf hexadecimal {
                       description "Format as hexadecimal";
                       type string {
                         length "1 .. 255";
                         junos:posix-pattern "^[[:xdigit:]]+$";
                         junos:pattern-message "Must be hexadecimal digits (0-9, a-f, A-F)";
                       }
                     }
                   }
                 }
               }
             }
           }
         }
       }
       case case_2 {
         container dynamic {
           description "Define a dynamic security association";
           uses apply-advanced;
           leaf replay-window-size {
             description "Define replay protection window size";
             type enumeration {
               enum "32" {
                 description "32-packet window size";
               }
               enum "64" {
                 description "64-packet window size";
               }
             }
           }
           leaf ipsec-policy {
             description "Name of the IPSec policy";
             junos:must "(\"security ipsec policy $$\")";
             junos:must-message "Referenced IPSec policy must be defined under [edit security ipsec policy]";
             type string {
               length "1 .. 32";
               junos:posix-pattern "^[[:alnum:]][[:alnum:]_-]*$";
               junos:pattern-message "Must be a string beginning with a number or letter and consisting of letters, numbers, dashes and underscores.";
             }
           }
         }
       }
     }
   }
   grouping ipsec-traceoptions {
     description "Data-plane IPSec tracing options";
     uses apply-advanced;
     list flag {
       key name;
       ordered-by user;
       description "Events to include in data-plane IPSec trace output";
       leaf name {
         type enumeration {
           enum "packet-processing" {
             description "Trace data packet processing events";
           }
           enum "packet-drops" {
             description "Trace packet drops";
           }
           enum "security-associations" {
             description "Trace security association management events";
           }
           enum "next-hop-tunnel-binding" {
             description "Trace next-hop tunnel binding events";
           }
           enum "all" {
             description "Trace with all flags enabled";
           }
         }
       }
     }
   }
   grouping ipsec-trusted-channel-sa {
     uses apply-advanced;
     leaf description {
       description "Text description of trusted channel security association";
       type string {
         length "1 .. 80";
       }
     }
     container manual {
       description "Define a manual security association";
       uses apply-advanced;
       list direction {
         key name;
         ordered-by user;
         description "Define the direction of the security association";
         leaf name {
           type enumeration {
             enum "inbound" {
               description "Inbound security association";
               junos:must "(\".. .. direction $$={outbound}\")";
               junos:must-message "Outbound block must be configured";
             }
             enum "outbound" {
               description "Outbound security association";
               junos:must "(\".. .. direction $$={inbound}\")";
               junos:must-message "Inbound block must be configured";
             }
             enum "bidirectional" {
               description "Bidirectional security association";
               junos:must "((!(\".. .. direction $$={inbound}\") && !(\".. .. direction $$={outbound}\")))";
               junos:must-message "Outbound or inbound blocks must not be configured";
             }
           }
         }
         uses apply-advanced;
         leaf protocol {
           description "Define an IPSec protocol for the security association";
           type enumeration {
             enum "ah" {
               description "Authentication header";
               junos:must "(!(\".. encryption\"))";
               junos:must-message "Encryption must not be defined for AH";
               junos:must "(\".. authentication\")";
               junos:must-message "Authentication must be defined for AH";
             }
             enum "esp" {
               description "Encapsulated Security Payload header";
               junos:must "((\".. authentication\" || \".. encryption\"))";
               junos:must-message "Either authentication or encryption must be defined for ESP";
             }
             enum "bundle" {
               description "Bundle (AH authentication plus ESP encryption)";
               junos:must "(\".. auxiliary-spi\")";
               junos:must-message "Auxiliary SPI must be defined for AH plus ESP bundle";
               junos:must "(\".. encryption\")";
               junos:must-message "Encryption must be defined for AH plus ESP bundle";
               junos:must "(\".. authentication\")";
               junos:must-message "Authentication must be defined for AH plus ESP bundle";
             }
           }
         }
         leaf spi {
           description "Define security parameter index";
           type union {
             type string {
               pattern "<.*>|$.*";
             }
             type uint32 {
               range "256 .. 16639";
             }
           }
         }
         leaf auxiliary-spi {
           description "ESP security parameter index for IPSec SA bundle";
           junos:must "(\".. protocol bundle\")";
           junos:must-message "Auxiliary SPI must be configured with protocol bundle only";
           type union {
             type string {
               pattern "<.*>|$.*";
             }
             type uint32 {
               range "256 .. 16639";
             }
           }
         }
         container authentication {
           description "Define authentication parameters";
           uses apply-advanced;
           leaf algorithm {
             description "Define authentication algorithm";
             type enumeration {
               enum "hmac-md5-96" {
                 description "HMAC-MD5-96 authentication algorithm";
               }
               enum "hmac-sha1-96" {
                 description "HMAC-SHA1-96 authentication algorithm";
               }
               enum "hmac-sha2-256" {
                 description "HMAC-SHA2-256 authentication algorithm";
               }
               enum "hmac-sha-256-128" {
                 description "HMAC-SHA-256-128 authentication algorithm";
               }
             }
           }
           container key {
             description "Define an authentication key";
             choice key-choice {
               case case_1 {
                 leaf ascii-text {
                   description "Format as text";
                   type string {
                     length "1 .. 255";
                   }
                 }
               }
               case case_2 {
                 leaf hexadecimal {
                   description "Format as hexadecimal";
                   type string {
                     length "1 .. 255";
                     junos:posix-pattern "^[[:xdigit:]]+$";
                     junos:pattern-message "Must be hexadecimal digits (0-9, a-f, A-F)";
                   }
                 }
               }
             }
           }
         }
         container encryption {
           description "Define encryption parameters";
           uses apply-advanced;
           leaf algorithm {
             description "Define encryption algorithm";
             type enumeration {
               enum "des-cbc" {
                 description "DES-CBC encryption algorithm";
               }
               enum "3des-cbc" {
                 description "3DES-CBC encryption algorithm";
               }
               enum "aes-128-cbc" {
                 description "AES-CBC 128-bit encryption algorithm";
               }
               enum "aes-192-cbc" {
                 description "AES-CBC 192-bit encryption algorithm";
               }
               enum "aes-256-cbc" {
                 description "AES-CBC 256-bit encryption algorithm";
               }
             }
           }
           container key {
             description "Define an encryption key";
             choice key-choice {
               case case_1 {
                 leaf ascii-text {
                   description "Format as text";
                   type string {
                     length "1 .. 255";
                   }
                 }
               }
               case case_2 {
                 leaf hexadecimal {
                   description "Format as hexadecimal";
                   type string {
                     length "1 .. 255";
                     junos:posix-pattern "^[[:xdigit:]]+$";
                     junos:pattern-message "Must be hexadecimal digits (0-9, a-f, A-F)";
                   }
                 }
               }
             }
           }
         }
       }
     }
   }
   grouping ipsec-vpn-monitor {
     description "Configure VPN monitoring";
     uses apply-advanced;
     leaf interval {
       description "Monitor interval in seconds";
       default "10";
       units "seconds";
       type union {
         type string {
           pattern "<.*>|$.*";
         }
         type uint32 {
           range "2 .. 3600";
         }
       }
     }
     leaf threshold {
       description "Number of consecutive failures to determine connectivity";
       default "10";
       type union {
         type string {
           pattern "<.*>|$.*";
         }
         type uint32 {
           range "1 .. 65536";
         }
       }
     }
   }
   grouping ipsec-vpn-template {
     description "Configure an IPSec VPN";
     leaf name {
       description "Name of the VPN";
       type string {
         length "1 .. 32";
       }
     }
     uses apply-advanced;
     leaf bind-interface {
       description "Bind to tunnel interface (route-based VPN)";
       junos:must "((\"interfaces $$\" || any \"logical-systems <*> interfaces $$\"))";
       junos:must-message "Referenced interface must be configured under [edit interfaces] hierarchy";
       type union {
         type jt:interface-name;
         type string {
           pattern "<.*>|$.*";
         }
       }
     }
     leaf df-bit {
       description "Specifies how to handle the Don't Fragment bit";
       type enumeration {
         enum "clear" {
           description "Clear DF bit of outer header";
         }
         enum "set" {
           description "Set DF bit of outer header";
         }
         enum "copy" {
           description "Copy DF bit from inner header";
         }
       }
     }
     container vpn-monitor {
       description "Monitor VPN liveliness";
       presence "enable vpn-monitor";
       uses ipsec-template-monitor;
     }
     choice negotiation {
       case case_1 {
         container manual {
           description "Define a manual security association";
           uses apply-advanced;
           leaf gateway {
             description "Define the IPSec peer";
             type jt:hostname;
           }
           leaf external-interface {
             description "External interface for the security association";
             junos:must "(!(\"interfaces $$ family bridge\"))";
             junos:must-message "Bridge interface is not allowed as external-interface";
             junos:must "(\"interfaces $$-IFL\")";
             junos:must-message "Referenced interface must be configured under [edit interfaces] hierarchy";
             type union {
               type jt:interface-unit;
               type string {
                 pattern "<.*>|$.*";
               }
             }
           }
           leaf protocol {
             description "Define an IPSec protocol for the security association";
             type enumeration {
               enum "ah" {
                 description "Authentication header";
                 junos:must "(!(\".. encryption\"))";
                 junos:must-message "Encryption must not be defined for AH";
                 junos:must "(\".. authentication\")";
                 junos:must-message "Authentication must be defined for AH";
               }
               enum "esp" {
                 description "Encapsulated Security Payload header";
                 junos:must "((\".. authentication\" || \".. encryption\"))";
                 junos:must-message "Either authentication or encryption must be defined for ESP";
               }
             }
           }
           leaf spi {
             description "Define security parameter index";
             type union {
               type string {
                 pattern "<.*>|$.*";
               }
               type uint32 {
                 range "256 .. 16639";
               }
             }
           }
           container authentication {
             description "Define authentication parameters";
             uses apply-advanced;
             leaf algorithm {
               description "Define authentication algorithm";
               type enumeration {
                 enum "hmac-md5-96" {
                   description "HMAC-MD5-96 authentication algorithm";
                 }
                 enum "hmac-sha1-96" {
                   description "HMAC-SHA1-96 authentication algorithm";
                 }
                 enum "hmac-sha-256-128" {
                   description "HMAC-SHA-256-128 authentication algorithm";
                 }
                 enum "hmac-sha-256-96" {
                   description "HMAC-SHA-256-96 authentication algorithm (non-RFC compliant)";
                 }
               }
             }
             container key {
               description "Define an authentication key";
               choice key-choice {
                 case case_1 {
                   leaf ascii-text {
                     description "Format as text";
                     type string {
                       length "1 .. 255";
                     }
                   }
                 }
                 case case_2 {
                   leaf hexadecimal {
                     description "Format as hexadecimal";
                     type string {
                       length "1 .. 255";
                       junos:posix-pattern "^[[:xdigit:]]+$";
                       junos:pattern-message "Must be hexadecimal digits (0-9, a-f, A-F)";
                     }
                   }
                 }
               }
             }
           }
           container encryption {
             description "Define encryption parameters";
             uses apply-advanced;
             leaf algorithm {
               description "Define encryption algorithm";
               type enumeration {
                 enum "des-cbc" {
                   description "DES-CBC encryption algorithm";
                 }
                 enum "3des-cbc" {
                   description "3DES-CBC encryption algorithm";
                 }
                 enum "aes-128-cbc" {
                   description "AES-CBC 128-bit encryption algorithm";
                 }
                 enum "aes-192-cbc" {
                   description "AES-CBC 192-bit encryption algorithm";
                 }
                 enum "aes-256-cbc" {
                   description "AES-CBC 256-bit encryption algorithm";
                 }
               }
             }
             container key {
               description "Define an encryption key";
               choice key-choice {
                 case case_1 {
                   leaf ascii-text {
                     description "Format as text";
                     type string {
                       length "1 .. 255";
                     }
                   }
                 }
                 case case_2 {
                   leaf hexadecimal {
                     description "Format as hexadecimal";
                     type string {
                       length "1 .. 255";
                       junos:posix-pattern "^[[:xdigit:]]+$";
                       junos:pattern-message "Must be hexadecimal digits (0-9, a-f, A-F)";
                     }
                   }
                 }
               }
             }
           }
         }
       }
       case case_2 {
         container ike {
           description "Define an IKE-keyed IPSec vpn";
           uses apply-advanced;
           leaf gateway {
             description "Name of remote gateway";
             junos:must "(!((\"security ike gateway $$ dynamic ike-user-type\" && \".. .. vpn-monitor destination-ip\")))";
             junos:must-message "No destination ip support for vpn-monitor in vpn using shared or group ike";
             junos:must "(!((\".. .. bind-interface\" && (\"security ike gateway $$ dynamic ike-user-type\" && \"security ike gateway $$ version v2-only\"))))";
             junos:must-message "No IKEv2 support for shared or group ike in route-based vpn";
             junos:must "(\"security ike gateway $$\")";
             junos:must-message "Referenced IKE gateway must be defined under [edit security ike gateway]";
             type string {
               length "1 .. 32";
               junos:posix-pattern "^[[:alnum:]][[:alnum:]_-]*$";
               junos:pattern-message "Must be a string beginning with a number or letter and consisting of letters, numbers, dashes and underscores.";
             }
           }
           leaf idle-time {
             description "Idle time to delete SA";
             units "seconds";
             type union {
               type string {
                 pattern "<.*>|$.*";
               }
               type uint32 {
                 range "60 .. 999999";
               }
             }
           }
           leaf no-anti-replay {
             description "Disable the anti-replay check";
             type empty;
           }
           container proxy-identity {
             description "IPSec proxy-id to use in IKE negotiations";
             presence "enable proxy-identity";
             uses ipsec-template-proxy-id;
           }
           leaf ipsec-policy {
             description "Name of the IPSec policy";
             junos:must "(\"security ipsec policy $$\")";
             junos:must-message "Referenced IPSec policy must be defined under [edit security ipsec policy]";
             type string {
               length "1 .. 32";
               junos:posix-pattern "^[[:alnum:]][[:alnum:]_-]*$";
               junos:pattern-message "Must be a string beginning with a number or letter and consisting of letters, numbers, dashes and underscores.";
             }
           }
           leaf install-interval {
             description "Delay installation of rekeyed outbound SAs on initiator";
             default "1";
             units "seconds";
             type union {
               type string {
                 pattern "<.*>|$.*";
               }
               type uint32 {
                 range "0 .. 10";
               }
             }
           }
         }
       }
     }
     leaf establish-tunnels {
       description "Define the criteria to establish tunnels";
       default "on-traffic";
       junos:must "(\".. ike\")";
       junos:must-message "VPN must be IKE-keyed to define establish-tunnel method";
       type enumeration {
         enum "immediately" {
           description "Establish tunnels immediately";
         }
         enum "on-traffic" {
           description "Establish tunnels on traffic";
         }
       }
     }
   }
   grouping ipsec-template-monitor {
     description "Configure VPN monitoring";
     uses apply-advanced;
     leaf optimized {
       description "Optimize for scalability";
       type empty;
     }
     leaf source-interface {
       description "Source interface for monitor message";
       type union {
         type jt:interface-unit;
         type string {
           pattern "<.*>|$.*";
         }
       }
     }
     leaf destination-ip {
       description "Destination IP addres for monitor message";
       type jt:ipaddr;
     }
   }
   grouping ipsec-template-proxy-id {
     description "Proxy identity settings";
     uses apply-advanced;
     leaf local {
       description "Local IP address/prefix length";
       type jt:ipprefix-mandatory;
     }
     leaf remote {
       description "Remote IP address/prefix length";
       type jt:ipprefix-mandatory;
     }
     leaf service {
       description "Name of serivce that passes through, any enables all services";
       type string {
         length "1 .. 32";
       }
     }
   }
   grouping security-macsec {
     uses apply-advanced;
     container traceoptions {
       description "Tracing options for debugging protocol operation";
       presence "enable traceoptions";
       uses macsec-trace-options;
     }
     list connectivity-association {
       key name;
       ordered-by user;
       description "Configure connectivity association properties";
       leaf name {
         description "Connectivity association name";
         type string {
           length "1 .. 32";
         }
       }
       uses apply-advanced;
       leaf cipher-suite {
         description "Cipher suite to be used for encryption";
         type enumeration {
           enum "gcm-aes-128" {
             description "GCM-AES-128 cipher suite";
           }
           enum "gcm-aes-256" {
             description "GCM-AES-256 cipher suite";
             junos:must "(!(\".. security-mode static-sak\"))";
             junos:must-message "GCM-AES-256 cipher suite not allowed for static-sak mode";
           }
           enum "gcm-aes-xpn-128" {
             description "GCM-AES-XPN-128 cipher suite";
             junos:must "(!(\".. security-mode static-sak\"))";
             junos:must-message "GCM-AES-XPN-128 cipher suite not allowed for static-sak mode";
           }
           enum "gcm-aes-xpn-256" {
             description "GCM-AES-XPN-256 cipher suite";
             junos:must "(!(\".. security-mode static-sak\"))";
             junos:must-message "GCM-AES-XPN-256 cipher suite not allowed for static-sak mode";
           }
         }
       }
       leaf security-mode {
         description "Connectivity association mode";
         junos:must "((!(\".. security-mode static-cak\") || (\".. pre-shared-key cak\" || (\".. pre-shared-key-chain\" || \".. fallback-key cak\"))))";
         junos:must-message "Pre-shared key or fallback-key or pre-shared-key-chain required for static-cak mode";
         type enumeration {
           enum "dynamic" {
             description "Dynamic connectivity and secure association mode (MKA and dot1x)";
           }
           enum "static-sak" {
             description "Static secure association key mode (no MKA)";
           }
           enum "static-cak" {
             description "Static connectivity association key mode (MKA and Pre-shared key)";
           }
         }
       }
       leaf sak-hash-128 {
         description "Configure to generate 128bit SAK hash to program HW";
         junos:must "((\".. cipher-suite gcm-aes-256\" || \".. cipher-suite gcm-aes-xpn-256\"))";
         junos:must-message "Allowed only for cipher-suite gcm-aes-256 or gcm-aes-xpn-256";
         type empty;
       }
       list secure-channel {
         key name;
         ordered-by user;
         description "Configure secure channel properties";
         junos:must "(\".. security-mode static-sak\")";
         junos:must-message "Secure-channel configuration allowed only for static-sak mode";
         leaf name {
           description "Secure channel name";
           type string;
         }
         uses apply-advanced;
         container id {
           description "Secure channel identifier";
           uses apply-advanced;
           leaf mac-address {
             description "MAC addresses";
             type jt:mac-addr;
           }
           leaf port-id {
             description "Port identifier";
             type union {
               type string {
                 pattern "<.*>|$.*";
               }
               type uint32 {
                 range "1 .. 65535";
               }
             }
           }
         }
         leaf direction {
           description "Secure channel direction";
           type enumeration {
             enum "inbound" {
             }
             enum "outbound" {
             }
           }
         }
         leaf encryption {
           description "Enable Encryption";
           type empty;
         }
         leaf offset {
           description "Confidentiality offset";
           type enumeration {
             enum "0" {
               description "Confidentiality protected for all octets of MACSec PDU data";
             }
             enum "30" {
               description "Confidentiality not protected for initial 30 octets of MACSec PDU data";
             }
             enum "50" {
               description "Confidentiality not protected for initial 50 octets of MACSec PDU data";
             }
           }
         }
         leaf include-sci {
           description "Include secure channel identifier in MAC Security PDU";
           type empty;
         }
         list security-association {
           key name;
           ordered-by user;
           description "Security association";
           leaf name {
             description "Security association number";
             type union {
               type string {
                 pattern "<.*>|$.*";
               }
               type uint32 {
                 range "0 .. 3";
               }
             }
           }
           uses apply-advanced;
           leaf key {
             description "Security association key in hexadecimal format of length 32";
             type string {
               length 32;
               junos:posix-pattern "^[[:xdigit:]]+$";
               junos:pattern-message "Must be hexadecimal digits (0-9, a-f, A-F) of length 32";
             }
           }
         }
       }
       container mka {
         presence "enable mka";
         junos:must "((\".. security-mode static-cak\" || \".. security-mode dynamic\"))";
         junos:must-message "MKA configuration can be set only for dynamic/static-cak modes";
         description "Configure MAC Security Key Agreement protocol properties";
         uses apply-advanced;
         leaf transmit-interval {
           description "Configure MKA periodic transmit interval";
           default "2000";
           units "milliseconds";
           junos:must "(!(\".. bounded-delay\"))";
           junos:must-message "Might not be configured with bounded-delay";
           type union {
             type string {
               pattern "<.*>|$.*";
             }
             type uint32 {
               range "2000 .. 6000";
             }
           }
         }
         leaf sak-rekey-interval {
           description "Configure SAK rekeying interval";
           units "seconds";
           type union {
             type string {
               pattern "<.*>|$.*";
             }
             type uint32 {
               range "60 .. 86400";
             }
           }
         }
         leaf bounded-delay {
           description "Configure Bounded Hello Time";
           junos:must "(\".. .. replay-protect replay-window-size\")";
           junos:must-message "replay-window-size must be configured with bounded-delay";
           type empty;
         }
         leaf key-server-priority {
           description "Configure MKA key server priority";
           default "16";
           junos:must "(\".. .. security-mode static-cak\")";
           junos:must-message "Allowed only for static-cak mode";
           type union {
             type string {
               pattern "<.*>|$.*";
             }
             type uint32 {
               range "0 .. 255";
             }
           }
         }
         leaf must-secure {
           description "Allow only secure dot1x traffic";
           junos:must "(\".. .. security-mode dynamic\")";
           junos:must-message "Allowed only for dynamic mode";
           type empty;
         }
         leaf should-secure {
           description "Configure fail open mode for MKA protocol";
           junos:must "(\".. .. security-mode static-cak\")";
           junos:must-message "Allowed only for static mode";
           type empty;
         }
         leaf eapol-address {
           description "Configure EAPOL destination group address";
           default "pae";
           junos:must "(\".. .. security-mode static-cak\")";
           junos:must-message "Allowed only for static-cak mode";
           type string;
         }
       }
       container replay-protect {
         junos:must "((\".. security-mode static-cak\" || \".. security-mode dynamic\"))";
         junos:must-message "Not allowed for static-sak mode";
         description "Configure replay protection";
         uses apply-advanced;
         leaf replay-window-size {
           description "Configure replay protection window size";
           units "packets";
           type union {
             type string {
               pattern "<.*>|$.*";
             }
             type uint32 {
               range "0 .. 65535";
             }
           }
         }
       }
       leaf no-encryption {
         description "Disable encryption";
         junos:must "(!(\".. offset\"))";
         junos:must-message "Offset can be configured only with encryption";
         junos:must "((\".. security-mode static-cak\" || \".. security-mode dynamic\"))";
         junos:must-message "Encryption for static-sak mode should be configured under secure-channel";
         type empty;
       }
       leaf disable-preceding-key {
         description "Disable CA preceding key duing key switch-over";
         junos:must "(\".. security-mode static-cak\")";
         junos:must-message "Enabling configuration allowed only in static-cak mode";
         type empty;
       }
       leaf offset {
         description "Confidentiality offset";
         default "0";
         junos:must "((\".. security-mode static-cak\" || \".. security-mode dynamic\"))";
         junos:must-message "Offset for static-sak mode should be configured under secure-channel";
         type enumeration {
           enum "0" {
             description "Confidentiality provided for all octets of data";
           }
           enum "30" {
             description "Confidentiality not provided for initial 30 octets of data";
           }
           enum "50" {
             description "Confidentiality not provided for initial 50 octets of data";
           }
         }
       }
       leaf include-sci {
         description "Include secure channel identifier in MAC Security PDU";
         junos:must "((\".. security-mode static-cak\" || \".. security-mode dynamic\"))";
         junos:must-message "Not allowed for static-sak mode";
         type empty;
       }
       container pre-shared-key {
         presence "enable pre-shared-key";
         junos:must "(\".. security-mode static-cak\")";
         junos:must-message "Pre-shared key configuration allowed only in static-cak mode";
         description "Configure pre-shared connectivity association key";
         uses apply-advanced;
         leaf ckn {
           description "Connectivity association key name in hexadecimal format";
           type string {
             length "2 .. 64";
             junos:posix-pattern "^([0-9a-fA-F][0-9a-fA-F]){1,32}$";
             junos:pattern-message "Must be an even-length string up to 64 hexadecimal digits (0-9, a-f, A-F)";
           }
         }
         leaf cak {
           description "Connectivity association key in hexadecimal format";
           type string {
             length "1 .. 64";
             junos:posix-pattern "^[[:xdigit:]]+$";
             junos:pattern-message "Must be hexadecimal digits (0-9, a-f, A-F)";
           }
         }
       }
       container fallback-key {
         presence "enable fallback-key";
         junos:must "(\".. security-mode static-cak\")";
         junos:must-message "Fallback key configuration allowed only in static-cak mode";
         description "Configure fallback key for connectivity association";
         uses apply-advanced;
         leaf ckn {
           description "Connectivity association fallback key name in hexadecimal format";
           junos:must "(!(\".. .. pre-shared-key ckn $$\"))";
           junos:must-message "fallback-key CKN cannot be same as pre-shared-key CKN";
           type string {
             length "2 .. 64";
             junos:posix-pattern "^([0-9a-fA-F][0-9a-fA-F]){1,32}$";
             junos:pattern-message "Must be an even-length string up to 64 hexadecimal digits (0-9, a-f, A-F)";
           }
         }
         leaf cak {
           description "Connectivity association fallback key secret in hexadecimal format";
           type string {
             length "1 .. 64";
             junos:posix-pattern "^[[:xdigit:]]+$";
             junos:pattern-message "Must be hexadecimal digits (0-9, a-f, A-F)";
           }
         }
       }
       leaf pre-shared-key-chain {
         description "Pre-shared key chain name for connectivity association";
         junos:must "(!(\".. pre-shared-key\"))";
         junos:must-message "May not be configured with pre-shared-key";
         junos:must "(\"security authentication-key-chains key-chain $$\")";
         junos:must-message "authentication-key-chains not defined !!";
         type string {
           junos:posix-pattern "^.{1,32}$";
           junos:pattern-message "Must be string of 32 characters or less";
         }
       }
       list exclude-protocol {
         key name;
         ordered-by user;
         description "Configure protocols to exclude from MAC Security";
         junos:must "((\".. security-mode static-cak\" || \".. security-mode dynamic\"))";
         junos:must-message "Not allowed for static-sak mode";
         leaf name {
           type enumeration {
             enum "cdp" {
               description "Cisco Discovery Protocol";
             }
             enum "lldp" {
               description "Link Level Discovery Protocol";
             }
             enum "lacp" {
               description "Link Aggregation Control Protocol";
             }
           }
         }
       }
     }
     list interfaces {
       key name;
       description "Interfaces on which macsec configuration is applied";
       leaf name {
         type union {
           type jt:interface-device;
           type string {
             pattern "<.*>|$.*";
           }
         }
       }
       uses apply-advanced;
       leaf connectivity-association {
         description "Connectivity association name";
         junos:must "(\"security macsec connectivity-association $$\")";
         junos:must-message "Connectivity association not defined";
         type string;
       }
       container traceoptions {
         description "Tracing options of MKA protocol";
         presence "enable traceoptions";
         junos:must "(\".. connectivity-association\")";
         junos:must-message "Connectivity association should be configured on interface to enable traceoptions";
         uses mka-trace-options;
       }
     }
   }
   grouping macsec-trace-options {
     description "Trace options for MACSec Protocol";
     uses apply-advanced;
     container file {
       description "Trace file options";
       leaf filename {
         description "Name of file in which to write trace information";
         type string {
           length "1 .. 1024";
           junos:posix-pattern "![/ %]";
           junos:pattern-message "Must not contain '/', % or a space";
         }
       }
       leaf replace {
         description "Replace trace file rather than appending to it";
         status deprecated;
         type empty;
       }
       leaf size {
         description "Maximum trace file size";
         type string;
       }
       leaf files {
         description "Maximum number of trace files";
         default "10";
         type union {
           type string {
             pattern "<.*>|$.*";
           }
           type uint32 {
             range "2 .. 1000";
           }
         }
       }
       leaf no-stamp {
         description "Do not timestamp trace file";
         status deprecated;
         type empty;
       }
       choice world-readable-choice {
         leaf world-readable {
           description "Allow any user to read the log file";
           type empty;
         }
         leaf no-world-readable {
           description "Don't allow any user to read the log file";
           type empty;
         }
       }
     }
     list flag {
       key name;
       ordered-by user;
       description "Tracing parameters";
       junos:must "(\".. file\")";
       junos:must-message "Trace file name required to enable tracing";
       leaf name {
         type enumeration {
           enum "config" {
             description "Trace configuration messages";
           }
           enum "debug" {
             description "Trace debug messages";
           }
           enum "normal" {
             description "Trace normal messages";
           }
           enum "all" {
             description "Trace all";
           }
         }
       }
     }
   }
   grouping mka-trace-options {
     description "Trace options for MKA protocol";
     uses apply-advanced;
     container file {
       description "Trace file options";
       leaf filename {
         description "Name of file in which to write trace information";
         type string {
           length "1 .. 1024";
           junos:posix-pattern "![/ %]";
           junos:pattern-message "Must not contain '/', % or a space";
         }
       }
       leaf replace {
         description "Replace trace file rather than appending to it";
         status deprecated;
         type empty;
       }
       leaf size {
         description "Maximum trace file size";
         type string;
       }
       leaf files {
         description "Maximum number of trace files";
         default "10";
         type union {
           type string {
             pattern "<.*>|$.*";
           }
           type uint32 {
             range "2 .. 1000";
           }
         }
       }
       leaf no-stamp {
         description "Do not timestamp trace file";
         status deprecated;
         type empty;
       }
       choice world-readable-choice {
         leaf world-readable {
           description "Allow any user to read the log file";
           type empty;
         }
         leaf no-world-readable {
           description "Don't allow any user to read the log file";
           type empty;
         }
       }
     }
     list flag {
       key name;
       ordered-by user;
       description "Tracing parameters";
       junos:must "(\".. file\")";
       junos:must-message "Trace file name required to enable tracing";
       leaf name {
         type enumeration {
           enum "mka-packets" {
             description "Trace MKA input and output packets";
           }
           enum "state" {
             description "Trace MKA state information";
           }
           enum "to-secy" {
             description "Trace MKA to SecY state changes";
           }
           enum "keys" {
             description "Trace key creation/generation information";
           }
           enum "normal" {
             description "Trace normal events";
           }
           enum "all" {
             description "Trace all";
           }
         }
       }
     }
   }
   grouping security-pki {
     uses apply-advanced;
     list ca-profile {
       key name;
       ordered-by user;
       description "Certificate authority profile configuration";
       leaf name {
         description "Name of certificate authority profile";
         type string {
           length "1 .. 32";
           junos:posix-pattern "![/%. ]";
           junos:pattern-message "Must not contain '/', %, '.' or a space";
         }
       }
       uses apply-advanced;
       leaf ca-identity {
         description "Certificate authority identifier";
         type string;
       }
       leaf source-address {
         description "Use specified address as source address";
         type jt:ipaddr;
       }
       leaf proxy-profile {
         description "Use specified proxy server";
         junos:must "(\"services proxy profile $$\")";
         junos:must-message "Referenced Proxy profile must be defined under [edit services proxy profile]";
         type string;
       }
       leaf routing-instance {
         description "Use specified routing instance";
         junos:must "((\"routing-instances $$\" || any \"tenants <*> routing-instances $$\"))";
         junos:must-message "referenced routing-instance must be defined";
         type string;
       }
       container enrollment {
         description "Enrollment parameters for certificate authority";
         uses apply-advanced;
         leaf url {
           description "Enrollment URL of certificate authority";
           type string;
         }
         leaf retry {
           description "Number of enrollment retry attempts before aborting";
           default "1000";
           type union {
             type string {
               pattern "<.*>|$.*";
             }
             type uint32 {
               range "0 .. 1080";
             }
           }
         }
         leaf retry-interval {
           description "Interval in seconds between the enrollment retries";
           default "600";
           type union {
             type string {
               pattern "<.*>|$.*";
             }
             type uint32 {
               range "0 .. 3600";
             }
           }
         }
       }
       container revocation-check {
         description "Method for checking certificate revocations";
         uses apply-advanced;
         choice revocation-check-options {
           case case_1 {
             leaf use-crl {
               description "Use CRL for revocation check";
               type empty;
             }
           }
           case case_2 {
             leaf use-ocsp {
               description "Use OCSP for revocation check";
               type empty;
             }
           }
           case case_3 {
             leaf disable {
               description "Disable revocation check";
               type empty;
             }
           }
         }
         container ocsp {
           presence "enable ocsp";
           description "Online Certificate Status Protocol (OCSP) configuration";
           uses apply-advanced;
           list url {
             key name;
             ordered-by user;
             leaf name {
               description "HTTP URL for OCSP access location";
               type string {
                 length "1 .. 500";
               }
             }
             uses apply-advanced;
           }
           leaf nonce-payload {
             description "Include nonce payload in OCSP requests";
             type enumeration {
               enum "enable" {
                 description "Send nonce paylod in OCSP request";
               }
               enum "disable" {
                 description "Do not send nonce payload in OCSP request";
               }
             }
           }
           leaf disable-responder-revocation-check {
             description "Disable OCSP responder certificate revocation check";
             type empty;
           }
           leaf accept-unknown-status {
             description "Accept certificates with unknown status";
             type empty;
           }
           container connection-failure {
             presence "enable connection-failure";
             description "Actions on failure to connect to OCSP Responder";
             uses apply-advanced;
             choice connection-failure-options {
               case case_1 {
                 leaf fallback-crl {
                   description "Use CRL for revocation check";
                   type empty;
                 }
               }
               case case_2 {
                 leaf disable {
                   description "Disable OCSP check on connection failure";
                   type empty;
                 }
               }
             }
           }
         }
         container crl {
           description "Certificate revocation list configuration";
           uses apply-advanced;
           container disable {
             leaf on-download-failure {
               description "Check revocation status with existing CRL file if present, otherwise skip. This feature must be enabled for manual CRL download.";
               type empty;
             }
           }
           list url {
             key name;
             ordered-by user;
             leaf name {
               description "URL of CRL distribution point for certificate authority";
               type string {
                 length "1 .. 500";
               }
             }
             uses apply-advanced;
             leaf password {
               description "Password for authentication with the server";
               type jt:unreadable;
             }
           }
           leaf refresh-interval {
             description "CRL refresh interval";
             units "hours";
             type union {
               type string {
                 pattern "<.*>|$.*";
               }
               type uint32 {
                 range "0 .. 8784";
               }
             }
           }
         }
       }
       container administrator {
         description "Administrator information";
         uses apply-advanced;
         leaf email-address {
           description "Administrator e-mail to which to send certificate requests";
           type string;
         }
       }
     }
     list trusted-ca-group {
       key name;
       ordered-by user;
       description "Trusted Certificate Authority group configuration";
       leaf name {
         description "Name of the trusted CA group";
         type string {
           length "1 .. 63";
         }
       }
       uses apply-advanced;
       leaf-list ca-profiles {
         ordered-by user;
         description "Name of the CA profiles (maximum 20)";
         type string {
           length "1 .. 63";
         }
         max-elements 20;
       }
     }
     container trap {
       presence "enable trap";
       description "Trap options for PKI certificates";
       uses apply-advanced;
       list certificate-id {
         key name;
         ordered-by user;
         description "Local certificate identifier";
         leaf name {
           description "Local cert id";
           type string;
         }
         uses apply-advanced;
         leaf days {
           description "Number of days to generate trap (default 60)";
           default "60";
           type union {
             type string {
               pattern "<.*>|$.*";
             }
             type uint32 {
               range "1 .. 100";
             }
           }
         }
       }
       list ca-identity {
         key name;
         ordered-by user;
         description "CA identity";
         leaf name {
           description "CA profile";
           junos:must "(\"security pki ca-profile $$\")";
           junos:must-message "Referenced ca-profile must be defined under [edit security pki ca-profile]";
           type string;
         }
         uses apply-advanced;
         leaf days {
           description "Number of days to generate trap (default 60)";
           default "60";
           type union {
             type string {
               pattern "<.*>|$.*";
             }
             type uint32 {
               range "1 .. 100";
             }
           }
         }
       }
       container all-certificates {
         presence "enable all-certificates";
         description "Trap config for all certificates";
         uses apply-advanced;
         leaf days {
           description "Number of days to generate trap (default 60)";
           default "60";
           type union {
             type string {
               pattern "<.*>|$.*";
             }
             type uint32 {
               range "1 .. 100";
             }
           }
         }
       }
     }
     container auto-re-enrollment {
       description "Auto re-enroll of certificate";
       uses apply-advanced;
       container cmpv2 {
         presence "enable cmpv2";
         description "CMPv2 auto re-enrollment configuration";
         uses apply-advanced;
         list certificate-id {
           key name;
           ordered-by user;
           description "CMPv2 auto re-enrollment configuration for certificate-id";
           leaf name {
             description "Certificate identifier that needs auto re-enrollment";
             type string {
               junos:posix-pattern "^.{1,32}$";
               junos:pattern-message "Must be string of 32 characters or less";
             }
           }
           uses apply-advanced;
           leaf ca-profile-name {
             description "Name of certificate authority profile";
             junos:must "(\"security pki ca-profile $$ enrollment url\")";
             junos:must-message "Referenced ca-profile must have enrollment url configured under [edit security pki ca-profile <ca-profile-name> enrollment url]";
             junos:must "(\"security pki ca-profile $$\")";
             junos:must-message "Referenced ca-profile must be defined under [edit security pki ca-profile]";
             type string {
               junos:posix-pattern "^.{1,32}$";
               junos:pattern-message "Must be string of 32 characters or less";
             }
           }
           leaf re-enroll-trigger-time-percentage {
             description "Re-enrollment trigger time before expiration as percentage";
             type union {
               type string {
                 pattern "<.*>|$.*";
               }
               type uint32 {
                 range "1 .. 99";
               }
             }
           }
           leaf re-generate-keypair {
             description "Generate new key-pair for auto-re-enrollment";
             type empty;
           }
         }
       }
       container scep {
         presence "enable scep";
         description "SCEP auto re-enrollment configuration";
         uses apply-advanced;
         list certificate-id {
           key name;
           ordered-by user;
           description "SCEP auto re-enrollment configuration for certificate-id";
           leaf name {
             description "Certificate identifier that needs auto re-enrollment";
             type string {
               junos:posix-pattern "^.{1,32}$";
               junos:pattern-message "Must be string of 32 characters or less";
             }
           }
           uses apply-advanced;
           leaf ca-profile-name {
             description "Name of certificate authority profile";
             junos:must "(\"security pki ca-profile $$ enrollment url\")";
             junos:must-message "Referenced ca-profile must have enrollment url configured under [edit security pki ca-profile <ca-profile-name> enrollment url]";
             junos:must "(\"security pki ca-profile $$\")";
             junos:must-message "Referenced ca-profile must be defined under [edit security pki ca-profile]";
             type string {
               junos:posix-pattern "^.{1,32}$";
               junos:pattern-message "Must be string of 32 characters or less";
             }
           }
           leaf re-generate-keypair {
             description "Generate new key-pair for auto-re-enrollment";
             type empty;
           }
           leaf re-enroll-trigger-time-percentage {
             description "Re-enrollment trigger time before expiration as percentage";
             type union {
               type string {
                 pattern "<.*>|$.*";
               }
               type uint32 {
                 range "1 .. 99";
               }
             }
           }
           leaf challenge-password {
             description "Password used by CA for enrollment and revocation";
             type jt:unreadable;
           }
           container scep-encryption-algorithm {
             presence "enable scep-encryption-algorithm";
             description "SCEP encryption algorithm";
             uses apply-advanced;
             choice scep-encryption-algorithm-options {
               case case_1 {
                 leaf des {
                   description "Use DES as SCEP encryption algorithm";
                   type empty;
                 }
               }
               case case_2 {
                 leaf des3 {
                   description "Use DES3 as SCEP encryption algorithm";
                   type empty;
                 }
               }
             }
           }
           container scep-digest-algorithm {
             presence "enable scep-digest-algorithm";
             description "SCEP digest algorithm";
             uses apply-advanced;
             choice scep-digest-algorithm-options {
               case case_1 {
                 leaf md5 {
                   description "Use MD5 as SCEP digest algorithm";
                   type empty;
                 }
               }
               case case_2 {
                 leaf sha1 {
                   description "Use SHA1 as SCEP digest algorithm";
                   type empty;
                 }
               }
             }
           }
         }
       }
       list certificate-id {
         key name;
         ordered-by user;
         description "Auto re-enrollment configuration for certificate-id";
         leaf name {
           description "Certificate identifier that needs auto re-enrollment";
           type string {
             junos:posix-pattern "^.{1,32}$";
             junos:pattern-message "Must be string of 32 characters or less";
           }
         }
         uses apply-advanced;
         leaf ca-profile-name {
           description "Name of certificate authority profile";
           junos:must "(\"security pki ca-profile $$ enrollment url\")";
           junos:must-message "Referenced ca-profile must have enrollment url configured under [edit security pki ca-profile <ca-profile-name> enrollment url]";
           junos:must "(\"security pki ca-profile $$\")";
           junos:must-message "Referenced ca-profile must be defined under [edit security pki ca-profile]";
           type string {
             junos:posix-pattern "^.{1,32}$";
             junos:pattern-message "Must be string of 32 characters or less";
           }
         }
         leaf re-generate-keypair {
           description "Generate new key-pair for auto-re-enrollment";
           type empty;
         }
         leaf re-enroll-trigger-time-percentage {
           description "Re-enrollment trigger time before expiration as percentage";
           type union {
             type string {
               pattern "<.*>|$.*";
             }
             type uint32 {
               range "1 .. 99";
             }
           }
         }
         leaf challenge-password {
           description "Password used by CA for enrollment and revocation";
           type jt:unreadable;
         }
         container scep-encryption-algorithm {
           presence "enable scep-encryption-algorithm";
           description "SCEP encryption algorithm";
           uses apply-advanced;
           choice scep-encryption-algorithm-options {
             case case_1 {
               leaf des {
                 description "Use DES as SCEP encryption algorithm";
                 type empty;
               }
             }
             case case_2 {
               leaf des3 {
                 description "Use DES3 as SCEP encryption algorithm";
                 type empty;
               }
             }
           }
         }
         container scep-digest-algorithm {
           presence "enable scep-digest-algorithm";
           description "SCEP digest algorithm";
           uses apply-advanced;
           choice scep-digest-algorithm-options {
             case case_1 {
               leaf md5 {
                 description "Use MD5 as SCEP digest algorithm";
                 type empty;
               }
             }
             case case_2 {
               leaf sha1 {
                 description "Use SHA1 as SCEP digest algorithm";
                 type empty;
               }
             }
           }
         }
         leaf validity-period {
           description "Certificate validity period in days from enrollment start date";
           status deprecated;
           type union {
             type string {
               pattern "<.*>|$.*";
             }
             type uint32 {
               range "1 .. 4095";
             }
           }
         }
       }
     }
     container traceoptions {
       description "PKI trace options";
       uses apply-advanced;
       leaf no-remote-trace {
         description "Disable remote tracing";
         junos:must "(\"system tracing\")";
         junos:must-message "'no-remote-trace' is valid only when [system tracing] is configured";
         type empty;
       }
       container file {
         description "Trace file information";
         leaf filename {
           description "Name of file in which to write trace information";
           type string {
             length "1 .. 1024";
             junos:posix-pattern "![/ %]";
             junos:pattern-message "Must not contain '/', % or a space";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing parameters";
         leaf name {
           type enumeration {
             enum "certificate-verification" {
               description "PKI certificate verification tracing";
             }
             enum "online-crl-check" {
               description "PKI online crl tracing";
             }
             enum "enrollment" {
               description "PKI certificate enrollment tracing";
             }
             enum "all" {
               description "Trace with all flags enabled";
             }
           }
         }
       }
     }
   }
   grouping security-traceoptions {
     description "Trace options for key management process";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf rate-limit {
       description "Limit the incoming rate of trace messages";
       default "0";
       type union {
         type string {
           pattern "<.*>|$.*";
         }
         type uint32 {
           range "0 .. 4294967295";
         }
       }
     }
     list flag {
       key name;
       ordered-by user;
       description "Tracing parameters";
       leaf name {
         type enumeration {
           enum "timer" {
             description "Trace internal timer events";
           }
           enum "routing-socket" {
             description "Trace routing socket messages";
           }
           enum "parse" {
             description "Trace configuration processing";
           }
           enum "config" {
             description "Trace configuration download processing";
           }
           enum "ike" {
             description "Trace IKE module processing";
           }
           enum "policy-manager" {
             description "Trace policy manager processing";
           }
           enum "general" {
             description "Trace general events";
           }
           enum "database" {
             description "Trace security associations database events";
           }
           enum "certificates" {
             description "Trace certificate events";
           }
           enum "snmp" {
             description "Trace SNMP operations";
           }
           enum "thread" {
             description "Trace thread processing";
           }
           enum "high-availability" {
             description "Trace high-availability operations";
           }
           enum "next-hop-tunnels" {
             description "Trace next-hop-tunnels operations";
           }
           enum "all" {
             description "Trace everything";
           }
           enum "ams" {
             description "Trace AMS events";
           }
           enum "lic" {
             description "Trace License events";
           }
         }
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
   }
   grouping tenant-system-type {
     description "Tenant name";
     leaf name {
       description "Tenant name";
       junos:must "(\"tenants $$\")";
       junos:must-message "Tenants must be defined under [tenants] ";
       type string;
     }
     uses apply-advanced;
     leaf max-sessions {
       description "Max number of IDP sessions";
       type union {
         type uint32;
         type string {
           pattern "<.*>|$.*";
         }
       }
     }
   }
   grouping tunable-object {
     leaf name {
       type string;
     }
     uses apply-advanced;
     leaf tunable-value {
       description "Protocol tunable value";
       type union {
         type uint32;
         type string {
           pattern "<.*>|$.*";
         }
       }
     }
   }
   grouping vendor-object {
     leaf name {
       description "Values for vendor field";
       type string;
     }
     uses apply-advanced;
     leaf product-name {
       description "Values for product field";
       type string;
     }
   }
 }
