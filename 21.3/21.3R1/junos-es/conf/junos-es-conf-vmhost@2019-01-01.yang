/*
 * Copyright (c) 2021 Juniper Networks, Inc.
 * All rights reserved.
 */
 module junos-es-conf-vmhost {
   namespace "http://yang.juniper.net/junos-es/conf/vmhost";

   prefix jc-vmhost;

   import junos-common-types {
     prefix jt;
     revision-date 2019-01-01;
   }

   import junos-es-conf-root {
     prefix jc;
     revision-date 2019-01-01;
   }

   organization "Juniper Networks, Inc.";

   contact "yang-support@juniper.net";

   description "Junos vmhost configuration module";

   revision 2019-01-01 {
     description "Junos: 21.3R1.9";
   }

   augment /jc:configuration {
     uses vmhost-group;
   }
   augment /jc:configuration/jc:groups {
     uses vmhost-group;
   }
   grouping vmhost-group {
     container vmhost {
       description "VM Host configurations";
       uses apply-advanced;
       leaf no-auto-recovery {
         description "Disable Guest auto recovery by the host";
         type empty;
       }
       container management-if {
         presence "enable management-if";
         description "Configuration for the host's side management interface";
         uses apply-advanced;
         leaf link-mode {
           description "Link operational mode";
           default "automatic";
           type enumeration {
             enum "automatic" {
               description "Automatically negotiate duplex";
             }
             enum "half-duplex" {
               description "Half-duplex operation";
             }
             enum "full-duplex" {
               description "Full-duplex operation";
             }
           }
         }
         leaf speed {
           description "Link speed";
           default "automatic";
           type enumeration {
             enum "automatic" {
               description "Automatically negotiate speed";
             }
             enum "10m" {
               description "10Mbps operation";
             }
             enum "100m" {
               description "100Mbps operation";
             }
             enum "1g" {
               description "1Gbps operation";
             }
           }
         }
         leaf disable {
           description "Administratively disable the management port";
           type empty;
         }
       }
       container resize {
         description "Resize the resource allocation of guest VM";
         uses apply-advanced;
         container vjunos {
           description "Vjunos/adminjunos VM";
           uses apply-advanced;
           leaf compact {
             description "Reduce the resource allocation of vjunos VM";
             type empty;
           }
         }
       }
       list interfaces {
         key name;
         ordered-by user;
         description "Interface configuration";
         leaf name {
           type enumeration {
             enum "management-if0" {
               description "Configuration for the host's side management interface0";
             }
             enum "management-if1" {
               description "Configuration for the host's side management interface1";
             }
           }
         }
         uses apply-advanced;
         container family {
           description "Protocol family";
           container inet {
             presence "enable inet";
             description "IPv4 parameters";
             uses apply-advanced;
             list address {
               key name;
               ordered-by user;
               description "Interface address/destination prefix";
               leaf name {
                 description "Interface address/destination prefix";
                 type jt:ipv4prefix;
               }
               uses apply-advanced;
               leaf master-only {
                 description "Master management IP address for host";
                 type empty;
               }
             }
             leaf gateway {
               description "Gateway IP address";
               type jt:ipv4addr;
             }
           }
           container inet6 {
             presence "enable inet6";
             description "IPv6 parameters";
             uses apply-advanced;
             list address {
               key name;
               ordered-by user;
               description "Interface address/destination prefix";
               leaf name {
                 description "Interface address/destination prefix";
                 type jt:ipv6prefix;
               }
               uses apply-advanced;
               leaf master-only {
                 description "Master management IP address for host";
                 type empty;
               }
             }
             leaf gateway {
               description "Gateway IP address";
               type jt:ipv6addr;
             }
           }
         }
       }
       container syslog {
         presence "enable syslog";
         description "VMhost logging facility";
         uses apply-advanced;
         list file {
           key name;
           description "File in which to log data";
           leaf name {
             description "Name of file in which to log data";
             type string {
               length "1 .. 1024";
             }
           }
           uses apply-advanced;
           list vmhost-syslog-object {
             key "facility level";
             leaf facility {
               description "Facility type";
               type enumeration {
                 enum "any" {
                   description "All facilities";
                 }
                 enum "authorization" {
                   description "Authorization system";
                 }
                 enum "privileged" {
                   description "Privileged authorization events";
                 }
                 enum "cron" {
                   description "Cron daemon";
                 }
                 enum "daemon" {
                   description "Various system processes";
                 }
                 enum "kernel" {
                   description "Kernel";
                 }
                 enum "lpr" {
                   description "Line printer spooling system";
                 }
                 enum "mail" {
                   description "Mail system";
                 }
                 enum "mark" {
                 }
                 enum "news" {
                   description "Network news system";
                 }
                 enum "syslog" {
                 }
                 enum "user" {
                   description "User processes";
                 }
                 enum "uucp" {
                   description "UUCP system";
                 }
                 enum "local0" {
                   description "Local logging option number 0";
                 }
                 enum "local1" {
                   description "Local logging option number 1";
                 }
                 enum "local2" {
                   description "Local logging option number 2";
                 }
                 enum "local3" {
                   description "Local logging option number 3";
                 }
                 enum "local4" {
                   description "Local logging option number 4";
                 }
                 enum "local5" {
                   description "Local logging option number 5";
                 }
                 enum "local6" {
                   description "Local logging option number 6";
                 }
                 enum "local7" {
                   description "Local logging option number 7";
                 }
               }
             }
             leaf level {
               description "Level name";
               type enumeration {
                 enum "any" {
                   description "All levels";
                 }
                 enum "emergency" {
                   description "Panic conditions";
                 }
                 enum "alert" {
                   description "Conditions that should be corrected immediately";
                 }
                 enum "critical" {
                   description "Critical conditions";
                 }
                 enum "error" {
                   description "Error conditions";
                 }
                 enum "warning" {
                   description "Warning messages";
                 }
                 enum "notice" {
                   description "Conditions that should be handled specially";
                 }
                 enum "info" {
                   description "Informational messages";
                 }
                 enum "none" {
                   description "No messages";
                 }
               }
             }
           }
         }
         list host {
           key name;
           ordered-by user;
           description "Host to be notified";
           leaf name {
             description "Host to be notified";
             type string {
             }
           }
           uses apply-advanced;
           list vmhost-syslog-object {
             key "facility level";
             leaf facility {
               description "Facility type";
               type enumeration {
                 enum "any" {
                   description "All facilities";
                 }
                 enum "authorization" {
                   description "Authorization system";
                 }
                 enum "privileged" {
                   description "Privileged authorization events";
                 }
                 enum "cron" {
                   description "Cron daemon";
                 }
                 enum "daemon" {
                   description "Various system processes";
                 }
                 enum "kernel" {
                   description "Kernel";
                 }
                 enum "lpr" {
                   description "Line printer spooling system";
                 }
                 enum "mail" {
                   description "Mail system";
                 }
                 enum "mark" {
                 }
                 enum "news" {
                   description "Network news system";
                 }
                 enum "syslog" {
                 }
                 enum "user" {
                   description "User processes";
                 }
                 enum "uucp" {
                   description "UUCP system";
                 }
                 enum "local0" {
                   description "Local logging option number 0";
                 }
                 enum "local1" {
                   description "Local logging option number 1";
                 }
                 enum "local2" {
                   description "Local logging option number 2";
                 }
                 enum "local3" {
                   description "Local logging option number 3";
                 }
                 enum "local4" {
                   description "Local logging option number 4";
                 }
                 enum "local5" {
                   description "Local logging option number 5";
                 }
                 enum "local6" {
                   description "Local logging option number 6";
                 }
                 enum "local7" {
                   description "Local logging option number 7";
                 }
               }
             }
             leaf level {
               description "Level name";
               type enumeration {
                 enum "any" {
                   description "All levels";
                 }
                 enum "emergency" {
                   description "Panic conditions";
                 }
                 enum "alert" {
                   description "Conditions that should be corrected immediately";
                 }
                 enum "critical" {
                   description "Critical conditions";
                 }
                 enum "error" {
                   description "Error conditions";
                 }
                 enum "warning" {
                   description "Warning messages";
                 }
                 enum "notice" {
                   description "Conditions that should be handled specially";
                 }
                 enum "info" {
                   description "Informational messages";
                 }
                 enum "none" {
                   description "No messages";
                 }
               }
             }
           }
           leaf transport {
             description "Transport type";
             default "udp";
             type enumeration {
               enum "tcp" {
                 description "TCP as transport of syslog";
               }
               enum "udp" {
                 description "UDP as transport of syslog";
               }
             }
           }
         }
       }
       container services {
         presence "enable services";
         description "System services";
         uses apply-advanced;
         container ssh {
           presence "enable ssh";
           description "Allow ssh access";
           uses apply-advanced;
           leaf root-login {
             description "Configure vmhost root access via ssh";
             type enumeration {
               enum "allow" {
                 description "Allow root access via ssh";
               }
               enum "deny" {
                 description "Do not allow root access via ssh";
               }
             }
           }
         }
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping macro-data-type {
     leaf name {
       description "Keyword part of the keyword-value pair";
       type string;
     }
     leaf value {
       description "Value part of the keyword-value pair";
       type string;
     }
   }
 }
