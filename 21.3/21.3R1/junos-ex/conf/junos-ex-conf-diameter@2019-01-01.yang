/*
 * Copyright (c) 2021 Juniper Networks, Inc.
 * All rights reserved.
 */
 module junos-ex-conf-diameter {
   namespace "http://yang.juniper.net/junos-ex/conf/diameter";

   prefix jc-diameter;

   import junos-common-types {
     prefix jt;
     revision-date 2019-01-01;
   }

   import junos-ex-conf-root {
     prefix jc;
     revision-date 2019-01-01;
   }

   organization "Juniper Networks, Inc.";

   contact "yang-support@juniper.net";

   description "Junos diameter configuration module";

   revision 2019-01-01 {
     description "Junos: 21.3R1.9";
   }

   augment /jc:configuration {
     uses diameter-group;
   }
   augment /jc:configuration/jc:groups {
     uses diameter-group;
   }
   grouping diameter-group {
     container diameter {
       presence "enable diameter";
       description "Diameter protocol layer";
       uses apply-advanced;
       container origin {
         presence "enable origin";
         description "Origin attributes of this diameter instance";
         uses apply-advanced;
         leaf realm {
           description "Origin realm of this diameter instance";
           type string {
             length "1 .. 255";
           }
         }
         leaf host {
           description "Origin host of this diameter instance";
           type string {
             length "1 .. 255";
           }
         }
       }
       list network-element {
         key name;
         ordered-by user;
         description "Network element of this diameter instance";
         leaf name {
           description "Name for this network element";
           type string {
             length "1 .. 255";
           }
         }
         uses apply-advanced;
         container dne-origin {
           presence "enable dne-origin";
           description "Optional origin filter of this networkd element";
           uses apply-advanced;
           leaf realm {
             description "Origin realm of this network element";
             type string {
               length "1 .. 255";
             }
           }
           leaf host {
             description "Optional origin host of this network element";
             type string {
               length "1 .. 255";
             }
           }
         }
         leaf-list function {
           ordered-by user;
           description "Diameter function associated with by this network element";
           type enumeration {
             enum "jsrc" {
               description "Function to use SRC application";
             }
             enum "gx-plus" {
               description "Function to use GX-PLUS application";
             }
             enum "sd-3gpp" {
               description "Function to use SD-3GPP application";
             }
             enum "nasreq" {
               description "Function to use NASREQ application";
             }
             enum "pcrf" {
               description "Function to use PCRF(GX) application";
             }
             enum "ocs" {
               description "Function to use OCS(GY) application";
             }
             enum "s6a" {
               description "Function to use S6A application";
             }
           }
           max-elements 8;
         }
         list peer {
           key name;
           ordered-by user;
           description "Peer associated with this network element";
           leaf name {
             description "Name of a peer associated with this network element";
             type string {
               length "1 .. 255";
             }
           }
           uses apply-advanced;
           leaf priority {
             description "Peer priority with this network element";
             type union {
               type string {
                 pattern "<.*>|$.*";
               }
               type uint32 {
                 range "1 .. 65535";
               }
             }
           }
         }
         container forwarding {
           description "Forwarding configuration for this network-element";
           uses apply-advanced;
           list route {
             key name;
             ordered-by user;
             description "Routes associated with this network-element";
             max-elements 256;
             leaf name {
               description "Name of a route associated with this network element";
               type string {
                 length "1 .. 255";
               }
             }
             uses apply-advanced;
             container function {
               description "Diameter function and partition associated with route";
               leaf function-name {
                 type enumeration {
                   enum "jsrc" {
                     description "Function to use SRC application";
                   }
                   enum "gx-plus" {
                     description "Function to use GX-PLUS application";
                   }
                   enum "sd-3gpp" {
                     description "Function to use SD-3GPP application";
                   }
                   enum "nasreq" {
                     description "Function to use NASREQ application";
                   }
                   enum "pcrf" {
                     description "Function to use PCRF(GX) application";
                   }
                   enum "ocs" {
                     description "Function to use OCS(GY) application";
                   }
                   enum "s6a" {
                     description "Function to use S6A application";
                   }
                 }
               }
               leaf partition {
                 description "Diameter function partition name";
                 type string {
                   length "1 .. 255";
                 }
               }
             }
             container destination {
               description "Destination for this route";
               leaf realm {
                 description "Diameter destination realm";
                 type string {
                   length "1 .. 255";
                 }
               }
               leaf host {
                 description "Diameter destination host";
                 type string {
                   length "1 .. 255";
                 }
               }
             }
             leaf metric {
               description "Metric for this route";
               type union {
                 type string {
                   pattern "<.*>|$.*";
                 }
                 type uint32 {
                   range "0 .. 255";
                 }
               }
             }
           }
         }
       }
       list transport {
         key name;
         ordered-by user;
         description "Diameter transport configuration";
         max-elements 31;
         leaf name {
           description "Name for this transport definition";
           type string {
             length "1 .. 255";
           }
         }
         uses apply-advanced;
         leaf address {
           description "Source IP address for a peer";
           type jt:ipaddr;
         }
         choice instance {
           case case_1 {
             container logical-system {
               description "Logical system to be used by transport";
               leaf logical-system-name {
                 description "Name of logical system";
                 type string {
                 }
               }
               leaf routing-instance {
                 description "Routing instance to be used by transport";
                 type union {
                   type string {
                     pattern "default";
                   }
                   type string {
                   }
                 }
               }
             }
           }
           case case_2 {
             leaf routing-instance {
               description "Routing instance of server to which to forward";
               type union {
                 type string {
                   pattern "default";
                 }
                 type string {
                 }
               }
             }
           }
         }
       }
       list peer {
         key name;
         ordered-by user;
         description "Diameter peer configuration";
         max-elements 31;
         leaf name {
           description "Name for this Diameter peer";
           type string {
             length "1 .. 255";
           }
         }
         uses apply-advanced;
         leaf address {
           description "IP Address of Diameter peer";
           type jt:ipaddr;
         }
         leaf send-origin-state-id {
           description "Include origin-state-id in peer messages";
           type empty;
         }
         choice instance {
           case case_1 {
             container logical-system {
               description "Logical system to be used by transport";
               leaf logical-system-name {
                 description "Name of logical system";
                 type string {
                 }
               }
               leaf routing-instance {
                 description "Routing instance to be used by transport";
                 type union {
                   type string {
                     pattern "default";
                   }
                   type string {
                   }
                 }
               }
             }
           }
           case case_2 {
             leaf routing-instance {
               description "Routing instance of server to which to forward";
               type union {
                 type string {
                   pattern "default";
                 }
                 type string {
                 }
               }
             }
           }
         }
         container connect-actively {
           presence "enable connect-actively";
           uses apply-advanced;
           leaf transport {
             description "Name of transport";
             type string {
               length "1 .. 255";
             }
           }
           leaf port {
             description "Peer port";
             default "3868";
             type union {
               type string {
                 pattern "<.*>|$.*";
               }
               type uint16 {
                 range "1 .. 65535";
               }
             }
           }
         }
         container peer-origin {
           presence "enable peer-origin";
           description "Optional origin attributes of this diameter peer";
           uses apply-advanced;
           leaf realm {
             description "Origin realm of this diameter peer";
             type string {
               length "1 .. 255";
             }
           }
           leaf host {
             description "Origin host of this diameter peer";
             type string {
               length "1 .. 255";
             }
           }
         }
       }
       leaf product-name {
         description "Product name to advertise in capability-exchange";
         type string {
           length "1 .. 255";
         }
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping macro-data-type {
     leaf name {
       description "Keyword part of the keyword-value pair";
       type string;
     }
     leaf value {
       description "Value part of the keyword-value pair";
       type string;
     }
   }
 }
