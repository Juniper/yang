/*
 * Copyright (c) 2019 Juniper Networks, Inc.
 * All rights reserved.
 */
 module junos-nfx-rpc-pfe {
   namespace "http://yang.juniper.net/junos-nfx/rpc/pfe";

   prefix pfe;

   import junos-common-types {
     prefix jt;
   }

   organization "Juniper Networks, Inc.";

   contact "yang-support@juniper.net";

   description "Junos RPC YANG module for pfe command(s)";

   revision 2019-01-01 {
     description "Junos: 18.4R3.3";
   }

   rpc get-pfe-data {
     description "Show Packet Forwarding Engine data";
     input {
       leaf command {
         description "Command line to show";
         type string {
           length "1 .. 80";
         }
         mandatory true;
       }
       leaf target {
         description "Component on which command is showed";
         type string;
       }
     }
     output {
       choice output_c {
         case output-tag {
           leaf output {
             type string;
           }
         }
         case multichassis-tag {
           anyxml multi-routing-engine-results;
         }
       }
     }
   }
   rpc get-pfe-information {
     description "Show list of Packet Forwarding Engine components";
     output {
       choice output_c {
         case output-tag {
           leaf output {
             type string;
           }
         }
         case actual-tag {
           anyxml pfe-information;
         }
         case multichassis-tag {
           anyxml multi-routing-engine-results;
         }
       }
     }
   }
   rpc get-pfe-statistics {
     description "Show Packet Forwarding Engine traffic statistics";
     input {
       leaf sfm {
         description "Slot number of SFM for which to show traffic statistics";
         type union {
           type string {
             pattern "<.*>|$.*";
           }
           type uint32;
         }
       }
       leaf feb {
         description "Slot number of FEB for which to show traffic statistics";
         type union {
           type string {
             pattern "<.*>|$.*";
           }
           type uint32;
         }
       }
       choice cid {
         case lcc {
           leaf lcc {
             description "Slot number of LCC that houses FPC";
             type union {
               type string {
                 pattern "<.*>|$.*";
               }
               type uint32;
             }
           }
         }
       }
       leaf fpc {
         description "Slot number of FPC for which to show traffic statistics";
         type union {
           type string {
             pattern "<.*>|$.*";
           }
           type uint32;
         }
       }
     }
     output {
       choice output_c {
         case output-tag {
           leaf output {
             type string;
           }
         }
         case actual-tag {
           anyxml pfe-statistics;
         }
         case multichassis-tag {
           anyxml multi-routing-engine-results;
         }
       }
     }
   }
   rpc get-pfe-traffic-statistics {
     description "Show Packet Forwarding Engine traffic detailed statistics";
     input {
       leaf fpc {
         description "FPC slot number";
         type union {
           type string {
             pattern "<.*>|$.*";
           }
           type uint32;
         }
       }
       leaf pfe {
         description "Pfe Index";
         type union {
           type string {
             pattern "<.*>|$.*";
           }
           type uint32;
         }
       }
     }
     output {
       choice output_c {
         case output-tag {
           leaf output {
             type string;
           }
         }
         case actual-tag {
           anyxml pfe-statistics;
         }
         case multichassis-tag {
           anyxml multi-routing-engine-results;
         }
       }
     }
   }
   rpc get-pfe-traffic-statistics-bandwidth {
     description "Show Packet Forwarding Engine TX bandwidth";
     input {
       leaf sfm {
         description "Slot number of SFM for which to show traffic statistics";
         type union {
           type string {
             pattern "<.*>|$.*";
           }
           type uint32;
         }
       }
       leaf feb {
         description "Slot number of FEB for which to show traffic statistics";
         type union {
           type string {
             pattern "<.*>|$.*";
           }
           type uint32;
         }
       }
       choice cid {
         case lcc {
           leaf lcc {
             description "Slot number of LCC that houses FPC";
             type union {
               type string {
                 pattern "<.*>|$.*";
               }
               type uint32;
             }
           }
         }
       }
       leaf fpc {
         description "Slot number of FPC for which to show traffic statistics";
         type union {
           type string {
             pattern "<.*>|$.*";
           }
           type uint32;
         }
       }
     }
     output {
       choice output_c {
         case output-tag {
           leaf output {
             type string;
           }
         }
         case actual-tag {
           anyxml pfe-traffic-statistics-bandwidth;
         }
         case multichassis-tag {
           anyxml multi-routing-engine-results;
         }
       }
     }
   }
   rpc get-pfe-tcam-usage-all-tcam-stages {
     description "Show packet forwarding engine tcam usage at all tcam stages";
     output {
       choice output_c {
         case output-tag {
           leaf output {
             type string;
           }
         }
         case multichassis-tag {
           anyxml multi-routing-engine-results;
         }
       }
     }
   }
   rpc get-pfe-tcam-usage-all-tcam-stages-detail {
     description "Show packet forwarding engine tcam usage at all tcam stages in detail";
     output {
       choice output_c {
         case output-tag {
           leaf output {
             type string;
           }
         }
         case multichassis-tag {
           anyxml multi-routing-engine-results;
         }
       }
     }
   }
   rpc get-pfe-tcam-usage-egress-tcam-stage {
     description "Show tcam usage for egress tcam-stage";
     output {
       choice output_c {
         case output-tag {
           leaf output {
             type string;
           }
         }
         case multichassis-tag {
           anyxml multi-routing-engine-results;
         }
       }
     }
   }
   rpc get-pfe-tcam-usage-egress-tcam-stage-detail {
     description "Show tcam usage for egress tcam-stage in detail";
     output {
       choice output_c {
         case output-tag {
           leaf output {
             type string;
           }
         }
         case multichassis-tag {
           anyxml multi-routing-engine-results;
         }
       }
     }
   }
   rpc get-pfe-tcam-usage-egress-app {
     description "Show tcam usage for a tcam app";
     output {
       choice output_c {
         case output-tag {
           leaf output {
             type string;
           }
         }
         case multichassis-tag {
           anyxml multi-routing-engine-results;
         }
       }
     }
   }
   rpc get-pfe-tcam-usage-egress-tcam-stage-detail-bd-dtag-validate {
     description "Bridge Domain dual-tagged validate";
     output {
       choice output_c {
         case output-tag {
           leaf output {
             type string;
           }
         }
         case multichassis-tag {
           anyxml multi-routing-engine-results;
         }
       }
     }
   }
   rpc get-pfe-tcam-usage-egress-tcam-stage-detail-bd-tpid-swap {
     description "Bridge domain vlan-map with swap tpid operation";
     output {
       choice output_c {
         case output-tag {
           leaf output {
             type string;
           }
         }
         case multichassis-tag {
           anyxml multi-routing-engine-results;
         }
       }
     }
   }
   rpc get-pfe-tcam-usage-egress-tcam-stage-detail-fw-family-out {
     description "Family level egress firewall";
     output {
       choice output_c {
         case output-tag {
           leaf output {
             type string;
           }
         }
         case multichassis-tag {
           anyxml multi-routing-engine-results;
         }
       }
     }
   }
   rpc get-pfe-tcam-usage-egress-tcam-stage-detail-fw-inet6-family-out {
     description "Inet6 Family level egress firewall";
     output {
       choice output_c {
         case output-tag {
           leaf output {
             type string;
           }
         }
         case multichassis-tag {
           anyxml multi-routing-engine-results;
         }
       }
     }
   }
   rpc get-pfe-tcam-usage-egress-tcam-stage-detail-fw-ifl-out {
     description "Ifl level egress firewall";
     output {
       choice output_c {
         case output-tag {
           leaf output {
             type string;
           }
         }
         case multichassis-tag {
           anyxml multi-routing-engine-results;
         }
       }
     }
   }
   rpc get-pfe-tcam-usage-egress-tcam-stage-detail-ifl-statistics-out {
     description "Ifl level statistics (egress)";
     output {
       choice output_c {
         case output-tag {
           leaf output {
             type string;
           }
         }
         case multichassis-tag {
           anyxml multi-routing-engine-results;
         }
       }
     }
   }
   rpc get-pfe-tcam-usage-egress-tcam-stage-detail-irb-cos-rw {
     description "IRB CoS rewrite";
     output {
       choice output_c {
         case output-tag {
           leaf output {
             type string;
           }
         }
         case multichassis-tag {
           anyxml multi-routing-engine-results;
         }
       }
     }
   }
   rpc get-pfe-tcam-usage-egress-tcam-stage-detail-lfm-802.3ah-out {
     description "Lfm-802.3ah (egress)";
     output {
       choice output_c {
         case output-tag {
           leaf output {
             type string;
           }
         }
         case multichassis-tag {
           anyxml multi-routing-engine-results;
         }
       }
     }
   }
   rpc get-pfe-tcam-usage-egress-tcam-stage-detail-ptpoe-cos-rw {
     description "CoS RW requires for PTPoE";
     output {
       choice output_c {
         case output-tag {
           leaf output {
             type string;
           }
         }
         case multichassis-tag {
           anyxml multi-routing-engine-results;
         }
       }
     }
   }
   rpc get-pfe-tcam-usage-egress-tcam-stage-detail-rfc2544-layer2-out {
     description "Rfc2544 for layer2 service (egress)";
     output {
       choice output_c {
         case output-tag {
           leaf output {
             type string;
           }
         }
         case multichassis-tag {
           anyxml multi-routing-engine-results;
         }
       }
     }
   }
   rpc get-pfe-tcam-usage-ingress-tcam-stage {
     description "Show tcam usage for ingress tcam-stage";
     output {
       choice output_c {
         case output-tag {
           leaf output {
             type string;
           }
         }
         case multichassis-tag {
           anyxml multi-routing-engine-results;
         }
       }
     }
   }
   rpc get-pfe-tcam-usage-ingress-tcam-stage-detail {
     description "Show tcam usage for ingress tcam-stage in detail";
     output {
       choice output_c {
         case output-tag {
           leaf output {
             type string;
           }
         }
         case multichassis-tag {
           anyxml multi-routing-engine-results;
         }
       }
     }
   }
   rpc get-pfe-tcam-usage-ingress-app {
     description "Show tcam usage for a tcam app";
     output {
       choice output_c {
         case output-tag {
           leaf output {
             type string;
           }
         }
         case multichassis-tag {
           anyxml multi-routing-engine-results;
         }
       }
     }
   }
   rpc get-pfe-tcam-usage-ingress-app-cfm-bd-filter {
     description "Cfm implicit bridge-domain filters";
     output {
       choice output_c {
         case output-tag {
           leaf output {
             type string;
           }
         }
         case multichassis-tag {
           anyxml multi-routing-engine-results;
         }
       }
     }
   }
   rpc get-pfe-tcam-usage-ingress-app-cfm-filter {
     description "Cfm implicit filters";
     output {
       choice output_c {
         case output-tag {
           leaf output {
             type string;
           }
         }
         case multichassis-tag {
           anyxml multi-routing-engine-results;
         }
       }
     }
   }
   rpc get-pfe-tcam-usage-ingress-app-cfm-vpls-filter {
     description "Cfm implicit vpls filters";
     output {
       choice output_c {
         case output-tag {
           leaf output {
             type string;
           }
         }
         case multichassis-tag {
           anyxml multi-routing-engine-results;
         }
       }
     }
   }
   rpc get-pfe-tcam-usage-ingress-app-cfm-vpls-ifl-filter {
     description "Cfm implicit vpls ifl filters";
     output {
       choice output_c {
         case output-tag {
           leaf output {
             type string;
           }
         }
         case multichassis-tag {
           anyxml multi-routing-engine-results;
         }
       }
     }
   }
   rpc get-pfe-tcam-usage-ingress-app-fw-ccc-in {
     description "Ccc family ingress firewall";
     output {
       choice output_c {
         case output-tag {
           leaf output {
             type string;
           }
         }
         case multichassis-tag {
           anyxml multi-routing-engine-results;
         }
       }
     }
   }
   rpc get-pfe-tcam-usage-ingress-app-fw-ifl-in {
     description "Ifl level ingress firewall";
     output {
       choice output_c {
         case output-tag {
           leaf output {
             type string;
           }
         }
         case multichassis-tag {
           anyxml multi-routing-engine-results;
         }
       }
     }
   }
   rpc get-pfe-tcam-usage-ingress-app-fw-inet-ftf {
     description "Inet family ingress firewall on a forwarding-table";
     output {
       choice output_c {
         case output-tag {
           leaf output {
             type string;
           }
         }
         case multichassis-tag {
           anyxml multi-routing-engine-results;
         }
       }
     }
   }
   rpc get-pfe-tcam-usage-ingress-app-fw-inet-in {
     description "Inet family ingress firewall";
     output {
       choice output_c {
         case output-tag {
           leaf output {
             type string;
           }
         }
         case multichassis-tag {
           anyxml multi-routing-engine-results;
         }
       }
     }
   }
   rpc get-pfe-tcam-usage-ingress-app-fw-inet-rpf {
     description "Inet family ingress firewall on rpf fail check";
     output {
       choice output_c {
         case output-tag {
           leaf output {
             type string;
           }
         }
         case multichassis-tag {
           anyxml multi-routing-engine-results;
         }
       }
     }
   }
   rpc get-pfe-tcam-usage-ingress-app-fw-inet6-ftf {
     description "Inet6 family ingress firewall on a forwarding-table";
     output {
       choice output_c {
         case output-tag {
           leaf output {
             type string;
           }
         }
         case multichassis-tag {
           anyxml multi-routing-engine-results;
         }
       }
     }
   }
   rpc get-pfe-tcam-usage-ingress-app-fw-inet6-in {
     description "Inet6 family ingress firewall";
     output {
       choice output_c {
         case output-tag {
           leaf output {
             type string;
           }
         }
         case multichassis-tag {
           anyxml multi-routing-engine-results;
         }
       }
     }
   }
   rpc get-pfe-tcam-usage-ingress-app-fw-inet6-rpf {
     description "Inet6 family ingress firewall on a rpf fail check";
     output {
       choice output_c {
         case output-tag {
           leaf output {
             type string;
           }
         }
         case multichassis-tag {
           anyxml multi-routing-engine-results;
         }
       }
     }
   }
   rpc get-pfe-tcam-usage-ingress-app-fw-inet-pm {
     description "Inet family firewall with port-mirror action";
     output {
       choice output_c {
         case output-tag {
           leaf output {
             type string;
           }
         }
         case multichassis-tag {
           anyxml multi-routing-engine-results;
         }
       }
     }
   }
   rpc get-pfe-tcam-usage-ingress-app-fw-l2-in {
     description "Bridge family ingress firewall on layer2 interface";
     output {
       choice output_c {
         case output-tag {
           leaf output {
             type string;
           }
         }
         case multichassis-tag {
           anyxml multi-routing-engine-results;
         }
       }
     }
   }
   rpc get-pfe-tcam-usage-ingress-app-fw-mpls-in {
     description "Mpls family ingress firewall";
     output {
       choice output_c {
         case output-tag {
           leaf output {
             type string;
           }
         }
         case multichassis-tag {
           anyxml multi-routing-engine-results;
         }
       }
     }
   }
   rpc get-pfe-tcam-usage-ingress-app-fw-vpls-in {
     description "VPLS family ingress firewall on vpls interface";
     output {
       choice output_c {
         case output-tag {
           leaf output {
             type string;
           }
         }
         case multichassis-tag {
           anyxml multi-routing-engine-results;
         }
       }
     }
   }
   rpc get-pfe-tcam-usage-ingress-app-gr-ifl-statistics-egr {
     description "GR Ifl level statistics (egress)";
     output {
       choice output_c {
         case output-tag {
           leaf output {
             type string;
           }
         }
         case multichassis-tag {
           anyxml multi-routing-engine-results;
         }
       }
     }
   }
   rpc get-pfe-tcam-usage-ingress-app-gr-ifl-statistics-ing {
     description "GR Ifl level statistics (ingress)";
     output {
       choice output_c {
         case output-tag {
           leaf output {
             type string;
           }
         }
         case multichassis-tag {
           anyxml multi-routing-engine-results;
         }
       }
     }
   }
   rpc get-pfe-tcam-usage-ingress-app-gr-ifl-statistics-preing {
     description "GR Ifl level statistics (pre-ingress)";
     output {
       choice output_c {
         case output-tag {
           leaf output {
             type string;
           }
         }
         case multichassis-tag {
           anyxml multi-routing-engine-results;
         }
       }
     }
   }
   rpc get-pfe-tcam-usage-ingress-app-ifl-statistics-in {
     description "Ifl level statistics (ingress)";
     output {
       choice output_c {
         case output-tag {
           leaf output {
             type string;
           }
         }
         case multichassis-tag {
           anyxml multi-routing-engine-results;
         }
       }
     }
   }
   rpc get-pfe-tcam-usage-ingress-app-irb-fixed-cos {
     description "IRB fixed classifier filter entries";
     output {
       choice output_c {
         case output-tag {
           leaf output {
             type string;
           }
         }
         case multichassis-tag {
           anyxml multi-routing-engine-results;
         }
       }
     }
   }
   rpc get-pfe-tcam-usage-ingress-app-mrouter-port-in {
     description "Multicast router port for snooping";
     output {
       choice output_c {
         case output-tag {
           leaf output {
             type string;
           }
         }
         case multichassis-tag {
           anyxml multi-routing-engine-results;
         }
       }
     }
   }
   rpc get-pfe-tcam-usage-ingress-app-ipsec-reverse-fil {
     description "Reverse filters for Ipsec service";
     output {
       choice output_c {
         case output-tag {
           leaf output {
             type string;
           }
         }
         case multichassis-tag {
           anyxml multi-routing-engine-results;
         }
       }
     }
   }
   rpc get-pfe-tcam-usage-ingress-app-lfm-802.3ah-in {
     description "Lfm-802.3ah (ingress)";
     output {
       choice output_c {
         case output-tag {
           leaf output {
             type string;
           }
         }
         case multichassis-tag {
           anyxml multi-routing-engine-results;
         }
       }
     }
   }
   rpc get-pfe-tcam-usage-ingress-app-lo0-inet-fil {
     description "Lo0 Inet Filter";
     output {
       choice output_c {
         case output-tag {
           leaf output {
             type string;
           }
         }
         case multichassis-tag {
           anyxml multi-routing-engine-results;
         }
       }
     }
   }
   rpc get-pfe-tcam-usage-ingress-app-lo0-inet6-fil {
     description "Lo0 Inet6 Filter";
     output {
       choice output_c {
         case output-tag {
           leaf output {
             type string;
           }
         }
         case multichassis-tag {
           anyxml multi-routing-engine-results;
         }
       }
     }
   }
   rpc get-pfe-tcam-usage-ingress-app-irb-inet6-fil {
     description "IRB Inet6 Filter";
     output {
       choice output_c {
         case output-tag {
           leaf output {
             type string;
           }
         }
         case multichassis-tag {
           anyxml multi-routing-engine-results;
         }
       }
     }
   }
   rpc get-pfe-tcam-usage-ingress-app-mac-drop-cnt {
     description "Statistics for drops by mac-validate/src-mac filters";
     output {
       choice output_c {
         case output-tag {
           leaf output {
             type string;
           }
         }
         case multichassis-tag {
           anyxml multi-routing-engine-results;
         }
       }
     }
   }
   rpc get-pfe-tcam-usage-ingress-app-napt-reverse-fil {
     description "Reverse filters for Napt service";
     output {
       choice output_c {
         case output-tag {
           leaf output {
             type string;
           }
         }
         case multichassis-tag {
           anyxml multi-routing-engine-results;
         }
       }
     }
   }
   rpc get-pfe-tcam-usage-ingress-app-no-local-switching {
     description "Bridge no-local-switching";
     output {
       choice output_c {
         case output-tag {
           leaf output {
             type string;
           }
         }
         case multichassis-tag {
           anyxml multi-routing-engine-results;
         }
       }
     }
   }
   rpc get-pfe-tcam-usage-pre-ingress-tcam-stage {
     description "Show tcam usage for pre-ingress tcam-stage";
     output {
       choice output_c {
         case output-tag {
           leaf output {
             type string;
           }
         }
         case multichassis-tag {
           anyxml multi-routing-engine-results;
         }
       }
     }
   }
   rpc get-pfe-tcam-usage-pre-ingress-tcam-stage-detail {
     description "Show tcam usage for pre-ingress tcam-stage in detail";
     output {
       choice output_c {
         case output-tag {
           leaf output {
             type string;
           }
         }
         case multichassis-tag {
           anyxml multi-routing-engine-results;
         }
       }
     }
   }
   rpc get-pfe-tcam-usage-pre-ingress-app {
     description "Show tcam usage for a tcam app";
     output {
       choice output_c {
         case output-tag {
           leaf output {
             type string;
           }
         }
         case multichassis-tag {
           anyxml multi-routing-engine-results;
         }
       }
     }
   }
   rpc get-pfe-tcam-usage-pre-ingress-app-cos-fc {
     description "Ifl level fixed classifier";
     output {
       choice output_c {
         case output-tag {
           leaf output {
             type string;
           }
         }
         case multichassis-tag {
           anyxml multi-routing-engine-results;
         }
       }
     }
   }
   rpc get-pfe-tcam-usage-pre-ingress-app-fw-fbf {
     description "Firewall filter based forwarding";
     output {
       choice output_c {
         case output-tag {
           leaf output {
             type string;
           }
         }
         case multichassis-tag {
           anyxml multi-routing-engine-results;
         }
       }
     }
   }
   rpc get-pfe-tcam-usage-pre-ingress-app-fw-fbf-inet6 {
     description "Firewall filter based forwarding for Inet6";
     output {
       choice output_c {
         case output-tag {
           leaf output {
             type string;
           }
         }
         case multichassis-tag {
           anyxml multi-routing-engine-results;
         }
       }
     }
   }
   rpc get-pfe-tcam-usage-pre-ingress-app-fw-semantics {
     description "Firewall sharing semantics for cli configured firewall";
     output {
       choice output_c {
         case output-tag {
           leaf output {
             type string;
           }
         }
         case multichassis-tag {
           anyxml multi-routing-engine-results;
         }
       }
     }
   }
   rpc get-pfe-tcam-usage-pre-ingress-app-ifd-src-mac-fil {
     description "Ifd level source mac filter";
     output {
       choice output_c {
         case output-tag {
           leaf output {
             type string;
           }
         }
         case multichassis-tag {
           anyxml multi-routing-engine-results;
         }
       }
     }
   }
   rpc get-pfe-tcam-usage-pre-ingress-app-ing-out-iff {
     description "Ingress app on behalf of egress family filter for log/syslog";
     output {
       choice output_c {
         case output-tag {
           leaf output {
             type string;
           }
         }
         case multichassis-tag {
           anyxml multi-routing-engine-results;
         }
       }
     }
   }
   rpc get-pfe-tcam-usage-pre-ingress-app-ip-mac-val {
     description "Ip mac validate";
     output {
       choice output_c {
         case output-tag {
           leaf output {
             type string;
           }
         }
         case multichassis-tag {
           anyxml multi-routing-engine-results;
         }
       }
     }
   }
   rpc get-pfe-tcam-usage-pre-ingress-app-ip-mac-val-bcast {
     description "Ip mac validate for broadcast";
     output {
       choice output_c {
         case output-tag {
           leaf output {
             type string;
           }
         }
         case multichassis-tag {
           anyxml multi-routing-engine-results;
         }
       }
     }
   }
   rpc get-pfe-tcam-usage-pre-ingress-app-rfc2544-layer2-in {
     description "Rfc2544 for layer2 service (ingress)";
     output {
       choice output_c {
         case output-tag {
           leaf output {
             type string;
           }
         }
         case multichassis-tag {
           anyxml multi-routing-engine-results;
         }
       }
     }
   }
   rpc get-pfe-tcam-usage-pre-ingress-app-vpls-mesh-group-ucast {
     description "VPLS mesh group unicast filters";
     output {
       choice output_c {
         case output-tag {
           leaf output {
             type string;
           }
         }
         case multichassis-tag {
           anyxml multi-routing-engine-results;
         }
       }
     }
   }
   rpc get-pfe-tcam-usage-pre-ingress-app-vpls-mesh-group-mcast {
     description "VPLS mesh group multicast filters";
     output {
       choice output_c {
         case output-tag {
           leaf output {
             type string;
           }
         }
         case multichassis-tag {
           anyxml multi-routing-engine-results;
         }
       }
     }
   }
   rpc get-pfe-tcam-usage-app {
     description "Show tcam usage for a tcam app";
     output {
       choice output_c {
         case output-tag {
           leaf output {
             type string;
           }
         }
         case multichassis-tag {
           anyxml multi-routing-engine-results;
         }
       }
     }
   }
   rpc get-pfe-tcam-usage-app-bd-dtag-validate {
     description "Bridge Domain dual-tagged validate";
     output {
       choice output_c {
         case output-tag {
           leaf output {
             type string;
           }
         }
         case multichassis-tag {
           anyxml multi-routing-engine-results;
         }
       }
     }
   }
   rpc get-pfe-tcam-usage-app-bd-tpid-swap {
     description "Bridge domain vlan-map with swap tpid operation";
     output {
       choice output_c {
         case output-tag {
           leaf output {
             type string;
           }
         }
         case multichassis-tag {
           anyxml multi-routing-engine-results;
         }
       }
     }
   }
   rpc get-pfe-tcam-usage-app-fw-family-out {
     description "Family level egress firewall";
     output {
       choice output_c {
         case output-tag {
           leaf output {
             type string;
           }
         }
         case multichassis-tag {
           anyxml multi-routing-engine-results;
         }
       }
     }
   }
   rpc get-pfe-tcam-usage-app-fw-inet6-family-out {
     description "Inet6 Family level egress firewall";
     output {
       choice output_c {
         case output-tag {
           leaf output {
             type string;
           }
         }
         case multichassis-tag {
           anyxml multi-routing-engine-results;
         }
       }
     }
   }
   rpc get-pfe-tcam-usage-app-fw-ifl-out {
     description "Ifl level egress firewall";
     output {
       choice output_c {
         case output-tag {
           leaf output {
             type string;
           }
         }
         case multichassis-tag {
           anyxml multi-routing-engine-results;
         }
       }
     }
   }
   rpc get-pfe-tcam-usage-app-ifl-statistics-out {
     description "Ifl level statistics (egress)";
     output {
       choice output_c {
         case output-tag {
           leaf output {
             type string;
           }
         }
         case multichassis-tag {
           anyxml multi-routing-engine-results;
         }
       }
     }
   }
   rpc get-pfe-tcam-usage-app-irb-cos-rw {
     description "IRB CoS rewrite";
     output {
       choice output_c {
         case output-tag {
           leaf output {
             type string;
           }
         }
         case multichassis-tag {
           anyxml multi-routing-engine-results;
         }
       }
     }
   }
   rpc get-pfe-tcam-usage-app-lfm-802.3ah-out {
     description "Lfm-802.3ah (egress)";
     output {
       choice output_c {
         case output-tag {
           leaf output {
             type string;
           }
         }
         case multichassis-tag {
           anyxml multi-routing-engine-results;
         }
       }
     }
   }
   rpc get-pfe-tcam-usage-app-ptpoe-cos-rw {
     description "CoS RW requires for PTPoE";
     output {
       choice output_c {
         case output-tag {
           leaf output {
             type string;
           }
         }
         case multichassis-tag {
           anyxml multi-routing-engine-results;
         }
       }
     }
   }
   rpc get-pfe-tcam-usage-app-rfc2544-layer2-out {
     description "Rfc2544 for layer2 service (egress)";
     output {
       choice output_c {
         case output-tag {
           leaf output {
             type string;
           }
         }
         case multichassis-tag {
           anyxml multi-routing-engine-results;
         }
       }
     }
   }
   rpc get-pfe-tcam-usage-app-cfm-bd-filter {
     description "Cfm implicit bridge-domain filters";
     output {
       choice output_c {
         case output-tag {
           leaf output {
             type string;
           }
         }
         case multichassis-tag {
           anyxml multi-routing-engine-results;
         }
       }
     }
   }
   rpc get-pfe-tcam-usage-app-cfm-filter {
     description "Cfm implicit filters";
     output {
       choice output_c {
         case output-tag {
           leaf output {
             type string;
           }
         }
         case multichassis-tag {
           anyxml multi-routing-engine-results;
         }
       }
     }
   }
   rpc get-pfe-tcam-usage-app-cfm-vpls-filter {
     description "Cfm implicit vpls filters";
     output {
       choice output_c {
         case output-tag {
           leaf output {
             type string;
           }
         }
         case multichassis-tag {
           anyxml multi-routing-engine-results;
         }
       }
     }
   }
   rpc get-pfe-tcam-usage-app-cfm-vpls-ifl-filter {
     description "Cfm implicit vpls ifl filters";
     output {
       choice output_c {
         case output-tag {
           leaf output {
             type string;
           }
         }
         case multichassis-tag {
           anyxml multi-routing-engine-results;
         }
       }
     }
   }
   rpc get-pfe-tcam-usage-app-fw-ccc-in {
     description "Ccc family ingress firewall";
     output {
       choice output_c {
         case output-tag {
           leaf output {
             type string;
           }
         }
         case multichassis-tag {
           anyxml multi-routing-engine-results;
         }
       }
     }
   }
   rpc get-pfe-tcam-usage-app-fw-ifl-in {
     description "Ifl level ingress firewall";
     output {
       choice output_c {
         case output-tag {
           leaf output {
             type string;
           }
         }
         case multichassis-tag {
           anyxml multi-routing-engine-results;
         }
       }
     }
   }
   rpc get-pfe-tcam-usage-app-fw-inet-ftf {
     description "Inet family ingress firewall on a forwarding-table";
     output {
       choice output_c {
         case output-tag {
           leaf output {
             type string;
           }
         }
         case multichassis-tag {
           anyxml multi-routing-engine-results;
         }
       }
     }
   }
   rpc get-pfe-tcam-usage-app-fw-inet-in {
     description "Inet family ingress firewall";
     output {
       choice output_c {
         case output-tag {
           leaf output {
             type string;
           }
         }
         case multichassis-tag {
           anyxml multi-routing-engine-results;
         }
       }
     }
   }
   rpc get-pfe-tcam-usage-app-fw-inet-rpf {
     description "Inet family ingress firewall on rpf fail check";
     output {
       choice output_c {
         case output-tag {
           leaf output {
             type string;
           }
         }
         case multichassis-tag {
           anyxml multi-routing-engine-results;
         }
       }
     }
   }
   rpc get-pfe-tcam-usage-app-fw-inet6-ftf {
     description "Inet6 family ingress firewall on a forwarding-table";
     output {
       choice output_c {
         case output-tag {
           leaf output {
             type string;
           }
         }
         case multichassis-tag {
           anyxml multi-routing-engine-results;
         }
       }
     }
   }
   rpc get-pfe-tcam-usage-app-fw-inet6-in {
     description "Inet6 family ingress firewall";
     output {
       choice output_c {
         case output-tag {
           leaf output {
             type string;
           }
         }
         case multichassis-tag {
           anyxml multi-routing-engine-results;
         }
       }
     }
   }
   rpc get-pfe-tcam-usage-app-fw-inet6-rpf {
     description "Inet6 family ingress firewall on a rpf fail check";
     output {
       choice output_c {
         case output-tag {
           leaf output {
             type string;
           }
         }
         case multichassis-tag {
           anyxml multi-routing-engine-results;
         }
       }
     }
   }
   rpc get-pfe-tcam-usage-app-fw-inet-pm {
     description "Inet family firewall with port-mirror action";
     output {
       choice output_c {
         case output-tag {
           leaf output {
             type string;
           }
         }
         case multichassis-tag {
           anyxml multi-routing-engine-results;
         }
       }
     }
   }
   rpc get-pfe-tcam-usage-app-fw-l2-in {
     description "Bridge family ingress firewall on layer2 interface";
     output {
       choice output_c {
         case output-tag {
           leaf output {
             type string;
           }
         }
         case multichassis-tag {
           anyxml multi-routing-engine-results;
         }
       }
     }
   }
   rpc get-pfe-tcam-usage-app-fw-mpls-in {
     description "Mpls family ingress firewall";
     output {
       choice output_c {
         case output-tag {
           leaf output {
             type string;
           }
         }
         case multichassis-tag {
           anyxml multi-routing-engine-results;
         }
       }
     }
   }
   rpc get-pfe-tcam-usage-app-fw-vpls-in {
     description "VPLS family ingress firewall on vpls interface";
     output {
       choice output_c {
         case output-tag {
           leaf output {
             type string;
           }
         }
         case multichassis-tag {
           anyxml multi-routing-engine-results;
         }
       }
     }
   }
   rpc get-pfe-tcam-usage-app-gr-ifl-statistics-egr {
     description "GR Ifl level statistics (egress)";
     output {
       choice output_c {
         case output-tag {
           leaf output {
             type string;
           }
         }
         case multichassis-tag {
           anyxml multi-routing-engine-results;
         }
       }
     }
   }
   rpc get-pfe-tcam-usage-app-gr-ifl-statistics-ing {
     description "GR Ifl level statistics (ingress)";
     output {
       choice output_c {
         case output-tag {
           leaf output {
             type string;
           }
         }
         case multichassis-tag {
           anyxml multi-routing-engine-results;
         }
       }
     }
   }
   rpc get-pfe-tcam-usage-app-gr-ifl-statistics-preing {
     description "GR Ifl level statistics (pre-ingress)";
     output {
       choice output_c {
         case output-tag {
           leaf output {
             type string;
           }
         }
         case multichassis-tag {
           anyxml multi-routing-engine-results;
         }
       }
     }
   }
   rpc get-pfe-tcam-usage-app-ifl-statistics-in {
     description "Ifl level statistics (ingress)";
     output {
       choice output_c {
         case output-tag {
           leaf output {
             type string;
           }
         }
         case multichassis-tag {
           anyxml multi-routing-engine-results;
         }
       }
     }
   }
   rpc get-pfe-tcam-usage-app-irb-fixed-cos {
     description "IRB fixed classifier filter entries";
     output {
       choice output_c {
         case output-tag {
           leaf output {
             type string;
           }
         }
         case multichassis-tag {
           anyxml multi-routing-engine-results;
         }
       }
     }
   }
   rpc get-pfe-tcam-usage-app-mrouter-port-in {
     description "Multicast router port for snooping";
     output {
       choice output_c {
         case output-tag {
           leaf output {
             type string;
           }
         }
         case multichassis-tag {
           anyxml multi-routing-engine-results;
         }
       }
     }
   }
   rpc get-pfe-tcam-usage-app-ipsec-reverse-fil {
     description "Reverse filters for Ipsec service";
     output {
       choice output_c {
         case output-tag {
           leaf output {
             type string;
           }
         }
         case multichassis-tag {
           anyxml multi-routing-engine-results;
         }
       }
     }
   }
   rpc get-pfe-tcam-usage-app-lfm-802.3ah-in {
     description "Lfm-802.3ah (ingress)";
     output {
       choice output_c {
         case output-tag {
           leaf output {
             type string;
           }
         }
         case multichassis-tag {
           anyxml multi-routing-engine-results;
         }
       }
     }
   }
   rpc get-pfe-tcam-usage-app-lo0-inet-fil {
     description "Lo0 Inet Filter";
     output {
       choice output_c {
         case output-tag {
           leaf output {
             type string;
           }
         }
         case multichassis-tag {
           anyxml multi-routing-engine-results;
         }
       }
     }
   }
   rpc get-pfe-tcam-usage-app-lo0-inet6-fil {
     description "Lo0 Inet6 Filter";
     output {
       choice output_c {
         case output-tag {
           leaf output {
             type string;
           }
         }
         case multichassis-tag {
           anyxml multi-routing-engine-results;
         }
       }
     }
   }
   rpc get-pfe-tcam-usage-app-irb-inet6-fil {
     description "IRB Inet6 Filter";
     output {
       choice output_c {
         case output-tag {
           leaf output {
             type string;
           }
         }
         case multichassis-tag {
           anyxml multi-routing-engine-results;
         }
       }
     }
   }
   rpc get-pfe-tcam-usage-app-mac-drop-cnt {
     description "Statistics for drops by mac-validate/src-mac filters";
     output {
       choice output_c {
         case output-tag {
           leaf output {
             type string;
           }
         }
         case multichassis-tag {
           anyxml multi-routing-engine-results;
         }
       }
     }
   }
   rpc get-pfe-tcam-usage-app-napt-reverse-fil {
     description "Reverse filters for Napt service";
     output {
       choice output_c {
         case output-tag {
           leaf output {
             type string;
           }
         }
         case multichassis-tag {
           anyxml multi-routing-engine-results;
         }
       }
     }
   }
   rpc get-pfe-tcam-usage-app-no-local-switching {
     description "Bridge no-local-switching";
     output {
       choice output_c {
         case output-tag {
           leaf output {
             type string;
           }
         }
         case multichassis-tag {
           anyxml multi-routing-engine-results;
         }
       }
     }
   }
   rpc get-pfe-tcam-usage-app-cos-fc {
     description "Ifl level fixed classifier";
     output {
       choice output_c {
         case output-tag {
           leaf output {
             type string;
           }
         }
         case multichassis-tag {
           anyxml multi-routing-engine-results;
         }
       }
     }
   }
   rpc get-pfe-tcam-usage-app-fw-fbf {
     description "Firewall filter based forwarding";
     output {
       choice output_c {
         case output-tag {
           leaf output {
             type string;
           }
         }
         case multichassis-tag {
           anyxml multi-routing-engine-results;
         }
       }
     }
   }
   rpc get-pfe-tcam-usage-app-fw-fbf-inet6 {
     description "Firewall filter based forwarding for Inet6";
     output {
       choice output_c {
         case output-tag {
           leaf output {
             type string;
           }
         }
         case multichassis-tag {
           anyxml multi-routing-engine-results;
         }
       }
     }
   }
   rpc get-pfe-tcam-usage-app-fw-semantics {
     description "Firewall sharing semantics for cli configured firewall";
     output {
       choice output_c {
         case output-tag {
           leaf output {
             type string;
           }
         }
         case multichassis-tag {
           anyxml multi-routing-engine-results;
         }
       }
     }
   }
   rpc get-pfe-tcam-usage-app-ifd-src-mac-fil {
     description "Ifd level source mac filter";
     output {
       choice output_c {
         case output-tag {
           leaf output {
             type string;
           }
         }
         case multichassis-tag {
           anyxml multi-routing-engine-results;
         }
       }
     }
   }
   rpc get-pfe-tcam-usage-app-ing-out-iff {
     description "Ingress app on behalf of egress family filter for log/syslog";
     output {
       choice output_c {
         case output-tag {
           leaf output {
             type string;
           }
         }
         case multichassis-tag {
           anyxml multi-routing-engine-results;
         }
       }
     }
   }
   rpc get-pfe-tcam-usage-app-ip-mac-val {
     description "Ip mac validate";
     output {
       choice output_c {
         case output-tag {
           leaf output {
             type string;
           }
         }
         case multichassis-tag {
           anyxml multi-routing-engine-results;
         }
       }
     }
   }
   rpc get-pfe-tcam-usage-app-ip-mac-val-bcast {
     description "Ip mac validate for broadcast";
     output {
       choice output_c {
         case output-tag {
           leaf output {
             type string;
           }
         }
         case multichassis-tag {
           anyxml multi-routing-engine-results;
         }
       }
     }
   }
   rpc get-pfe-tcam-usage-app-rfc2544-layer2-in {
     description "Rfc2544 for layer2 service (ingress)";
     output {
       choice output_c {
         case output-tag {
           leaf output {
             type string;
           }
         }
         case multichassis-tag {
           anyxml multi-routing-engine-results;
         }
       }
     }
   }
   rpc get-pfe-tcam-usage-app-vpls-mesh-group-ucast {
     description "VPLS mesh group unicast filters";
     output {
       choice output_c {
         case output-tag {
           leaf output {
             type string;
           }
         }
         case multichassis-tag {
           anyxml multi-routing-engine-results;
         }
       }
     }
   }
   rpc get-pfe-tcam-usage-app-vpls-mesh-group-mcast {
     description "VPLS mesh group multicast filters";
     output {
       choice output_c {
         case output-tag {
           leaf output {
             type string;
           }
         }
         case multichassis-tag {
           anyxml multi-routing-engine-results;
         }
       }
     }
   }
   rpc get-pfe-tcam-errors {
     description "Show packet forwarding engine tcam errors";
     output {
       choice output_c {
         case output-tag {
           leaf output {
             type string;
           }
         }
         case multichassis-tag {
           anyxml multi-routing-engine-results;
         }
       }
     }
   }
   rpc get-pfe-tcam-errors-all-tcam-stages {
     description "Show packet forwarding engine tcam errors at all tcam stages";
     output {
       choice output_c {
         case output-tag {
           leaf output {
             type string;
           }
         }
         case multichassis-tag {
           anyxml multi-routing-engine-results;
         }
       }
     }
   }
   rpc get-pfe-tcam-errors-all-tcam-stages-detail {
     description "Show packet forwarding engine tcam errors at all tcam stages in detail";
     output {
       choice output_c {
         case output-tag {
           leaf output {
             type string;
           }
         }
         case multichassis-tag {
           anyxml multi-routing-engine-results;
         }
       }
     }
   }
   rpc get-pfe-tcam-errors-egress-tcam-stage {
     description "Show tcam errors for egress tcam-stage";
     output {
       choice output_c {
         case output-tag {
           leaf output {
             type string;
           }
         }
         case multichassis-tag {
           anyxml multi-routing-engine-results;
         }
       }
     }
   }
   rpc get-pfe-tcam-errors-egress-tcam-stage-detail {
     description "Show tcam errors for egress tcam-stage in detail";
     output {
       choice output_c {
         case output-tag {
           leaf output {
             type string;
           }
         }
         case multichassis-tag {
           anyxml multi-routing-engine-results;
         }
       }
     }
   }
   rpc get-pfe-tcam-errors-egress-app {
     description "Show tcam errors for a tcam app";
     output {
       choice output_c {
         case output-tag {
           leaf output {
             type string;
           }
         }
         case multichassis-tag {
           anyxml multi-routing-engine-results;
         }
       }
     }
   }
   rpc get-pfe-tcam-errors-egress-app-bd-dtag-validate {
     description "Bridge Domain dual-tagged validate";
     output {
       choice output_c {
         case output-tag {
           leaf output {
             type string;
           }
         }
         case multichassis-tag {
           anyxml multi-routing-engine-results;
         }
       }
     }
   }
   rpc get-pfe-tcam-errors-egress-app-bd-tpid-swap {
     description "Bridge domain vlan-map with swap tpid operation";
     output {
       choice output_c {
         case output-tag {
           leaf output {
             type string;
           }
         }
         case multichassis-tag {
           anyxml multi-routing-engine-results;
         }
       }
     }
   }
   rpc get-pfe-tcam-errors-egress-app-fw-family-out {
     description "Family level egress firewall";
     output {
       choice output_c {
         case output-tag {
           leaf output {
             type string;
           }
         }
         case multichassis-tag {
           anyxml multi-routing-engine-results;
         }
       }
     }
   }
   rpc get-pfe-tcam-errors-egress-app-fw-inet6-family-out {
     description "Inet6 Family level egress firewall";
     output {
       choice output_c {
         case output-tag {
           leaf output {
             type string;
           }
         }
         case multichassis-tag {
           anyxml multi-routing-engine-results;
         }
       }
     }
   }
   rpc get-pfe-tcam-errors-egress-app-fw-ifl-out {
     description "Ifl level egress firewall";
     output {
       choice output_c {
         case output-tag {
           leaf output {
             type string;
           }
         }
         case multichassis-tag {
           anyxml multi-routing-engine-results;
         }
       }
     }
   }
   rpc get-pfe-tcam-errors-egress-app-ifl-statistics-out {
     description "Ifl level statistics (egress)";
     output {
       choice output_c {
         case output-tag {
           leaf output {
             type string;
           }
         }
         case multichassis-tag {
           anyxml multi-routing-engine-results;
         }
       }
     }
   }
   rpc get-pfe-tcam-errors-egress-app-irb-cos-rw {
     description "IRB CoS rewrite";
     output {
       choice output_c {
         case output-tag {
           leaf output {
             type string;
           }
         }
         case multichassis-tag {
           anyxml multi-routing-engine-results;
         }
       }
     }
   }
   rpc get-pfe-tcam-errors-egress-app-lfm-802.3ah-out {
     description "Lfm-802.3ah (egress)";
     output {
       choice output_c {
         case output-tag {
           leaf output {
             type string;
           }
         }
         case multichassis-tag {
           anyxml multi-routing-engine-results;
         }
       }
     }
   }
   rpc get-pfe-tcam-errors-egress-app-ptpoe-cos-rw {
     description "CoS RW requires for PTPoE";
     output {
       choice output_c {
         case output-tag {
           leaf output {
             type string;
           }
         }
         case multichassis-tag {
           anyxml multi-routing-engine-results;
         }
       }
     }
   }
   rpc get-pfe-tcam-errors-egress-app-rfc2544-layer2-out {
     description "Rfc2544 for layer2 service (egress)";
     output {
       choice output_c {
         case output-tag {
           leaf output {
             type string;
           }
         }
         case multichassis-tag {
           anyxml multi-routing-engine-results;
         }
       }
     }
   }
   rpc get-pfe-tcam-errors-ingress-tcam-stage {
     description "Show tcam errors for ingress tcam-stage";
     output {
       choice output_c {
         case output-tag {
           leaf output {
             type string;
           }
         }
         case multichassis-tag {
           anyxml multi-routing-engine-results;
         }
       }
     }
   }
   rpc get-pfe-tcam-errors-ingress-tcam-stage-app {
     description "Show tcam errors for a tcam app";
     output {
       choice output_c {
         case output-tag {
           leaf output {
             type string;
           }
         }
         case multichassis-tag {
           anyxml multi-routing-engine-results;
         }
       }
     }
   }
   rpc get-pfe-tcam-errors-ingress-tcam-stage-cfm-bd-filter {
     description "Cfm implicit bridge-domain filters";
     output {
       choice output_c {
         case output-tag {
           leaf output {
             type string;
           }
         }
         case multichassis-tag {
           anyxml multi-routing-engine-results;
         }
       }
     }
   }
   rpc get-pfe-tcam-errors-ingress-tcam-stage-cfm-filter {
     description "Cfm implicit filters";
     output {
       choice output_c {
         case output-tag {
           leaf output {
             type string;
           }
         }
         case multichassis-tag {
           anyxml multi-routing-engine-results;
         }
       }
     }
   }
   rpc get-pfe-tcam-errors-ingress-tcam-stage-cfm-vpls-filter {
     description "Cfm implicit vpls filters";
     output {
       choice output_c {
         case output-tag {
           leaf output {
             type string;
           }
         }
         case multichassis-tag {
           anyxml multi-routing-engine-results;
         }
       }
     }
   }
   rpc get-pfe-tcam-errors-ingress-tcam-stage-cfm-vpls-ifl-filter {
     description "Cfm implicit vpls ifl filters";
     output {
       choice output_c {
         case output-tag {
           leaf output {
             type string;
           }
         }
         case multichassis-tag {
           anyxml multi-routing-engine-results;
         }
       }
     }
   }
   rpc get-pfe-tcam-errors-ingress-tcam-stage-fw-ccc-in {
     description "Ccc family ingress firewall";
     output {
       choice output_c {
         case output-tag {
           leaf output {
             type string;
           }
         }
         case multichassis-tag {
           anyxml multi-routing-engine-results;
         }
       }
     }
   }
   rpc get-pfe-tcam-errors-ingress-tcam-stage-fw-ifl-in {
     description "Ifl level ingress firewall";
     output {
       choice output_c {
         case output-tag {
           leaf output {
             type string;
           }
         }
         case multichassis-tag {
           anyxml multi-routing-engine-results;
         }
       }
     }
   }
   rpc get-pfe-tcam-errors-ingress-tcam-stage-fw-inet-ftf {
     description "Inet family ingress firewall on a forwarding-table";
     output {
       choice output_c {
         case output-tag {
           leaf output {
             type string;
           }
         }
         case multichassis-tag {
           anyxml multi-routing-engine-results;
         }
       }
     }
   }
   rpc get-pfe-tcam-errors-ingress-tcam-stage-fw-inet-in {
     description "Inet family ingress firewall";
     output {
       choice output_c {
         case output-tag {
           leaf output {
             type string;
           }
         }
         case multichassis-tag {
           anyxml multi-routing-engine-results;
         }
       }
     }
   }
   rpc get-pfe-tcam-errors-ingress-tcam-stage-fw-inet-rpf {
     description "Inet family ingress firewall on rpf fail check";
     output {
       choice output_c {
         case output-tag {
           leaf output {
             type string;
           }
         }
         case multichassis-tag {
           anyxml multi-routing-engine-results;
         }
       }
     }
   }
   rpc get-pfe-tcam-errors-ingress-tcam-stage-fw-inet6-ftf {
     description "Inet6 family ingress firewall on a forwarding-table";
     output {
       choice output_c {
         case output-tag {
           leaf output {
             type string;
           }
         }
         case multichassis-tag {
           anyxml multi-routing-engine-results;
         }
       }
     }
   }
   rpc get-pfe-tcam-errors-ingress-tcam-stage-fw-inet6-in {
     description "Inet6 family ingress firewall";
     output {
       choice output_c {
         case output-tag {
           leaf output {
             type string;
           }
         }
         case multichassis-tag {
           anyxml multi-routing-engine-results;
         }
       }
     }
   }
   rpc get-pfe-tcam-errors-ingress-tcam-stage-fw-inet6-rpf {
     description "Inet6 family ingress firewall on a rpf fail check";
     output {
       choice output_c {
         case output-tag {
           leaf output {
             type string;
           }
         }
         case multichassis-tag {
           anyxml multi-routing-engine-results;
         }
       }
     }
   }
   rpc get-pfe-tcam-errors-ingress-tcam-stage-fw-inet-pm {
     description "Inet family firewall with port-mirror action";
     output {
       choice output_c {
         case output-tag {
           leaf output {
             type string;
           }
         }
         case multichassis-tag {
           anyxml multi-routing-engine-results;
         }
       }
     }
   }
   rpc get-pfe-tcam-errors-ingress-tcam-stage-fw-l2-in {
     description "Bridge family ingress firewall on layer2 interface";
     output {
       choice output_c {
         case output-tag {
           leaf output {
             type string;
           }
         }
         case multichassis-tag {
           anyxml multi-routing-engine-results;
         }
       }
     }
   }
   rpc get-pfe-tcam-errors-ingress-tcam-stage-fw-mpls-in {
     description "Mpls family ingress firewall";
     output {
       choice output_c {
         case output-tag {
           leaf output {
             type string;
           }
         }
         case multichassis-tag {
           anyxml multi-routing-engine-results;
         }
       }
     }
   }
   rpc get-pfe-tcam-errors-ingress-tcam-stage-fw-vpls-in {
     description "VPLS family ingress firewall on vpls interface";
     output {
       choice output_c {
         case output-tag {
           leaf output {
             type string;
           }
         }
         case multichassis-tag {
           anyxml multi-routing-engine-results;
         }
       }
     }
   }
   rpc get-pfe-tcam-errors-ingress-tcam-stage-gr-ifl-statistics-egr {
     description "GR Ifl level statistics (egress)";
     output {
       choice output_c {
         case output-tag {
           leaf output {
             type string;
           }
         }
         case multichassis-tag {
           anyxml multi-routing-engine-results;
         }
       }
     }
   }
   rpc get-pfe-tcam-errors-ingress-tcam-stage-gr-ifl-statistics-ing {
     description "GR Ifl level statistics (ingress)";
     output {
       choice output_c {
         case output-tag {
           leaf output {
             type string;
           }
         }
         case multichassis-tag {
           anyxml multi-routing-engine-results;
         }
       }
     }
   }
   rpc get-pfe-tcam-errors-ingress-tcam-stage-gr-ifl-statistics-preing {
     description "GR Ifl level statistics (pre-ingress)";
     output {
       choice output_c {
         case output-tag {
           leaf output {
             type string;
           }
         }
         case multichassis-tag {
           anyxml multi-routing-engine-results;
         }
       }
     }
   }
   rpc get-pfe-tcam-errors-ingress-tcam-stage-ifl-statistics-in {
     description "Ifl level statistics (ingress)";
     output {
       choice output_c {
         case output-tag {
           leaf output {
             type string;
           }
         }
         case multichassis-tag {
           anyxml multi-routing-engine-results;
         }
       }
     }
   }
   rpc get-pfe-tcam-errors-ingress-tcam-stage-irb-fixed-cos {
     description "IRB fixed classifier filter entries";
     output {
       choice output_c {
         case output-tag {
           leaf output {
             type string;
           }
         }
         case multichassis-tag {
           anyxml multi-routing-engine-results;
         }
       }
     }
   }
   rpc get-pfe-tcam-errors-ingress-tcam-stage-mrouter-port-in {
     description "Multicast router port for snooping";
     output {
       choice output_c {
         case output-tag {
           leaf output {
             type string;
           }
         }
         case multichassis-tag {
           anyxml multi-routing-engine-results;
         }
       }
     }
   }
   rpc get-pfe-tcam-errors-ingress-tcam-stage-ipsec-reverse-fil {
     description "Reverse filters for Ipsec service";
     output {
       choice output_c {
         case output-tag {
           leaf output {
             type string;
           }
         }
         case multichassis-tag {
           anyxml multi-routing-engine-results;
         }
       }
     }
   }
   rpc get-pfe-tcam-errors-ingress-tcam-stage-lfm-802.3ah-in {
     description "Lfm-802.3ah (ingress)";
     output {
       choice output_c {
         case output-tag {
           leaf output {
             type string;
           }
         }
         case multichassis-tag {
           anyxml multi-routing-engine-results;
         }
       }
     }
   }
   rpc get-pfe-tcam-errors-ingress-tcam-stage-lo0-inet-fil {
     description "Lo0 Inet Filter";
     output {
       choice output_c {
         case output-tag {
           leaf output {
             type string;
           }
         }
         case multichassis-tag {
           anyxml multi-routing-engine-results;
         }
       }
     }
   }
   rpc get-pfe-tcam-errors-ingress-tcam-stage-lo0-inet6-fil {
     description "Lo0 Inet6 Filter";
     output {
       choice output_c {
         case output-tag {
           leaf output {
             type string;
           }
         }
         case multichassis-tag {
           anyxml multi-routing-engine-results;
         }
       }
     }
   }
   rpc get-pfe-tcam-errors-ingress-tcam-stage-irb-inet6-fil {
     description "IRB Inet6 Filter";
     output {
       choice output_c {
         case output-tag {
           leaf output {
             type string;
           }
         }
         case multichassis-tag {
           anyxml multi-routing-engine-results;
         }
       }
     }
   }
   rpc get-pfe-tcam-errors-ingress-tcam-stage-mac-drop-cnt {
     description "Statistics for drops by mac-validate/src-mac filters";
     output {
       choice output_c {
         case output-tag {
           leaf output {
             type string;
           }
         }
         case multichassis-tag {
           anyxml multi-routing-engine-results;
         }
       }
     }
   }
   rpc get-pfe-tcam-errors-ingress-tcam-stage-napt-reverse-fil {
     description "Reverse filters for Napt service";
     output {
       choice output_c {
         case output-tag {
           leaf output {
             type string;
           }
         }
         case multichassis-tag {
           anyxml multi-routing-engine-results;
         }
       }
     }
   }
   rpc get-pfe-tcam-errors-ingress-tcam-stage-no-local-switching {
     description "Bridge no-local-switching";
     output {
       choice output_c {
         case output-tag {
           leaf output {
             type string;
           }
         }
         case multichassis-tag {
           anyxml multi-routing-engine-results;
         }
       }
     }
   }
   rpc get-pfe-tcam-errors-pre-ingress-tcam-stage {
     description "Show tcam errors for pre-ingress tcam-stage";
     output {
       choice output_c {
         case output-tag {
           leaf output {
             type string;
           }
         }
         case multichassis-tag {
           anyxml multi-routing-engine-results;
         }
       }
     }
   }
   rpc get-pfe-tcam-errors-pre-ingress-tcam-stage-detail {
     description "Show tcam errors for pre-ingress tcam-stage in detail";
     output {
       choice output_c {
         case output-tag {
           leaf output {
             type string;
           }
         }
         case multichassis-tag {
           anyxml multi-routing-engine-results;
         }
       }
     }
   }
   rpc get-pfe-tcam-errors-pre-ingress-app {
     description "Show tcam errors for a tcam app";
     output {
       choice output_c {
         case output-tag {
           leaf output {
             type string;
           }
         }
         case multichassis-tag {
           anyxml multi-routing-engine-results;
         }
       }
     }
   }
   rpc get-pfe-tcam-errors-pre-ingress-app-cos-fc {
     description "Ifl level fixed classifier";
     output {
       choice output_c {
         case output-tag {
           leaf output {
             type string;
           }
         }
         case multichassis-tag {
           anyxml multi-routing-engine-results;
         }
       }
     }
   }
   rpc get-pfe-tcam-errors-pre-ingress-app-fw-fbf {
     description "Firewall filter based forwarding";
     output {
       choice output_c {
         case output-tag {
           leaf output {
             type string;
           }
         }
         case multichassis-tag {
           anyxml multi-routing-engine-results;
         }
       }
     }
   }
   rpc get-pfe-tcam-errors-pre-ingress-app-fw-fbf-inet6 {
     description "Firewall filter based forwarding for Inet6";
     output {
       choice output_c {
         case output-tag {
           leaf output {
             type string;
           }
         }
         case multichassis-tag {
           anyxml multi-routing-engine-results;
         }
       }
     }
   }
   rpc get-pfe-tcam-errors-pre-ingress-app-fw-semantics {
     description "Firewall sharing semantics for cli configured firewall";
     output {
       choice output_c {
         case output-tag {
           leaf output {
             type string;
           }
         }
         case multichassis-tag {
           anyxml multi-routing-engine-results;
         }
       }
     }
   }
   rpc get-pfe-tcam-errors-pre-ingress-app-ifd-src-mac-fil {
     description "Ifd level source mac filter";
     output {
       choice output_c {
         case output-tag {
           leaf output {
             type string;
           }
         }
         case multichassis-tag {
           anyxml multi-routing-engine-results;
         }
       }
     }
   }
   rpc get-pfe-tcam-errors-pre-ingress-app-ing-out-iff {
     description "Ingress app on behalf of egress family filter for log/syslog";
     output {
       choice output_c {
         case output-tag {
           leaf output {
             type string;
           }
         }
         case multichassis-tag {
           anyxml multi-routing-engine-results;
         }
       }
     }
   }
   rpc get-pfe-tcam-errors-pre-ingress-app-ip-mac-val {
     description "Ip mac validate";
     output {
       choice output_c {
         case output-tag {
           leaf output {
             type string;
           }
         }
         case multichassis-tag {
           anyxml multi-routing-engine-results;
         }
       }
     }
   }
   rpc get-pfe-tcam-errors-pre-ingress-app-ip-mac-val-bcast {
     description "Ip mac validate for broadcast";
     output {
       choice output_c {
         case output-tag {
           leaf output {
             type string;
           }
         }
         case multichassis-tag {
           anyxml multi-routing-engine-results;
         }
       }
     }
   }
   rpc get-pfe-tcam-errors-pre-ingress-app-rfc2544-layer2-in {
     description "Rfc2544 for layer2 service (ingress)";
     output {
       choice output_c {
         case output-tag {
           leaf output {
             type string;
           }
         }
         case multichassis-tag {
           anyxml multi-routing-engine-results;
         }
       }
     }
   }
   rpc get-pfe-tcam-errors-pre-ingress-app-vpls-mesh-group-ucast {
     description "VPLS mesh group unicast filters";
     output {
       choice output_c {
         case output-tag {
           leaf output {
             type string;
           }
         }
         case multichassis-tag {
           anyxml multi-routing-engine-results;
         }
       }
     }
   }
   rpc get-pfe-tcam-errors-pre-ingress-app-vpls-mesh-group-mcast {
     description "VPLS mesh group multicast filters";
     output {
       choice output_c {
         case output-tag {
           leaf output {
             type string;
           }
         }
         case multichassis-tag {
           anyxml multi-routing-engine-results;
         }
       }
     }
   }
   rpc get-pfe-tcam-errors-app {
     description "Show tcam errors for a tcam app";
     output {
       choice output_c {
         case output-tag {
           leaf output {
             type string;
           }
         }
         case multichassis-tag {
           anyxml multi-routing-engine-results;
         }
       }
     }
   }
   rpc get-pfe-tcam-errors-app-bd-dtag-validate {
     description "Bridge Domain dual-tagged validate";
     output {
       choice output_c {
         case output-tag {
           leaf output {
             type string;
           }
         }
         case multichassis-tag {
           anyxml multi-routing-engine-results;
         }
       }
     }
   }
   rpc get-pfe-tcam-errors-app-bd-tpid-swap {
     description "Bridge domain vlan-map with swap tpid operation";
     output {
       choice output_c {
         case output-tag {
           leaf output {
             type string;
           }
         }
         case multichassis-tag {
           anyxml multi-routing-engine-results;
         }
       }
     }
   }
   rpc get-pfe-tcam-errors-app-fw-family-out {
     description "Family level egress firewall";
     output {
       choice output_c {
         case output-tag {
           leaf output {
             type string;
           }
         }
         case multichassis-tag {
           anyxml multi-routing-engine-results;
         }
       }
     }
   }
   rpc get-pfe-tcam-errors-app-fw-inet6-family-out {
     description "Inet6 Family level egress firewall";
     output {
       choice output_c {
         case output-tag {
           leaf output {
             type string;
           }
         }
         case multichassis-tag {
           anyxml multi-routing-engine-results;
         }
       }
     }
   }
   rpc get-pfe-tcam-errors-app-fw-ifl-out {
     description "Ifl level egress firewall";
     output {
       choice output_c {
         case output-tag {
           leaf output {
             type string;
           }
         }
         case multichassis-tag {
           anyxml multi-routing-engine-results;
         }
       }
     }
   }
   rpc get-pfe-tcam-errors-app-ifl-statistics-out {
     description "Ifl level statistics (egress)";
     output {
       choice output_c {
         case output-tag {
           leaf output {
             type string;
           }
         }
         case multichassis-tag {
           anyxml multi-routing-engine-results;
         }
       }
     }
   }
   rpc get-pfe-tcam-errors-app-irb-cos-rw {
     description "IRB CoS rewrite";
     output {
       choice output_c {
         case output-tag {
           leaf output {
             type string;
           }
         }
         case multichassis-tag {
           anyxml multi-routing-engine-results;
         }
       }
     }
   }
   rpc get-pfe-tcam-errors-app-lfm-802.3ah-out {
     description "Lfm-802.3ah (egress)";
     output {
       choice output_c {
         case output-tag {
           leaf output {
             type string;
           }
         }
         case multichassis-tag {
           anyxml multi-routing-engine-results;
         }
       }
     }
   }
   rpc get-pfe-tcam-errors-app-ptpoe-cos-rw {
     description "CoS RW requires for PTPoE";
     output {
       choice output_c {
         case output-tag {
           leaf output {
             type string;
           }
         }
         case multichassis-tag {
           anyxml multi-routing-engine-results;
         }
       }
     }
   }
   rpc get-pfe-tcam-errors-app-rfc2544-layer2-out {
     description "Rfc2544 for layer2 service (egress)";
     output {
       choice output_c {
         case output-tag {
           leaf output {
             type string;
           }
         }
         case multichassis-tag {
           anyxml multi-routing-engine-results;
         }
       }
     }
   }
   rpc get-pfe-tcam-errors-app-cfm-bd-filter {
     description "Cfm implicit bridge-domain filters";
     output {
       choice output_c {
         case output-tag {
           leaf output {
             type string;
           }
         }
         case multichassis-tag {
           anyxml multi-routing-engine-results;
         }
       }
     }
   }
   rpc get-pfe-tcam-errors-app-cfm-filter {
     description "Cfm implicit filters";
     output {
       choice output_c {
         case output-tag {
           leaf output {
             type string;
           }
         }
         case multichassis-tag {
           anyxml multi-routing-engine-results;
         }
       }
     }
   }
   rpc get-pfe-tcam-errors-app-cfm-vpls-filter {
     description "Cfm implicit vpls filters";
     output {
       choice output_c {
         case output-tag {
           leaf output {
             type string;
           }
         }
         case multichassis-tag {
           anyxml multi-routing-engine-results;
         }
       }
     }
   }
   rpc get-pfe-tcam-errors-app-cfm-vpls-ifl-filter {
     description "Cfm implicit vpls ifl filters";
     output {
       choice output_c {
         case output-tag {
           leaf output {
             type string;
           }
         }
         case multichassis-tag {
           anyxml multi-routing-engine-results;
         }
       }
     }
   }
   rpc get-pfe-tcam-errors-app-fw-ccc-in {
     description "Ccc family ingress firewall";
     output {
       choice output_c {
         case output-tag {
           leaf output {
             type string;
           }
         }
         case multichassis-tag {
           anyxml multi-routing-engine-results;
         }
       }
     }
   }
   rpc get-pfe-tcam-errors-app-fw-ifl-in {
     description "Ifl level ingress firewall";
     output {
       choice output_c {
         case output-tag {
           leaf output {
             type string;
           }
         }
         case multichassis-tag {
           anyxml multi-routing-engine-results;
         }
       }
     }
   }
   rpc get-pfe-tcam-errors-app-fw-inet-ftf {
     description "Inet family ingress firewall on a forwarding-table";
     output {
       choice output_c {
         case output-tag {
           leaf output {
             type string;
           }
         }
         case multichassis-tag {
           anyxml multi-routing-engine-results;
         }
       }
     }
   }
   rpc get-pfe-tcam-errors-app-fw-inet-in {
     description "Inet family ingress firewall";
     output {
       choice output_c {
         case output-tag {
           leaf output {
             type string;
           }
         }
         case multichassis-tag {
           anyxml multi-routing-engine-results;
         }
       }
     }
   }
   rpc get-pfe-tcam-errors-app-fw-inet-rpf {
     description "Inet family ingress firewall on rpf fail check";
     output {
       choice output_c {
         case output-tag {
           leaf output {
             type string;
           }
         }
         case multichassis-tag {
           anyxml multi-routing-engine-results;
         }
       }
     }
   }
   rpc get-pfe-tcam-errors-app-fw-inet6-ftf {
     description "Inet6 family ingress firewall on a forwarding-table";
     output {
       choice output_c {
         case output-tag {
           leaf output {
             type string;
           }
         }
         case multichassis-tag {
           anyxml multi-routing-engine-results;
         }
       }
     }
   }
   rpc get-pfe-tcam-errors-app-fw-inet6-in {
     description "Inet6 family ingress firewall";
     output {
       choice output_c {
         case output-tag {
           leaf output {
             type string;
           }
         }
         case multichassis-tag {
           anyxml multi-routing-engine-results;
         }
       }
     }
   }
   rpc get-pfe-tcam-errors-app-fw-inet6-rpf {
     description "Inet6 family ingress firewall on a rpf fail check";
     output {
       choice output_c {
         case output-tag {
           leaf output {
             type string;
           }
         }
         case multichassis-tag {
           anyxml multi-routing-engine-results;
         }
       }
     }
   }
   rpc get-pfe-tcam-errors-app-fw-inet-pm {
     description "Inet family firewall with port-mirror action";
     output {
       choice output_c {
         case output-tag {
           leaf output {
             type string;
           }
         }
         case multichassis-tag {
           anyxml multi-routing-engine-results;
         }
       }
     }
   }
   rpc get-pfe-tcam-errors-app-fw-l2-in {
     description "Bridge family ingress firewall on layer2 interface";
     output {
       choice output_c {
         case output-tag {
           leaf output {
             type string;
           }
         }
         case multichassis-tag {
           anyxml multi-routing-engine-results;
         }
       }
     }
   }
   rpc get-pfe-tcam-errors-app-fw-mpls-in {
     description "Mpls family ingress firewall";
     output {
       choice output_c {
         case output-tag {
           leaf output {
             type string;
           }
         }
         case multichassis-tag {
           anyxml multi-routing-engine-results;
         }
       }
     }
   }
   rpc get-pfe-tcam-errors-app-fw-vpls-in {
     description "VPLS family ingress firewall on vpls interface";
     output {
       choice output_c {
         case output-tag {
           leaf output {
             type string;
           }
         }
         case multichassis-tag {
           anyxml multi-routing-engine-results;
         }
       }
     }
   }
   rpc get-pfe-tcam-errors-app-gr-ifl-statistics-egr {
     description "GR Ifl level statistics (egress)";
     output {
       choice output_c {
         case output-tag {
           leaf output {
             type string;
           }
         }
         case multichassis-tag {
           anyxml multi-routing-engine-results;
         }
       }
     }
   }
   rpc get-pfe-tcam-errors-app-gr-ifl-statistics-ing {
     description "GR Ifl level statistics (ingress)";
     output {
       choice output_c {
         case output-tag {
           leaf output {
             type string;
           }
         }
         case multichassis-tag {
           anyxml multi-routing-engine-results;
         }
       }
     }
   }
   rpc get-pfe-tcam-errors-app-gr-ifl-statistics-preing {
     description "GR Ifl level statistics (pre-ingress)";
     output {
       choice output_c {
         case output-tag {
           leaf output {
             type string;
           }
         }
         case multichassis-tag {
           anyxml multi-routing-engine-results;
         }
       }
     }
   }
   rpc get-pfe-tcam-errors-app-ifl-statistics-in {
     description "Ifl level statistics (ingress)";
     output {
       choice output_c {
         case output-tag {
           leaf output {
             type string;
           }
         }
         case multichassis-tag {
           anyxml multi-routing-engine-results;
         }
       }
     }
   }
   rpc get-pfe-tcam-errors-app-irb-fixed-cos {
     description "IRB fixed classifier filter entries";
     output {
       choice output_c {
         case output-tag {
           leaf output {
             type string;
           }
         }
         case multichassis-tag {
           anyxml multi-routing-engine-results;
         }
       }
     }
   }
   rpc get-pfe-tcam-errors-app-mrouter-port-in {
     description "Multicast router port for snooping";
     output {
       choice output_c {
         case output-tag {
           leaf output {
             type string;
           }
         }
         case multichassis-tag {
           anyxml multi-routing-engine-results;
         }
       }
     }
   }
   rpc get-pfe-tcam-errors-app-ipsec-reverse-fil {
     description "Reverse filters for Ipsec service";
     output {
       choice output_c {
         case output-tag {
           leaf output {
             type string;
           }
         }
         case multichassis-tag {
           anyxml multi-routing-engine-results;
         }
       }
     }
   }
   rpc get-pfe-tcam-errors-app-lfm-802.3ah-in {
     description "Lfm-802.3ah (ingress)";
     output {
       choice output_c {
         case output-tag {
           leaf output {
             type string;
           }
         }
         case multichassis-tag {
           anyxml multi-routing-engine-results;
         }
       }
     }
   }
   rpc get-pfe-tcam-errors-app-lo0-inet-fil {
     description "Lo0 Inet Filter";
     output {
       choice output_c {
         case output-tag {
           leaf output {
             type string;
           }
         }
         case multichassis-tag {
           anyxml multi-routing-engine-results;
         }
       }
     }
   }
   rpc get-pfe-tcam-errors-app-lo0-inet6-fil {
     description "Lo0 Inet6 Filter";
     output {
       choice output_c {
         case output-tag {
           leaf output {
             type string;
           }
         }
         case multichassis-tag {
           anyxml multi-routing-engine-results;
         }
       }
     }
   }
   rpc get-pfe-tcam-errors-app-irb-inet6-fil {
     description "IRB Inet6 Filter";
     output {
       choice output_c {
         case output-tag {
           leaf output {
             type string;
           }
         }
         case multichassis-tag {
           anyxml multi-routing-engine-results;
         }
       }
     }
   }
   rpc get-pfe-tcam-errors-app-mac-drop-cnt {
     description "Statistics for drops by mac-validate/src-mac filters";
     output {
       choice output_c {
         case output-tag {
           leaf output {
             type string;
           }
         }
         case multichassis-tag {
           anyxml multi-routing-engine-results;
         }
       }
     }
   }
   rpc get-pfe-tcam-errors-app-napt-reverse-fil {
     description "Reverse filters for Napt service";
     output {
       choice output_c {
         case output-tag {
           leaf output {
             type string;
           }
         }
         case multichassis-tag {
           anyxml multi-routing-engine-results;
         }
       }
     }
   }
   rpc get-pfe-tcam-errors-app-no-local-switching {
     description "Bridge no-local-switching";
     output {
       choice output_c {
         case output-tag {
           leaf output {
             type string;
           }
         }
         case multichassis-tag {
           anyxml multi-routing-engine-results;
         }
       }
     }
   }
   rpc get-pfe-tcam-errors-app-cos-fc {
     description "Ifl level fixed classifier";
     output {
       choice output_c {
         case output-tag {
           leaf output {
             type string;
           }
         }
         case multichassis-tag {
           anyxml multi-routing-engine-results;
         }
       }
     }
   }
   rpc get-pfe-tcam-errors-app-fw-fbf {
     description "Firewall filter based forwarding";
     output {
       choice output_c {
         case output-tag {
           leaf output {
             type string;
           }
         }
         case multichassis-tag {
           anyxml multi-routing-engine-results;
         }
       }
     }
   }
   rpc get-pfe-tcam-errors-app-fw-fbf-inet6 {
     description "Firewall filter based forwarding for Inet6";
     output {
       choice output_c {
         case output-tag {
           leaf output {
             type string;
           }
         }
         case multichassis-tag {
           anyxml multi-routing-engine-results;
         }
       }
     }
   }
   rpc get-pfe-tcam-errors-app-fw-semantics {
     description "Firewall sharing semantics for cli configured firewall";
     output {
       choice output_c {
         case output-tag {
           leaf output {
             type string;
           }
         }
         case multichassis-tag {
           anyxml multi-routing-engine-results;
         }
       }
     }
   }
   rpc get-pfe-tcam-errors-app-ifd-src-mac-fil {
     description "Ifd level source mac filter";
     output {
       choice output_c {
         case output-tag {
           leaf output {
             type string;
           }
         }
         case multichassis-tag {
           anyxml multi-routing-engine-results;
         }
       }
     }
   }
   rpc get-pfe-tcam-errors-app-ing-out-iff {
     description "Ingress app on behalf of egress family filter for log/syslog";
     output {
       choice output_c {
         case output-tag {
           leaf output {
             type string;
           }
         }
         case multichassis-tag {
           anyxml multi-routing-engine-results;
         }
       }
     }
   }
   rpc get-pfe-tcam-errors-app-ip-mac-val {
     description "Ip mac validate";
     output {
       choice output_c {
         case output-tag {
           leaf output {
             type string;
           }
         }
         case multichassis-tag {
           anyxml multi-routing-engine-results;
         }
       }
     }
   }
   rpc get-pfe-tcam-errors-app-ip-mac-val-bcast {
     description "Ip mac validate for broadcast";
     output {
       choice output_c {
         case output-tag {
           leaf output {
             type string;
           }
         }
         case multichassis-tag {
           anyxml multi-routing-engine-results;
         }
       }
     }
   }
   rpc get-pfe-tcam-errors-app-rfc2544-layer2-in {
     description "Rfc2544 for layer2 service (ingress)";
     output {
       choice output_c {
         case output-tag {
           leaf output {
             type string;
           }
         }
         case multichassis-tag {
           anyxml multi-routing-engine-results;
         }
       }
     }
   }
   rpc get-pfe-tcam-errors-app-vpls-mesh-group-ucast {
     description "VPLS mesh group unicast filters";
     output {
       choice output_c {
         case output-tag {
           leaf output {
             type string;
           }
         }
         case multichassis-tag {
           anyxml multi-routing-engine-results;
         }
       }
     }
   }
   rpc get-pfe-tcam-errors-app-vpls-mesh-group-mcast {
     description "VPLS mesh group multicast filters";
     output {
       choice output_c {
         case output-tag {
           leaf output {
             type string;
           }
         }
         case multichassis-tag {
           anyxml multi-routing-engine-results;
         }
       }
     }
   }
   rpc get-pfe-tcam-app-list {
     description "Show tcam apps";
     output {
       choice output_c {
         case output-tag {
           leaf output {
             type string;
           }
         }
         case multichassis-tag {
           anyxml multi-routing-engine-results;
         }
       }
     }
   }
   rpc get-pfe-tcam-app-list-bd-dtag-validate {
     description "Bridge Domain dual-tagged validate";
     output {
       choice output_c {
         case output-tag {
           leaf output {
             type string;
           }
         }
         case multichassis-tag {
           anyxml multi-routing-engine-results;
         }
       }
     }
   }
   rpc get-pfe-tcam-app-list-bd-tpid-swap {
     description "Bridge domain vlan-map with swap tpid operation";
     output {
       choice output_c {
         case output-tag {
           leaf output {
             type string;
           }
         }
         case multichassis-tag {
           anyxml multi-routing-engine-results;
         }
       }
     }
   }
   rpc get-pfe-tcam-app-list-fw-family-out {
     description "Family level egress firewall";
     output {
       choice output_c {
         case output-tag {
           leaf output {
             type string;
           }
         }
         case multichassis-tag {
           anyxml multi-routing-engine-results;
         }
       }
     }
   }
   rpc get-pfe-tcam-app-list-fw-inet6-family-out {
     description "Inet6 Family level egress firewall";
     output {
       choice output_c {
         case output-tag {
           leaf output {
             type string;
           }
         }
         case multichassis-tag {
           anyxml multi-routing-engine-results;
         }
       }
     }
   }
   rpc get-pfe-tcam-app-list-fw-ifl-out {
     description "Ifl level egress firewall";
     output {
       choice output_c {
         case output-tag {
           leaf output {
             type string;
           }
         }
         case multichassis-tag {
           anyxml multi-routing-engine-results;
         }
       }
     }
   }
   rpc get-pfe-tcam-app-list-ifl-statistics-out {
     description "Ifl level statistics (egress)";
     output {
       choice output_c {
         case output-tag {
           leaf output {
             type string;
           }
         }
         case multichassis-tag {
           anyxml multi-routing-engine-results;
         }
       }
     }
   }
   rpc get-pfe-tcam-app-list-irb-cos-rw {
     description "IRB CoS rewrite";
     output {
       choice output_c {
         case output-tag {
           leaf output {
             type string;
           }
         }
         case multichassis-tag {
           anyxml multi-routing-engine-results;
         }
       }
     }
   }
   rpc get-pfe-tcam-app-list-lfm-802.3ah-out {
     description "Lfm-802.3ah (egress)";
     output {
       choice output_c {
         case output-tag {
           leaf output {
             type string;
           }
         }
         case multichassis-tag {
           anyxml multi-routing-engine-results;
         }
       }
     }
   }
   rpc get-pfe-tcam-app-list-ptpoe-cos-rw {
     description "CoS RW requires for PTPoE";
     output {
       choice output_c {
         case output-tag {
           leaf output {
             type string;
           }
         }
         case multichassis-tag {
           anyxml multi-routing-engine-results;
         }
       }
     }
   }
   rpc get-pfe-tcam-app-list-rfc2544-layer2-out {
     description "Rfc2544 for layer2 service (egress)";
     output {
       choice output_c {
         case output-tag {
           leaf output {
             type string;
           }
         }
         case multichassis-tag {
           anyxml multi-routing-engine-results;
         }
       }
     }
   }
   rpc get-pfe-tcam-app-list-cfm-bd-filter {
     description "Cfm implicit bridge-domain filters";
     output {
       choice output_c {
         case output-tag {
           leaf output {
             type string;
           }
         }
         case multichassis-tag {
           anyxml multi-routing-engine-results;
         }
       }
     }
   }
   rpc get-pfe-tcam-app-list-cfm-filter {
     description "Cfm implicit filters";
     output {
       choice output_c {
         case output-tag {
           leaf output {
             type string;
           }
         }
         case multichassis-tag {
           anyxml multi-routing-engine-results;
         }
       }
     }
   }
   rpc get-pfe-tcam-app-list-cfm-vpls-filter {
     description "Cfm implicit vpls filters";
     output {
       choice output_c {
         case output-tag {
           leaf output {
             type string;
           }
         }
         case multichassis-tag {
           anyxml multi-routing-engine-results;
         }
       }
     }
   }
   rpc get-pfe-tcam-app-list-cfm-vpls-ifl-filter {
     description "Cfm implicit vpls ifl filters";
     output {
       choice output_c {
         case output-tag {
           leaf output {
             type string;
           }
         }
         case multichassis-tag {
           anyxml multi-routing-engine-results;
         }
       }
     }
   }
   rpc get-pfe-tcam-app-list-fw-ccc-in {
     description "Ccc family ingress firewall";
     output {
       choice output_c {
         case output-tag {
           leaf output {
             type string;
           }
         }
         case multichassis-tag {
           anyxml multi-routing-engine-results;
         }
       }
     }
   }
   rpc get-pfe-tcam-app-list-fw-ifl-in {
     description "Ifl level ingress firewall";
     output {
       choice output_c {
         case output-tag {
           leaf output {
             type string;
           }
         }
         case multichassis-tag {
           anyxml multi-routing-engine-results;
         }
       }
     }
   }
   rpc get-pfe-tcam-app-list-fw-inet-ftf {
     description "Inet family ingress firewall on a forwarding-table";
     output {
       choice output_c {
         case output-tag {
           leaf output {
             type string;
           }
         }
         case multichassis-tag {
           anyxml multi-routing-engine-results;
         }
       }
     }
   }
   rpc get-pfe-tcam-app-list-fw-inet-in {
     description "Inet family ingress firewall";
     output {
       choice output_c {
         case output-tag {
           leaf output {
             type string;
           }
         }
         case multichassis-tag {
           anyxml multi-routing-engine-results;
         }
       }
     }
   }
   rpc get-pfe-tcam-app-list-fw-inet-rpf {
     description "Inet family ingress firewall on rpf fail check";
     output {
       choice output_c {
         case output-tag {
           leaf output {
             type string;
           }
         }
         case multichassis-tag {
           anyxml multi-routing-engine-results;
         }
       }
     }
   }
   rpc get-pfe-tcam-app-list-fw-inet6-ftf {
     description "Inet6 family ingress firewall on a forwarding-table";
     output {
       choice output_c {
         case output-tag {
           leaf output {
             type string;
           }
         }
         case multichassis-tag {
           anyxml multi-routing-engine-results;
         }
       }
     }
   }
   rpc get-pfe-tcam-app-list-fw-inet6-in {
     description "Inet6 family ingress firewall";
     output {
       choice output_c {
         case output-tag {
           leaf output {
             type string;
           }
         }
         case multichassis-tag {
           anyxml multi-routing-engine-results;
         }
       }
     }
   }
   rpc get-pfe-tcam-app-list-fw-inet6-rpf {
     description "Inet6 family ingress firewall on a rpf fail check";
     output {
       choice output_c {
         case output-tag {
           leaf output {
             type string;
           }
         }
         case multichassis-tag {
           anyxml multi-routing-engine-results;
         }
       }
     }
   }
   rpc get-pfe-tcam-app-list-fw-inet-pm {
     description "Inet family firewall with port-mirror action";
     output {
       choice output_c {
         case output-tag {
           leaf output {
             type string;
           }
         }
         case multichassis-tag {
           anyxml multi-routing-engine-results;
         }
       }
     }
   }
   rpc get-pfe-tcam-app-list-fw-l2-in {
     description "Bridge family ingress firewall on layer2 interface";
     output {
       choice output_c {
         case output-tag {
           leaf output {
             type string;
           }
         }
         case multichassis-tag {
           anyxml multi-routing-engine-results;
         }
       }
     }
   }
   rpc get-pfe-tcam-app-list-fw-mpls-in {
     description "Mpls family ingress firewall";
     output {
       choice output_c {
         case output-tag {
           leaf output {
             type string;
           }
         }
         case multichassis-tag {
           anyxml multi-routing-engine-results;
         }
       }
     }
   }
   rpc get-pfe-tcam-app-list-fw-vpls-in {
     description "VPLS family ingress firewall on vpls interface";
     output {
       choice output_c {
         case output-tag {
           leaf output {
             type string;
           }
         }
         case multichassis-tag {
           anyxml multi-routing-engine-results;
         }
       }
     }
   }
   rpc get-pfe-tcam-app-list-gr-ifl-statistics-egr {
     description "GR Ifl level statistics (egress)";
     output {
       choice output_c {
         case output-tag {
           leaf output {
             type string;
           }
         }
         case multichassis-tag {
           anyxml multi-routing-engine-results;
         }
       }
     }
   }
   rpc get-pfe-tcam-app-list-gr-ifl-statistics-ing {
     description "GR Ifl level statistics (ingress)";
     output {
       choice output_c {
         case output-tag {
           leaf output {
             type string;
           }
         }
         case multichassis-tag {
           anyxml multi-routing-engine-results;
         }
       }
     }
   }
   rpc get-pfe-tcam-app-list-gr-ifl-statistics-preing {
     description "GR Ifl level statistics (pre-ingress)";
     output {
       choice output_c {
         case output-tag {
           leaf output {
             type string;
           }
         }
         case multichassis-tag {
           anyxml multi-routing-engine-results;
         }
       }
     }
   }
   rpc get-pfe-tcam-app-list-ifl-statistics-in {
     description "Ifl level statistics (ingress)";
     output {
       choice output_c {
         case output-tag {
           leaf output {
             type string;
           }
         }
         case multichassis-tag {
           anyxml multi-routing-engine-results;
         }
       }
     }
   }
   rpc get-pfe-tcam-app-list-irb-fixed-cos {
     description "IRB fixed classifier filter entries";
     output {
       choice output_c {
         case output-tag {
           leaf output {
             type string;
           }
         }
         case multichassis-tag {
           anyxml multi-routing-engine-results;
         }
       }
     }
   }
   rpc get-pfe-tcam-app-list-mrouter-port-in {
     description "Multicast router port for snooping";
     output {
       choice output_c {
         case output-tag {
           leaf output {
             type string;
           }
         }
         case multichassis-tag {
           anyxml multi-routing-engine-results;
         }
       }
     }
   }
   rpc get-pfe-tcam-app-list-ipsec-reverse-fil {
     description "Reverse filters for Ipsec service";
     output {
       choice output_c {
         case output-tag {
           leaf output {
             type string;
           }
         }
         case multichassis-tag {
           anyxml multi-routing-engine-results;
         }
       }
     }
   }
   rpc get-pfe-tcam-app-list-lfm-802.3ah-in {
     description "Lfm-802.3ah (ingress)";
     output {
       choice output_c {
         case output-tag {
           leaf output {
             type string;
           }
         }
         case multichassis-tag {
           anyxml multi-routing-engine-results;
         }
       }
     }
   }
   rpc get-pfe-tcam-app-list-lo0-inet-fil {
     description "Lo0 Inet Filter";
     output {
       choice output_c {
         case output-tag {
           leaf output {
             type string;
           }
         }
         case multichassis-tag {
           anyxml multi-routing-engine-results;
         }
       }
     }
   }
   rpc get-pfe-tcam-app-list-lo0-inet6-fil {
     description "Lo0 Inet6 Filter";
     output {
       choice output_c {
         case output-tag {
           leaf output {
             type string;
           }
         }
         case multichassis-tag {
           anyxml multi-routing-engine-results;
         }
       }
     }
   }
   rpc get-pfe-tcam-app-list-irb-inet6-fil {
     description "IRB Inet6 Filter";
     output {
       choice output_c {
         case output-tag {
           leaf output {
             type string;
           }
         }
         case multichassis-tag {
           anyxml multi-routing-engine-results;
         }
       }
     }
   }
   rpc get-pfe-tcam-app-list-mac-drop-cnt {
     description "Statistics for drops by mac-validate/src-mac filters";
     output {
       choice output_c {
         case output-tag {
           leaf output {
             type string;
           }
         }
         case multichassis-tag {
           anyxml multi-routing-engine-results;
         }
       }
     }
   }
   rpc get-pfe-tcam-app-list-napt-reverse-fil {
     description "Reverse filters for Napt service";
     output {
       choice output_c {
         case output-tag {
           leaf output {
             type string;
           }
         }
         case multichassis-tag {
           anyxml multi-routing-engine-results;
         }
       }
     }
   }
   rpc get-pfe-tcam-app-list-no-local-switching {
     description "Bridge no-local-switching";
     output {
       choice output_c {
         case output-tag {
           leaf output {
             type string;
           }
         }
         case multichassis-tag {
           anyxml multi-routing-engine-results;
         }
       }
     }
   }
   rpc get-pfe-tcam-app-list-cos-fc {
     description "Ifl level fixed classifier";
     output {
       choice output_c {
         case output-tag {
           leaf output {
             type string;
           }
         }
         case multichassis-tag {
           anyxml multi-routing-engine-results;
         }
       }
     }
   }
   rpc get-pfe-tcam-app-list-fw-fbf {
     description "Firewall filter based forwarding";
     output {
       choice output_c {
         case output-tag {
           leaf output {
             type string;
           }
         }
         case multichassis-tag {
           anyxml multi-routing-engine-results;
         }
       }
     }
   }
   rpc get-pfe-tcam-app-list-fw-fbf-inet6 {
     description "Firewall filter based forwarding for Inet6";
     output {
       choice output_c {
         case output-tag {
           leaf output {
             type string;
           }
         }
         case multichassis-tag {
           anyxml multi-routing-engine-results;
         }
       }
     }
   }
   rpc get-pfe-tcam-app-list-fw-semantics {
     description "Firewall sharing semantics for cli configured firewall";
     output {
       choice output_c {
         case output-tag {
           leaf output {
             type string;
           }
         }
         case multichassis-tag {
           anyxml multi-routing-engine-results;
         }
       }
     }
   }
   rpc get-pfe-tcam-app-list-ifd-src-mac-fil {
     description "Ifd level source mac filter";
     output {
       choice output_c {
         case output-tag {
           leaf output {
             type string;
           }
         }
         case multichassis-tag {
           anyxml multi-routing-engine-results;
         }
       }
     }
   }
   rpc get-pfe-tcam-app-list-ing-out-iff {
     description "Ingress app on behalf of egress family filter for log/syslog";
     output {
       choice output_c {
         case output-tag {
           leaf output {
             type string;
           }
         }
         case multichassis-tag {
           anyxml multi-routing-engine-results;
         }
       }
     }
   }
   rpc get-pfe-tcam-app-list-ip-mac-val {
     description "Ip mac validate";
     output {
       choice output_c {
         case output-tag {
           leaf output {
             type string;
           }
         }
         case multichassis-tag {
           anyxml multi-routing-engine-results;
         }
       }
     }
   }
   rpc get-pfe-tcam-app-list-ip-mac-val-bcast {
     description "Ip mac validate for broadcast";
     output {
       choice output_c {
         case output-tag {
           leaf output {
             type string;
           }
         }
         case multichassis-tag {
           anyxml multi-routing-engine-results;
         }
       }
     }
   }
   rpc get-pfe-tcam-app-list-rfc2544-layer2-in {
     description "Rfc2544 for layer2 service (ingress)";
     output {
       choice output_c {
         case output-tag {
           leaf output {
             type string;
           }
         }
         case multichassis-tag {
           anyxml multi-routing-engine-results;
         }
       }
     }
   }
   rpc get-pfe-tcam-app-list-vpls-mesh-group-ucast {
     description "VPLS mesh group unicast filters";
     output {
       choice output_c {
         case output-tag {
           leaf output {
             type string;
           }
         }
         case multichassis-tag {
           anyxml multi-routing-engine-results;
         }
       }
     }
   }
   rpc get-pfe-tcam-app-list-vpls-mesh-group-mcast {
     description "VPLS mesh group multicast filters";
     output {
       choice output_c {
         case output-tag {
           leaf output {
             type string;
           }
         }
         case multichassis-tag {
           anyxml multi-routing-engine-results;
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice vc-selector {
       case case_1 {
         leaf local {
           description "Local virtual chassis member";
           type empty;
         }
       }
     }
     choice tenant-selector {
       case case_1 {
         leaf tenant {
           description "Name of tenant, or 'all'";
           type string;
         }
       }
     }
     leaf all-members {
       description "All virtual chassis members";
       type empty;
     }
     leaf member {
       description "Specific virtual chassis member";
       type union {
         type string {
           pattern "<.*>|$.*";
         }
         type uint32;
       }
     }
   }
 }
