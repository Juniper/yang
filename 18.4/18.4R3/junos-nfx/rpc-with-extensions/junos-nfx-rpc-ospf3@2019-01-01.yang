/*
 * Copyright (c) 2019 Juniper Networks, Inc.
 * All rights reserved.
 */
 module junos-nfx-rpc-ospf3 {
   namespace "http://yang.juniper.net/junos-nfx/rpc/ospf3";

   prefix ospf3;

   import junos-common-ddl-extensions {
     prefix junos;
   }

   import junos-common-odl-extensions {
     prefix junos-odl;
   }

   import junos-common-types {
     prefix jt;
   }

   organization "Juniper Networks, Inc.";

   contact "yang-support@juniper.net";

   description "Junos RPC YANG module for ospf3 command(s)";

   revision 2019-01-01 {
     description "Junos: 18.4R3.3";
   }

   rpc get-ospf3-overview-information {
     description "Show overview of OSPFv3 information";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf tenant {
         description "Name of tenant, or 'all'";
         type string {
           junos:posix-pattern "^[a-zA-Z0-9-]{1,63}$";
           junos:pattern-message "Tenant name is a string consisting of up to 63 letters, numbers and dashes";
         }
       }
       leaf verbosity_level {
         default "brief";
         type enumeration {
           enum "brief" {
             description "Display brief output (default)";
           }
           enum "extensive" {
             description "Display extensive output";
           }
         }
       }
       leaf instance {
         description "Name of OSPFv3 instance";
         type string;
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
     }
     output {
       choice output_c {
         case output-tag {
           leaf output {
             type string;
           }
         }
         case actual-tag {
           anyxml ospf3-overview-information;
         }
         case multichassis-tag {
           anyxml multi-routing-engine-results;
         }
       }
     }
   }
   rpc get-ospf3-database-information {
     description "Show OSPFv3 link-state database";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf tenant {
         description "Name of tenant, or 'all'";
         type string {
           junos:posix-pattern "^[a-zA-Z0-9-]{1,63}$";
           junos:pattern-message "Tenant name is a string consisting of up to 63 letters, numbers and dashes";
         }
       }
       leaf level {
         default "brief";
         type enumeration {
           enum "brief" {
             description "Display brief output (default)";
           }
           enum "detail" {
             description "Display detailed output";
           }
           enum "extensive" {
             description "Display extensive output";
           }
           enum "summary" {
             description "Display summary output";
           }
         }
       }
       leaf lsa-type {
         type enumeration {
           enum "router" {
             description "Router LSAs";
           }
           enum "network" {
             description "Network LSAs";
           }
           enum "inter-area-prefix" {
             description "Inter-area-prefix LSAs";
           }
           enum "inter-area-router" {
             description "Inter-area-router LSAs";
           }
           enum "external" {
             description "External LSAs";
           }
           enum "nssa" {
             description "NSSA LSAs";
           }
           enum "link" {
             description "Link LSAs";
           }
           enum "link-local" {
             description "Link-local LSAs";
           }
           enum "intra-area-prefix" {
             description "Intra-area-prefix LSAs";
           }
         }
       }
       leaf area {
         description "Area ID of OSPFv3 area";
         default "all";
         type string;
       }
       leaf lsa-id {
         description "ID of link-state advertisement";
         default "all";
         type string;
       }
       leaf advertising-router {
         description "Router ID of advertising router";
         type string;
       }
       leaf instance {
         description "Name of OSPFv3 instance";
         type string;
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
     }
     output {
       choice output_c {
         case output-tag {
           leaf output {
             type string;
           }
         }
         case actual-tag {
           anyxml ospf3-database-information;
         }
         case multichassis-tag {
           anyxml multi-routing-engine-results;
         }
       }
     }
   }
   rpc get-ospf3-interface-information {
     description "Show OSPFv3 interface status";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf tenant {
         description "Name of tenant, or 'all'";
         type string {
           junos:posix-pattern "^[a-zA-Z0-9-]{1,63}$";
           junos:pattern-message "Tenant name is a string consisting of up to 63 letters, numbers and dashes";
         }
       }
       leaf verbosity_level {
         default "brief";
         type enumeration {
           enum "brief" {
             description "Display brief output (default)";
           }
           enum "detail" {
             description "Display detailed output";
           }
           enum "extensive" {
             description "Display extensive output";
           }
         }
       }
       leaf interface-name {
         description "Name of logical interface";
         type string;
       }
       leaf area {
         description "OSPF area ID";
         type jt:areaid;
       }
       leaf instance {
         description "Name of OSPFv3 instance";
         type string;
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
     }
     output {
       choice output_c {
         case output-tag {
           leaf output {
             type string;
           }
         }
         case actual-tag {
           anyxml ospf3-interface-information;
         }
         case multichassis-tag {
           anyxml multi-routing-engine-results;
         }
       }
     }
   }
   rpc get-ospf3-neighbor-information {
     description "Show OSPFv3 neighbor status";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf tenant {
         description "Name of tenant, or 'all'";
         type string {
           junos:posix-pattern "^[a-zA-Z0-9-]{1,63}$";
           junos:pattern-message "Tenant name is a string consisting of up to 63 letters, numbers and dashes";
         }
       }
       leaf verbosity_level {
         default "brief";
         type enumeration {
           enum "brief" {
             description "Display brief output (default)";
           }
           enum "detail" {
             description "Display detailed output";
           }
           enum "extensive" {
             description "Display extensive output";
           }
         }
       }
       leaf interface {
         description "Name of logical interface";
         type string;
       }
       leaf area {
         description "OSPF area ID";
         type jt:areaid;
       }
       leaf neighbor {
         description "IP address or ID of neighbor";
         type string;
       }
       leaf instance {
         description "Name of OSPFv3 instance";
         type string;
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
     }
     output {
       choice output_c {
         case output-tag {
           leaf output {
             type string;
           }
         }
         case actual-tag {
           anyxml ospf3-neighbor-information;
         }
         case multichassis-tag {
           anyxml multi-routing-engine-results;
         }
       }
     }
   }
   rpc get-ospf3-route-information {
     description "Show the OSPFv3 routing table";
     input {
       leaf tenant {
         description "Name of tenant, or 'all'";
         type string {
           junos:posix-pattern "^[a-zA-Z0-9-]{1,63}$";
           junos:pattern-message "Tenant name is a string consisting of up to 63 letters, numbers and dashes";
         }
       }
       leaf logical-system {
         description "Name of logical system, or 'all'";
         type string {
           junos:posix-pattern "^[a-zA-Z0-9_-]{1,63}$";
           junos:pattern-message "Logical-system name is a string consisting of up to 63 letters, numbers, dashes and underscores";
         }
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
       leaf path-type {
         description "OSPF path type";
         type enumeration {
           enum "intra" {
             description "Display intra-area routes";
           }
           enum "inter" {
             description "Display inter-area routes";
           }
           enum "extern" {
             description "Display external routes";
           }
         }
       }
       leaf route-type {
         description "OSPF route type";
         type enumeration {
           enum "router" {
             description "Display routes to all routers";
           }
           enum "abr" {
             description "Display routes to area border routers";
           }
           enum "asbr" {
             description "Display routes to AS border routers";
           }
           enum "transit" {
             description "Display routes to pseudonodes";
           }
           enum "network" {
             description "Display routes to networks";
           }
         }
       }
       leaf no-backup-coverage {
         description "Display routes with no backup coverage";
         type empty;
       }
       leaf destination {
         description "Address and optional prefix length of destination";
         type jt:ipprefix;
       }
       leaf verbosity_level {
         default "brief";
         type enumeration {
           enum "brief" {
             description "Display brief output (default)";
           }
           enum "detail" {
             description "Display detailed output";
           }
           enum "extensive" {
             description "Display extensive output";
           }
         }
       }
       leaf instance {
         description "Name of OSPFv3 instance";
         type string;
       }
     }
     output {
       choice output_c {
         case output-tag {
           leaf output {
             type string;
           }
         }
         case actual-tag {
           anyxml ospf3-route-information;
         }
         case multichassis-tag {
           anyxml multi-routing-engine-results;
         }
       }
     }
   }
   rpc get-ospf3-statistics-information {
     description "Show OSPFv3 statistics";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf tenant {
         description "Name of tenant, or 'all'";
         type string {
           junos:posix-pattern "^[a-zA-Z0-9-]{1,63}$";
           junos:pattern-message "Tenant name is a string consisting of up to 63 letters, numbers and dashes";
         }
       }
       leaf instance {
         description "Name of OSPFv3 instance";
         type string;
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
     }
     output {
       choice output_c {
         case output-tag {
           leaf output {
             type string;
           }
         }
         case actual-tag {
           anyxml ospf3-statistics-information;
         }
         case multichassis-tag {
           anyxml multi-routing-engine-results;
         }
       }
     }
   }
   rpc get-ospf3-io-statistics-information {
     description "Show OSPFv3 I/O statistics";
     input {
       leaf logical-system {
         description "Name of logical system, or 'all'";
         type string {
           junos:posix-pattern "^[a-zA-Z0-9_-]{1,63}$";
           junos:pattern-message "Logical-system name is a string consisting of up to 63 letters, numbers, dashes and underscores";
         }
       }
     }
     output {
       choice output_c {
         case output-tag {
           leaf output {
             type string;
           }
         }
         case actual-tag {
           anyxml ospf3-io-statistics-information;
         }
         case multichassis-tag {
           anyxml multi-routing-engine-results;
         }
       }
     }
   }
   rpc get-ospf3-log-information {
     description "Show OSPFv3 SPF log";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of OSPFv3 instance";
         type string;
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
     }
     output {
       choice output_c {
         case output-tag {
           leaf output {
             type string;
           }
         }
         case actual-tag {
           anyxml ospf3-log-information;
         }
         case multichassis-tag {
           anyxml multi-routing-engine-results;
         }
       }
     }
   }
   rpc get-ospf3-backup-spf-information {
     description "Show OSPFv3 backup SPF calculations information";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of OSPF instance";
         type string;
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
       leaf area {
         description "OSPF area ID";
         type jt:areaid;
       }
       leaf no-coverage {
         description "Entries with no backup coverage";
         type empty;
       }
       leaf node-id {
         description "Display nodes matching the node-id";
         type string;
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml ospf3-backup-spf-information;
         }
         case multichassis-tag {
           anyxml multi-routing-engine-results;
         }
       }
     }
   }
   rpc get-ospf3-backup-lsp-information {
     description "Show OSPFv3 MPLS backup LSP information";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
     }
     output {
       choice output_c {
         case output-tag {
           leaf output {
             type string;
           }
         }
         case actual-tag {
           anyxml ospf3-backup-mplsp-information;
         }
         case multichassis-tag {
           anyxml multi-routing-engine-results;
         }
       }
     }
   }
   rpc get-ospf3-backup-coverage-information {
     description "Show OSPFv3 backup coverage";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of OSPF instance";
         type string;
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
     }
     output {
       choice output_c {
         case output-tag {
           leaf output {
             type string;
           }
         }
         case actual-tag {
           anyxml ospf3-backup-coverage-information;
         }
         case multichassis-tag {
           anyxml multi-routing-engine-results;
         }
       }
     }
   }
   rpc get-ospf3-backup-neighbor-information {
     description "Show OSPFv3 backup neighbors";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf instance {
         description "Name of OSPF instance";
         type string;
       }
       leaf area {
         description "OSPF area ID";
         type jt:areaid;
       }
     }
     output {
       choice output_c {
         case output-tag {
           leaf output {
             type string;
           }
         }
         case actual-tag {
           anyxml ospf3-backup-neighbor-information;
         }
         case multichassis-tag {
           anyxml multi-routing-engine-results;
         }
       }
     }
   }
   rpc get-ospf3-bgporr-information {
     description "Show BGP optimal route-reflection groups";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf group {
         description "BGP optimal route-reflection peer group name";
         type string;
       }
       leaf topology {
         description "Name of topology";
         type string;
       }
       leaf path-type {
         description "OSPF path type";
         type enumeration {
           enum "intra" {
             description "Display intra-area routes";
           }
           enum "inter" {
             description "Display inter-area routes";
           }
           enum "extern" {
             description "Display external routes";
           }
         }
       }
       leaf route-type {
         description "OSPF route type";
         type enumeration {
           enum "router" {
             description "Display routes to all routers";
           }
           enum "abr" {
             description "Display routes to area border routers";
           }
           enum "asbr" {
             description "Display routes to AS border routers";
           }
           enum "transit" {
             description "Display routes to pseudonodes";
           }
           enum "network" {
             description "Display routes to networks";
           }
         }
       }
       leaf destination {
         description "Address and optional prefix length of destination";
         type jt:ipprefix;
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
       leaf instance {
         description "Name of OSPF instance";
         type string;
       }
       leaf verbosity_level {
         default "brief";
         type enumeration {
           enum "brief" {
             description "Display brief output (default)";
           }
           enum "detail" {
             description "Display detailed output";
           }
           enum "extensive" {
             description "Display extensive output";
           }
         }
       }
     }
     output {
       choice output_c {
         case output-tag {
           leaf output {
             type string;
           }
         }
         case actual-tag {
           anyxml ospf3-bgporr-route-information;
         }
         case multichassis-tag {
           anyxml multi-routing-engine-results;
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice vc-selector {
       case case_1 {
         leaf local {
           description "Local virtual chassis member";
           type empty;
         }
       }
     }
     choice tenant-selector {
       case case_1 {
         leaf tenant {
           description "Name of tenant, or 'all'";
           type string;
         }
       }
     }
     leaf all-members {
       description "All virtual chassis members";
       type empty;
     }
     leaf member {
       description "Specific virtual chassis member";
       type union {
         type string {
           pattern "<.*>|$.*";
         }
         type uint32;
       }
     }
   }
 }
