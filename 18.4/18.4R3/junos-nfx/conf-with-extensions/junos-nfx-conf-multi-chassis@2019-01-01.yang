/*
 * Copyright (c) 2019 Juniper Networks, Inc.
 * All rights reserved.
 */
 module junos-nfx-conf-multi-chassis {
   namespace "http://yang.juniper.net/junos-nfx/conf/multi-chassis";

   prefix jc-multi-chassis;

   import junos-common-ddl-extensions {
     prefix junos;
   }

   import junos-common-types {
     prefix jt;
   }

   import junos-nfx-conf-root {
     prefix jc;
   }

   organization "Juniper Networks, Inc.";

   contact "yang-support@juniper.net";

   description "Junos multi-chassis configuration module";

   revision 2019-01-01 {
     description "Junos: 18.4R3.3";
   }

   augment /jc:configuration {
     uses multi-chassis-group;
   }
   augment /jc:configuration/jc:groups {
     uses multi-chassis-group;
   }
   grouping multi-chassis-group {
     container multi-chassis {
       presence "enable multi-chassis";
       description "Multi-chassis configuration";
       uses apply-advanced;
       container mc-lag {
         presence "enable mc-lag";
         description "Multi-chassis Lag configuration";
         uses apply-advanced;
         container consistency-check {
           presence "enable consistency-check";
           description "Consistency Check properties";
           uses apply-advanced;
           leaf comparison-delay-time {
             description "Time after which local and remote config are compared";
             units "seconds";
             type union {
               type string {
                 pattern "<.*>|$.*";
               }
               type uint32 {
                 range "5 .. 600";
               }
             }
           }
           container traceoptions {
             description "Trace options for MCLAG_CFGCHK";
             uses apply-advanced;
             leaf no-remote-trace {
               description "Disable remote tracing";
               junos:must "(\"system tracing\")";
               junos:must-message "'no-remote-trace' is valid only when [system tracing] is configured";
               type empty;
             }
             container file {
               description "Trace file information";
               leaf filename {
                 description "Name of file in which to write trace information";
                 type string {
                   length "1 .. 1024";
                   junos:posix-pattern "![/ %]";
                   junos:pattern-message "Must not contain '/', % or a space";
                 }
               }
               leaf size {
                 description "Maximum trace file size";
                 type string;
               }
               leaf files {
                 description "Maximum number of trace files";
                 default "3";
                 type union {
                   type string {
                     pattern "<.*>|$.*";
                   }
                   type uint32 {
                     range "2 .. 1000";
                   }
                 }
               }
               choice world-readable-choice {
                 leaf world-readable {
                   description "Allow any user to read the log file";
                   type empty;
                 }
                 leaf no-world-readable {
                   description "Don't allow any user to read the log file";
                   type empty;
                 }
               }
               leaf match {
                 description "Regular expression for lines to be logged";
                 type jt:regular-expression;
               }
             }
             list flag {
               key name;
               ordered-by user;
               description "Trace flag information";
               leaf name {
                 type enumeration {
                   enum "error" {
                     description "Trace all errors";
                   }
                   enum "event" {
                     description "Trace all events";
                   }
                   enum "packet" {
                     description "Trace all packets";
                   }
                   enum "pipe" {
                     description "Trace pipe messages";
                   }
                   enum "pipe-detail" {
                     description "Trace pipe messages in detail";
                   }
                   enum "all" {
                     description "Trace everything";
                   }
                 }
               }
             }
           }
         }
       }
       list multi-chassis-protection {
         key name;
         description "Inter-Chassis protection configuration";
         junos:must "(\"switch-options service-id\")";
         junos:must-message "Service-id required to configure multi-chassis lag";
         uses multi-chassis-protection-group;
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping macro-data-type {
     leaf name {
       description "Keyword part of the keyword-value pair";
       type string;
     }
     leaf value {
       description "Value part of the keyword-value pair";
       type string;
     }
   }
   grouping multi-chassis-protection-group {
     leaf name {
       description "IP address for this peer";
       junos:must "((\"protocols iccp peer $$\" || any \"logical-systems <*> protocols iccp peer $$\"))";
       junos:must-message "The peer ip must match with ones defined at <protocols iccp peer>";
       type jt:ipv4addr;
     }
     uses apply-advanced;
     leaf interface {
       description "Inter-Chassis protection link";
       junos:must "(((((!(any \"logical-systems <*> routing-instances <*> protocols rstp interface $$\") && !(any \"logical-systems <*> routing-instances <*> protocols rstp interface all\")) || any \"logical-systems <*> routing-instances <*> protocols rstp interface $$ disable\") && ((((!(any \"logical-systems <*> routing-instances <*> protocols vstp interface $$\") && !(any \"logical-systems <*> routing-instances <*> protocols vstp interface all\")) && (!(any \"logical-systems <*> routing-instances <*> protocols vstp vlan all interface all\") && (!(any \"logical-systems <*> routing-instances <*> protocols vstp vlan <*> interface $$\") && !(any \"logical-systems <*> routing-instances <*> protocols vstp vlan <*> interface all\")))) || any \"logical-systems <*> routing-instances <*> protocols vstp interface $$ disable\") && ((!(any \"logical-systems <*> routing-instances <*> protocols mstp interface $$\") && !(any \"logical-systems <*> routing-instances <*> protocols mstp interface all\")) || any \"logical-systems <*> routing-instances <*> protocols mstp interface $$ disable\"))) && (((!(any \"logical-systems <*> protocols rstp interface $$\") && !(any \"logical-systems <*> protocols rstp interface all\")) || any \"logical-systems <*> protocols rstp interface $$ disable\") && ((((!(any \"logical-systems <*> protocols vstp interface $$\") && !(any \"logical-systems <*> protocols vstp interface all\")) && (!(any \"logical-systems <*> protocols vstp vlan all interface all\") && (!(any \"logical-systems <*> protocols vstp vlan <*> interface $$\") && !(any \"logical-systems <*> protocols vstp vlan <*> interface all\")))) || any \"logical-systems <*> protocols vstp interface $$ disable\") && ((!(any \"logical-systems <*> protocols mstp interface $$\") && !(any \"logical-systems <*> protocols mstp interface all\")) || any \"logical-systems <*> protocols mstp interface $$ disable\")))))";
       junos:must-message "Inter-Chasis link interface cannot be an STP interface. Please disable xstp on this interface";
       junos:must "(((((!(any \"routing-instances <*> protocols rstp interface $$\") && !(any \"routing-instances <*> protocols rstp interface all\")) || any \"routing-instances <*> protocols rstp interface $$ disable\") && ((((!(any \"routing-instances <*> protocols vstp interface $$\") && !(any \"routing-instances <*> protocols vstp interface all\")) && (!(any \"routing-instances <*> protocols vstp vlan all interface all\") && (!(any \"routing-instances <*> protocols vstp vlan <*> interface $$\") && !(any \"routing-instances <*> protocols vstp vlan <*> interface all\")))) || any \"routing-instances <*> protocols vstp interface $$ disable\") && ((!(any \"routing-instances <*> protocols mstp interface $$\") && !(any \"routing-instances <*> protocols mstp interface all\")) || any \"routing-instances <*> protocols mstp interface $$ disable\"))) && (((!(\"protocols rstp interface $$\") && !(\"protocols rstp interface all\")) || \"protocols rstp interface $$ disable\") && ((((!(\"protocols vstp interface $$\") && !(\"protocols vstp interface all\")) && (!(\"protocols vstp vlan all interface all\") && (!(any \"protocols vstp vlan <*> interface $$\") && !(any \"protocols vstp vlan <*> interface all\")))) || \"protocols vstp interface $$ disable\") && ((!(\"protocols mstp interface $$\") && !(\"protocols mstp interface all\")) || \"protocols mstp interface $$ disable\")))))";
       junos:must-message "Inter-Chasis link interface cannot be an STP interface. Please disable xstp on this interface";
       type string {
         length "1 .. 40";
         junos:posix-pattern "^((ge-)|(mge-)|(xe-)|(ae)|(xle-)|(et-)|(sxe-))";
         junos:pattern-message "Only ae, ge, mge, xe, xle, sxe and et inteface is supported";
       }
     }
   }
 }
