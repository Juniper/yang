/*
 * Copyright (c) 2019 Juniper Networks, Inc.
 * All rights reserved.
 */
 module junos-es-conf-logical-systems {
   namespace "http://yang.juniper.net/junos-es/conf/logical-systems";

   prefix jc-logical-systems;

   import junos-common-types {
     prefix jt;
   }

   import junos-es-conf-root {
     prefix jc;
   }

   organization "Juniper Networks, Inc.";

   contact "yang-support@juniper.net";

   description "Junos logical-systems configuration module";

   revision 2019-01-01 {
     description "Junos: 18.4R3.3";
   }

   augment /jc:configuration {
     uses logical-systems-group;
   }
   augment /jc:configuration/jc:groups {
     uses logical-systems-group;
   }
   grouping logical-systems-group {
     list logical-systems {
       key name;
       description "Logical systems";
       uses juniper-logical-system;
     }
   }
   grouping juniper-logical-system {
     description "Logical system configuration";
     leaf name {
       description "Logical system name";
       type string {
       }
     }
     uses apply-advanced;
     container interfaces {
       description "Interface configuration";
       uses apply-advanced;
       list interface {
         key name;
         uses lr_interfaces_type;
       }
     }
     container protocols {
       description "Routing protocol configuration";
       uses juniper-protocols;
     }
     container policy-options {
       description "Policy option configuration";
       uses juniper-policy-options;
     }
     container routing-instances {
       description "Routing instance configuration";
       uses apply-advanced;
       list instance {
         key name;
         uses juniper-routing-instance;
       }
     }
     container routing-options {
       description "Protocol-independent routing option configuration";
       uses juniper-routing-options;
     }
     container forwarding-options {
       description "Configure options to control packet forwarding";
       uses apply-advanced;
       container dhcp-relay {
         description "Dynamic Host Configuration Protocol relay configuration";
         uses jdhcp-relay-type;
       }
       list storm-control-profiles {
         key name;
         description "Storm control profile for this instance";
         leaf name {
           description "Storm control profile name";
           type string {
             length "1 .. 127";
           }
         }
         uses apply-advanced;
         container all {
           presence "enable all";
           description "For all BUM traffic";
           uses apply-advanced;
           choice bandwidth {
             case case_1 {
               leaf bandwidth-percentage {
                 description "Percentage of link bandwidth";
                 type union {
                   type string {
                     pattern "<.*>|$.*";
                   }
                   type uint32 {
                     range "1 .. 100";
                   }
                 }
               }
             }
             case case_2 {
               leaf bandwidth-level {
                 description "Link bandwidth";
                 units "kbps";
                 type union {
                   type string {
                     pattern "<.*>|$.*";
                   }
                   type uint32;
                 }
               }
             }
           }
           leaf burst-size {
             description "Burst size";
             units "bytes";
             type union {
               type string {
                 pattern "<.*>|$.*";
               }
               type uint32 {
                 range "1500 .. 100000000";
               }
             }
           }
           leaf no-broadcast {
             description "Disable broadcast storm control";
             type empty;
           }
           leaf no-unknown-unicast {
             description "Disable unknown unicast storm control";
             type empty;
           }
           choice no-multicast-choices {
             case case_1 {
               leaf no-multicast {
                 description "Disable multicast storm control";
                 type empty;
               }
             }
             case case_2 {
               leaf no-registered-multicast {
                 description "Disable registered multicast storm control";
                 type empty;
               }
             }
             case case_3 {
               leaf no-unregistered-multicast {
                 description "Disable unregistered multicast storm control";
                 type empty;
               }
             }
           }
         }
         leaf action-shutdown {
           description "Disable port for excessive storm control errors";
           type empty;
         }
       }
       container sampling {
         presence "enable sampling";
         uses apply-advanced;
         container family {
           description "Address family of packets to sample";
           container inet {
             description "Sample IPv4 packets";
             uses apply-advanced;
             container output {
               description "Configure output options for packet sampling";
               uses apply-advanced;
               list flow-server {
                 key name;
                 description "Configure sending traffic aggregates in cflowd format";
                 max-elements 8;
                 uses cflowd_sampling_inet_lr_type;
               }
             }
           }
           container mpls {
             description "Sample MPLS packets";
             uses apply-advanced;
             container output {
               description "Configure output options for packet sampling";
               uses apply-advanced;
               list flow-server {
                 key name;
                 description "Configure sending traffic aggregates in cflowd format";
                 max-elements 8;
                 uses cflowd_sampling_mpls_lr_type;
               }
             }
           }
         }
         list instance {
           key name;
           ordered-by user;
           description "Instance of sampling parameters";
           leaf name {
             description "Name for sampling instance";
             type string;
           }
           uses apply-advanced;
           choice enable-disable {
             case case_1 {
               leaf disable {
                 description "Disable sampling instance";
                 type empty;
               }
             }
           }
           container family {
             description "Address family of packets to sample";
             container inet {
               description "Sample IPv4 packets";
               uses apply-advanced;
               container output {
                 description "Configure output options for packet sampling";
                 uses apply-advanced;
                 list flow-server {
                   key name;
                   description "Configure sending traffic aggregates in cflowd format";
                   max-elements 8;
                   uses cflowd_sampling_inet_lr_inst_type;
                 }
               }
             }
             container mpls {
               description "Sample MPLS packets";
               uses apply-advanced;
               container output {
                 description "Configure output options for packet sampling";
                 uses apply-advanced;
                 list flow-server {
                   key name;
                   description "Configure sending traffic aggregates in cflowd format";
                   max-elements 8;
                   uses cflowd_sampling_mpls_lr_inst_type;
                 }
               }
             }
           }
         }
       }
     }
     container system {
       description "System parameters";
       uses apply-advanced;
       container arp {
         description "ARP settings";
         uses apply-advanced;
         leaf aging-timer {
           description "Change the ARP aging time value";
           units "minutes";
           type union {
             type string {
               pattern "<.*>|$.*";
             }
             type int32 {
               range "1 .. 240";
             }
           }
         }
         container interfaces {
           description "Logical interface on which to specify ARP aging timer";
           uses apply-advanced;
           list arp-interface {
             key name;
             uses arp-interface-type;
           }
         }
         leaf passive-learning {
           description "ARP passive learning";
           type empty;
         }
         leaf purging {
           description "ARP purging when link goes down";
           type empty;
         }
         leaf gratuitous-arp-on-ifup {
           description "Gratuitous ARP announcement on interface up";
           type empty;
         }
         leaf gratuitous-arp-delay {
           description "Delay gratuitous ARP request";
           type union {
             type int32;
             type string {
               pattern "<.*>|$.*";
             }
           }
         }
         leaf non-subscriber-no-reply {
           description "Do not reply to ARP requests from non-subscribers";
           type empty;
         }
       }
       container services {
         description "System services";
         uses apply-advanced;
         container dhcp-local-server {
           description "Dynamic Host Configuration Protocol server configuration";
           uses jdhcp-local-server-type;
         }
         container static-subscribers {
           description "Static Subscriber Client configuration";
           uses jsscd-static-subscribers-type;
         }
       }
       container processes {
         description "Process control";
         uses apply-advanced;
         container routing {
           presence "enable routing";
           description "Routing process";
           uses apply-advanced;
           choice mode {
             case case_1 {
               leaf force-32-bit {
                 description "Always use 32-bit mode";
                 type empty;
               }
             }
             case case_2 {
               leaf force-64-bit {
                 description "Always use 64-bit mode";
                 type empty;
               }
             }
             case case_3 {
               leaf auto-64-bit {
                 description "Ignored; same as force-32-bit";
                 type empty;
               }
             }
           }
         }
       }
     }
     container access {
       description "Network access configuration";
       uses apply-advanced;
       container address-assignment {
         description "Address assignment configuration";
         uses address-assignment-type;
       }
       container address-protection {
         presence "enable address-protection";
         description "Initiate Duplicate Address Protection";
         uses apply-advanced;
         leaf reassign-on-match {
           description "Disconnect owning session and reassign to this session";
           type empty;
         }
       }
       container firewall-authentication {
         description "Type of firewall authentication";
         uses apply-advanced;
         container pass-through {
           description "Pass-through firewall authentication settings";
           uses apply-advanced;
           leaf default-profile {
             description "Name of profile to use if not specified in policy";
             type string {
               length "1 .. 250";
             }
           }
           container ftp {
             description "FTP banners";
             uses banner-object;
           }
           container telnet {
             description "Telnet banners";
             uses banner-object;
           }
           container http {
             description "HTTP banners";
             uses banner-object;
           }
         }
         container web-authentication {
           description "Web-authentication settings";
           uses apply-advanced;
           leaf default-profile {
             description "Name of profile to use for web-authentication";
             type string {
               length "1 .. 250";
             }
           }
           container banner {
             uses apply-advanced;
             leaf success {
               description "The message that will be displayed on successful login";
               type string {
                 length "1 .. 250";
               }
             }
           }
           leaf timeout {
             description "Web-authentication timeout value in seconds";
             type union {
               type string {
                 pattern "<.*>|$.*";
               }
               type int32 {
                 range "5 .. 60";
               }
             }
           }
         }
         container traceoptions {
           description "Firewall authentication tracing options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "configuration" {
                   description "Trace configuration events";
                 }
                 enum "setup" {
                   description "Trace setup of firewall authentication service";
                 }
                 enum "authentication" {
                   description "Trace authentication events";
                 }
                 enum "all" {
                   description "Trace with all flags enabled";
                 }
               }
             }
           }
         }
       }
     }
     container access-profile {
       description "Access profile for this instance";
       leaf access-profile-name {
         description "Profile name";
         type string;
       }
     }
     container firewall {
       description "Define a firewall configuration";
       uses apply-advanced;
       container family {
         description "Protocol family";
         container inet {
           description "Protocol family IPv4 for firewall filter";
           uses apply-advanced;
           list dialer-filter {
             key name;
             ordered-by user;
             description "Define an IPv4 dialer filter";
             uses inet_dialer_filter;
           }
           list prefix-action {
             key name;
             ordered-by user;
             description "Define a prefix action";
             uses prefix_action;
           }
           list filter {
             key name;
             ordered-by user;
             description "Define an IPv4 firewall filter";
             uses inet_filter;
           }
           list simple-filter {
             key name;
             ordered-by user;
             description "Define an IPv4 firewall simple filter";
             uses inet_simple_filter;
           }
           list service-filter {
             key name;
             ordered-by user;
             description "One or more IPv4 service filters";
             uses inet_service_filter;
           }
           list fast-update-filter {
             key name;
             ordered-by user;
             description "One or more fast update filters";
             uses inet_fuf;
           }
         }
         container inet6 {
           description "Protocol family IPv6 for firewall filter";
           uses apply-advanced;
           list dialer-filter {
             key name;
             ordered-by user;
             description "Define an IPv6 dialer filter";
             uses inet6_dialer_filter;
           }
           list filter {
             key name;
             ordered-by user;
             description "Define an IPv6 firewall filter";
             uses inet6_filter;
           }
           list service-filter {
             key name;
             ordered-by user;
             description "One or more IPv6 service filters";
             uses inet6_service_filter;
           }
           list fast-update-filter {
             key name;
             ordered-by user;
             description "One or more fast update filters";
             uses inet6_fuf;
           }
         }
         container mpls {
           description "Protocol family MPLS for firewall filter";
           uses apply-advanced;
           list dialer-filter {
             key name;
             ordered-by user;
             description "Define an mpls dialer filter";
             uses mpls_dialer_filter;
           }
           list filter {
             key name;
             ordered-by user;
             uses mpls_filter;
           }
         }
         container vpls {
           description "Protocol family VPLS for firewall filter";
           uses apply-advanced;
           list filter {
             key name;
             ordered-by user;
             uses vpls_filter;
           }
         }
         container evpn {
           description "Protocol family EVPN for firewall filter";
           uses apply-advanced;
           list filter {
             key name;
             ordered-by user;
             uses vpls_filter;
           }
         }
         container bridge {
           description "Protocol family BRIDGE for firewall filter";
           uses apply-advanced;
           list filter {
             key name;
             ordered-by user;
             uses bridge_filter;
           }
         }
         container ccc {
           description "Protocol family CCC for firewall filter";
           uses apply-advanced;
           list filter {
             key name;
             ordered-by user;
             uses ccc_filter;
           }
         }
         container any {
           description "Protocol-independent filter";
           uses apply-advanced;
           list filter {
             key name;
             ordered-by user;
             description "Define a protocol independent filter";
             uses any_filter;
           }
         }
         container ethernet-switching {
           description "Protocol family Ethernet Switching for firewall filter";
           uses apply-advanced;
           list filter {
             key name;
             ordered-by user;
             description "Define an Ethernet Switching firewall filter";
             uses es_filter;
           }
         }
       }
       list policer {
         key name;
         ordered-by user;
         description "Policer template definition";
         uses firewall_policer;
       }
       list flexible-match {
         key name;
         ordered-by user;
         description "Flexible packet match template definition";
         uses firewall_flexible_match;
       }
       list tunnel-end-point {
         key name;
         ordered-by user;
         description "Tunnel end-point template definition";
         uses tunnel_end_point;
       }
       list interface-set {
         key name;
         ordered-by user;
         description "Interface set definition";
         uses interface_set_type;
       }
       list three-color-policer {
         key name;
         ordered-by user;
         description "Three-color policer";
         uses three-color-policer-type;
       }
       list filter {
         key name;
         ordered-by user;
         description "Define an IPv4 firewall filter";
         uses inet_filter;
       }
     }
     container multicast-snooping-options {
       description "Multicast snooping option configuration";
       uses juniper-multicast-snooping-options;
     }
     container services {
       description "Service PIC daemon configuration";
       uses apply-advanced;
       container flow-monitoring {
         presence "enable flow-monitoring";
         description "Configure flow monitoring under logical-systems";
         uses apply-advanced;
         container version9 {
           description "Version 9 configuration";
           uses apply-advanced;
           list template {
             key name;
             ordered-by user;
             description "One or more version 9 templates";
             max-elements 10;
             uses version9-template;
           }
         }
       }
       container icap-redirect {
         description "Configure ICAP redirection service";
         uses apply-advanced;
         list profile {
           key name;
           ordered-by user;
           description "Congifure ICAP service profile";
           uses icap-profile-object;
         }
         container traceoptions {
           description "ICAP redirect trace options";
           uses icap-redirect-traceoptions;
         }
       }
       container security-intelligence {
         uses apply-advanced;
         container category {
           description "Category to be disabled";
           uses apply-advanced;
           container all {
             presence "enable all";
             description "All categories";
             uses apply-advanced;
             container disable {
               presence "enable disable";
               description "To disable all categories";
             }
           }
           list category-name {
             key name;
             ordered-by user;
             uses secintel-category-disable;
           }
         }
         leaf url {
           description "Configure the url of feed server [https://<ip or hostname>:<port>/<uri>]";
           type string;
         }
         leaf url-parameter {
           description "Configure the parameter of url";
           type jt:unreadable;
         }
         leaf proxy-profile {
           description "The proxy profile name";
           type string {
             length "1 .. 64";
           }
         }
         container authentication {
           description "Authenticate to use feed update services";
           uses apply-advanced;
           leaf auth-token {
             description "Token string for authentication";
             type string {
             }
           }
           leaf tls-profile {
             description "TLS profile";
             type string;
           }
         }
         container traceoptions {
           description "Security intelligence trace options";
           uses secintel-traceoptions;
         }
         list profile {
           key name;
           ordered-by user;
           description "Configure security intelligence profile";
           uses secintel-profile-setting;
         }
         container default-policy {
           description "Configure security intelligence default policy";
           uses apply-advanced;
           list category-profiles {
             key name;
             ordered-by user;
             description "Security intelligence category profiles";
             leaf name {
               description "Name of security intelligence category";
               type string;
             }
             uses apply-advanced;
             leaf profile-name {
               description "Name of profile";
               type string;
             }
           }
         }
         list policy {
           key name;
           ordered-by user;
           description "Configure security intelligence policy";
           uses secintel-policy-setting;
         }
       }
       container advanced-anti-malware {
         uses apply-advanced;
         container connection {
           presence "enable connection";
           description "Cloud service RE connection, only for master logical domain";
           uses apply-advanced;
           leaf url {
             description "The url of the cloud server [https://<ip or hostname>:<port>]";
             type string;
           }
           container authentication {
             description "The authentication profile for using cloud services";
             uses apply-advanced;
             leaf tls-profile {
               description "TLS profile";
               type string;
             }
           }
           leaf proxy-profile {
             description "Proxy profile";
             type string {
               length "1 .. 63";
             }
           }
           leaf source-address {
             description "The source ip for connecting to the cloud server.";
             type jt:ipaddr;
           }
           leaf source-interface {
             description "The source interface for connecting to the cloud server";
             type union {
               type jt:interface-name;
               type string {
                 pattern "<.*>|$.*";
               }
             }
           }
         }
         container default-policy {
           presence "enable default-policy";
           description "Advanced Anti-malware default policy";
           uses apply-advanced;
           container http {
             description "Configure HTTP options";
             uses apply-advanced;
             leaf inspection-profile {
               description "Advanced Anti-malware inspection-profile name (default:default_profile)";
               type string {
                 length "1 .. 63";
               }
             }
             leaf action {
               description "Action taken for contents with verdict meet threshold";
               type enumeration {
                 enum "permit" {
                   description "Allow contents";
                 }
                 enum "block" {
                   description "Disallow contents";
                 }
               }
             }
             container notification {
               description "Notification action taken for contents with verdict meet threshold";
               uses apply-advanced;
               leaf log {
                 description "Logging option for Advanced Anti-malware actions";
                 type empty;
               }
             }
           }
           container smtp {
             description "Configure SMTP options";
             uses apply-advanced;
             leaf inspection-profile {
               description "Advanced Anti-malware inspection-profile name (default:default_profile)";
               type string {
                 length "1 .. 63";
               }
             }
             container notification {
               description "Notification action taken for contents with verdict meet threshold";
               uses apply-advanced;
               leaf log {
                 description "Logging option for Advanced Anti-malware actions";
                 type empty;
               }
             }
           }
           container imap {
             description "Configure IMAP options";
             uses apply-advanced;
             leaf inspection-profile {
               description "Advanced Anti-malware inspection-profile name (default:default_profile)";
               type string {
                 length "1 .. 63";
               }
             }
             container notification {
               description "Notification action taken for contents with verdict meet threshold";
               uses apply-advanced;
               leaf log {
                 description "Logging option for Advanced Anti-malware actions";
                 type empty;
               }
             }
           }
           leaf verdict-threshold {
             description "Verdict threshold";
             type enumeration {
               enum "1" {
                 description "Verdict-threshold level 1";
               }
               enum "2" {
                 description "Verdict-threshold level 2";
               }
               enum "3" {
                 description "Verdict-threshold level 3";
               }
               enum "4" {
                 description "Verdict-threshold level 4";
               }
               enum "5" {
                 description "Verdict-threshold level 5";
               }
               enum "6" {
                 description "Verdict-threshold level 6";
               }
               enum "7" {
                 description "Verdict-threshold level 7";
               }
               enum "8" {
                 description "Verdict-threshold level 8";
               }
               enum "9" {
                 description "Verdict-threshold level 9";
               }
               enum "10" {
                 description "Verdict-threshold level 10";
               }
               enum "recommended" {
                 description "Recommended verdict-threshold";
               }
             }
           }
           leaf inspection-profile {
             description "Advanced Anti-malware inspection-profile name";
             status deprecated;
             type string {
               length "1 .. 63";
             }
           }
           container fallback-options {
             description "Fallback options for abnormal conditions";
             uses apply-advanced;
             leaf action {
               description "Action taken for fallback conditions";
               type enumeration {
                 enum "permit" {
                   description "Allow contents";
                 }
                 enum "block" {
                   description "Disallow contents";
                 }
               }
             }
             container notification {
               description "Notification action taken for fallback action";
               uses apply-advanced;
               leaf log {
                 description "Logging option for Advanced Anti-malware fallback action";
                 type empty;
               }
             }
           }
           container default-notification {
             description "Notification action taken for action";
             uses apply-advanced;
             leaf log {
               description "Logging option for Advanced Anti-malware action";
               type empty;
             }
           }
           container whitelist-notification {
             description "Whitelist notification logging option";
             uses apply-advanced;
             leaf log {
               description "Logging option for Advanced Anti-malware whitelist hit";
               type empty;
             }
           }
           container blacklist-notification {
             description "Blacklist notification logging option";
             uses apply-advanced;
             leaf log {
               description "Logging option for Advanced Anti-malware blacklist hit";
               type empty;
             }
           }
         }
         list policy {
           key name;
           description "Advanced Anti-malware policy";
           leaf name {
             description "Policy name, default policy must name (default-policy)";
             type string {
               length "1 .. 63";
             }
           }
           uses apply-advanced;
           container match {
             description "Policy match conditions";
             status deprecated;
             uses apply-advanced;
             leaf application {
               description "Application";
               type enumeration {
                 enum "HTTP" {
                   description "HTTP Traffic";
                 }
               }
             }
             leaf verdict-threshold {
               description "Verdict threshold";
               type enumeration {
                 enum "1" {
                   description "Verdict-threshold level 1";
                 }
                 enum "2" {
                   description "Verdict-threshold level 2";
                 }
                 enum "3" {
                   description "Verdict-threshold level 3";
                 }
                 enum "4" {
                   description "Verdict-threshold level 4";
                 }
                 enum "5" {
                   description "Verdict-threshold level 5";
                 }
                 enum "6" {
                   description "Verdict-threshold level 6";
                 }
                 enum "7" {
                   description "Verdict-threshold level 7";
                 }
                 enum "8" {
                   description "Verdict-threshold level 8";
                 }
                 enum "9" {
                   description "Verdict-threshold level 9";
                 }
                 enum "10" {
                   description "Verdict-threshold level 10";
                 }
                 enum "recommended" {
                   description "Recommended verdict-threshold";
                 }
               }
             }
           }
           container then {
             status deprecated;
             uses apply-advanced;
             leaf action {
               description "Action taken for contents with verdict meet threshold";
               type enumeration {
                 enum "permit" {
                   description "Allow contents";
                 }
                 enum "block" {
                   description "Disallow contents";
                 }
               }
             }
             container notification {
               description "Notification action taken for contents with verdict meet threshold";
               uses apply-advanced;
               leaf log {
                 description "Logging option for Advanced Anti-malware actions";
                 type empty;
               }
             }
           }
           container http {
             description "Configure HTTP options";
             uses apply-advanced;
             leaf inspection-profile {
               description "Advanced Anti-malware inspection-profile name (default:default_profile)";
               type string {
                 length "1 .. 63";
               }
             }
             leaf action {
               description "Action taken for contents with verdict meet threshold";
               type enumeration {
                 enum "permit" {
                   description "Allow contents";
                 }
                 enum "block" {
                   description "Disallow contents";
                 }
               }
             }
             container notification {
               description "Notification action taken for contents with verdict meet threshold";
               uses apply-advanced;
               leaf log {
                 description "Logging option for Advanced Anti-malware actions";
                 type empty;
               }
             }
           }
           container smtp {
             description "Configure SMTP options";
             uses apply-advanced;
             leaf inspection-profile {
               description "Advanced Anti-malware inspection-profile name (default:default_profile)";
               type string {
                 length "1 .. 63";
               }
             }
             container notification {
               description "Notification action taken for contents with verdict meet threshold";
               uses apply-advanced;
               leaf log {
                 description "Logging option for Advanced Anti-malware actions";
                 type empty;
               }
             }
           }
           container imap {
             description "Configure IMAP options";
             uses apply-advanced;
             leaf inspection-profile {
               description "Advanced Anti-malware inspection-profile name (default:default_profile)";
               type string {
                 length "1 .. 63";
               }
             }
             container notification {
               description "Notification action taken for contents with verdict meet threshold";
               uses apply-advanced;
               leaf log {
                 description "Logging option for Advanced Anti-malware actions";
                 type empty;
               }
             }
           }
           leaf verdict-threshold {
             description "Verdict threshold";
             type enumeration {
               enum "1" {
                 description "Verdict-threshold level 1";
               }
               enum "2" {
                 description "Verdict-threshold level 2";
               }
               enum "3" {
                 description "Verdict-threshold level 3";
               }
               enum "4" {
                 description "Verdict-threshold level 4";
               }
               enum "5" {
                 description "Verdict-threshold level 5";
               }
               enum "6" {
                 description "Verdict-threshold level 6";
               }
               enum "7" {
                 description "Verdict-threshold level 7";
               }
               enum "8" {
                 description "Verdict-threshold level 8";
               }
               enum "9" {
                 description "Verdict-threshold level 9";
               }
               enum "10" {
                 description "Verdict-threshold level 10";
               }
               enum "recommended" {
                 description "Recommended verdict-threshold";
               }
             }
           }
           leaf inspection-profile {
             description "Advanced Anti-malware inspection-profile name";
             status deprecated;
             type string {
               length "1 .. 63";
             }
           }
           container fallback-options {
             description "Fallback options for abnormal conditions";
             uses apply-advanced;
             leaf action {
               description "Action taken for fallback conditions";
               type enumeration {
                 enum "permit" {
                   description "Allow contents";
                 }
                 enum "block" {
                   description "Disallow contents";
                 }
               }
             }
             container notification {
               description "Notification action taken for fallback action";
               uses apply-advanced;
               leaf log {
                 description "Logging option for Advanced Anti-malware fallback action";
                 type empty;
               }
             }
           }
           container default-notification {
             description "Notification action taken for action";
             uses apply-advanced;
             leaf log {
               description "Logging option for Advanced Anti-malware action";
               type empty;
             }
           }
           container whitelist-notification {
             description "Whitelist notification logging option";
             uses apply-advanced;
             leaf log {
               description "Logging option for Advanced Anti-malware whitelist hit";
               type empty;
             }
           }
           container blacklist-notification {
             description "Blacklist notification logging option";
             uses apply-advanced;
             leaf log {
               description "Logging option for Advanced Anti-malware blacklist hit";
               type empty;
             }
           }
         }
         container traceoptions {
           description "Advanced Anti-malware trace options";
           uses aamwd-traceoptions;
         }
       }
     }
     container bridge-domains {
       description "Bridge domain configuration";
       uses apply-advanced;
       list domain {
         key name;
         uses juniper-bridge-domains;
       }
     }
     container switch-options {
       description "Options for default routing-instance of type virtual-switch";
       uses juniper-def-rtb-switch-options;
     }
     container vlans {
       description "VLAN configuration";
       uses apply-advanced;
       list vlan {
         key name;
         description "Virtual LAN";
         uses vlan-types;
       }
     }
     container security {
       description "Security configuration";
       uses apply-advanced;
       container alarms {
         description "Configure security alarms";
         uses apply-advanced;
         container audible {
           presence "enable audible";
           description "Beep when new security alarms arrive";
           uses apply-advanced;
           leaf continuous {
             description "Keep beeping until all security alarms have been cleared";
             type empty;
           }
         }
         container potential-violation {
           description "Configure potential security violations";
           uses apply-advanced;
           leaf authentication {
             description "Raise alarm for specified number of authentication failures";
             type union {
               type string {
                 pattern "<.*>|$.*";
               }
               type uint32 {
                 range "2 .. 10";
               }
             }
           }
           leaf cryptographic-self-test {
             description "Raise alarm for cryptographic self test failures";
             type empty;
           }
           container decryption-failures {
             presence "enable decryption-failures";
             description "No. of decryption failures before which an alarm needs to be raised";
             uses apply-advanced;
             leaf threshold {
               description "Threshold value [default is 1000]";
               default "1000";
               type union {
                 type string {
                   pattern "<.*>|$.*";
                 }
                 type uint32 {
                   range "1 .. 1000000000";
                 }
               }
             }
           }
           container encryption-failures {
             presence "enable encryption-failures";
             description "No. of encryption failures before which an alarm needs to be raised";
             uses apply-advanced;
             leaf threshold {
               description "Threshold value [default is 1000]";
               default "1000";
               type union {
                 type string {
                   pattern "<.*>|$.*";
                 }
                 type uint32 {
                   range "1 .. 1000000000";
                 }
               }
             }
           }
           container ike-phase1-failures {
             presence "enable ike-phase1-failures";
             description "No. of IKE Phase-1 failures before which an alarm needs to be raised";
             uses apply-advanced;
             leaf threshold {
               description "Threshold value [default is 20]";
               default "20";
               type union {
                 type string {
                   pattern "<.*>|$.*";
                 }
                 type uint32 {
                   range "1 .. 1000000000";
                 }
               }
             }
           }
           container ike-phase2-failures {
             presence "enable ike-phase2-failures";
             description "No. of IKE Phase-2 failures before which an alarm needs to be raised";
             uses apply-advanced;
             leaf threshold {
               description "Threshold value [default is 20]";
               default "20";
               type union {
                 type string {
                   pattern "<.*>|$.*";
                 }
                 type uint32 {
                   range "1 .. 1000000000";
                 }
               }
             }
           }
           leaf key-generation-self-test {
             description "Raise alarm for key generation self test failures";
             type empty;
           }
           leaf non-cryptographic-self-test {
             description "Raise alarm for non-cryptographic self test failures";
             type empty;
           }
           container policy {
             description "Raise alarm for flow policy violations";
             uses apply-advanced;
             container source-ip {
               presence "enable source-ip";
               description "Configure source address type of policy violation";
               uses apply-advanced;
               leaf threshold {
                 description "Number of source IP address matches to raise alarm";
                 default "1000";
                 type union {
                   type string {
                     pattern "<.*>|$.*";
                   }
                   type uint32 {
                     range "1 .. 4294967295";
                   }
                 }
               }
               leaf duration {
                 description "Time window matches must occur within";
                 default "1";
                 units "seconds";
                 type union {
                   type string {
                     pattern "<.*>|$.*";
                   }
                   type uint32 {
                     range "1 .. 3600";
                   }
                 }
               }
               leaf size {
                 description "Total source IP address number that can be done policy violation check concurrently";
                 default "1024";
                 type union {
                   type string {
                     pattern "<.*>|$.*";
                   }
                   type uint32 {
                     range "1 .. 10240";
                   }
                 }
               }
             }
             container destination-ip {
               presence "enable destination-ip";
               description "Configure destination address type of policy violation";
               uses apply-advanced;
               leaf threshold {
                 description "Number of destination IP address matches to raise alarm";
                 default "1000";
                 type union {
                   type string {
                     pattern "<.*>|$.*";
                   }
                   type uint32 {
                     range "1 .. 4294967295";
                   }
                 }
               }
               leaf duration {
                 description "Time window matches must occur within";
                 default "1";
                 units "seconds";
                 type union {
                   type string {
                     pattern "<.*>|$.*";
                   }
                   type uint32 {
                     range "1 .. 3600";
                   }
                 }
               }
               leaf size {
                 description "Total destination IP address number that can be done policy violation check concurrently";
                 default "1024";
                 type union {
                   type string {
                     pattern "<.*>|$.*";
                   }
                   type uint32 {
                     range "1 .. 10240";
                   }
                 }
               }
             }
             container application {
               presence "enable application";
               description "Configure application type of policy violation";
               uses apply-advanced;
               leaf threshold {
                 description "Number of application matches to raise alarm";
                 default "1000";
                 type union {
                   type string {
                     pattern "<.*>|$.*";
                   }
                   type uint32 {
                     range "1 .. 4294967295";
                   }
                 }
               }
               leaf duration {
                 description "Time window matches must occur within";
                 default "1";
                 units "seconds";
                 type union {
                   type string {
                     pattern "<.*>|$.*";
                   }
                   type uint32 {
                     range "1 .. 3600";
                   }
                 }
               }
               leaf size {
                 description "Total application number that can be done policy violation check concurrently";
                 default "1024";
                 type union {
                   type string {
                     pattern "<.*>|$.*";
                   }
                   type uint32 {
                     range "1 .. 10240";
                   }
                 }
               }
             }
             container policy-match {
               presence "enable policy-match";
               description "Configure policy type of policy violation";
               uses apply-advanced;
               leaf threshold {
                 description "Number of policy matches to raise alarm";
                 default "100";
                 type union {
                   type string {
                     pattern "<.*>|$.*";
                   }
                   type uint32 {
                     range "1 .. 4294967295";
                   }
                 }
               }
               leaf duration {
                 description "Time window matches must occur within";
                 default "1";
                 units "seconds";
                 type union {
                   type string {
                     pattern "<.*>|$.*";
                   }
                   type uint32 {
                     range "1 .. 3600";
                   }
                 }
               }
               leaf size {
                 description "Total concurrent number of policy check violations";
                 default "1024";
                 type union {
                   type string {
                     pattern "<.*>|$.*";
                   }
                   type uint32 {
                     range "1 .. 10240";
                   }
                 }
               }
             }
           }
           container replay-attacks {
             presence "enable replay-attacks";
             description "No. of Replay attacks before which an alarm needs to be raised";
             uses apply-advanced;
             leaf threshold {
               description "Replay threshold value";
               default "1000";
               type union {
                 type string {
                   pattern "<.*>|$.*";
                 }
                 type uint32 {
                   range "1 .. 1000000000";
                 }
               }
             }
           }
           leaf security-log-percent-full {
             description "Raise alarm when security log exceeds this percent capacity";
             type union {
               type string {
                 pattern "<.*>|$.*";
               }
               type uint8 {
                 range "0 .. 100";
               }
             }
           }
           leaf idp {
             description "Raise alarm for idp attack";
             type empty;
           }
         }
       }
       container log {
         description "Configure security log";
         uses log-object;
       }
       container certificates {
         description "X.509 certificate configuration";
         uses apply-advanced;
         list local {
           key name;
           ordered-by user;
           description "Local X.509 certificate configuration";
           uses certificate-object;
         }
         leaf path-length {
           description "Maximum certificate path length";
           default "15";
           type union {
             type string {
               pattern "<.*>|$.*";
             }
             type uint32 {
               range "0 .. 15";
             }
           }
         }
         leaf maximum-certificates {
           description "Maximum number of certificates to cache";
           default "1024";
           type union {
             type string {
               pattern "<.*>|$.*";
             }
             type uint32 {
               range "64 .. 4294967295";
             }
           }
         }
         leaf cache-size {
           description "Maximum size of certificate cache";
           units "bytes";
           type string;
         }
         leaf cache-timeout-negative {
           description "Time in seconds to cache negative responses";
           default "20";
           type union {
             type string {
               pattern "<.*>|$.*";
             }
             type uint32 {
               range "10 .. 4294967295";
             }
           }
         }
         leaf enrollment-retry {
           description "Number of retry attempts for an enrollment request";
           type union {
             type string {
               pattern "<.*>|$.*";
             }
             type uint32 {
               range "0 .. 1080";
             }
           }
         }
         list certification-authority {
           key name;
           ordered-by user;
           description "CA X.509 certificate configuration";
           leaf name {
             description "CA profile name";
             type string {
             }
           }
           uses apply-advanced;
           leaf ca-name {
             description "CA name";
             type string;
           }
           leaf file {
             description "File to read certificate from";
             type string;
           }
           leaf crl {
             description "File to read crl from";
             type string;
           }
           leaf enrollment-url {
             description "URL";
             type string;
           }
           leaf ldap-url {
             description "URL";
             type string;
           }
           leaf encoding {
             description "Encoding to use for certificate or CRL on disk";
             default "binary";
             type enumeration {
               enum "binary" {
                 description "DER encoding";
               }
               enum "pem" {
                 description "Privacy-enhanced-mail encoding, base64";
               }
             }
           }
         }
       }
       container authentication-key-chains {
         description "Authentication key chain configuration";
         uses security-authentication-key-chains;
       }
       container ssh-known-hosts {
         description "SSH known host list";
         uses apply-advanced;
         list host {
           key name;
           ordered-by user;
           description "SSH known host entry";
           leaf name {
             description "Host name";
             type string;
           }
           uses apply-advanced;
           leaf rsa1-key {
             description "Base64 encoded RSA key (protocol version 1)";
             type string;
           }
           leaf rsa-key {
             description "Base64 encoded RSA key";
             type string;
           }
           leaf dsa-key {
             description "Base64 encoded DSA key";
             type string;
           }
           leaf ecdsa-key {
             description "Base64 encoded ECDSA key";
             status deprecated;
             type string;
           }
           leaf ecdsa-sha2-nistp256-key {
             description "Base64 encoded ECDSA-SHA2-NIST256 key";
             type string;
           }
           leaf ecdsa-sha2-nistp384-key {
             description "Base64 encoded ECDSA-SHA2-NIST384 key";
             type string;
           }
           leaf ecdsa-sha2-nistp521-key {
             description "Base64 encoded ECDSA-SHA2-NIST521 key";
             type string;
           }
           leaf ed25519-key {
             description "Base64 encoded ED25519 key";
             type string;
           }
         }
       }
       leaf key-protection {
         description "Common-Criteria key-protection configuration";
         type empty;
       }
       container pki {
         description "PKI service configuration";
         presence "enable pki";
         uses security-pki;
       }
       container ike {
         description "IKE configuration";
         uses security-ike;
       }
       container ipsec {
         description "IPSec configuration";
         uses security-ipsec-vpn;
       }
       container group-vpn {
         description "Group VPN configuration";
         uses security-group-vpn;
       }
       container ipsec-policy {
         description "IPSec policy configuration";
         uses security-ipsec-policies;
       }
       container idp {
         description "Configure IDP";
         list idp-policy {
           key name;
           ordered-by user;
           description "Configure IDP policy";
           uses idp-policy-type;
         }
         leaf active-policy {
           description "Set active policy";
           status deprecated;
           type string;
         }
         leaf default-policy {
           description "Set active policy";
           type string;
         }
         list custom-attack {
           key name;
           ordered-by user;
           description "Configure custom attacks";
           uses custom-attack-type;
         }
         list custom-attack-group {
           key name;
           ordered-by user;
           description "Configure custom attack groups";
           uses custom-attack-group-type;
         }
         list dynamic-attack-group {
           key name;
           ordered-by user;
           description "Configure dynamic attack groups";
           uses dynamic-attack-group-type;
         }
         container traceoptions {
           description "Trace options for idp services";
           uses idpd-traceoptions-type;
         }
         container security-package {
           description "Security package options";
           uses apply-advanced;
           leaf url {
             description "URL of Security package download";
             type string;
           }
           leaf source-address {
             description "Source address to be used for sending download request";
             type jt:ipv4addr;
           }
           leaf proxy-profile {
             description "Proxy profile of security package download";
             type string {
               length "1 .. 64";
             }
           }
           container install {
             presence "enable install";
             description "Configure install command";
             uses apply-advanced;
             leaf ignore-version-check {
               description "Skip version check  when attack database gets installed";
               type empty;
             }
             leaf ignore-appid-failure {
               description "Continue idp installation even if appid installation fails";
               type empty;
             }
           }
           container automatic {
             presence "enable automatic";
             description "Scheduled download and update";
             uses apply-advanced;
             leaf start-time {
               description "Start time (YYYY-MM-DD.HH:MM:SS)";
               type jt:time;
             }
             leaf interval {
               description "Interval";
               units "hours";
               type union {
                 type string {
                   pattern "<.*>|$.*";
                 }
                 type uint32 {
                   range "1 .. 336";
                 }
               }
             }
             leaf download-timeout {
               description "Maximum time for download to complete";
               status deprecated;
               default "1";
               units "minutes";
               type union {
                 type string {
                   pattern "<.*>|$.*";
                 }
                 type uint32 {
                   range "1 .. 60";
                 }
               }
             }
             choice enable-disable {
               case case_1 {
                 leaf enable {
                   description "Enable";
                   type empty;
                 }
               }
             }
           }
         }
         container sensor-configuration {
           description "IDP Sensor Configuration";
           container log {
             description "IDP Log Configuration";
             uses apply-advanced;
             leaf cache-size {
               description "Log cache size";
               type union {
                 type string {
                   pattern "<.*>|$.*";
                 }
                 type uint32;
               }
             }
             container suppression {
               presence "enable suppression";
               description "Log suppression";
               uses apply-advanced;
               choice enable-disable {
                 case case_1 {
                   leaf disable {
                     description "Disable log suppression";
                     type empty;
                   }
                 }
               }
               choice include-destination-address-choice {
                 leaf include-destination-address {
                   description "Include destination address while performing a log suppression";
                   type empty;
                 }
                 leaf no-include-destination-address {
                   description "Don't include destination address while performing a log suppression";
                   type empty;
                 }
               }
               leaf start-log {
                 description "Suppression start log";
                 type union {
                   type string {
                     pattern "<.*>|$.*";
                   }
                   type uint32;
                 }
               }
               leaf max-logs-operate {
                 description "Maximum logs can be operate on";
                 type union {
                   type string {
                     pattern "<.*>|$.*";
                   }
                   type uint32;
                 }
               }
               leaf max-time-report {
                 description "Time after suppressed logs will be reported";
                 type union {
                   type string {
                     pattern "<.*>|$.*";
                   }
                   type uint32;
                 }
               }
             }
           }
           container packet-log {
             description "IDP Packetlog Configuration";
             uses apply-advanced;
             leaf total-memory {
               description "Total memory unit(%)";
               type union {
                 type string {
                   pattern "<.*>|$.*";
                 }
                 type uint32;
               }
             }
             leaf max-sessions {
               description "Max num of sessions in unit(%)";
               type union {
                 type string {
                   pattern "<.*>|$.*";
                 }
                 type uint32;
               }
             }
             leaf threshold-logging-interval {
               description "Interval of logs for max limit session/memory reached in minutes";
               type union {
                 type string {
                   pattern "<.*>|$.*";
                 }
                 type uint32;
               }
             }
             leaf source-address {
               description "Source IP address used to transport packetlog to a host";
               type jt:ipv4addr;
             }
             container host {
               description "Destination host to send packetlog to";
               uses apply-advanced;
               leaf ipaddr {
                 description "IP address";
                 type jt:ipv4addr;
               }
               leaf port {
                 description "UDP port number";
                 type union {
                   type uint16;
                   type string {
                     pattern "<.*>|$.*";
                   }
                 }
               }
             }
           }
           container application-identification {
             presence "enable application-identification";
             description "Application identification";
             uses apply-advanced;
             choice enable-disable {
               case case_1 {
                 leaf disable {
                   description "Disable application identification";
                   type empty;
                 }
               }
             }
             choice application-system-cache-choice {
               leaf application-system-cache {
                 description "Application system cache";
                 type empty;
               }
               leaf no-application-system-cache {
                 description "Don't application system cache";
                 type empty;
               }
             }
             leaf max-tcp-session-packet-memory {
               description "Max TCP session memory";
               status deprecated;
               type union {
                 type string {
                   pattern "<.*>|$.*";
                 }
                 type uint32;
               }
             }
             leaf max-udp-session-packet-memory {
               description "Max UDP session memory";
               status deprecated;
               type union {
                 type string {
                   pattern "<.*>|$.*";
                 }
                 type uint32;
               }
             }
             leaf max-sessions {
               description "Max sessions that can run AI at the same time";
               status deprecated;
               type union {
                 type string {
                   pattern "<.*>|$.*";
                 }
                 type uint32;
               }
             }
             leaf max-packet-memory {
               description "Max packet memory";
               status deprecated;
               type union {
                 type string {
                   pattern "<.*>|$.*";
                 }
                 type uint32;
               }
             }
             leaf max-packet-memory-ratio {
               description "Max packet memory ratio";
               type union {
                 type string {
                   pattern "<.*>|$.*";
                 }
                 type uint32;
               }
             }
             leaf max-reass-packet-memory-ratio {
               description "Max reass packet memory ratio";
               status deprecated;
               type union {
                 type string {
                   pattern "<.*>|$.*";
                 }
                 type uint32;
               }
             }
             leaf application-system-cache-timeout {
               description "Application system cache timeout";
               type union {
                 type string {
                   pattern "<.*>|$.*";
                 }
                 type uint32;
               }
             }
           }
           container flow {
             description "Flow configuration";
             uses apply-advanced;
             choice log-errors-choice {
               leaf log-errors {
                 description "Flow log errors";
                 type empty;
               }
               leaf no-log-errors {
                 description "Don't flow log errors";
                 type empty;
               }
             }
             choice allow-icmp-without-flow-choice {
               leaf allow-icmp-without-flow {
                 description "Allow icmp without flow";
                 status deprecated;
                 type empty;
               }
               leaf no-allow-icmp-without-flow {
                 description "Don't allow icmp without flow";
                 status deprecated;
                 type empty;
               }
             }
             leaf hash-table-size {
               description "Flow hash table size";
               type union {
                 type string {
                   pattern "<.*>|$.*";
                 }
                 type uint32;
               }
             }
             leaf reject-timeout {
               description "Flow reject timeout";
               type union {
                 type string {
                   pattern "<.*>|$.*";
                 }
                 type uint32;
               }
             }
             leaf max-timers-poll-ticks {
               description "Maximum timers poll ticks";
               type union {
                 type string {
                   pattern "<.*>|$.*";
                 }
                 type uint32;
               }
             }
             leaf fifo-max-size {
               description "Maximum fifo size";
               type union {
                 type string {
                   pattern "<.*>|$.*";
                 }
                 type uint32;
               }
             }
             leaf udp-anticipated-timeout {
               description "Maximum udp anticipated timeout";
               type union {
                 type string {
                   pattern "<.*>|$.*";
                 }
                 type uint32;
               }
             }
             leaf drop-on-limit {
               description "Drop connections on exceeding resource limits";
               type empty;
             }
             leaf drop-on-failover {
               description "Drop traffic on HA failover sessions";
               type empty;
             }
             leaf drop-if-no-policy-loaded {
               description "Drop all traffic till IDP policy gets loaded";
               type empty;
             }
             leaf max-sessions-offset {
               description "Maximum session offset limit percentage";
               type union {
                 type string {
                   pattern "<.*>|$.*";
                 }
                 type uint32;
               }
             }
             leaf min-objcache-limit-lt {
               description "Memory lower threshold limit percentage";
               type union {
                 type string {
                   pattern "<.*>|$.*";
                 }
                 type uint32;
               }
             }
             leaf min-objcache-limit-ut {
               description "Memory upper threshold limit percentage";
               type union {
                 type string {
                   pattern "<.*>|$.*";
                 }
                 type uint32;
               }
             }
             leaf session-steering {
               description "Session steering for session anticipation";
               type empty;
             }
             leaf idp-bypass-cpu-usg-overload {
               description "Enable IDP bypass of sessions/packets on CPU usage overload";
               type empty;
             }
             leaf idp-bypass-cpu-threshold {
               description "Threshold of CPU usage in percentage for IDP bypass";
               default "85";
               type union {
                 type string {
                   pattern "<.*>|$.*";
                 }
                 type uint32;
               }
             }
             leaf idp-bypass-cpu-tolerance {
               description "Tolerance of CPU usage in percentage for IDP bypass";
               default "5";
               type union {
                 type string {
                   pattern "<.*>|$.*";
                 }
                 type uint32;
               }
             }
           }
           container re-assembler {
             description "Re-assembler configuration";
             uses apply-advanced;
             choice drop-on-syn-in-window-choice {
               leaf drop-on-syn-in-window {
                 description "Drop session when SYN is seen in the window";
                 type empty;
               }
               leaf no-drop-on-syn-in-window {
                 description "Don't drop session when SYN is seen in the window";
                 type empty;
               }
             }
             choice ignore-memory-overflow-choice {
               leaf ignore-memory-overflow {
                 description "Ignore memory overflow";
                 type empty;
               }
               leaf no-ignore-memory-overflow {
                 description "Don't ignore memory overflow";
                 type empty;
               }
             }
             choice ignore-reassembly-memory-overflow-choice {
               leaf ignore-reassembly-memory-overflow {
                 description "Ignore packet reassembly memory overflow";
                 type empty;
               }
               leaf no-ignore-reassembly-memory-overflow {
                 description "Don't ignore packet reassembly memory overflow";
                 type empty;
               }
             }
             leaf ignore-reassembly-overflow {
               description "Ignore global reassembly overflow";
               type empty;
             }
             leaf max-packet-mem {
               description "Maximum packet memory";
               status deprecated;
               type union {
                 type string {
                   pattern "<.*>|$.*";
                 }
                 type uint32;
               }
             }
             leaf max-flow-mem {
               description "Maximum flow memory";
               type union {
                 type string {
                   pattern "<.*>|$.*";
                 }
                 type uint32;
               }
             }
             leaf max-packet-mem-ratio {
               description "Maximum packet memory ratio";
               type union {
                 type string {
                   pattern "<.*>|$.*";
                 }
                 type uint32;
               }
             }
             leaf action-on-reassembly-failure {
               description "Select the action on reassembly failures";
               default "drop";
               type enumeration {
                 enum "ignore" {
                   description "No action is taken.";
                 }
                 enum "drop" {
                   description "Drop the packet.";
                 }
                 enum "drop-session" {
                   description "Drop the session.";
                 }
               }
             }
             choice tcp-error-logging-choice {
               leaf tcp-error-logging {
                 description "Enable logging on tcp errors";
                 type empty;
               }
               leaf no-tcp-error-logging {
                 description "Don't enable logging on tcp errors";
                 type empty;
               }
             }
             leaf max-synacks-queued {
               description "Maximum syn-acks queued with different SEQ numbers ";
               type union {
                 type string {
                   pattern "<.*>|$.*";
                 }
                 type uint32;
               }
             }
             choice force-tcp-window-checks-choice {
               leaf force-tcp-window-checks {
                 description "Force TCP window checks if uni-directional policy is configured";
                 type empty;
               }
               leaf no-force-tcp-window-checks {
                 description "Don't force TCP window checks if uni-directional policy is configured";
                 type empty;
               }
             }
           }
           container ips {
             description "Ips configuration";
             uses apply-advanced;
             choice process-override-choice {
               leaf process-override {
                 description "Process override";
                 type empty;
               }
               leaf no-process-override {
                 description "Don't process override";
                 type empty;
               }
             }
             choice detect-shellcode-choice {
               leaf detect-shellcode {
                 description "Detect shellcode";
                 type empty;
               }
               leaf no-detect-shellcode {
                 description "Don't detect shellcode";
                 type empty;
               }
             }
             choice process-ignore-s2c-choice {
               leaf process-ignore-s2c {
                 description "Process ignore s2c";
                 type empty;
               }
               leaf no-process-ignore-s2c {
                 description "Don't process ignore s2c";
                 type empty;
               }
             }
             choice ignore-regular-expression-choice {
               leaf ignore-regular-expression {
                 description "Ignore regular expression";
                 type empty;
               }
               leaf no-ignore-regular-expression {
                 description "Don't ignore regular expression";
                 type empty;
               }
             }
             leaf process-port {
               description "Process port";
               type union {
                 type string {
                   pattern "<.*>|$.*";
                 }
                 type uint32;
               }
             }
             leaf fifo-max-size {
               description "Maximum fifo size";
               type union {
                 type string {
                   pattern "<.*>|$.*";
                 }
                 type uint32;
               }
             }
             leaf log-supercede-min {
               description "Minimum log supercede";
               type union {
                 type string {
                   pattern "<.*>|$.*";
                 }
                 type uint32;
               }
             }
             leaf content-decompression-max-memory-kb {
               description "Maximum memory usage in kilo bytes";
               type union {
                 type string {
                   pattern "<.*>|$.*";
                 }
                 type uint32;
               }
             }
             leaf content-decompression-max-ratio {
               description "Maximum decompression ratio supported";
               type union {
                 type string {
                   pattern "<.*>|$.*";
                 }
                 type uint32;
               }
             }
             leaf session-pkt-depth {
               description "Session pkt scanning depth";
               type union {
                 type string {
                   pattern "<.*>|$.*";
                 }
                 type uint32;
               }
             }
           }
           container global {
             description "Global configuration";
             uses apply-advanced;
             choice enable-packet-pool-choice {
               leaf enable-packet-pool {
                 description "Enable packet pool";
                 type empty;
               }
               leaf no-enable-packet-pool {
                 description "Don't enable packet pool";
                 type empty;
               }
             }
             choice enable-all-qmodules-choice {
               leaf enable-all-qmodules {
                 description "Enable all qmodules";
                 type empty;
               }
               leaf no-enable-all-qmodules {
                 description "Don't enable all qmodules";
                 type empty;
               }
             }
             choice policy-lookup-cache-choice {
               leaf policy-lookup-cache {
                 description "Policy lookup cache";
                 type empty;
               }
               leaf no-policy-lookup-cache {
                 description "Don't policy lookup cache";
                 type empty;
               }
             }
             leaf memory-limit-percent {
               description "Memory limit percentage";
               type union {
                 type string {
                   pattern "<.*>|$.*";
                 }
                 type uint32;
               }
             }
           }
           container detector {
             description "Detector Configuration";
             uses apply-advanced;
             list protocol-name {
               key name;
               ordered-by user;
               description "Apropriate help string";
               uses proto-object;
             }
           }
           container ssl-inspection {
             description "SSL inspection";
             uses apply-advanced;
             leaf sessions {
               description "Number of SSL sessions to inspect";
               default "10000";
               type union {
                 type string {
                   pattern "<.*>|$.*";
                 }
                 type uint32;
               }
             }
             leaf session-id-cache-timeout {
               description "Timeout value for SSL session ID cache";
               default "600";
               units "seconds";
               type union {
                 type string {
                   pattern "<.*>|$.*";
                 }
                 type uint32;
               }
             }
             leaf maximum-cache-size {
               description "Maximum SSL session ID cache size";
               default "100000";
               units "sessions";
               type union {
                 type string {
                   pattern "<.*>|$.*";
                 }
                 type uint32;
               }
             }
             leaf cache-prune-chunk-size {
               description "Number of cache entries to delete when pruning SSL session ID cache";
               default "100";
               type union {
                 type string {
                   pattern "<.*>|$.*";
                 }
                 type uint32;
               }
             }
             leaf key-protection {
               description "Enable SSL key protection";
               type empty;
             }
           }
           leaf disable-low-memory-handling {
             description "Do not abort IDP operations under low memory condition";
             type empty;
           }
           container high-availability {
             description "High availability configuration";
             uses apply-advanced;
             leaf no-policy-cold-synchronization {
               description "Disable policy cold synchronization";
               type empty;
             }
           }
           container security-configuration {
             description "IDP security configuration";
             uses apply-advanced;
             leaf protection-mode {
               description "Enable security protection mode";
               type enumeration {
                 enum "datacenter" {
                   description "Security protection mode for datacenter";
                 }
                 enum "datacenter-full" {
                   description "Full security protection mode for datacenter";
                 }
                 enum "perimeter" {
                   description "Security protection mode for perimeter";
                 }
                 enum "perimeter-full" {
                   description "Full security protection mode for perimeter";
                 }
               }
             }
           }
         }
         leaf max-sessions {
           description "Max number of IDP sessions";
           type union {
             type uint32;
             type string {
               pattern "<.*>|$.*";
             }
           }
         }
         list logical-system {
           key name;
           ordered-by user;
           description "Configure max IDP sessions for the logial system";
           uses logical-system-type;
         }
         uses apply-advanced;
         container processes {
           description "Configure IDP Processes";
           uses apply-advanced;
         }
       }
       list address-book {
         key name;
         ordered-by user;
         description "Security address book";
         max-elements 4096;
         uses named-address-book-type;
       }
       container alg {
         description "Configure ALG security options";
         uses alg-object;
       }
       container application-firewall {
         presence "enable application-firewall";
         description "Configure application-firewall rule-sets";
         status deprecated;
         uses apply-advanced;
         container traceoptions {
           description "Rule-sets Tracing Options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "configuration" {
                   description "Trace configuration events";
                 }
                 enum "lookup" {
                   description "Trace lookup events";
                 }
                 enum "compilation" {
                   description "Rule-sets compilation events";
                 }
                 enum "ipc" {
                   description "Inter-process communication events";
                 }
                 enum "all" {
                   description "Trace everything";
                 }
               }
             }
           }
         }
         list profile {
           key name;
           ordered-by user;
           description "Configure application-firewall profile";
           leaf name {
             description "Surf control integrated profile name";
             type string {
               length "1 .. 63";
             }
           }
           uses apply-advanced;
           container block-message {
             description "Block message settings";
             uses apply-advanced;
             container type {
               description "Type of block message desired";
               uses apply-advanced;
               choice type-choice {
                 case case_1 {
                   container custom-text {
                     description "Custom defined block message";
                     uses apply-advanced;
                     leaf content {
                       description "Content of custom-text";
                       type string {
                         length "1 .. 511";
                       }
                     }
                   }
                 }
                 case case_2 {
                   container custom-redirect-url {
                     description "Custom redirect URL server";
                     uses apply-advanced;
                     leaf content {
                       description "URL of block message";
                       type string {
                         length "1 .. 1023";
                       }
                     }
                   }
                 }
               }
             }
           }
         }
         list rule-sets {
           key name;
           ordered-by user;
           description "Configure application-firewall rule-sets";
           leaf name {
             description "Application firewall rule-set name";
             type string {
               length "1 .. 63";
             }
           }
           uses apply-advanced;
           list rule {
             key name;
             ordered-by user;
             description "Rule";
             uses appfw_rule_type;
           }
           container default-rule {
             presence "enable default-rule";
             description "Specify default rule for a rule-set";
             uses apply-advanced;
             choice action {
               case case_1 {
                 leaf permit {
                   description "Permit packets";
                   type empty;
                 }
               }
               case case_2 {
                 container deny {
                   presence "enable deny";
                   description "Deny packets";
                   uses apply-advanced;
                   leaf block-message {
                     description "Block message";
                     type empty;
                   }
                 }
               }
               case case_3 {
                 container reject {
                   presence "enable reject";
                   description "Reject packets";
                   uses apply-advanced;
                   leaf block-message {
                     description "Block message";
                     type empty;
                   }
                 }
               }
             }
           }
           leaf profile {
             description "Profile for block message";
             type string;
           }
         }
         container nested-application {
           presence "enable nested-application";
           description "Configure nested application dynamic lookup";
           status deprecated;
           uses apply-advanced;
           container dynamic-lookup {
             presence "enable dynamic-lookup";
             description "Configure dynamic lookup";
             uses apply-advanced;
             leaf enable {
               description "Enable dynamic lookup";
               type empty;
             }
           }
         }
       }
       container application-tracking {
         presence "enable application-tracking";
         description "Application tracking configuration";
         uses apply-advanced;
         leaf disable {
           description "Disable Application tracking";
           type empty;
         }
         choice update-interval {
           case case_1 {
             leaf first-update-interval {
               description "Interval when the first update message is sent";
               units "minutes";
               type union {
                 type uint32;
                 type string {
                   pattern "<.*>|$.*";
                 }
               }
             }
           }
           case case_2 {
             leaf first-update {
               description "Generate Application tracking initial message when a session is created";
               type empty;
             }
           }
         }
         leaf session-update-interval {
           description "Frequency in which Application tracking update messages are generated";
           units "minutes";
           type union {
             type uint32;
             type string {
               pattern "<.*>|$.*";
             }
           }
         }
       }
       container utm {
         description "Content security service configuration";
         uses apply-advanced;
         container traceoptions {
           description "Trace options for utm";
           uses utm-traceoptions;
         }
         container application-proxy {
           description "Application proxy settings";
           uses apply-advanced;
           container traceoptions {
             description "Trace options for application proxy";
             uses utm-apppxy-traceoptions;
           }
         }
         container ipc {
           description "IPC settings";
           uses apply-advanced;
           container traceoptions {
             description "Trace options for IPC";
             uses utm-ipc-traceoptions;
           }
         }
         container custom-objects {
           description "Custom-objects settings";
           uses apply-advanced;
           container category-package {
             description "Category package download and install options";
             uses apply-advanced;
             leaf url {
               description "HTTPS URL of category package download";
               type string;
             }
             leaf proxy-profile {
               description "Proxy profile";
               type string {
                 length "1 .. 64";
               }
             }
             leaf routing-instance {
               description "Routing instance name";
               type string;
             }
             container automatic {
               description "Scheduled download and install";
               uses apply-advanced;
               leaf start-time {
                 description "Start time (YYYY-MM-DD.HH:MM:SS)";
                 type jt:time;
               }
               leaf interval {
                 description "Interval in hours";
                 default "168";
                 type union {
                   type string {
                     pattern "<.*>|$.*";
                   }
                   type uint32 {
                     range "1 .. 336";
                   }
                 }
               }
               leaf enable {
                 description "Enable automatic download and install";
                 type empty;
               }
             }
           }
           list mime-pattern {
             key name;
             ordered-by user;
             description "Configure mime-list object";
             uses mime-list-type;
           }
           list filename-extension {
             key name;
             ordered-by user;
             description "Configure extension-list object";
             uses extension-list-type;
           }
           list url-pattern {
             key name;
             ordered-by user;
             description "Configure url-list object";
             uses url-list-type;
           }
           list custom-url-category {
             key name;
             ordered-by user;
             description "Configure category-list object";
             uses category-list-type;
           }
           list protocol-command {
             key name;
             ordered-by user;
             description "Configure command-list object";
             uses command-list-type;
           }
           list custom-message {
             key name;
             ordered-by user;
             description "Configure custom-message object";
             uses custom-message-type;
           }
         }
         container default-configuration {
           description "Global default UTM configurations";
           uses apply-advanced;
           container anti-virus {
             description "Configure anti-virus feature";
             uses default-anti-virus-feature;
           }
           container web-filtering {
             description "Configure web-filtering feature";
             uses default-webfilter-feature;
           }
           container anti-spam {
             description "Configure anti-spam feature";
             uses default-anti-spam-feature;
           }
           container content-filtering {
             description "Configure content filtering feature";
             uses default-content-filtering-feature;
           }
         }
         container feature-profile {
           description "Feature-profile settings";
           uses apply-advanced;
           container anti-virus {
             description "Configure anti-virus feature";
             uses anti-virus-feature;
           }
           container web-filtering {
             description "Configure web-filtering feature";
             uses webfilter-feature;
           }
           container anti-spam {
             description "Configure anti-spam feature";
             uses anti-spam-feature;
           }
           container content-filtering {
             description "Configure content filtering feature";
             uses content-filtering-feature;
           }
         }
         list utm-policy {
           key name;
           ordered-by user;
           description "Configure profile ";
           uses profile-setting;
         }
       }
       container dynamic-address {
         presence "enable dynamic-address";
         description "Configure security dynamic address";
         uses apply-advanced;
         container traceoptions {
           description "Security dynamic address tracing options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           leaf level {
             description "Level of debugging output";
             type enumeration {
               enum "error" {
                 description "Match error conditions";
               }
               enum "warning" {
                 description "Match warning messages";
               }
               enum "notice" {
                 description "Match conditions that should be handled specially";
               }
               enum "info" {
                 description "Match informational messages";
               }
               enum "verbose" {
                 description "Match verbose messages";
               }
               enum "all" {
                 description "Match all levels";
               }
             }
           }
           list flag {
             key name;
             ordered-by user;
             description "Tracing parameters";
             leaf name {
               type enumeration {
                 enum "configuration" {
                   description "Configuration details";
                 }
                 enum "control" {
                   description "Daemon control message";
                 }
                 enum "ipc" {
                   description "IPC message sending and receiving";
                 }
                 enum "ip-entry" {
                   description "IP entry management";
                 }
                 enum "file-retrieval" {
                   description "File retrieval";
                 }
                 enum "lookup" {
                   description "Lookup detail";
                 }
                 enum "all" {
                   description "Trace everything";
                 }
               }
             }
           }
         }
         list feed-server {
           key name;
           ordered-by user;
           description "Security dynamic address feed-server";
           leaf name {
             description "Security dynamic address feed-server name";
             type string {
               length "1 .. 16";
             }
           }
           uses apply-advanced;
           leaf description {
             description "Text description of feed-server";
             type string {
               length "1 .. 900";
             }
           }
           leaf hostname {
             description "Hostname or IP address of feed-server";
             type string {
               length "1 .. 256";
             }
           }
           leaf update-interval {
             description "Interval to retrieve update";
             default "300";
             units "seconds";
             type union {
               type string {
                 pattern "<.*>|$.*";
               }
               type uint32 {
                 range "30 .. 4294967295";
               }
             }
           }
           leaf hold-interval {
             description "Time to keep IP entry when update failed";
             default "86400";
             units "seconds";
             type union {
               type string {
                 pattern "<.*>|$.*";
               }
               type uint32 {
                 range "0 .. 4294967295";
               }
             }
           }
           list feed-name {
             key name;
             ordered-by user;
             description "Feed name in feed-server";
             leaf name {
               description "Security dynamic address feed name in feed-server";
               type string {
                 length "1 .. 240";
               }
             }
             uses apply-advanced;
             leaf description {
               description "Text description of feed in feed-server";
               type string {
                 length "1 .. 900";
               }
             }
             leaf path {
               description "Path of feed, appended to feed-server to form a complete URL";
               type string {
                 length "1 .. 1024";
               }
             }
             leaf update-interval {
               description "Interval to retrieve update";
               units "seconds";
               type union {
                 type string {
                   pattern "<.*>|$.*";
                 }
                 type uint32 {
                   range "30 .. 4294967295";
                 }
               }
             }
             leaf hold-interval {
               description "Time to keep IP entry when update failed";
               units "seconds";
               type union {
                 type string {
                   pattern "<.*>|$.*";
                 }
                 type uint32 {
                   range "0 .. 4294967295";
                 }
               }
             }
           }
         }
         list address-name {
           key name;
           ordered-by user;
           description "Security dynamic address name";
           leaf name {
             description "Security dynamic address name";
             type string {
               length "1 .. 240";
             }
           }
           uses apply-advanced;
           leaf description {
             description "Text description of dynamic address";
             type string {
               length "1 .. 900";
             }
           }
           container profile {
             presence "enable profile";
             description "Information to categorize feed data into this dynamic address";
             uses apply-advanced;
             list feed-name {
               key name;
               ordered-by user;
               description "Name of feed in feed-server for this dynamic address";
               max-elements 1;
               leaf name {
                 description "Name of feed in feed-server which is mapped to this dynamic address";
                 type string {
                   length "1 .. 240";
                 }
               }
               uses apply-advanced;
             }
             list category {
               key name;
               ordered-by user;
               description "Name of category";
               max-elements 1;
               leaf name {
                 description "Name of category";
                 type string {
                   length "1 .. 32";
                 }
               }
               uses apply-advanced;
               leaf feed {
                 description "Name of feed under category";
                 type string {
                   length "1 .. 32";
                 }
               }
               list property {
                 key name;
                 ordered-by user;
                 description "Property to match";
                 max-elements 3;
                 leaf name {
                   description "Name of property";
                   type string {
                     length "1 .. 32";
                   }
                 }
                 uses apply-advanced;
                 choice property-value {
                   case case_1 {
                     list string {
                       key name;
                       ordered-by user;
                       description "Value type is strings";
                       max-elements 256;
                       leaf name {
                         description "String value";
                         type string {
                           length "1 .. 32";
                         }
                       }
                       uses apply-advanced;
                     }
                   }
                 }
               }
             }
           }
         }
       }
       container dynamic-vpn {
         description "Configure dynamic VPN";
         uses apply-advanced;
         container traceoptions {
           description "Dynamic-vpn trace options";
           uses httpd_dvpn_traceoptions_type;
         }
         leaf force-upgrade {
           description "Force Upgrade";
           type empty;
         }
         leaf access-profile {
           description "Configure access";
           type string;
         }
         leaf-list interface {
           ordered-by user;
           description "Interfaces that accept Dynamic-VPN client access";
           type union {
             type jt:interface-name;
             type string {
               pattern "<.*>|$.*";
             }
           }
         }
         list clients {
           key name;
           ordered-by user;
           description "Configure for remote access client";
           uses clients-object;
         }
         leaf config-check {
           description "Perform extra configuration validation";
           type empty;
         }
       }
       container dynamic-application {
         presence "enable dynamic-application";
         description "Configure dynamic-application";
         uses apply-advanced;
         container traceoptions {
           description "Dynamic application tracing options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "configuration" {
                   description "Trace configuration events";
                 }
                 enum "lookup" {
                   description "Trace lookup events";
                 }
                 enum "compilation" {
                   description "Rule-sets compilation events";
                 }
                 enum "ipc" {
                   description "Inter-process communication events";
                 }
                 enum "all" {
                   description "Trace everything";
                 }
               }
             }
           }
         }
         list profile {
           key name;
           ordered-by user;
           description "Configure application-firewall profile";
           leaf name {
             description "Surf control integrated profile name";
             type string {
               length "1 .. 63";
             }
           }
           uses apply-advanced;
           container redirect-message {
             description "Redirect message settings";
             uses apply-advanced;
             container type {
               description "Type of redirect message desired";
               uses apply-advanced;
               choice type-choice {
                 case case_1 {
                   container custom-text {
                     description "Custom defined text block message";
                     uses apply-advanced;
                     leaf content {
                       description "Content of custom-text";
                       type string {
                         length "1 .. 511";
                       }
                     }
                   }
                 }
                 case case_2 {
                   container redirect-url {
                     description "Custom redirect URL server";
                     uses apply-advanced;
                     leaf content {
                       description "URL of block message";
                       type string {
                         length "1 .. 1023";
                       }
                     }
                   }
                 }
               }
             }
           }
         }
       }
       container softwires {
         description "Configure softwire feature";
         uses softwires-object;
       }
       container forwarding-options {
         description "Security-forwarding-options configuration";
         uses apply-advanced;
         container family {
           description "Security forwarding-options for family";
           uses apply-advanced;
           container inet6 {
             description "Family IPv6";
             uses apply-advanced;
             leaf mode {
               description "Forwarding mode";
               type enumeration {
                 enum "packet-based" {
                   description "Enable packet-based forwarding";
                 }
                 enum "flow-based" {
                   description "Enable flow-based forwarding";
                 }
                 enum "drop" {
                   description "Disable forwarding";
                 }
               }
             }
           }
           container mpls {
             description "Family MPLS";
             uses apply-advanced;
             leaf mode {
               description "Forwarding mode";
               type enumeration {
                 enum "packet-based" {
                   description "Enable packet-based forwarding";
                 }
                 enum "flow-based" {
                   description "Enable flow-based forwarding for mpls";
                 }
               }
             }
           }
           container iso {
             description "Family ISO";
             uses apply-advanced;
             leaf mode {
               description "Forwarding mode";
               type enumeration {
                 enum "packet-based" {
                   description "Enable packet-based forwarding";
                 }
               }
             }
           }
         }
         list mirror-filter {
           key name;
           ordered-by user;
           description "Security mirror filters";
           max-elements 15;
           uses mirror-filter-type;
         }
         list secure-wire {
           key name;
           description "Secure-wire cross connections";
           uses secure-wire-type;
         }
         container mode {
           description "Tap or sniffer mode";
           uses apply-advanced;
           container tap {
             description "Tap mode";
             uses apply-advanced;
             leaf interface {
               description "Tap enabled interface";
               type union {
                 type jt:interface-name;
                 type string {
                   pattern "<.*>|$.*";
                 }
               }
             }
           }
         }
       }
       container advanced-services {
         description "Advanced services configuration";
         uses apply-advanced;
         container data-plane {
           description "Data plane configuration";
           uses apply-advanced;
           container memory {
             description "Data plane memory configuration";
             uses apply-advanced;
             leaf low {
               description "Reduce data plane memory";
               type empty;
             }
           }
         }
       }
       container flow {
         description "FLOW configuration";
         uses apply-advanced;
         leaf enhanced-routing-mode {
           description "Enable enhanced route scaling";
           type empty;
         }
         container traceoptions {
           description "Trace options for flow services";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Events and other information to include in trace output";
             leaf name {
               type enumeration {
                 enum "all" {
                   description "All events";
                 }
                 enum "basic-datapath" {
                   description "Basic packet flow";
                 }
                 enum "high-availability" {
                   description "Flow high-availability information";
                 }
                 enum "host-traffic" {
                   description "Flow host-traffic information";
                 }
                 enum "fragmentation" {
                   description "Ip fragmentation and reassembly events";
                 }
                 enum "multicast" {
                   description "Multicast flow information";
                 }
                 enum "route" {
                   description "Route lookup information";
                 }
                 enum "session" {
                   description "Session creation and deletion events";
                 }
                 enum "session-scan" {
                   description "Session scan information";
                 }
                 enum "tcp-basic" {
                   description "TCP packet flow";
                 }
                 enum "tunnel" {
                   description "Tunnel information";
                 }
               }
             }
           }
           leaf rate-limit {
             description "Limit the incoming rate of trace messages";
             default "0";
             type union {
               type string {
                 pattern "<.*>|$.*";
               }
               type uint32 {
                 range "0 .. 4294967295";
               }
             }
           }
           list packet-filter {
             key name;
             ordered-by user;
             description "Flow packet debug filters";
             max-elements 64;
             uses flow-filter-type;
           }
           container trace-level {
             description "FLow trace level";
             uses apply-advanced;
             choice level {
               case case_1 {
                 leaf error {
                   description "Error messages";
                   type empty;
                 }
               }
               case case_2 {
                 leaf brief {
                   description "Brief messages";
                   type empty;
                 }
               }
               case case_3 {
                 leaf detail {
                   description "Detail messages";
                   type empty;
                 }
               }
             }
           }
         }
         leaf pending-sess-queue-length {
           description "Maximum queued length per pending session";
           default "normal";
           type enumeration {
             enum "normal" {
               description "Normal number of sessions queued";
             }
             enum "moderate" {
               description "Allow more queued sessions than normal";
             }
             enum "high" {
               description "Maximum number of queued sessions";
             }
           }
         }
         container enable-reroute-uniform-link-check {
           description "Enable reroute check with uniform link";
           uses apply-advanced;
           leaf nat {
             description "Enable NAT check";
             type empty;
           }
         }
         leaf allow-dns-reply {
           description "Allow unmatched incoming DNS reply packet";
           type empty;
         }
         leaf route-change-timeout {
           description "Timeout value for route change to nonexistent route";
           default "6";
           units "seconds";
           type union {
             type string {
               pattern "<.*>|$.*";
             }
             type uint32 {
               range "6 .. 1800";
             }
           }
         }
         leaf syn-flood-protection-mode {
           description "TCP SYN flood protection mode";
           default "syn-cookie";
           type enumeration {
             enum "syn-cookie" {
               description "Enable SYN cookie protection";
             }
             enum "syn-proxy" {
               description "Enable SYN proxy protection";
             }
           }
         }
         leaf allow-embedded-icmp {
           description "Allow embedded ICMP packets not matching a session to pass through";
           type empty;
         }
         leaf mcast-buffer-enhance {
           description "Allow to hold more packets during multicast session creation";
           type empty;
         }
         leaf allow-reverse-ecmp {
           description "Allow reverse ECMP route lookup";
           type empty;
         }
         leaf no-local-favor-ecmp {
           description "Not prefer local node in HA ECMP route lookup";
           type empty;
         }
         leaf sync-icmp-session {
           description "Allow icmp sessions to sync to peer node";
           type empty;
         }
         leaf ipsec-performance-acceleration {
           description "Accelerate the IPSec traffic performance";
           type empty;
         }
         container aging {
           description "Aging configuration";
           uses apply-advanced;
           leaf early-ageout {
             description "Delay before device declares session invalid";
             default "20";
             units "seconds";
             type union {
               type string {
                 pattern "<.*>|$.*";
               }
               type uint32 {
                 range "1 .. 65535";
               }
             }
           }
           leaf low-watermark {
             description "Percentage of session-table capacity at which aggressive aging-out ends";
             default "100";
             units "percent";
             type union {
               type string {
                 pattern "<.*>|$.*";
               }
               type uint32 {
                 range "0 .. 100";
               }
             }
           }
           leaf high-watermark {
             description "Percentage of session-table capacity at which aggressive aging-out starts";
             default "100";
             units "percent";
             type union {
               type string {
                 pattern "<.*>|$.*";
               }
               type uint32 {
                 range "0 .. 100";
               }
             }
           }
         }
         container ethernet-switching {
           description "Ethernet-switching configuration for flow";
           uses apply-advanced;
           leaf block-non-ip-all {
             description "Block all non-IP and non-ARP traffic including broadcast/multicast";
             type empty;
           }
           leaf bypass-non-ip-unicast {
             description "Allow all non-IP (including unicast) traffic";
             type empty;
           }
           container no-packet-flooding {
             presence "enable no-packet-flooding";
             description "Stop IP flooding, send ARP/ICMP to trigger MAC learning";
             uses apply-advanced;
             leaf no-trace-route {
               description "Don't send ICMP to trigger MAC learning";
               type empty;
             }
           }
           leaf bpdu-vlan-flooding {
             description "Set 802.1D BPDU flooding based on VLAN";
             type empty;
           }
         }
         container tcp-mss {
           description "TCP maximum segment size configuration";
           uses apply-advanced;
           container all-tcp {
             description "Enable MSS override for all packets";
             uses apply-advanced;
             leaf mss {
               description "MSS value";
               type union {
                 type string {
                   pattern "<.*>|$.*";
                 }
                 type uint32 {
                   range "64 .. 65535";
                 }
               }
             }
           }
           container ipsec-vpn {
             presence "enable ipsec-vpn";
             description "Enable MSS override for all packets entering IPSec tunnel";
             uses apply-advanced;
             leaf mss {
               description "MSS value";
               default "1320";
               type union {
                 type string {
                   pattern "<.*>|$.*";
                 }
                 type uint32 {
                   range "64 .. 65535";
                 }
               }
             }
           }
           container gre-in {
             presence "enable gre-in";
             description "Enable MSS override for all GRE packets coming out of an IPSec tunnel";
             uses apply-advanced;
             leaf mss {
               description "MSS value";
               default "1320";
               type union {
                 type string {
                   pattern "<.*>|$.*";
                 }
                 type uint32 {
                   range "64 .. 65535";
                 }
               }
             }
           }
           container gre-out {
             presence "enable gre-out";
             description "Enable MSS override for all GRE packets entering an IPsec tunnel";
             uses apply-advanced;
             leaf mss {
               description "MSS value";
               default "1320";
               type union {
                 type string {
                   pattern "<.*>|$.*";
                 }
                 type uint32 {
                   range "64 .. 65535";
                 }
               }
             }
           }
         }
         container tcp-session {
           description "Transmission Control Protocol session configuration";
           uses apply-advanced;
           leaf rst-invalidate-session {
             description "Immediately end session on receipt of reset (RST) segment";
             type empty;
           }
           leaf fin-invalidate-session {
             description "Immediately end session on receipt of fin (FIN) segment";
             type empty;
           }
           leaf rst-sequence-check {
             description "Check sequence number in reset (RST) segment";
             type empty;
           }
           leaf no-syn-check {
             description "Disable creation-time SYN-flag check";
             type empty;
           }
           leaf strict-syn-check {
             description "Enable strict syn check";
             type empty;
           }
           leaf no-syn-check-in-tunnel {
             description "Disable creation-time SYN-flag check for tunnel packets";
             type empty;
           }
           leaf no-sequence-check {
             description "Disable sequence-number checking";
             type empty;
           }
           leaf aggressive-tcp-ack {
             description "Enable aggressive TCP ACK, root lsys only";
             type empty;
           }
           leaf tcp-initial-timeout {
             description "Timeout for TCP session when initialization fails";
             default "20";
             units "seconds";
             type union {
               type string {
                 pattern "<.*>|$.*";
               }
               type uint32 {
                 range "4 .. 300";
               }
             }
           }
           leaf maximum-window {
             description "Maximum TCP proxy scaled receive window, default 256K bytes";
             default "256K";
             type enumeration {
               enum "64K" {
                 description "64K bytes receive window";
               }
               enum "128K" {
                 description "128K bytes receive window";
               }
               enum "256K" {
                 description "256K bytes receive window";
               }
               enum "512K" {
                 description "512K bytes receive window";
               }
               enum "1M" {
                 description "1M bytes receive window";
               }
             }
           }
           container time-wait-state {
             presence "enable time-wait-state";
             description "Session timeout value in time-wait state, default 150 seconds";
             uses apply-advanced;
             choice session-age-option {
               case case_1 {
                 leaf session-ageout {
                   description "Allow session to ageout using service based timeout values";
                   type empty;
                 }
               }
               case case_2 {
                 leaf session-timeout {
                   description "Configure session timeout value for time-wait state";
                   units "seconds";
                   type union {
                     type string {
                       pattern "<.*>|$.*";
                     }
                     type uint32 {
                       range "2 .. 600";
                     }
                   }
                 }
               }
             }
             leaf apply-to-half-close-state {
               description "Apply time-wait-state timeout to half-close state";
               type empty;
             }
           }
         }
         leaf force-ip-reassembly {
           description "Force to reassemble ip fragments";
           type empty;
         }
         leaf preserve-incoming-fragment-size {
           description "Preserve incoming fragment size for egress MTU";
           type empty;
         }
         container log {
           description "Enable log";
           uses apply-advanced;
           leaf dropped-icmp-packet {
             description "Log dropped ICMPv4 packet";
             type empty;
           }
           leaf dropped-illegal-packet {
             description "Log dropped illegal packet";
             type empty;
           }
         }
         container advanced-options {
           description "Flow config advanced options";
           uses apply-advanced;
           leaf drop-matching-reserved-ip-address {
             description "Drop matching reserved source IP address";
             type empty;
           }
           leaf drop-matching-link-local-address {
             description "Drop matching link local address";
             type empty;
           }
           leaf reverse-route-packet-mode-vr {
             description "Allow reverse route lookup with packet mode vr";
             type empty;
           }
         }
         container load-distribution {
           description "Flow config SPU load distribution";
           uses apply-advanced;
           container session-affinity {
             description "SPU load distribution based on the service anchor SPU";
             uses apply-advanced;
             leaf ipsec {
               description "IPsec service";
               type empty;
             }
           }
         }
         container packet-log {
           description "Configure flow packet log";
           uses apply-advanced;
           leaf enable {
             description "Enable log for dropped packet";
             type empty;
           }
           leaf throttle-interval {
             description "Interval should be configured as a power of two";
             default "1024";
             units "milliseconds";
             type union {
               type string {
                 pattern "<.*>|$.*";
               }
               type uint32 {
                 range "0 .. 32768";
               }
             }
           }
           list packet-filter {
             key name;
             ordered-by user;
             description "Configure packet log filter";
             max-elements 64;
             uses flow-filter-type;
           }
         }
         leaf power-mode-ipsec {
           description "Enable power mode ipsec processing";
           type empty;
         }
       }
       container firewall-authentication {
         description "Firewall authentication parameters";
         uses apply-advanced;
         container traceoptions {
           description "Data-plane firewall authentication tracing options";
           uses apply-advanced;
           list flag {
             key name;
             ordered-by user;
             description "Events to include in trace output";
             leaf name {
               type enumeration {
                 enum "authentication" {
                   description "Data-plane firewall authentication events";
                 }
                 enum "proxy" {
                   description "Data-plane firewall authentication proxy events";
                 }
                 enum "all" {
                   description "All events";
                 }
               }
             }
             choice level {
               case case_1 {
                 leaf terse {
                   description "Include terse amount of output in trace";
                   type empty;
                 }
               }
               case case_2 {
                 leaf detail {
                   description "Include detailed amount of output in trace";
                   type empty;
                 }
               }
               case case_3 {
                 leaf extensive {
                   description "Include extensive amount of output in trace";
                   type empty;
                 }
               }
             }
           }
         }
       }
       container screen {
         description "Configure screen feature";
         uses apply-advanced;
         container trap {
           presence "enable trap";
           description "Configure trap interval";
           leaf interval {
             description "Trap interval";
             default "2";
             units "seconds";
             type union {
               type string {
                 pattern "<.*>|$.*";
               }
               type uint32 {
                 range "1 .. 3600";
               }
             }
           }
         }
         list ids-option {
           key name;
           description "Configure ids-option";
           uses ids-option-type;
         }
         container traceoptions {
           description "Trace options for Network Security Screen";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "configuration" {
                   description "Trace configuration events";
                 }
                 enum "flow" {
                   description "Trace flow events";
                 }
                 enum "all" {
                   description "Trace everything";
                 }
               }
             }
           }
         }
         list white-list {
           key name;
           description "Set of IP addresses for white list";
           max-elements 32;
           uses ids-wlist-type;
         }
       }
       container nat {
         description "Configure Network Address Translation";
         uses nat-object;
       }
       container forwarding-process {
         description "Configure security forwarding-process options";
         uses apply-advanced;
         leaf enhanced-services-mode {
           description "Enable enhanced application services mode";
           type empty;
         }
         container application-services {
           description "Configure application service options";
           uses apply-advanced;
           leaf maximize-alg-sessions {
             description "Maximize ALG session capacity";
             type empty;
           }
           leaf maximize-persistent-nat-capacity {
             description "Increase persistent NAT capacity by reducing maximum flow sessions";
             type empty;
           }
           container maximize-cp-sessions {
             presence "enable maximize-cp-sessions";
             description "Maximize CP session capacity";
             status deprecated;
             uses apply-advanced;
           }
           leaf session-distribution-mode {
             description "Session distribution mode";
             status deprecated;
             type enumeration {
               enum "normal" {
                 description "Normal mode";
                 status deprecated;
               }
               enum "hash-based" {
                 description "Hash mode";
                 status deprecated;
               }
             }
           }
           leaf enable-gtpu-distribution {
             description "Enable GTP-U distribution";
             type empty;
           }
           leaf packet-ordering-mode {
             description "Packet ordering mode";
             type enumeration {
               enum "hardware" {
                 description "Hardware mode";
               }
               enum "software" {
                 description "Software mode";
               }
             }
           }
           container maximize-idp-sessions {
             presence "enable maximize-idp-sessions";
             description "Run security services in dedicated processes to maximize IDP session capacity";
             uses apply-advanced;
             container weight {
               description "Adjust the weighting of the resources available for idp";
               uses apply-advanced;
               choice weight {
                 case case_1 {
                   leaf equal {
                     description "Equal resources to IDP and firewall";
                     status deprecated;
                     type empty;
                   }
                 }
                 case case_2 {
                   container idp {
                     presence "enable idp";
                     description "IDP has more resources than firewall";
                     uses apply-advanced;
                   }
                 }
                 case case_3 {
                   leaf firewall {
                     description "Firewall has more resources than IDP";
                     type empty;
                   }
                 }
               }
             }
             leaf inline-tap {
               description "Configure IDP in inline tap mode";
               type empty;
             }
           }
         }
       }
       container policies {
         description "Configure Network Security Policies";
         presence "enable policies";
         uses policy-object-type;
       }
       container tcp-encap {
         presence "enable tcp-encap";
         description "Configure TCP Encapsulation.";
         uses apply-advanced;
         container traceoptions {
           description "Trace options for TCP encapsulation service";
           uses ragw-traceoptions;
         }
         list profile {
           key name;
           ordered-by user;
           description "Configure profile.";
           leaf name {
             description "Profile name identifier.";
             type string {
               length "1 .. 64";
             }
           }
           uses apply-advanced;
           leaf ssl-profile {
             description "SSL Termination profile";
             type string;
           }
           leaf log {
             description "Enable logging for remote-access";
             type empty;
           }
         }
         container global-options {
           description "Global settings for TCP encapsulation";
           leaf enable-tunnel-tracking {
             description "Track ESP tunnels";
             type empty;
           }
         }
       }
       container resource-manager {
         description "Configure resource manager security options";
         uses apply-advanced;
         container traceoptions {
           description "Traceoptions for resource manager";
           uses apply-advanced;
           list flag {
             key name;
             ordered-by user;
             description "Resource manager objects and events to include in trace";
             leaf name {
               type enumeration {
                 enum "client" {
                   description "Trace resource manager client";
                 }
                 enum "group" {
                   description "Trace resource manager group";
                 }
                 enum "resource" {
                   description "Trace resource manager resource";
                 }
                 enum "gate" {
                   description "Trace resource manager created gates";
                 }
                 enum "session" {
                   description "Trace resource manager created session";
                 }
                 enum "chassis cluster" {
                   description "Trace resource manager's chassis cluster events";
                 }
                 enum "messaging" {
                   description "Trace resource manager messaging";
                 }
                 enum "service pinhole" {
                   description "Trace resource manager created service pinholes";
                 }
                 enum "error" {
                   description "Trace all resource manager errors";
                 }
                 enum "all" {
                   description "Trace all resource manager objects and events";
                 }
               }
             }
             choice level {
               case case_1 {
                 leaf terse {
                   description "Set trace verbosity level to terse";
                   type empty;
                 }
               }
               case case_2 {
                 leaf detail {
                   description "Set trace verbosity level to detail";
                   type empty;
                 }
               }
               case case_3 {
                 leaf extensive {
                   description "Set trace verbosity level to extensive";
                   type empty;
                 }
               }
             }
           }
         }
       }
       container analysis {
         description "Configure security analysis";
         uses apply-advanced;
         leaf no-report {
           description "Stops security analysis reporting";
           type empty;
         }
       }
       container traceoptions {
         description "Network security daemon tracing options";
         uses apply-advanced;
         leaf no-remote-trace {
           description "Disable remote tracing";
           type empty;
         }
         container file {
           description "Trace file information";
           leaf filename {
             description "Name of file in which to write trace information";
             type string {
               length "1 .. 1024";
             }
           }
           leaf size {
             description "Maximum trace file size";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           ordered-by user;
           description "Tracing parameters";
           leaf name {
             type enumeration {
               enum "configuration" {
                 description "Trace configuration events";
               }
               enum "routing-socket" {
                 description "Trace routing socket events";
               }
               enum "compilation" {
                 description "Trace compilation events";
               }
               enum "all" {
                 description "Trace everything";
               }
             }
           }
         }
         leaf rate-limit {
           description "Limit the incoming rate of trace messages";
           default "0";
           type union {
             type string {
               pattern "<.*>|$.*";
             }
             type uint32 {
               range "0 .. 4294967295";
             }
           }
         }
       }
       container datapath-debug {
         description "Datapath debug options";
         uses apply-advanced;
         container traceoptions {
           description "End to end debug trace options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
         }
         container capture-file {
           description "Packet capture options";
           leaf filename {
             description "Capture file name";
             type string;
           }
           leaf format {
             description "Capture file format";
             type enumeration {
               enum "pcap" {
                 description "PCAP capture format";
               }
             }
           }
           leaf size {
             description "Maximum file size";
             type string;
           }
           leaf files {
             description "Maximum number of files";
             type union {
               type string {
                 pattern "<.*>|$.*";
               }
               type uint32 {
                 range "1 .. 10";
               }
             }
           }
           choice world-readable-choice {
             leaf world-readable {
               description "Allow any user to read packet-capture files";
               type empty;
             }
             leaf no-world-readable {
               description "Don't allow any user to read packet-capture files";
               type empty;
             }
           }
         }
         leaf maximum-capture-size {
           description "Max packet capture length";
           default "68";
           units "bytes";
           type union {
             type string {
               pattern "<.*>|$.*";
             }
             type uint32 {
               range "68 .. 10000";
             }
           }
         }
         list action-profile {
           key name;
           ordered-by user;
           description "Action profile definitions";
           uses e2e-action-profile;
         }
         list packet-filter {
           key name;
           ordered-by user;
           description "Packet filter configuration";
           max-elements 4;
           uses end-to-end-debug-filter;
         }
       }
       container user-identification {
         description "Configure user-identification";
         uses apply-advanced;
         container traceoptions {
           description "User-identification Tracing Options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "all" {
                   description "Trace everything";
                 }
               }
             }
           }
         }
         list authentication-source {
           key name;
           description "Configure user-identification authentication-source";
           uses authentication-source-type;
         }
       }
       container zones {
         description "Zone configuration";
         uses apply-advanced;
         container functional-zone {
           presence "enable functional-zone";
           description "Functional zone";
           container management {
             presence "enable management";
             description "Host for out of band management interfaces";
             uses apply-advanced;
             list interfaces {
               key name;
               ordered-by user;
               description "Interfaces that are part of this zone";
               uses zone-interface-list-type;
             }
             leaf screen {
               description "Name of ids option object applied to the zone";
               type string {
                 length "1 .. 64";
               }
             }
             container host-inbound-traffic {
               description "Allowed system services & protocols";
               uses zone_host_inbound_traffic_t;
             }
             leaf description {
               description "Text description of zone";
               type string {
                 length "1 .. 900";
               }
             }
           }
         }
         list security-zone {
           key name;
           ordered-by user;
           description "Security zones";
           uses security-zone-type;
         }
       }
       container advance-policy-based-routing {
         presence "enable advance-policy-based-routing";
         description "Configure Network Security APBR Policies";
         uses apply-advanced;
         container traceoptions {
           description "Advance policy based routing tracing options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "configuration" {
                   description "Trace configuration events";
                 }
                 enum "lookup" {
                   description "Trace lookup events";
                 }
                 enum "compilation" {
                   description "Rule-sets compilation events";
                 }
                 enum "ipc" {
                   description "Inter-process communication events";
                 }
                 enum "all" {
                   description "Trace everything";
                 }
               }
             }
           }
         }
         container tunables {
           description "Configure advance policy based routing tunables";
           uses apply-advanced;
           leaf max-route-change {
             description "Maximum route change";
             default "1";
             type union {
               type string {
                 pattern "<.*>|$.*";
               }
               type uint32 {
                 range "0 .. 5";
               }
             }
           }
           leaf drop-on-zone-mismatch {
             description "Drop session if zone mismatches";
             type empty;
           }
           leaf enable-logging {
             description "Enable AppTrack logging";
             type empty;
           }
         }
         list profile {
           key name;
           ordered-by user;
           description "Configure advance-policy-based-routing profile";
           leaf name {
             description "Advance policy based routing profile name";
             type string {
               length "1 .. 63";
             }
           }
           uses apply-advanced;
           list rule {
             key name;
             ordered-by user;
             description "Specify an advance policy based routing rule";
             uses apbr_rule_type;
           }
         }
         list active-probe-params {
           key name;
           ordered-by user;
           description "Active probe's settings";
           max-elements 32;
           leaf name {
             description "Active probe setting name";
             type string {
               length "1 .. 63";
             }
           }
           uses apply-advanced;
           container settings {
             description "Settings";
             uses appqoe-probe-params;
           }
         }
         list metrics-profile {
           key name;
           ordered-by user;
           description "Configure metric profiles";
           max-elements 32;
           leaf name {
             description "Profile name";
             type string {
               length "1 .. 63";
             }
           }
           uses apply-advanced;
           container sla-threshold {
             description "Configure SLA metric threshold";
             uses appqoe_sla_metric_profile;
           }
         }
         list underlay-interface {
           key name;
           ordered-by user;
           description "Underlay interface setting";
           max-elements 99;
           leaf name {
             description "Underlay Interface name";
             type union {
               type jt:interface-device;
               type string {
                 pattern "<.*>|$.*";
               }
             }
           }
           uses apply-advanced;
           list unit {
             key name;
             description "One of more logical interface unit-numbers";
             leaf name {
               description "Unit number";
               type union {
                 type string {
                   pattern "<.*>|$.*";
                 }
                 type uint32 {
                   range "0 .. 1073741823";
                 }
               }
             }
             uses apply-advanced;
             leaf link-type {
               description "Link type of the interface";
               default "IP";
               type enumeration {
                 enum "IP" {
                   description "Select IP as the link-type";
                 }
                 enum "MPLS" {
                   description "Select MPLS as the link-type";
                 }
               }
             }
             leaf priority {
               description "Configure the priority for selecting this link";
               default "255";
               type union {
                 type string {
                   pattern "<.*>|$.*";
                 }
                 type uint8 {
                   range "1 .. 255";
                 }
               }
             }
           }
         }
         list overlay-path {
           key name;
           ordered-by user;
           description "List of overlay paths";
           max-elements 100;
           leaf name {
             description "Create a single instance of overlay path";
             type string {
               length "1 .. 63";
             }
           }
           uses apply-advanced;
           container tunnel-path {
             description "Tunnel start & end ip addresses";
             presence "enable tunnel-path";
             uses appqoe-probe-path;
           }
           container probe-path {
             description "Probe start & end ip addresses";
             presence "enable probe-path";
             uses appqoe-probe-path;
           }
         }
         list destination-path-group {
           key name;
           ordered-by user;
           description "Group of tunnels to a particular destination";
           max-elements 50;
           leaf name {
             description "Destination group name";
             type string {
               length "1 .. 63";
             }
           }
           uses apply-advanced;
           container probe-routing-instance {
             presence "enable probe-routing-instance";
             description "Set routing instance for the probe-path";
             uses apply-advanced;
             leaf routing-instance-name {
               description "Name of routing instance";
               type string;
             }
           }
           container inline-gre-encap {
             presence "enable inline-gre-encap";
             description "Enable inline GRE encapsulation";
           }
           list overlay-path {
             key name;
             ordered-by user;
             description "List of paths";
             max-elements 20;
             leaf name {
               description "Name of Overlay Path";
               type string;
             }
             uses apply-advanced;
           }
         }
         container sla-options {
           presence "enable sla-options";
           description "Global SLA options";
           uses apply-advanced;
           container local-route-switch {
             presence "enable local-route-switch";
             description "Enable/disable Automatic local route switching";
             uses apply-advanced;
             leaf switch-type {
               type enumeration {
                 enum "enabled" {
                   description "Enable";
                 }
                 enum "disabled" {
                   description "Disable";
                 }
               }
             }
           }
           container log-type {
             presence "enable log-type";
             description "Choose the logging mechanism";
             uses apply-advanced;
             leaf log {
               type enumeration {
                 enum "syslog" {
                   description "Choose syslog";
                 }
               }
             }
           }
           container max-passive-probe-limit {
             presence "enable max-passive-probe-limit";
             description "Set max passive probe limits";
             uses apply-advanced;
             container number-of-probes {
               presence "enable number-of-probes";
               description "Number of passive probes to be sent";
               uses apply-advanced;
               leaf probes {
                 description "Number of probes";
                 default "5000";
                 type union {
                   type string {
                     pattern "<.*>|$.*";
                   }
                   type uint32 {
                     range "10 .. 5000";
                   }
                 }
               }
             }
             container interval {
               presence "enable interval";
               description "Interval within which to send";
               uses apply-advanced;
               leaf refresh-interval {
                 description "Interval in milli seconds";
                 default "500";
                 type union {
                   type string {
                     pattern "<.*>|$.*";
                   }
                   type uint32 {
                     range "500 .. 1000";
                   }
                 }
               }
             }
           }
         }
         list sla-rule {
           key name;
           ordered-by user;
           description "Create SLA rule";
           max-elements 640;
           leaf name {
             description "Set rule name";
             type string {
               length "1 .. 63";
             }
           }
           uses apply-advanced;
           leaf preferred-link-type {
             description "Configure the link-type preference";
             default "Any";
             type enumeration {
               enum "IP" {
                 description "IP link-type preference";
               }
               enum "MPLS" {
                 description "MPLS link-type preference";
               }
               enum "Any" {
                 description "Any link-type preference";
               }
             }
           }
           leaf link-type-affinity {
             description "Configure the link-type affinity";
             type enumeration {
               enum "strict" {
                 description "Strict link-type affinity";
               }
             }
           }
           container switch-idle-time {
             presence "enable switch-idle-time";
             description "Idle timeout period where no SLA violation will be detected once path switch has happened";
             uses apply-advanced;
             leaf timeout {
               description "Idle timeout period (in seconds)";
               type union {
                 type string {
                   pattern "<.*>|$.*";
                 }
                 type uint32 {
                   range "5 .. 300";
                 }
               }
             }
           }
           container metrics-profile {
             presence "enable metrics-profile";
             description "Set metrics profile for the SLA";
             uses apply-advanced;
             leaf metrics-profile-name {
               description "Metrics Profile name";
               type string;
             }
           }
           container active-probe-params {
             presence "enable active-probe-params";
             description "Set Probe params for the overlay-path";
             uses apply-advanced;
             leaf probe-params-name {
               description "Probe parameter's name";
               type string;
             }
           }
           container passive-probe-params {
             presence "enable passive-probe-params";
             description "Passive probe settings";
             uses apply-advanced;
             container sampling-percentage {
               presence "enable sampling-percentage";
               description "Mininmum percentage of Sessions to be evaluated for the application";
               uses apply-advanced;
               leaf percentage {
                 description "Percentage";
                 default "5";
                 type union {
                   type string {
                     pattern "<.*>|$.*";
                   }
                   type uint32 {
                     range "1 .. 100";
                   }
                 }
               }
             }
             container violation-count {
               presence "enable violation-count";
               description "Number of SLA violations within sampling period to be considered as a violation.";
               uses apply-advanced;
               leaf count {
                 description "Count";
                 default "5";
                 type union {
                   type string {
                     pattern "<.*>|$.*";
                   }
                   type uint32 {
                     range "1 .. 32";
                   }
                 }
               }
             }
             container sampling-period {
               presence "enable sampling-period";
               description "Time period in which the sampling is done";
               uses apply-advanced;
               leaf period {
                 description "Period (in milli-sec)";
                 default "5000";
                 type union {
                   type string {
                     pattern "<.*>|$.*";
                   }
                   type uint32 {
                     range "2000 .. 60000";
                   }
                 }
               }
             }
             container sla-export-factor {
               presence "enable sla-export-factor";
               description "Enabled sampling window based SLA exporting";
               uses apply-advanced;
               leaf factor {
                 description "No of sampling windows after which to report";
                 default "25";
                 type union {
                   type string {
                     pattern "<.*>|$.*";
                   }
                   type uint32 {
                     range "5 .. 200";
                   }
                 }
               }
             }
             container type {
               presence "enable type";
               description "Choose type of SLA measurement";
               uses apply-advanced;
               leaf type-val {
                 type enumeration {
                   enum "book-ended" {
                     description "Choose custom method of probing within WAN link";
                   }
                 }
               }
             }
             container sampling-frequency {
               presence "enable sampling-frequency";
               description "Sampling frequency settings";
               uses apply-advanced;
               container interval {
                 presence "enable interval";
                 description "Time based sampling interval";
                 uses apply-advanced;
                 leaf sampling-interval {
                   description "Interval in milli seconds";
                   default "100";
                   type union {
                     type string {
                       pattern "<.*>|$.*";
                     }
                     type uint32 {
                       range "0 .. 500";
                     }
                   }
                 }
               }
               container ratio {
                 presence "enable ratio";
                 description "1:N based sampling ratio";
                 uses apply-advanced;
                 leaf sampling-ratio {
                   description "Value of N";
                   default "200";
                   type union {
                     type string {
                       pattern "<.*>|$.*";
                     }
                     type uint32 {
                       range "0 .. 10000";
                     }
                   }
                 }
               }
             }
           }
           container multipath-rule {
             presence "enable multipath-rule";
             description "Set AppBased Multipath Routing action";
             uses apply-advanced;
             leaf multipath-rule-name {
               description "Multipath action parameter's name";
               type string;
             }
           }
         }
         list multipath-rule {
           key name;
           ordered-by user;
           description "APP based MULTIPATH Route Action's settings";
           leaf name {
             description "AMR rule name";
             type string {
               length "1 .. 63";
             }
           }
           uses apply-advanced;
           leaf number-of-paths {
             description "No. of Paths in AMR";
             default "2";
             type union {
               type string {
                 pattern "<.*>|$.*";
               }
               type uint32 {
                 range "2 .. 16";
               }
             }
           }
           leaf bandwidth-limit {
             description "Bandwidth limit on Slowest link to avoid saturation (%)";
             default "50";
             type union {
               type string {
                 pattern "<.*>|$.*";
               }
               type uint32 {
                 range "1 .. 100";
               }
             }
           }
           leaf max-time-to-wait {
             description "Max Wait time to restart AMR";
             default "10";
             type union {
               type string {
                 pattern "<.*>|$.*";
               }
               type uint32 {
                 range "1 .. 60";
               }
             }
           }
           leaf-list application {
             ordered-by user;
             type string;
           }
           leaf-list application-group {
             ordered-by user;
             description "Specify dynamic application group name to match";
             type string;
           }
         }
         list policy {
           key name;
           ordered-by user;
           description "Define a policy context from this zone";
           leaf name {
             description "Source zone";
             type string {
               length "1 .. 63";
             }
           }
           uses apply-advanced;
           list policy {
             key name;
             ordered-by user;
             description "Define security policy in specified zone-to-zone direction";
             uses sla_policy_type;
           }
         }
       }
       container gprs {
         presence "enable gprs";
         description "GPRS configuration";
         uses apply-advanced;
         container gtp {
           description "GPRS tunneling protocol configuration";
           uses apply-advanced;
           list profile {
             key name;
             description "Configure GTP Profile";
             leaf name {
               description "GTP profile name";
               type string {
                 length "1 .. 24";
               }
             }
             uses apply-advanced;
             leaf min-message-length {
               description "Minimum message length, from 0 to 65535 ";
               type union {
                 type string {
                   pattern "<.*>|$.*";
                 }
                 type uint32 {
                   range "0 .. 65535";
                 }
               }
             }
             leaf max-message-length {
               description "Maximum message length, from 1 to 65535";
               type union {
                 type string {
                   pattern "<.*>|$.*";
                 }
                 type uint32 {
                   range "1 .. 65535";
                 }
               }
             }
             leaf timeout {
               description "Tunnel idle timeout";
               units "hour";
               type union {
                 type string {
                   pattern "<.*>|$.*";
                 }
                 type uint32 {
                   range "1 .. 1000";
                 }
               }
             }
             leaf rate-limit {
               description "Limit messages per second";
               type union {
                 type string {
                   pattern "<.*>|$.*";
                 }
                 type uint32 {
                   range "1 .. 80000";
                 }
               }
             }
             container log {
               presence "enable log";
               description "GPRS tunneling protocol logs";
               uses apply-advanced;
               leaf forwarded {
                 description "Log passed good packets";
                 type enumeration {
                   enum "basic" {
                     description "Basic logs";
                   }
                   enum "detail" {
                     description "Detailed logs";
                   }
                 }
               }
               leaf state-invalid {
                 description "Dropped by state-inspection or sanity failure";
                 type enumeration {
                   enum "basic" {
                     description "Basic logs";
                   }
                   enum "detail" {
                     description "Detailed logs";
                   }
                 }
               }
               leaf prohibited {
                 description "Dropped for type/length/version filtering";
                 type enumeration {
                   enum "basic" {
                     description "Basic logs";
                   }
                   enum "detail" {
                     description "Detailed logs";
                   }
                 }
               }
               list gtp-u {
                 key name;
                 description "Logs for gtp-u";
                 leaf name {
                   description "Logs for gtp-u";
                   type enumeration {
                     enum "all" {
                       description "All gtp-u logs";
                     }
                     enum "dropped" {
                       description "Dropped gtp-u logs";
                     }
                   }
                 }
                 uses apply-advanced;
               }
               container rate-limited {
                 presence "enable rate-limited";
                 description "Dropped for rate-limit";
                 uses apply-advanced;
                 choice rate-limited-attr {
                   case case_1 {
                     leaf basic {
                       description "Basic logs";
                       type empty;
                     }
                   }
                   case case_2 {
                     leaf detail {
                       description "Detailed logs";
                       type empty;
                     }
                   }
                 }
                 leaf frequency-number {
                   description "Logging frequency over threshold, set by rate-limit";
                   type union {
                     type string {
                       pattern "<.*>|$.*";
                     }
                     type uint32 {
                       range "2 .. 500";
                     }
                   }
                 }
               }
             }
             container remove-ie {
               presence "enable remove-ie";
               description "Remove information elements";
               uses apply-advanced;
               list version {
                 key name;
                 description "GTP version";
                 leaf name {
                   description "Version name";
                   type enumeration {
                     enum "v1" {
                       description "GTP v1";
                     }
                   }
                 }
                 uses apply-advanced;
                 list release {
                   key name;
                   description "Remove information elements by release";
                   leaf name {
                     description "Release name";
                     type enumeration {
                       enum "R6" {
                         description "Release 6";
                       }
                       enum "R7" {
                         description "Release 7";
                       }
                       enum "R8" {
                         description "Release 8";
                       }
                       enum "R9" {
                         description "Release 9";
                       }
                     }
                   }
                   uses apply-advanced;
                 }
                 list number {
                   key name;
                   description "Remove information elements by number";
                   leaf name {
                     type union {
                       type string {
                         pattern "<.*>|$.*";
                       }
                       type uint32 {
                         range "1 .. 255";
                       }
                     }
                   }
                   uses apply-advanced;
                 }
               }
             }
             container path-rate-limit {
               description "Limit control messages based on IP pairs";
               uses apply-advanced;
               list message-type {
                 key name;
                 description "Specific group of control messages";
                 leaf name {
                   description "Specific group of control messages";
                   type enumeration {
                     enum "create-req" {
                       description "Limit packet-per-second of GTP create request";
                     }
                     enum "delete-req" {
                       description "Limit packet-per-second of GTP delete request";
                     }
                     enum "echo-req" {
                       description "Limit packet-per-minute of GTP echo request";
                     }
                     enum "other" {
                       description "Limit packet-per-second of all other GTP control messages";
                     }
                   }
                 }
                 uses apply-advanced;
                 container drop-threshold {
                   description "Set drop threshold for path rate limiting";
                   uses apply-advanced;
                   leaf forward {
                     description "Limit messages of forward direction";
                     type union {
                       type string {
                         pattern "<.*>|$.*";
                       }
                       type uint32 {
                         range "1 .. 10000";
                       }
                     }
                   }
                   leaf reverse {
                     description "Limit messages of reverse direction";
                     type union {
                       type string {
                         pattern "<.*>|$.*";
                       }
                       type uint32 {
                         range "1 .. 10000";
                       }
                     }
                   }
                 }
                 container alarm-threshold {
                   description "Set alarm threshold for path rate limiting";
                   uses apply-advanced;
                   leaf forward {
                     description "Limit messages of forward direction";
                     type union {
                       type string {
                         pattern "<.*>|$.*";
                       }
                       type uint32 {
                         range "1 .. 10000";
                       }
                     }
                   }
                   leaf reverse {
                     description "Limit messages of reverse direction";
                     type union {
                       type string {
                         pattern "<.*>|$.*";
                       }
                       type uint32 {
                         range "1 .. 10000";
                       }
                     }
                   }
                 }
               }
             }
             container drop {
               description "Drop certain type of messages";
               uses apply-advanced;
               list aa-create-pdp {
                 key name;
                 ordered-by user;
                 description "Create AA pdp request/response message";
                 leaf name {
                   description "GTP version for message";
                   type enumeration {
                     enum "0" {
                       description "Version 0";
                     }
                   }
                 }
                 uses apply-advanced;
               }
               list aa-delete-pdp {
                 key name;
                 ordered-by user;
                 description "Delete AA pdp request/response message";
                 leaf name {
                   description "GTP version for message";
                   type enumeration {
                     enum "0" {
                       description "Version 0";
                     }
                   }
                 }
                 uses apply-advanced;
               }
               list bearer-resource {
                 key name;
                 ordered-by user;
                 description "Bearer resource command/failure message";
                 leaf name {
                   description "GTP version for message";
                   type enumeration {
                     enum "2" {
                       description "Version 2";
                     }
                   }
                 }
                 uses apply-advanced;
               }
               list change-notification {
                 key name;
                 ordered-by user;
                 description "Change notification request/response message";
                 leaf name {
                   description "GTP version for message";
                   type enumeration {
                     enum "2" {
                       description "Version 2";
                     }
                   }
                 }
                 uses apply-advanced;
               }
               list config-transfer {
                 key name;
                 ordered-by user;
                 description "Configuration transfer message";
                 leaf name {
                   description "GTP version for message";
                   type enumeration {
                     enum "2" {
                       description "Version 2";
                     }
                   }
                 }
                 uses apply-advanced;
               }
               list context {
                 key name;
                 ordered-by user;
                 description "Context request/response/ack message";
                 leaf name {
                   description "GTP version for message";
                   type enumeration {
                     enum "2" {
                       description "Version 2";
                     }
                   }
                 }
                 uses apply-advanced;
               }
               list create-bearer {
                 key name;
                 ordered-by user;
                 description "Create bearer request/response message";
                 leaf name {
                   description "GTP version for message";
                   type enumeration {
                     enum "2" {
                       description "Version 2";
                     }
                   }
                 }
                 uses apply-advanced;
               }
               list create-data-forwarding {
                 key name;
                 ordered-by user;
                 description "Create indirect data forwarding tunnel request/response message";
                 leaf name {
                   description "GTP version for message";
                   type enumeration {
                     enum "2" {
                       description "Version 2";
                     }
                   }
                 }
                 uses apply-advanced;
               }
               list create-pdp {
                 key name;
                 ordered-by user;
                 description "Create pdp request/response message";
                 leaf name {
                   description "GTP version for message";
                   type enumeration {
                     enum "0" {
                       description "Version 0";
                     }
                     enum "1" {
                       description "Version 1";
                     }
                     enum "all" {
                       description "All versions";
                     }
                   }
                 }
                 uses apply-advanced;
               }
               list create-session {
                 key name;
                 ordered-by user;
                 description "Create session request/response message";
                 leaf name {
                   description "GTP version for message";
                   type enumeration {
                     enum "2" {
                       description "Version 2";
                     }
                   }
                 }
                 uses apply-advanced;
               }
               list create-tnl-forwarding {
                 key name;
                 ordered-by user;
                 description "Create forwarding tunnel request/response message";
                 leaf name {
                   description "GTP version for message";
                   type enumeration {
                     enum "2" {
                       description "Version 2";
                     }
                   }
                 }
                 uses apply-advanced;
               }
               list cs-paging {
                 key name;
                 ordered-by user;
                 description "CS paging indication message";
                 leaf name {
                   description "GTP version for message";
                   type enumeration {
                     enum "2" {
                       description "Version 2";
                     }
                   }
                 }
                 uses apply-advanced;
               }
               list data-record {
                 key name;
                 ordered-by user;
                 description "Data record request/response message";
                 leaf name {
                   description "GTP version for message";
                   type enumeration {
                     enum "0" {
                       description "Version 0";
                     }
                     enum "1" {
                       description "Version 1";
                     }
                     enum "all" {
                       description "All versions";
                     }
                   }
                 }
                 uses apply-advanced;
               }
               list delete-bearer {
                 key name;
                 ordered-by user;
                 description "Delete bearer request/response message";
                 leaf name {
                   description "GTP version for message";
                   type enumeration {
                     enum "2" {
                       description "Version 2";
                     }
                   }
                 }
                 uses apply-advanced;
               }
               list delete-command {
                 key name;
                 ordered-by user;
                 description "Delete bearer command/failure message";
                 leaf name {
                   description "GTP version for message";
                   type enumeration {
                     enum "2" {
                       description "Version 2";
                     }
                   }
                 }
                 uses apply-advanced;
               }
               list delete-data-forwarding {
                 key name;
                 ordered-by user;
                 description "Delete indirect data forwarding tunnel request/response message";
                 leaf name {
                   description "GTP version for message";
                   type enumeration {
                     enum "2" {
                       description "Version 2";
                     }
                   }
                 }
                 uses apply-advanced;
               }
               list delete-pdn {
                 key name;
                 ordered-by user;
                 description "Delete PDN connection set request/response message";
                 leaf name {
                   description "GTP version for message";
                   type enumeration {
                     enum "2" {
                       description "Version 2";
                     }
                   }
                 }
                 uses apply-advanced;
               }
               list delete-pdp {
                 key name;
                 ordered-by user;
                 description "Delete pdp request/response message";
                 leaf name {
                   description "GTP version for message";
                   type enumeration {
                     enum "0" {
                       description "Version 0";
                     }
                     enum "1" {
                       description "Version 1";
                     }
                     enum "all" {
                       description "All versions";
                     }
                   }
                 }
                 uses apply-advanced;
               }
               list delete-session {
                 key name;
                 ordered-by user;
                 description "Delete session request/response message";
                 leaf name {
                   description "GTP version for message";
                   type enumeration {
                     enum "2" {
                       description "Version 2";
                     }
                   }
                 }
                 uses apply-advanced;
               }
               list detach {
                 key name;
                 ordered-by user;
                 description "Detach notification/ack message";
                 leaf name {
                   description "GTP version for message";
                   type enumeration {
                     enum "2" {
                       description "Version 2";
                     }
                   }
                 }
                 uses apply-advanced;
               }
               list downlink-notification {
                 key name;
                 ordered-by user;
                 description "Downlink data notification/ack/failure message";
                 leaf name {
                   description "GTP version for message";
                   type enumeration {
                     enum "2" {
                       description "Version 2";
                     }
                   }
                 }
                 uses apply-advanced;
               }
               list echo {
                 key name;
                 ordered-by user;
                 description "Echo request/response message";
                 leaf name {
                   description "GTP version for message";
                   type enumeration {
                     enum "0" {
                       description "Version 0";
                     }
                     enum "1" {
                       description "Version 1";
                     }
                     enum "2" {
                       description "Version 2";
                     }
                     enum "all" {
                       description "All versions";
                     }
                   }
                 }
                 uses apply-advanced;
               }
               list error-indication {
                 key name;
                 ordered-by user;
                 description "Error indication message";
                 leaf name {
                   description "GTP version for message";
                   type enumeration {
                     enum "0" {
                       description "Version 0";
                     }
                     enum "1" {
                       description "Version 1";
                     }
                     enum "all" {
                       description "All versions";
                     }
                   }
                 }
                 uses apply-advanced;
               }
               list failure-report {
                 key name;
                 ordered-by user;
                 description "Failure report request/response message";
                 leaf name {
                   description "GTP version for message";
                   type enumeration {
                     enum "0" {
                       description "Version 0";
                     }
                     enum "1" {
                       description "Version 1";
                     }
                     enum "all" {
                       description "All versions";
                     }
                   }
                 }
                 uses apply-advanced;
               }
               list fwd-access {
                 key name;
                 ordered-by user;
                 description "Forward access context notification/ack message";
                 leaf name {
                   description "GTP version for message";
                   type enumeration {
                     enum "2" {
                       description "Version 2";
                     }
                   }
                 }
                 uses apply-advanced;
               }
               list fwd-relocation {
                 key name;
                 ordered-by user;
                 description "Forward relocation request/response/comp/comp-ack message";
                 leaf name {
                   description "GTP version for message";
                   type enumeration {
                     enum "1" {
                       description "Version 1";
                     }
                     enum "2" {
                       description "Version 2";
                     }
                     enum "all" {
                       description "All versions";
                     }
                   }
                 }
                 uses apply-advanced;
               }
               list fwd-srns-context {
                 key name;
                 ordered-by user;
                 description "Forward SRNS context/context-ack message";
                 leaf name {
                   description "GTP version for message";
                   type enumeration {
                     enum "1" {
                       description "Version 1";
                     }
                   }
                 }
                 uses apply-advanced;
               }
               list g-pdu {
                 key name;
                 ordered-by user;
                 description "G-PDU (user PDU) message/T-PDU";
                 leaf name {
                   description "GTP version for message";
                   type enumeration {
                     enum "0" {
                       description "Version 0";
                     }
                     enum "1" {
                       description "Version 1";
                     }
                     enum "all" {
                       description "All versions";
                     }
                   }
                 }
                 uses apply-advanced;
               }
               list identification {
                 key name;
                 ordered-by user;
                 description "Identification request/response message";
                 leaf name {
                   description "GTP version for message";
                   type enumeration {
                     enum "0" {
                       description "Version 0";
                     }
                     enum "1" {
                       description "Version 1";
                     }
                     enum "2" {
                       description "Version 2";
                     }
                     enum "all" {
                       description "All versions";
                     }
                   }
                 }
                 uses apply-advanced;
               }
               list mbms-session-start {
                 key name;
                 ordered-by user;
                 description "MBMS session start request/response message";
                 leaf name {
                   description "GTP version for message";
                   type enumeration {
                     enum "1" {
                       description "Version 1";
                     }
                     enum "2" {
                       description "Version 2";
                     }
                     enum "all" {
                       description "All versions";
                     }
                   }
                 }
                 uses apply-advanced;
               }
               list mbms-session-stop {
                 key name;
                 ordered-by user;
                 description "MBMS session stop request/response message";
                 leaf name {
                   description "GTP version for message";
                   type enumeration {
                     enum "1" {
                       description "Version 1";
                     }
                     enum "2" {
                       description "Version 2";
                     }
                     enum "all" {
                       description "All versions";
                     }
                   }
                 }
                 uses apply-advanced;
               }
               list mbms-session-update {
                 key name;
                 ordered-by user;
                 description "MBMS session update request/response message";
                 leaf name {
                   description "GTP version for message";
                   type enumeration {
                     enum "1" {
                       description "Version 1";
                     }
                     enum "2" {
                       description "Version 2";
                     }
                     enum "all" {
                       description "All versions";
                     }
                   }
                 }
                 uses apply-advanced;
               }
               list modify-bearer {
                 key name;
                 ordered-by user;
                 description "Modify bearer request/response message";
                 leaf name {
                   description "GTP version for message";
                   type enumeration {
                     enum "2" {
                       description "Version 2";
                     }
                   }
                 }
                 uses apply-advanced;
               }
               list modify-command {
                 key name;
                 ordered-by user;
                 description "Modify bearer command/failure message";
                 leaf name {
                   description "GTP version for message";
                   type enumeration {
                     enum "2" {
                       description "Version 2";
                     }
                   }
                 }
                 uses apply-advanced;
               }
               list node-alive {
                 key name;
                 ordered-by user;
                 description "Node alive request/response message";
                 leaf name {
                   description "GTP version for message";
                   type enumeration {
                     enum "0" {
                       description "Version 0";
                     }
                     enum "1" {
                       description "Version 1";
                     }
                     enum "all" {
                       description "All versions";
                     }
                   }
                 }
                 uses apply-advanced;
               }
               list note-ms-present {
                 key name;
                 ordered-by user;
                 description "Note MS GPRS present request/response message";
                 leaf name {
                   description "GTP version for message";
                   type enumeration {
                     enum "0" {
                       description "Version 0";
                     }
                     enum "1" {
                       description "Version 1";
                     }
                     enum "all" {
                       description "All versions";
                     }
                   }
                 }
                 uses apply-advanced;
               }
               list pdu-notification {
                 key name;
                 ordered-by user;
                 description "PDU notification requst/response/reject/reject-response message";
                 leaf name {
                   description "GTP version for message";
                   type enumeration {
                     enum "0" {
                       description "Version 0";
                     }
                     enum "1" {
                       description "Version 1";
                     }
                     enum "all" {
                       description "All versions";
                     }
                   }
                 }
                 uses apply-advanced;
               }
               list ran-info {
                 key name;
                 ordered-by user;
                 description "RAN info relay message";
                 leaf name {
                   description "GTP version for message";
                   type enumeration {
                     enum "1" {
                       description "Version 1";
                     }
                     enum "2" {
                       description "Version 2";
                     }
                     enum "all" {
                       description "All versions";
                     }
                   }
                 }
                 uses apply-advanced;
               }
               list redirection {
                 key name;
                 ordered-by user;
                 description "Redirection request/response message";
                 leaf name {
                   description "GTP version for message";
                   type enumeration {
                     enum "0" {
                       description "Version 0";
                     }
                     enum "1" {
                       description "Version 1";
                     }
                     enum "all" {
                       description "All versions";
                     }
                   }
                 }
                 uses apply-advanced;
               }
               list release-access {
                 key name;
                 ordered-by user;
                 description "Release access-bearer request/response message";
                 leaf name {
                   description "GTP version for message";
                   type enumeration {
                     enum "2" {
                       description "Version 2";
                     }
                   }
                 }
                 uses apply-advanced;
               }
               list relocation-cancel {
                 key name;
                 ordered-by user;
                 description "Relocation cancel request/response message";
                 leaf name {
                   description "GTP version for message";
                   type enumeration {
                     enum "1" {
                       description "Version 1";
                     }
                     enum "2" {
                       description "Version 2";
                     }
                     enum "all" {
                       description "All versions";
                     }
                   }
                 }
                 uses apply-advanced;
               }
               list resume {
                 key name;
                 ordered-by user;
                 description "Resume notification/ack message";
                 leaf name {
                   description "GTP version for message";
                   type enumeration {
                     enum "2" {
                       description "Version 2";
                     }
                   }
                 }
                 uses apply-advanced;
               }
               list send-route {
                 key name;
                 ordered-by user;
                 description "Send route info request/response message";
                 leaf name {
                   description "GTP version for message";
                   type enumeration {
                     enum "0" {
                       description "Version 0";
                     }
                     enum "1" {
                       description "Version 1";
                     }
                     enum "all" {
                       description "All versions";
                     }
                   }
                 }
                 uses apply-advanced;
               }
               list sgsn-context {
                 key name;
                 ordered-by user;
                 description "SGSN context request/response/ack message";
                 leaf name {
                   description "GTP version for message";
                   type enumeration {
                     enum "0" {
                       description "Version 0";
                     }
                     enum "1" {
                       description "Version 1";
                     }
                     enum "all" {
                       description "All versions";
                     }
                   }
                 }
                 uses apply-advanced;
               }
               list stop-paging {
                 key name;
                 ordered-by user;
                 description "Stop paging indication message";
                 leaf name {
                   description "GTP version for message";
                   type enumeration {
                     enum "2" {
                       description "Version 2";
                     }
                   }
                 }
                 uses apply-advanced;
               }
               list supported-extension {
                 key name;
                 ordered-by user;
                 description "Supported extension headers notification message";
                 leaf name {
                   description "GTP version for message";
                   type enumeration {
                     enum "1" {
                       description "Version 1";
                     }
                   }
                 }
                 uses apply-advanced;
               }
               list suspend {
                 key name;
                 ordered-by user;
                 description "Suspend notification/ack message";
                 leaf name {
                   description "GTP version for message";
                   type enumeration {
                     enum "2" {
                       description "Version 2";
                     }
                   }
                 }
                 uses apply-advanced;
               }
               list trace-session {
                 key name;
                 ordered-by user;
                 description "Trace session activation/deactivation message";
                 leaf name {
                   description "GTP version for message";
                   type enumeration {
                     enum "2" {
                       description "Version 2";
                     }
                   }
                 }
                 uses apply-advanced;
               }
               list update-bearer {
                 key name;
                 ordered-by user;
                 description "Update bearer request/response message";
                 leaf name {
                   description "GTP version for message";
                   type enumeration {
                     enum "2" {
                       description "Version 2";
                     }
                   }
                 }
                 uses apply-advanced;
               }
               list update-pdn {
                 key name;
                 ordered-by user;
                 description "Update PDN connection set request/response message";
                 leaf name {
                   description "GTP version for message";
                   type enumeration {
                     enum "2" {
                       description "Version 2";
                     }
                   }
                 }
                 uses apply-advanced;
               }
               list update-pdp {
                 key name;
                 ordered-by user;
                 description "Update pdp request/response message";
                 leaf name {
                   description "GTP version for message";
                   type enumeration {
                     enum "0" {
                       description "Version 0";
                     }
                     enum "1" {
                       description "Version 1";
                     }
                     enum "all" {
                       description "All versions";
                     }
                   }
                 }
                 uses apply-advanced;
               }
               list ver-not-supported {
                 key name;
                 ordered-by user;
                 description "Version not supported message";
                 leaf name {
                   description "GTP version for message";
                   type enumeration {
                     enum "0" {
                       description "Version 0";
                     }
                     enum "1" {
                       description "Version 1";
                     }
                     enum "2" {
                       description "Version 2";
                     }
                     enum "all" {
                       description "All versions";
                     }
                   }
                 }
                 uses apply-advanced;
               }
             }
             list apn {
               key name;
               description "GTP Access Point Name (APN) filter";
               leaf name {
                 description "Specific APN pattern string";
                 type string {
                   length "1 .. 64";
                 }
               }
               uses apply-advanced;
               list imsi-prefix {
                 key name;
                 description "Specific filter prefix digits for International Mobile Subscriber Identification(IMSI)";
                 leaf name {
                   description "IMSI prefix should be * or 5-15 digits";
                   type string {
                     length "1 .. 15";
                   }
                 }
                 uses apply-advanced;
                 container action {
                   description "Configure GTP profile APN action";
                   uses apply-advanced;
                   choice action-c {
                     case case_1 {
                       leaf pass {
                         description "Pass all selection modes for this APN";
                         type empty;
                       }
                     }
                     case case_2 {
                       leaf drop {
                         description "Drop all selection modes for this APN";
                         type empty;
                       }
                     }
                     case case_3 {
                       container selection {
                         presence "enable selection";
                         description "Allowed selection modes for this APN";
                         uses apply-advanced;
                         leaf ms {
                           description "Mobile Station selection mode";
                           type empty;
                         }
                         leaf net {
                           description "Network selection mode";
                           type empty;
                         }
                         leaf vrf {
                           description "Subscriber verified mode";
                           type empty;
                         }
                       }
                     }
                   }
                 }
               }
             }
             leaf restart-path {
               description "Restart GTP paths";
               type enumeration {
                 enum "echo" {
                   description "Restart GTP paths by detecting restart number stored in the Echo messages";
                 }
                 enum "create" {
                   description "Restart GTP paths by detecting restart number stored in the Create messages";
                 }
                 enum "all" {
                   description "Restart GTP paths by detecting restart number stored in the Echo or Create messages";
                 }
               }
             }
             leaf seq-number-validated {
               description "Validate G-PDU sequence number";
               type empty;
             }
             leaf gtp-in-gtp-denied {
               description "Deny nested GTP";
               type empty;
             }
             leaf u-tunnel-validated {
               description "Validate GTP-u tunnel";
               type empty;
             }
             leaf end-user-address-validated {
               description "Validate end user address";
               type empty;
             }
             leaf req-timeout {
               description "Request message timeout, default timeout value 5 seconds";
               units "second";
               type union {
                 type string {
                   pattern "<.*>|$.*";
                 }
                 type uint8 {
                   range "1 .. 30";
                 }
               }
             }
             leaf handover-on-roaming-intf {
               description "Enable tunnel setup by Handover messages on roaming interface";
               type empty;
             }
             container handover-group {
               description "SGSN handover group configuration";
               uses apply-advanced;
               leaf group-name {
                 description "SGSN handover group name";
                 type string {
                   length "1 .. 24";
                 }
               }
             }
           }
           container traceoptions {
             description "Trace options for GPRS tunneling protocol";
             uses apply-advanced;
             leaf no-remote-trace {
               description "Disable remote tracing";
               type empty;
             }
             container file {
               description "Trace file information";
               leaf filename {
                 description "Name of file in which to write trace information";
                 type string {
                   length "1 .. 1024";
                 }
               }
               leaf size {
                 description "Maximum trace file size";
                 type string;
               }
               leaf files {
                 description "Maximum number of trace files";
                 default "3";
                 type union {
                   type string {
                     pattern "<.*>|$.*";
                   }
                   type uint32 {
                     range "2 .. 1000";
                   }
                 }
               }
               choice world-readable-choice {
                 leaf world-readable {
                   description "Allow any user to read the log file";
                   type empty;
                 }
                 leaf no-world-readable {
                   description "Don't allow any user to read the log file";
                   type empty;
                 }
               }
               leaf match {
                 description "Regular expression for lines to be logged";
                 type jt:regular-expression;
               }
             }
             list flag {
               key name;
               ordered-by user;
               description "Tracing parameters";
               leaf name {
                 type enumeration {
                   enum "configuration" {
                     description "Trace configuration events";
                   }
                   enum "flow" {
                     description "Trace flow events";
                   }
                   enum "parser" {
                     description "Trace parser events";
                   }
                   enum "chassis-cluster" {
                     description "Trace chassis cluster events";
                   }
                   enum "gsn" {
                     description "Trace gsn events";
                   }
                   enum "jmpi" {
                     description "Trace jmpi events";
                   }
                   enum "tnl" {
                     description "Trace tnl events";
                   }
                   enum "req" {
                     description "Trace req events";
                   }
                   enum "path" {
                     description "Trace path events";
                   }
                   enum "all" {
                     description "Trace everything";
                   }
                 }
               }
             }
             container trace-level {
               description "GTP trace level";
               uses apply-advanced;
               choice level {
                 case case_1 {
                   leaf error {
                     description "Match error conditions";
                     type empty;
                   }
                 }
                 case case_2 {
                   leaf warning {
                     description "Match warning messages";
                     type empty;
                   }
                 }
                 case case_3 {
                   leaf notice {
                     description "Match conditions that should be handled specially";
                     type empty;
                   }
                 }
                 case case_4 {
                   leaf info {
                     description "Match informational messages";
                     type empty;
                   }
                 }
                 case case_5 {
                   leaf verbose {
                     description "Match verbose messages";
                     type empty;
                   }
                 }
               }
             }
           }
           list handover-group {
             key name;
             description "Set handover group";
             leaf name {
               description "Set handover group name";
               type string {
                 length "1 .. 24";
               }
             }
             uses apply-advanced;
             list address-book {
               key name;
               description "Set addreess book";
               leaf name {
                 description "Set address book name";
                 type string {
                   length "1 .. 63";
                 }
               }
               uses apply-advanced;
               container address-set {
                 description "Set address set";
                 uses apply-advanced;
                 leaf set-name {
                   description "Set address set name";
                   type string {
                     length "1 .. 63";
                   }
                 }
               }
             }
           }
           container handover-default {
             description "Set handover default deny";
             uses apply-advanced;
             leaf deny {
               description "Handover default deny";
               type empty;
             }
           }
         }
         container sctp {
           presence "enable sctp";
           description "GPRS stream control transmission protocol configuration";
           uses apply-advanced;
           list profile {
             key name;
             description "Configure stream transmission protocol";
             leaf name {
               description "SCTP configuration name";
               type string {
                 length "1 .. 31";
               }
             }
             uses apply-advanced;
             leaf nat-only {
               description "Only do payload IPs translation for SCTP packet";
               type empty;
             }
             leaf association-timeout {
               description "SCTP association timeout length, in minutes";
               type union {
                 type string {
                   pattern "<.*>|$.*";
                 }
                 type uint32 {
                   range "10 .. 1440";
                 }
               }
             }
             leaf handshake-timeout {
               description "SCTP handshake timeout, in seconds";
               type union {
                 type string {
                   pattern "<.*>|$.*";
                 }
                 type uint32 {
                   range "10 .. 30";
                 }
               }
             }
             container drop {
               description "Disallowed SCTP payload message";
               uses apply-advanced;
               list m3ua-service {
                 key name;
                 ordered-by user;
                 description "MTP level 3 (MTP3) user adaptation layer service";
                 leaf name {
                   type enumeration {
                     enum "sccp" {
                       description "Signaling connection control part";
                     }
                     enum "tup" {
                       description "Telephone user part";
                     }
                     enum "isup" {
                       description "ISDN user part";
                     }
                   }
                 }
               }
               list payload-protocol {
                 key name;
                 ordered-by user;
                 description "SCTP payload protocol identifier";
                 leaf name {
                   type string;
                 }
               }
             }
             container permit {
               description "Permit SCTP payload message";
               uses apply-advanced;
               list payload-protocol {
                 key name;
                 ordered-by user;
                 description "SCTP payload protocol identifier";
                 leaf name {
                   type string;
                 }
               }
             }
             container limit {
               description "Packet limits";
               uses apply-advanced;
               list payload-protocol {
                 key name;
                 ordered-by user;
                 description "Payload Rate limit";
                 leaf name {
                   type string;
                 }
                 leaf rate {
                   description "Rate limit";
                   type union {
                     type string {
                       pattern "<.*>|$.*";
                     }
                     type uint16 {
                       range "1 .. 12000";
                     }
                   }
                 }
               }
               list address {
                 key name;
                 ordered-by user;
                 description "Rate limit for a list of IP addresses";
                 leaf name {
                   description "IP address";
                   type jt:ipaddr;
                 }
                 uses apply-advanced;
                 list payload-protocol {
                   key name;
                   ordered-by user;
                   description "Payload Rate limit";
                   leaf name {
                     type string;
                   }
                   leaf rate {
                     description "Rate limit";
                     type union {
                       type string {
                         pattern "<.*>|$.*";
                       }
                       type uint16 {
                         range "1 .. 12000";
                       }
                     }
                   }
                 }
               }
               container rate {
                 description "Rate limit";
                 uses apply-advanced;
                 leaf sccp {
                   description "Global SCCP messages rate limit";
                   type union {
                     type string {
                       pattern "<.*>|$.*";
                     }
                     type uint16 {
                       range "1 .. 12000";
                     }
                   }
                 }
                 leaf ssp {
                   description "Global SSP messages rate limit";
                   type union {
                     type string {
                       pattern "<.*>|$.*";
                     }
                     type uint16 {
                       range "1 .. 12000";
                     }
                   }
                 }
                 leaf sst {
                   description "Global SST messages rate limit";
                   type union {
                     type string {
                       pattern "<.*>|$.*";
                     }
                     type uint16 {
                       range "1 .. 12000";
                     }
                   }
                 }
                 list address {
                   key name;
                   ordered-by user;
                   description "Rate limit for a list of IP addresses";
                   leaf name {
                     description "IP address";
                     type jt:ipaddr;
                   }
                   uses apply-advanced;
                   leaf sccp {
                     description "SCCP messages rate limit";
                     type union {
                       type string {
                         pattern "<.*>|$.*";
                       }
                       type uint16 {
                         range "1 .. 12000";
                       }
                     }
                   }
                   leaf ssp {
                     description "SSP messages rate limit";
                     type union {
                       type string {
                         pattern "<.*>|$.*";
                       }
                       type uint16 {
                         range "1 .. 12000";
                       }
                     }
                   }
                   leaf sst {
                     description "SST messages rate limit";
                     type union {
                       type string {
                         pattern "<.*>|$.*";
                       }
                       type uint16 {
                         range "1 .. 12000";
                       }
                     }
                   }
                 }
               }
             }
           }
           container multichunk-inspection {
             description "Configure for SCTP multi chunks inspection";
             uses apply-advanced;
             choice multichunk-flag {
               case case_1 {
                 leaf disable {
                   description "Set multichunk inspection flag to disable";
                   type empty;
                 }
               }
             }
           }
           container nullpdu {
             description "Configure for SCTP NULLPDU protocol value";
             uses apply-advanced;
             container protocol {
               description "SCTP NULLPDU payload protocol identifier";
               uses apply-advanced;
               choice nullpdu-protocol {
                 case case_1 {
                   leaf ID-0x0000 {
                     description "Set 0x0000 to be NULLPDU ID value";
                     type empty;
                   }
                 }
                 case case_2 {
                   leaf ID-0xFFFF {
                     description "Set 0xFFFF to be NULLPDU ID value";
                     type empty;
                   }
                 }
               }
             }
           }
           list log {
             key name;
             ordered-by user;
             description "GPRS stream control transmission protocol logs";
             leaf name {
               type enumeration {
                 enum "configuration" {
                   description "Log CLI configuration";
                 }
                 enum "rate-limit" {
                   description "Log exceeding rate limits";
                 }
                 enum "association" {
                   description "Log association event";
                 }
                 enum "data-message-drop" {
                   description "Log the drop of SCTP data message";
                 }
                 enum "control-message-drop" {
                   description "Log the drop of SCTP control message";
                 }
                 enum "control-message-all" {
                   description "Log SCTP control message both drop and pass";
                 }
               }
             }
           }
           container traceoptions {
             description "Trace options for GPRS stream control transmission protocol";
             uses apply-advanced;
             leaf no-remote-trace {
               description "Disable remote tracing";
               type empty;
             }
             container file {
               description "Trace file information";
               leaf filename {
                 description "Name of file in which to write trace information";
                 type string {
                   length "1 .. 1024";
                 }
               }
               leaf size {
                 description "Maximum trace file size";
                 type string;
               }
               leaf files {
                 description "Maximum number of trace files";
                 default "3";
                 type union {
                   type string {
                     pattern "<.*>|$.*";
                   }
                   type uint32 {
                     range "2 .. 1000";
                   }
                 }
               }
               choice world-readable-choice {
                 leaf world-readable {
                   description "Allow any user to read the log file";
                   type empty;
                 }
                 leaf no-world-readable {
                   description "Don't allow any user to read the log file";
                   type empty;
                 }
               }
               leaf match {
                 description "Regular expression for lines to be logged";
                 type jt:regular-expression;
               }
             }
             list flag {
               key name;
               ordered-by user;
               description "Tracing parameters";
               leaf name {
                 type enumeration {
                   enum "configuration" {
                     description "Trace configuration events";
                   }
                   enum "detail" {
                     description "Trace detail events";
                   }
                   enum "flow" {
                     description "Trace flow events";
                   }
                   enum "parser" {
                     description "Trace parser events";
                   }
                   enum "chassis-cluster" {
                     description "Trace chassis cluster events";
                   }
                   enum "all" {
                     description "Trace everything";
                   }
                 }
               }
             }
           }
         }
       }
       container ngfw {
         description "Next generation unified L4/L7 firewall";
         uses apply-advanced;
         container default-profile {
           description "Unified L4/L7 firewall default profile configuration";
           uses apply-advanced;
           container ssl-proxy {
             presence "enable ssl-proxy";
             description "SSL proxy services";
             uses apply-advanced;
             leaf profile-name {
               description "Specify SSL proxy service profile name";
               type string;
             }
           }
           container application-traffic-control {
             description "Application traffic control services";
             uses jsf_application_traffic_control_rule_set_type;
           }
         }
       }
       container macsec {
         description "MAC Security configuration";
         uses security-macsec;
       }
     }
     container applications {
       description "Define applications by protocol characteristics";
       uses apply-advanced;
       list application {
         key name;
         ordered-by user;
         description "Define an application";
         uses application_object;
       }
       list application-set {
         key name;
         ordered-by user;
         description "Define an application set";
         uses application_set_object;
       }
     }
     container schedulers {
       description "Security scheduler";
       uses apply-advanced;
       list scheduler {
         key name;
         ordered-by user;
         description "Scheduler configuration";
         uses scheduler_object_type;
       }
     }
   }
   grouping aamwd-traceoptions {
     description "Advanced anti-malware trace options";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Trace flags";
       leaf name {
         type enumeration {
           enum "all" {
             description "Trace everything";
           }
           enum "connection" {
             description "Trace the connection to server";
           }
           enum "content" {
             description "Trace the content buffer management";
           }
           enum "daemon" {
             description "Trace advanced-anti-malware daemon";
           }
           enum "http" {
             description "Trace http protocol operations";
           }
           enum "identification" {
             description "Trace file identification";
           }
           enum "imap" {
             description "Trace imap protocol operations";
           }
           enum "parser" {
             description "Trace protocol context parser";
           }
           enum "plugin" {
             description "Trace advanced-anti-malware plugin";
           }
           enum "policy" {
             description "Trace advanced-anti-malware policy";
           }
           enum "smtp" {
             description "Trace smtp protocol operations";
           }
         }
       }
     }
   }
   grouping address-assignment-type {
     description "Address assignment configuration";
     uses apply-advanced;
     container neighbor-discovery-router-advertisement {
       description "Designated NDRA pool for this instance";
       leaf ndra-name {
         description "Designated NDRA pool name";
         type string {
           length "1 .. 63";
         }
       }
     }
     leaf high-utilization {
       description "Generate an SNMP trap when address pool use surpasses this percentage";
       type union {
         type string {
           pattern "<.*>|$.*";
         }
         type uint16 {
           range "2 .. 99";
         }
       }
     }
     leaf abated-utilization {
       description "Generate an SNMP clear trap when address pool use falls below this percentage";
       type union {
         type string {
           pattern "<.*>|$.*";
         }
         type uint16 {
           range "1 .. 98";
         }
       }
     }
     leaf high-utilization-v6 {
       description "Generate an SNMP trap when address pool use surpasses this percentage";
       type union {
         type string {
           pattern "<.*>|$.*";
         }
         type uint16 {
           range "2 .. 99";
         }
       }
     }
     leaf abated-utilization-v6 {
       description "Generate an SNMP clear trap when address pool use falls below this percentage";
       type union {
         type string {
           pattern "<.*>|$.*";
         }
         type uint16 {
           range "1 .. 98";
         }
       }
     }
     list dynamic-pool {
       key name;
       ordered-by user;
       description "Dynamic address pool";
       leaf name {
         description "Dynamic address pool name";
         type string {
           length "1 .. 63";
         }
       }
       uses apply-advanced;
       container family {
         presence "enable family";
         description "Address family";
         uses apply-advanced;
         container inet6 {
           description "IPv6";
           uses apply-advanced;
           leaf delegated-prefix-length {
             description "Delegated IPv6 network prefix length";
             type union {
               type string {
                 pattern "<.*>|$.*";
               }
               type uint32 {
                 range "1 .. 64";
               }
             }
           }
           leaf from-interface {
             description "Get prefix from interface name";
             type union {
               type jt:interface-name;
               type string {
                 pattern "<.*>|$.*";
               }
             }
           }
           list range {
             key name;
             ordered-by user;
             description "IPv6 address range";
             leaf name {
               description "Range name";
               type string {
                 length "1 .. 63";
               }
             }
             uses apply-advanced;
             leaf masked-low {
               description "Lower limit of ipv6 address range";
               type jt:ipv6prefix-mandatory;
             }
             leaf masked-high {
               description "Upper limit of ipv6 address range";
               type jt:ipv6prefix-mandatory;
             }
             leaf prefix-length {
               description "IPv6 delegated prefix length";
               type union {
                 type string {
                   pattern "<.*>|$.*";
                 }
                 type uint32 {
                   range "1 .. 64";
                 }
               }
             }
           }
           container dhcp-attributes {
             description "DHCP options and match criteria";
             uses dynamic-dhcp-attribute-type;
           }
         }
       }
     }
     list pool {
       key name;
       ordered-by user;
       description "Address pool";
       leaf name {
         description "Address pool name";
         type string {
           length "1 .. 63";
         }
       }
       uses apply-advanced;
       leaf active-drain {
         description "Notify client of pool active drain mode";
         type empty;
       }
       leaf hold-down {
         description "Place pool in passive drain mode";
         type empty;
       }
       leaf link {
         description "Address pool link name";
         type string {
           length "1 .. 63";
         }
       }
       container family {
         presence "enable family";
         description "Address family";
         choice family_type {
           case case_1 {
             container inet {
               presence "enable inet";
               description "IPv4";
               uses apply-advanced;
               leaf network {
                 description "Network address";
                 type jt:ipv4prefix;
               }
               list range {
                 key name;
                 ordered-by user;
                 description "Address range";
                 leaf name {
                   description "Range name";
                   type string {
                     length "1 .. 63";
                   }
                 }
                 uses apply-advanced;
                 leaf low {
                   description "Lower limit of address range";
                   type jt:ipv4addr;
                 }
                 leaf high {
                   description "Upper limit of address range";
                   type jt:ipv4addr;
                 }
               }
               container dhcp-attributes {
                 description "DHCP options and match criteria";
                 uses dhcp-attribute-type;
               }
               container xauth-attributes {
                 description "Configure xauth attributes";
                 uses apply-advanced;
                 leaf primary-dns {
                   description "Specify the primary-dns IP address";
                   type jt:ipv4prefix;
                 }
                 leaf secondary-dns {
                   description "Specify the secondary-dns IP address";
                   type jt:ipv4prefix;
                 }
                 leaf primary-wins {
                   description "Specify the primary-wins IP address";
                   type jt:ipv4prefix;
                 }
                 leaf secondary-wins {
                   description "Specify the secondary-wins IP address";
                   type jt:ipv4prefix;
                 }
               }
               list host {
                 key name;
                 ordered-by user;
                 description "Hostname for static reservations";
                 leaf name {
                   description "Hostname";
                   type string {
                     length "1 .. 63";
                   }
                 }
                 uses apply-advanced;
                 leaf hardware-address {
                   description "Hardware address";
                   type jt:mac-addr;
                 }
                 leaf ip-address {
                   description "Reserved address";
                   type jt:ipv4addr;
                 }
               }
               list excluded-address {
                 key name;
                 ordered-by user;
                 description "Excluded Addresses";
                 max-elements 20;
                 leaf name {
                   description "Excluded address";
                   type jt:ipv4addr;
                 }
                 uses apply-advanced;
               }
               list excluded-range {
                 key name;
                 ordered-by user;
                 description "Excluded address range";
                 max-elements 20;
                 leaf name {
                   description "Range name";
                   type string {
                     length "1 .. 63";
                   }
                 }
                 uses apply-advanced;
                 leaf low {
                   description "Lower limit of excluded address range";
                   type jt:ipv4addr;
                 }
                 leaf high {
                   description "Upper limit of excluded address range";
                   type jt:ipv4addr;
                 }
               }
             }
           }
           case case_2 {
             container inet6 {
               presence "enable inet6";
               description "IPv6";
               uses apply-advanced;
               leaf prefix {
                 description "IPv6 network prefix";
                 type jt:ipv6prefix-mandatory;
               }
               list range {
                 key name;
                 ordered-by user;
                 description "IPv6 address range";
                 leaf name {
                   description "Range name";
                   type string {
                     length "1 .. 63";
                   }
                 }
                 uses apply-advanced;
                 leaf low {
                   description "Lower limit of ipv6 address range";
                   type jt:ipv6prefix-mandatory;
                 }
                 leaf high {
                   description "Upper limit of ipv6 address range";
                   type jt:ipv6prefix-mandatory;
                 }
                 leaf prefix-length {
                   description "IPv6 delegated prefix length";
                   type union {
                     type string {
                       pattern "<.*>|$.*";
                     }
                     type uint32 {
                       range "1 .. 128";
                     }
                   }
                 }
               }
               container dhcp-attributes {
                 description "DHCP options and match criteria";
                 uses dhcp-attribute-type;
               }
               list excluded-address {
                 key name;
                 ordered-by user;
                 description "Excluded Addresses";
                 max-elements 20;
                 leaf name {
                   description "Excluded address";
                   type jt:ipv6addr;
                 }
                 uses apply-advanced;
               }
               list excluded-range {
                 key name;
                 ordered-by user;
                 description "Excluded address range";
                 max-elements 20;
                 leaf name {
                   description "Range name";
                   type string {
                     length "1 .. 63";
                   }
                 }
                 uses apply-advanced;
                 leaf low {
                   description "Lower limit of excluded address range";
                   type jt:ipv6addr;
                 }
                 leaf high {
                   description "Upper limit of excluded address range";
                   type jt:ipv6addr;
                 }
               }
             }
           }
         }
       }
     }
     list location-pool {
       key name;
       ordered-by user;
       description "Location-based IP address pool";
       max-elements 10;
       leaf name {
         description "Pool name";
         type string {
           length "1 .. 64";
         }
       }
       uses apply-advanced;
       container family {
         presence "enable family";
         description "Address family";
         container inet {
           description "IPv4 location pool";
           uses apply-advanced;
           list location {
             key name;
             description "Relative location of router";
             max-elements 32;
             leaf name {
               description "Location number";
               type union {
                 type string {
                   pattern "<.*>|$.*";
                 }
                 type uint32 {
                   range "1 .. 32";
                 }
               }
             }
             uses apply-advanced;
             leaf address {
               description "IP address/destination prefix";
               type jt:ipv4prefix;
             }
           }
         }
       }
     }
   }
   grouping alg-object {
     uses apply-advanced;
     container traceoptions {
       description "ALG trace options";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       leaf level {
         description "Set level of tracing output";
         default "brief";
         type enumeration {
           enum "brief" {
             description "Brief messages";
           }
           enum "detail" {
             description "Detail messages";
           }
           enum "extensive" {
             description "Extensive messages";
           }
           enum "verbose" {
             description "Verbose messages";
           }
         }
       }
     }
     container alg-manager {
       description "Configure ALG-MANAGER";
       leaf clear-dont-frag-bit {
         description "Enable ALG clear DF(don't frag) bit in IP header";
         type empty;
       }
       container traceoptions {
         description "ALG-MANAGER trace options";
         uses apply-advanced;
         list flag {
           key name;
           ordered-by user;
           description "ALG-MANAGER trace flags";
           leaf name {
             type enumeration {
               enum "all" {
                 description "Trace everything";
               }
             }
           }
           choice level {
             case case_1 {
               leaf extensive {
                 description "Set trace verbosity level to extensive";
                 type empty;
               }
             }
           }
         }
       }
     }
     container alg-support-lib {
       description "Configure ALG-SUPPORT-LIB";
       container traceoptions {
         description "ALG-SUPPORT-LIB trace options";
         uses apply-advanced;
         list flag {
           key name;
           ordered-by user;
           description "ALG-SUPPORT-LIB trace flags";
           leaf name {
             type enumeration {
               enum "all" {
                 description "Trace everything";
               }
             }
           }
           choice level {
             case case_1 {
               leaf extensive {
                 description "Set trace verbosity level to extensive";
                 type empty;
               }
             }
           }
         }
       }
     }
     container dns {
       description "Configure DNS ALG";
       uses apply-advanced;
       leaf disable {
         description "Disable DNS ALG";
         type empty;
       }
       leaf maximum-message-length {
         description "Set maximum message length";
         default "512";
         units "bytes";
         type union {
           type string {
             pattern "<.*>|$.*";
           }
           type uint32 {
             range "512 .. 8192";
           }
         }
       }
       leaf oversize-message-drop {
         description "Drop oversized DNS packets";
         type empty;
       }
       container doctoring {
         description "Configure DNS ALG doctoring";
         uses apply-advanced;
         choice type {
           case case_1 {
             leaf none {
               description "Disable all DNS ALG Doctoring";
               type empty;
             }
           }
           case case_2 {
             leaf sanity-check {
               description "Perform only DNS ALG sanity checks";
               type empty;
             }
           }
         }
       }
       container traceoptions {
         description "DNS ALG trace options";
         uses apply-advanced;
         list flag {
           key name;
           ordered-by user;
           description "DNS ALG trace flags";
           leaf name {
             type enumeration {
               enum "all" {
                 description "Trace everything";
               }
             }
           }
           choice level {
             case case_1 {
               leaf extensive {
                 description "Set trace verbosity level to extensive";
                 type empty;
               }
             }
           }
         }
       }
     }
     container ftp {
       description "Configure FTP ALG";
       leaf disable {
         description "Disable FTP ALG";
         type empty;
       }
       leaf ftps-extension {
         description "Enable secure FTP and FTP-ssl protocols";
         type empty;
       }
       leaf line-break-extension {
         description "Enable CR+LF line termination";
         type empty;
       }
       leaf allow-mismatch-ip-address {
         description "Pass FTP packets with mismatched ip address headers and payload";
         type empty;
       }
       container traceoptions {
         description "FTP ALG trace options";
         uses apply-advanced;
         list flag {
           key name;
           ordered-by user;
           description "FTP ALG trace flags";
           leaf name {
             type enumeration {
               enum "all" {
                 description "Trace everything";
               }
             }
           }
           choice level {
             case case_1 {
               leaf extensive {
                 description "Set trace verbosity level to extensive";
                 type empty;
               }
             }
           }
         }
       }
     }
     container h323 {
       presence "enable h323";
       description "Configure H.323 ALG";
       uses apply-advanced;
       leaf disable {
         description "Disable H.323 ALG";
         type empty;
       }
       leaf endpoint-registration-timeout {
         description "Timeout for endpoints";
         default "64800";
         units "seconds";
         type union {
           type string {
             pattern "<.*>|$.*";
           }
           type uint32 {
             range "10 .. 65535";
           }
         }
       }
       leaf media-source-port-any {
         description "Permit media from any source port on the endpoint";
         type empty;
       }
       container application-screen {
         description "Configure application screens";
         uses apply-advanced;
         container unknown-message {
           description "Configure ALG action on receiving an unknown message";
           uses apply-advanced;
           leaf permit-nat-applied {
             description "Permit unknown messages on packets that are NATed";
             type empty;
           }
           leaf permit-routed {
             description "Permit unknown messages on routed packets";
             type empty;
           }
         }
         container message-flood {
           description "Configure Message flood ALG options";
           uses apply-advanced;
           container gatekeeper {
             description "Set options for gatekeeper messages";
             leaf threshold {
               description "Message flood gatekeeper threshold";
               default "1000";
               units "messages per second";
               type union {
                 type string {
                   pattern "<.*>|$.*";
                 }
                 type uint32 {
                   range "1 .. 50000";
                 }
               }
             }
           }
         }
       }
       container dscp-rewrite {
         description "DSCP code rewrite";
         uses apply-advanced;
         leaf code-point {
           description "Set dscp codepoint 6-bit string";
           type string {
           }
         }
       }
       container traceoptions {
         description "H.323 ALG trace options";
         uses apply-advanced;
         list flag {
           key name;
           ordered-by user;
           description "H.323 ALG trace flags";
           leaf name {
             type enumeration {
               enum "q931" {
                 description "Enable tracing for Q.931 processing";
               }
               enum "h245" {
                 description "Enable tracing for H.245 processing";
               }
               enum "ras" {
                 description "Enable tracing for RAS processing";
               }
               enum "h225-asn1" {
                 description "Enable tracing for H.225 ASN.1 processing";
               }
               enum "h245-asn1" {
                 description "Enable tracing for H.245 ASN.1 processing";
               }
               enum "ras-asn1" {
                 description "Enable tracing for RAS ASN.1 processing";
               }
               enum "chassis-cluster" {
                 description "Enable tracing for H.323 chassis cluster functions";
               }
               enum "all" {
                 description "Trace everything";
               }
             }
           }
           choice level {
             case case_1 {
               leaf terse {
                 description "Set trace verbosity level to terse";
                 type empty;
               }
             }
             case case_2 {
               leaf detail {
                 description "Set trace verbosity level to detail";
                 type empty;
               }
             }
             case case_3 {
               leaf extensive {
                 description "Set trace verbosity level to extensive";
                 type empty;
               }
             }
           }
         }
       }
     }
     container mgcp {
       presence "enable mgcp";
       description "Configure MGCP ALG";
       uses apply-advanced;
       leaf disable {
         description "Disable MGCP ALG";
         type empty;
       }
       leaf inactive-media-timeout {
         description "Set inactive media timeout";
         default "120";
         units "seconds";
         type union {
           type string {
             pattern "<.*>|$.*";
           }
           type uint32 {
             range "10 .. 2550";
           }
         }
       }
       leaf transaction-timeout {
         description "Set transaction timeout";
         default "30";
         units "seconds";
         type union {
           type string {
             pattern "<.*>|$.*";
           }
           type uint32 {
             range "3 .. 50";
           }
         }
       }
       leaf maximum-call-duration {
         description "Set maximum call duration";
         default "720";
         units "minutes";
         type union {
           type string {
             pattern "<.*>|$.*";
           }
           type uint32 {
             range "3 .. 720";
           }
         }
       }
       container application-screen {
         description "Configure application screens";
         uses apply-advanced;
         container unknown-message {
           description "Configure ALG action on receiving an unknown message";
           uses apply-advanced;
           leaf permit-nat-applied {
             description "Permit unknown messages on packets that are NATed";
             type empty;
           }
           leaf permit-routed {
             description "Permit unknown messages on routed packets";
             type empty;
           }
         }
         container message-flood {
           description "Set message flood ALG options";
           leaf threshold {
             description "Message flood threshold";
             default "100";
             units "messages per second per MG";
             type union {
               type string {
                 pattern "<.*>|$.*";
               }
               type uint32 {
                 range "2 .. 50000";
               }
             }
           }
         }
         container connection-flood {
           description "Set connection flood options";
           leaf threshold {
             description "Connection flood threshold";
             default "10";
             units "connection requests per second per MG";
             type union {
               type string {
                 pattern "<.*>|$.*";
               }
               type uint32 {
                 range "2 .. 10000";
               }
             }
           }
         }
       }
       container dscp-rewrite {
         description "DSCP code rewrite";
         uses apply-advanced;
         leaf code-point {
           description "Set dscp codepoint 6-bit string";
           type string {
           }
         }
       }
       container traceoptions {
         description "MGCP ALG trace options";
         uses apply-advanced;
         list flag {
           key name;
           ordered-by user;
           description "MGCP ALG trace flags";
           leaf name {
             type enumeration {
               enum "call" {
                 description "Enable tracing for MGCP call processing";
               }
               enum "decode" {
                 description "Enable tracing for MGCP decoder operations";
               }
               enum "error" {
                 description "Enable tracing for MGCP processing errors";
               }
               enum "chassis-cluster" {
                 description "Enable tracing for MGCP chassis cluster functions";
               }
               enum "nat" {
                 description "Enable tracing for MGCP Network Address Translation (NAT) processing";
               }
               enum "packet" {
                 description "Enable tracing for MGCP protocol packet processing";
               }
               enum "rm" {
                 description "Enable tracing MGCP Resource Management (Resmgr) functions";
               }
               enum "all" {
                 description "Trace everything";
               }
             }
           }
           choice level {
             case case_1 {
               leaf extensive {
                 description "Set trace verbosity level to extensive";
                 type empty;
               }
             }
           }
         }
       }
     }
     container msrpc {
       description "Configure MSRPC ALG";
       leaf disable {
         description "Disable MSRPC ALG";
         type empty;
       }
       leaf group-max-usage {
         description "Set maximum group usage percentage, default 80";
         default "80";
         type union {
           type string {
             pattern "<.*>|$.*";
           }
           type uint32 {
             range "10 .. 100";
           }
         }
       }
       leaf map-entry-timeout {
         description "Set entry timeout, default 8hour";
         default "480";
         units "minutes";
         type union {
           type string {
             pattern "<.*>|$.*";
           }
           type uint32 {
             range "5 .. 4320";
           }
         }
       }
       container traceoptions {
         description "MSRPC ALG trace options";
         uses apply-advanced;
         list flag {
           key name;
           ordered-by user;
           description "MSRPC ALG trace flags";
           leaf name {
             type enumeration {
               enum "all" {
                 description "Trace everything";
               }
             }
           }
           choice level {
             case case_1 {
               leaf extensive {
                 description "Set trace verbosity level to extensive";
                 type empty;
               }
             }
           }
         }
       }
     }
     container sunrpc {
       description "Configure SUNRPC ALG";
       leaf disable {
         description "Disable SUNRPC ALG";
         type empty;
       }
       leaf group-max-usage {
         description "Set maximum group usage percentage, default 80";
         default "80";
         type union {
           type string {
             pattern "<.*>|$.*";
           }
           type uint32 {
             range "10 .. 100";
           }
         }
       }
       leaf map-entry-timeout {
         description "Set entry timeout, default 8hour";
         default "480";
         units "minutes";
         type union {
           type string {
             pattern "<.*>|$.*";
           }
           type uint32 {
             range "5 .. 4320";
           }
         }
       }
       container traceoptions {
         description "SUNRPC ALG trace options";
         uses apply-advanced;
         list flag {
           key name;
           ordered-by user;
           description "SUNRPC ALG trace flags";
           leaf name {
             type enumeration {
               enum "all" {
                 description "Trace everything";
               }
             }
           }
           choice level {
             case case_1 {
               leaf extensive {
                 description "Set trace verbosity level to extensive";
                 type empty;
               }
             }
           }
         }
       }
     }
     container rsh {
       presence "enable rsh";
       description "Configure RSH ALG";
       uses apply-advanced;
       leaf disable {
         description "Disable RSH ALG";
         type empty;
       }
       container traceoptions {
         description "RSH ALG trace options";
         uses apply-advanced;
         list flag {
           key name;
           ordered-by user;
           description "RSH ALG trace flags";
           leaf name {
             type enumeration {
               enum "all" {
                 description "Trace everything";
               }
             }
           }
           choice level {
             case case_1 {
               leaf extensive {
                 description "Set trace verbosity level to extensive";
                 type empty;
               }
             }
           }
         }
       }
     }
     container rtsp {
       presence "enable rtsp";
       description "Configure RTSP ALG";
       leaf disable {
         description "Disable RTSP ALG";
         type empty;
       }
       container traceoptions {
         description "RTSP ALG trace options";
         uses apply-advanced;
         list flag {
           key name;
           ordered-by user;
           description "RTSP ALG trace flags";
           leaf name {
             type enumeration {
               enum "all" {
                 description "Trace everything";
               }
             }
           }
           choice level {
             case case_1 {
               leaf extensive {
                 description "Set trace verbosity level to extensive";
                 type empty;
               }
             }
           }
         }
       }
     }
     container sccp {
       presence "enable sccp";
       description "Configure SCCP ALG";
       uses apply-advanced;
       leaf disable {
         description "Disable SCCP ALG";
         type empty;
       }
       leaf inactive-media-timeout {
         description "Set inactive media timeout";
         default "120";
         units "seconds";
         type union {
           type string {
             pattern "<.*>|$.*";
           }
           type uint32 {
             range "10 .. 600";
           }
         }
       }
       container application-screen {
         description "Configure application screens";
         uses apply-advanced;
         container unknown-message {
           description "Configure ALG action on receiving an unknown message";
           uses apply-advanced;
           leaf permit-nat-applied {
             description "Permit unknown messages on packets that are NATed";
             type empty;
           }
           leaf permit-routed {
             description "Permit unknown messages on routed packets";
             type empty;
           }
         }
         container call-flood {
           description "Configure call flood thresholds";
           leaf threshold {
             description "Calls per second per client";
             default "20";
             type union {
               type string {
                 pattern "<.*>|$.*";
               }
               type uint32 {
                 range "2 .. 1000";
               }
             }
           }
         }
       }
       container dscp-rewrite {
         description "DSCP code rewrite";
         uses apply-advanced;
         leaf code-point {
           description "Set dscp codepoint 6-bit string";
           type string {
           }
         }
       }
       container traceoptions {
         description "SCCP ALG trace options";
         uses apply-advanced;
         list flag {
           key name;
           ordered-by user;
           description "SCCP ALG trace flags";
           leaf name {
             type enumeration {
               enum "call" {
                 description "Enable tracing SCCP call processing";
               }
               enum "cli" {
                 description "Enable tracing SCCP cli processing";
               }
               enum "decode" {
                 description "Enable tracing for SCCP decoder operations";
               }
               enum "error" {
                 description "Enable tracing for SCCP processing errors";
               }
               enum "chassis-cluster" {
                 description "Enable tracing for SCCP chassis cluster functions";
               }
               enum "init" {
                 description "Enable tracing for SCCP initialization errors";
               }
               enum "nat" {
                 description "Enable tracing for SCCP Network Address Translation (NAT) processing";
               }
               enum "rm" {
                 description "Enable tracing SCCP Resource Management (Resmgr) functions";
               }
               enum "all" {
                 description "Trace everything";
               }
             }
           }
           choice level {
             case case_1 {
               leaf extensive {
                 description "Set trace verbosity level to extensive";
                 type empty;
               }
             }
           }
         }
       }
     }
     container sip {
       presence "enable sip";
       description "Configure SIP ALG";
       uses apply-advanced;
       leaf disable {
         description "Disable SIP ALG";
         type empty;
       }
       leaf inactive-media-timeout {
         description "Set inactive media timeout";
         default "120";
         units "seconds";
         type union {
           type string {
             pattern "<.*>|$.*";
           }
           type uint32 {
             range "10 .. 2550";
           }
         }
       }
       leaf maximum-call-duration {
         description "Set maximum call duration";
         default "720";
         units "minutes";
         type union {
           type string {
             pattern "<.*>|$.*";
           }
           type uint32 {
             range "3 .. 720";
           }
         }
       }
       leaf t1-interval {
         description "Set T1 interval";
         default "500";
         units "milliseconds";
         type union {
           type string {
             pattern "<.*>|$.*";
           }
           type uint32 {
             range "500 .. 5000";
           }
         }
       }
       leaf t4-interval {
         description "Set T4 interval";
         default "5";
         units "seconds";
         type union {
           type string {
             pattern "<.*>|$.*";
           }
           type uint32 {
             range "5 .. 10";
           }
         }
       }
       leaf c-timeout {
         description "Set C timeout";
         default "3";
         units "minutes";
         type union {
           type string {
             pattern "<.*>|$.*";
           }
           type uint32 {
             range "3 .. 10";
           }
         }
       }
       leaf disable-call-id-hiding {
         description "Disable translation of host IP in Call-ID header";
         status deprecated;
         type empty;
       }
       leaf retain-hold-resource {
         description "Retain SDP resources during call hold";
         type empty;
       }
       container hide-via-headers {
         description "Hide via headers options";
         uses apply-advanced;
         leaf disable {
           description "Disable hide via headers function";
           type empty;
         }
       }
       list distribution-ip {
         key name;
         ordered-by user;
         description "Configure SIP distribute server IPV6 or IPV4 ip";
         leaf name {
           description "Distribution IP address";
           type jt:ipaddr;
         }
         uses apply-advanced;
         container distribute-to {
           description "Distribute sip packet";
           uses apply-advanced;
           container fpc {
             description "FPC card number";
             uses apply-advanced;
             leaf slot {
               description "FPC slot number";
               type union {
                 type string {
                   pattern "<.*>|$.*";
                 }
                 type uint32 {
                   range "0 .. 127";
                 }
               }
             }
             container pic {
               description "PIC card number";
               uses apply-advanced;
               leaf slot {
                 description "Physical Interface Card number";
                 type union {
                   type string {
                     pattern "<.*>|$.*";
                   }
                   type uint32 {
                     range "0 .. 5";
                   }
                 }
               }
             }
           }
         }
       }
       container application-screen {
         description "Configure application screens";
         uses apply-advanced;
         container unknown-message {
           description "Configure ALG action on receiving an unknown message";
           uses apply-advanced;
           leaf permit-nat-applied {
             description "Permit unknown messages on packets that are NATed";
             type empty;
           }
           leaf permit-routed {
             description "Permit unknown messages on routed packets";
             type empty;
           }
         }
         container protect {
           description "Configure Protect options";
           uses apply-advanced;
           container deny {
             presence "enable deny";
             description "Protect deny options";
             uses apply-advanced;
             choice deny-choice {
               case case_1 {
                 list destination-ip {
                   key name;
                   ordered-by user;
                   description "List of protected destination server IP";
                   leaf name {
                     description "Protected destination server IPv4 or IPv6 entry";
                     type jt:ipprefix;
                   }
                   uses apply-advanced;
                 }
               }
               case case_2 {
                 leaf all {
                   description "Enable attack protection for all servers";
                   type empty;
                 }
               }
             }
             leaf timeout {
               description "Timeout value for SIP INVITE attack table entry";
               default "5";
               units "seconds";
               type union {
                 type string {
                   pattern "<.*>|$.*";
                 }
                 type uint32 {
                   range "1 .. 3600";
                 }
               }
             }
           }
         }
       }
       container dscp-rewrite {
         description "DSCP code rewrite";
         uses apply-advanced;
         leaf code-point {
           description "Set dscp codepoint 6-bit string";
           type string {
           }
         }
       }
       container traceoptions {
         description "SIP ALG trace options";
         uses apply-advanced;
         list flag {
           key name;
           ordered-by user;
           description "SIP ALG trace flags";
           leaf name {
             type enumeration {
               enum "call" {
                 description "Enable tracing for SIP call processing";
               }
               enum "chassis-cluster" {
                 description "Enable tracing for SIP chassis cluster functions";
               }
               enum "nat" {
                 description "Enable tracing for SIP Network Address Translation (NAT) processing";
               }
               enum "parser" {
                 description "Enable tracing for SIP parser operations";
               }
               enum "rm" {
                 description "Enable tracing SIP Resource Management (Resmgr) functions";
               }
               enum "all" {
                 description "Trace everything";
               }
             }
           }
           choice level {
             case case_1 {
               leaf terse {
                 description "Set trace verbosity level to terse";
                 type empty;
               }
             }
             case case_2 {
               leaf detail {
                 description "Set trace verbosity level to detail";
                 type empty;
               }
             }
             case case_3 {
               leaf extensive {
                 description "Set trace verbosity level to extensive";
                 type empty;
               }
             }
           }
         }
       }
     }
     container sql {
       presence "enable sql";
       description "Configure SQL ALG";
       leaf disable {
         description "Disable SQL ALG";
         type empty;
       }
       container traceoptions {
         description "SQL ALG trace options";
         uses apply-advanced;
         list flag {
           key name;
           ordered-by user;
           description "SQL ALG trace flags";
           leaf name {
             type enumeration {
               enum "all" {
                 description "Trace everything";
               }
             }
           }
           choice level {
             case case_1 {
               leaf extensive {
                 description "Set trace verbosity level to extensive";
                 type empty;
               }
             }
           }
         }
       }
     }
     container talk {
       description "Configure Talk ALG";
       leaf disable {
         description "Disable Talk ALG";
         type empty;
       }
       container traceoptions {
         description "TALK ALG trace options";
         uses apply-advanced;
         list flag {
           key name;
           ordered-by user;
           description "TALK ALG trace flags";
           leaf name {
             type enumeration {
               enum "all" {
                 description "Trace everything";
               }
             }
           }
           choice level {
             case case_1 {
               leaf extensive {
                 description "Set trace verbosity level to extensive";
                 type empty;
               }
             }
           }
         }
       }
     }
     container tftp {
       description "Configure TFTP ALG";
       leaf disable {
         description "Disable TFTP ALG";
         type empty;
       }
       container traceoptions {
         description "TFTP ALG trace options";
         uses apply-advanced;
         list flag {
           key name;
           ordered-by user;
           description "TFTP ALG trace flags";
           leaf name {
             type enumeration {
               enum "all" {
                 description "Trace everything";
               }
             }
           }
           choice level {
             case case_1 {
               leaf extensive {
                 description "Set trace verbosity level to extensive";
                 type empty;
               }
             }
           }
         }
       }
     }
     container pptp {
       description "Configure PPTP ALG";
       leaf disable {
         description "Disable PPTP ALG";
         type empty;
       }
       container traceoptions {
         description "PPTP ALG trace options";
         uses apply-advanced;
         list flag {
           key name;
           ordered-by user;
           description "PPTP ALG trace flags";
           leaf name {
             type enumeration {
               enum "all" {
                 description "Trace everything";
               }
             }
           }
           choice level {
             case case_1 {
               leaf extensive {
                 description "Set trace verbosity level to extensive";
                 type empty;
               }
             }
           }
         }
       }
     }
     container ike-esp-nat {
       description "Configure IKE-ESP ALG with NAT";
       uses apply-advanced;
       leaf enable {
         description "Enable IKE-ESP ALG";
         type empty;
       }
       leaf esp-gate-timeout {
         description "Set ESP gate timeout";
         default "5";
         units "seconds";
         type union {
           type string {
             pattern "<.*>|$.*";
           }
           type uint32 {
             range "2 .. 30";
           }
         }
       }
       leaf esp-session-timeout {
         description "Set ESP session timeout";
         default "1800";
         units "seconds";
         type union {
           type string {
             pattern "<.*>|$.*";
           }
           type uint32 {
             range "60 .. 2400";
           }
         }
       }
       leaf state-timeout {
         description "Set ALG state timeout";
         default "14400";
         units "seconds";
         type union {
           type string {
             pattern "<.*>|$.*";
           }
           type uint32 {
             range "180 .. 86400";
           }
         }
       }
       container traceoptions {
         description "IKE-ESP ALG trace options";
         uses apply-advanced;
         list flag {
           key name;
           ordered-by user;
           description "IKE-ESP ALG trace flags";
           leaf name {
             type enumeration {
               enum "all" {
                 description "Trace everything";
               }
             }
           }
           choice level {
             case case_1 {
               leaf extensive {
                 description "Set trace verbosity level to extensive";
                 type empty;
               }
             }
           }
         }
       }
     }
     container twamp {
       presence "enable twamp";
       description "Configure TWAMP ALG";
       uses apply-advanced;
       container traceoptions {
         description "TWAMP ALG trace options";
         uses apply-advanced;
         list flag {
           key name;
           ordered-by user;
           description "TWAMP ALG trace flags";
           leaf name {
             type enumeration {
               enum "all" {
                 description "Trace everything";
               }
             }
           }
           choice level {
             case case_1 {
               leaf extensive {
                 description "Trace verbosity level to extensive";
                 type empty;
               }
             }
           }
         }
       }
     }
   }
   grouping anti-spam-feature {
     description "Anti-spam feature";
     uses apply-advanced;
     container sbl {
       description "SBL settings";
       presence "enable sbl";
       uses sbl-type;
     }
   }
   grouping anti-virus-feature {
     description "Anti-virus feature";
     uses apply-advanced;
     container mime-whitelist {
       description "Anti-virus MIME whitelist";
       status deprecated;
       uses apply-advanced;
       leaf list {
         description "MIME list";
         type string;
       }
       leaf exception {
         description "Exception settings for MIME white list";
         type string;
       }
     }
     leaf url-whitelist {
       description "Anti-virus URL white list";
       status deprecated;
       type string;
     }
     leaf type {
       description "Anti-virus engine type";
       status deprecated;
       type enumeration {
         enum "sophos-engine" {
           description "Anti-virus sophos-engine";
           status deprecated;
         }
         enum "avira-engine" {
           description "Anti-virus avira-engine";
           status deprecated;
         }
         enum "anti-virus-none" {
           status deprecated;
         }
       }
     }
     list profile {
       key name;
       ordered-by user;
       description "Anti-virus profile";
       leaf name {
         description "Anti-virus profile name";
         type string {
           length "1 .. 29";
         }
       }
       uses apply-advanced;
       container fallback-options {
         description "Anti-virus fallback options";
         presence "enable fallback-options";
         uses av-fallback-settings;
       }
       container notification-options {
         description "Anti-virus notification options";
         presence "enable notification-options";
         uses anti-virus-notification-options;
       }
       container mime-whitelist {
         description "Anti-virus MIME whitelist";
         uses apply-advanced;
         leaf list {
           description "MIME list";
           type string;
         }
         leaf exception {
           description "Exception settings for MIME white list";
           type string;
         }
       }
       leaf url-whitelist {
         description "Anti-virus URL white list";
         type string;
       }
     }
     container traceoptions {
       description "Trace options for anti-virus feature";
       status deprecated;
       uses anti-virus-traceoptions;
     }
     container sophos-engine {
       description "Anti-virus sophos-engine";
       status deprecated;
       uses apply-advanced;
       container server {
         description "SAV and Anti-Spam first hop DNS server";
         status deprecated;
         uses apply-advanced;
         leaf ip {
           description "SAV and Anti-Spam first hop DNS server ip";
           type jt:ipaddr;
         }
         leaf routing-instance {
           description "Routing instance name";
           type string;
         }
       }
       leaf sxl-timeout {
         description "Sxl sophos anti-virus engine timeout";
         status deprecated;
         units "seconds";
         type union {
           type string {
             pattern "<.*>|$.*";
           }
           type uint32 {
             range "1 .. 5";
           }
         }
       }
       leaf sxl-retry {
         description "Sxl sophos anti-virus engine query retry (number of times)";
         status deprecated;
         type union {
           type string {
             pattern "<.*>|$.*";
           }
           type uint32 {
             range "0 .. 5";
           }
         }
       }
       container pattern-update {
         description "Anti-virus sophos-engine pattern update";
         presence "enable pattern-update";
         status deprecated;
         uses anti-virus-pattern-update;
       }
       list profile {
         key name;
         ordered-by user;
         description "Anti-virus sophos-engine profile";
         status deprecated;
         leaf name {
           description "Anti-virus sophos-engine profile name";
           type string {
             length "1 .. 29";
           }
         }
         uses apply-advanced;
         container fallback-options {
           description "Anti-virus sophos-engine fallback options";
           presence "enable fallback-options";
           uses av-fallback-settings;
         }
         container scan-options {
           description "Anti-virus sophos-engine scan options";
           presence "enable scan-options";
           uses sophos-scan-options;
         }
         container trickling {
           description "Anti-virus trickling";
           presence "enable trickling";
           uses anti-virus-trickling;
         }
         container notification-options {
           description "Anti-virus notification options";
           presence "enable notification-options";
           uses anti-virus-notification-options;
         }
         container mime-whitelist {
           description "Anti-virus MIME whitelist";
           uses apply-advanced;
           leaf list {
             description "MIME list";
             type string;
           }
           leaf exception {
             description "Exception settings for MIME white list";
             type string;
           }
         }
         leaf url-whitelist {
           description "Anti-virus URL white list";
           type string;
         }
       }
     }
   }
   grouping anti-virus-notification-options {
     description "Anti-virus notification options";
     uses apply-advanced;
     container virus-detection {
       presence "enable virus-detection";
       description "Virus detection notification";
       uses apply-advanced;
       leaf type {
         description "Virus detection notification type";
         type enumeration {
           enum "protocol-only" {
             description "Notification in protocol level only";
           }
           enum "message" {
             description "Notification in message";
           }
         }
       }
       choice notify-mail-sender-choice {
         leaf notify-mail-sender {
           description "Notify mail sender";
           type empty;
         }
         leaf no-notify-mail-sender {
           description "Don't notify mail sender";
           type empty;
         }
       }
       leaf custom-message {
         description "Custom message for notification";
         type string {
           length "1 .. 512";
         }
       }
       leaf custom-message-subject {
         description "Custom message subject for notification";
         type string {
           length "1 .. 255";
         }
       }
     }
     container fallback-block {
       presence "enable fallback-block";
       description "Fallback block notification";
       uses apply-advanced;
       leaf type {
         description "Fallback block notification type";
         type enumeration {
           enum "protocol-only" {
             description "Notification in protocol level only";
           }
           enum "message" {
             description "Notification in message";
           }
         }
       }
       choice notify-mail-sender-choice {
         leaf notify-mail-sender {
           description "Notify mail sender";
           type empty;
         }
         leaf no-notify-mail-sender {
           description "Don't notify mail sender";
           type empty;
         }
       }
       leaf custom-message {
         description "Custom message for notification";
         type string {
           length "1 .. 512";
         }
       }
       leaf custom-message-subject {
         description "Custom message subject for notification";
         type string {
           length "1 .. 255";
         }
       }
     }
     container fallback-non-block {
       presence "enable fallback-non-block";
       description "Fallback non block notification";
       uses apply-advanced;
       choice notify-mail-recipient-choice {
         leaf notify-mail-recipient {
           description "Notify mail recipient";
           type empty;
         }
         leaf no-notify-mail-recipient {
           description "Don't notify mail recipient";
           type empty;
         }
       }
       leaf custom-message {
         description "Custom message for notification";
         type string {
           length "1 .. 512";
         }
       }
       leaf custom-message-subject {
         description "Custom message subject for notification";
         type string {
           length "1 .. 255";
         }
       }
     }
   }
   grouping anti-virus-pattern-update {
     description "Anti-virus pattern update";
     uses apply-advanced;
     container email-notify {
       presence "enable email-notify";
       description "Virus pattern file updated notification";
       uses apply-advanced;
       leaf admin-email {
         description "Admin emails to be notified about pattern file update";
         type string {
           length "1 .. 255";
         }
       }
       leaf custom-message {
         description "Custom message for notification";
         type string {
           length "1 .. 512";
         }
       }
       leaf custom-message-subject {
         description "Custom message subject for notification";
         type string {
           length "1 .. 255";
         }
       }
     }
     leaf url {
       description "Server URL";
       type string {
         length "1 .. 256";
       }
     }
     leaf proxy-profile {
       description "Proxy profile";
       type string {
         length "1 .. 64";
       }
     }
     leaf routing-instance {
       description "Routing instance name";
       type string;
     }
     leaf interval {
       description "Interval in minutes to check the update";
       type union {
         type string {
           pattern "<.*>|$.*";
         }
         type uint32 {
           range "10 .. 10080";
         }
       }
     }
     leaf start-time {
       description "Start time (YYYY-MM-DD.HH:MM:SS)";
       type jt:time;
     }
     leaf no-autoupdate {
       description "Don't automatically update anti-virus pattern";
       type empty;
     }
   }
   grouping anti-virus-traceoptions {
     description "Trace options for anti-virus feature";
     uses apply-advanced;
     list flag {
       key name;
       ordered-by user;
       description "Trace options for anti-virus feature flag";
       leaf name {
         description "Trace options for anti-virus feature flag name";
         type enumeration {
           enum "basic" {
             description "Trace anti-virus module generic basic information";
           }
           enum "detail" {
             description "Trace anti-virus module generic detail information";
           }
           enum "engine" {
             description "Trace scan engine information";
           }
           enum "pattern" {
             description "Trace detail information of pattern loading";
           }
           enum "updater" {
             description "Trace pattern updater process activities";
           }
           enum "manager" {
             description "Trace anti-virus manager process activities";
           }
           enum "worker" {
             description "Trace anti-virus worker process activities";
           }
           enum "sendmail" {
             description "Trace mail notifier process activities";
           }
           enum "ipc" {
             description "Trace communication events with PFE";
           }
           enum "event" {
             description "Trace communication events between RE side processes";
           }
           enum "statistics" {
             description "Trace statistics information";
           }
           enum "all" {
             description "Enable trace all anti-virus trace options";
           }
         }
       }
     }
   }
   grouping anti-virus-trickling {
     description "Anti-virus trickling";
     leaf timeout {
       description "Trickling timeout";
       type union {
         type string {
           pattern "<.*>|$.*";
         }
         type uint32 {
           range "0 .. 600";
         }
       }
     }
   }
   grouping any_filter {
     leaf name {
       description "Filter name";
       type string {
       }
     }
     uses apply-advanced;
     list term {
       key name;
       ordered-by user;
       description "Define a firewall term";
       leaf name {
         description "Term name";
         type string {
         }
       }
       uses apply-advanced;
       container from {
         description "Define match criteria";
         uses apply-advanced;
         list interface {
           key name;
           ordered-by user;
           description "Match interface name";
           uses match_interface_object_oam;
         }
         list interface-set {
           key name;
           ordered-by user;
           description "Match interface in set";
           uses match_interface_set_object;
         }
         choice packet-length_choice {
           case case_1 {
             leaf-list packet-length {
               ordered-by user;
               description "Range of values";
               type string {
               }
             }
           }
           case case_2 {
             leaf-list packet-length-except {
               ordered-by user;
               description "Range of values";
               type string {
               }
             }
           }
         }
         choice forwarding-class_choice {
           case case_1 {
             leaf-list forwarding-class {
               ordered-by user;
               description "String name";
               type string {
               }
             }
           }
           case case_2 {
             leaf-list forwarding-class-except {
               ordered-by user;
               description "String name";
               type string {
               }
             }
           }
         }
         choice loss-priority_choice {
           case case_1 {
           }
           case case_2 {
           }
         }
         choice policy-map_choice {
           case case_1 {
             leaf-list policy-map {
               ordered-by user;
               description "String name";
               type string {
                 length "1 .. 64";
               }
             }
           }
           case case_2 {
             leaf-list policy-map-except {
               ordered-by user;
               description "String name";
               type string {
                 length "1 .. 64";
               }
             }
           }
         }
       }
       container then {
         description "Action to take if the 'from' condition is matched";
         uses apply-advanced;
         choice policer-choice {
           case case_1 {
             leaf policer {
               description "Name of policer to use to rate-limit traffic";
               type string {
               }
             }
           }
           case case_2 {
             container three-color-policer {
               description "Police the packet using a three-color-policer";
               uses apply-advanced;
               choice type-choice {
                 case case_1 {
                   leaf single-rate {
                     description "Name of single-rate three-color policer to use to rate-limit traffic";
                     type string {
                     }
                   }
                 }
                 case case_2 {
                   leaf single-packet-rate {
                     description "Name of single-packet-rate three-color policer to use to rate-limit traffic";
                     type string {
                     }
                   }
                 }
                 case case_3 {
                   leaf two-rate {
                     description "Name of two-rate three-color policer to use to rate-limit traffic";
                     type string {
                     }
                   }
                 }
                 case case_4 {
                   leaf two-packet-rate {
                     description "Name of two-packet-rate three-color policer to use to rate-limit traffic";
                     type string {
                     }
                   }
                 }
               }
             }
           }
           case case_3 {
           }
         }
         choice policy-map-choice {
           case case_1 {
             leaf clear-policy-map {
               description "Clear the policy marking";
               type empty;
             }
           }
           case case_2 {
             leaf policy-map {
               description "Policy map action";
               type string {
               }
             }
           }
         }
         leaf count {
           description "Count the packet in the named counter";
           type string {
           }
         }
         leaf service-accounting-deferred {
           description "Count the packets for deferred service accounting";
           type empty;
         }
         leaf loss-priority {
           description "Classify packet to loss-priority";
           type enumeration {
             enum "low" {
               description "Loss priority low";
             }
             enum "high" {
               description "Loss priority high";
             }
             enum "medium-low" {
               description "Loss priority medium-low";
             }
             enum "medium-high" {
               description "Loss priority medium-high";
             }
           }
         }
         leaf port-mirror {
           description "Port-mirror the packet";
           type empty;
         }
         leaf forwarding-class {
           description "Classify packet to forwarding class";
           type string {
           }
         }
         choice designation {
           case case_1 {
           }
           case case_2 {
             leaf accept {
               description "Accept the packet";
               type empty;
             }
           }
           case case_3 {
             leaf discard {
               description "Discard the packet";
               type empty;
             }
           }
           case case_4 {
             leaf next {
               description "Continue to next term in a filter";
               type enumeration {
                 enum "term" {
                   description "Continue to next term in a filter";
                 }
               }
             }
           }
         }
       }
     }
   }
   grouping apbr_rule_type {
     leaf name {
       description "Rule name";
       type string {
         length "1 .. 63";
       }
     }
     uses apply-advanced;
     container match {
       presence "enable match";
       description "Specify security rule  match-criteria";
       uses apply-advanced;
       leaf-list dynamic-application {
         ordered-by user;
         type string;
       }
       leaf-list dynamic-application-group {
         ordered-by user;
         description "Specify dynamic application group name to match";
         type string;
       }
       leaf-list category {
         ordered-by user;
         description "Url category";
         type string;
       }
     }
     container then {
       presence "enable then";
       description "Specify rule action to take when packet match criteria";
       uses apply-advanced;
       container routing-instance {
         description "Packets are directed to specified routing instance";
         leaf routing-instance-name {
           description "Name of routing instance";
           type string {
           }
         }
       }
       container sla-rule {
         presence "enable sla-rule";
         description "SLA Rule";
         uses apply-advanced;
         leaf sla-rule-name {
           description "SLA rule name";
           type string;
         }
       }
     }
   }
   grouping appfw_rule_type {
     leaf name {
       description "Rule name";
       type string {
         length "1 .. 63";
       }
     }
     uses apply-advanced;
     container match {
       presence "enable match";
       description "Specify security rule  match-criteria";
       uses apply-advanced;
       leaf-list dynamic-application {
         ordered-by user;
         type string;
       }
       leaf-list dynamic-application-group {
         ordered-by user;
         description "Specify dynamic application group name to match";
         type string;
       }
       leaf ssl-encryption {
         description "Select SSL encryption rules";
         type enumeration {
           enum "any" {
             description "Encrypted and non-encrypted rule";
           }
           enum "yes" {
             description "Encrypted rule";
           }
           enum "no" {
             description "Non-encrypted rule";
           }
         }
       }
     }
     container then {
       presence "enable then";
       description "Specify rule action to take when packet match criteria";
       uses apply-advanced;
       choice action {
         case case_1 {
           leaf permit {
             description "Permit packets";
             type empty;
           }
         }
         case case_2 {
           container deny {
             presence "enable deny";
             description "Deny packets";
             uses apply-advanced;
             leaf block-message {
               description "Redirect sessions";
               type empty;
             }
           }
         }
         case case_3 {
           container reject {
             presence "enable reject";
             description "Reject packets";
             uses apply-advanced;
             leaf block-message {
               description "Redirect sessions";
               type empty;
             }
           }
         }
       }
     }
   }
   grouping application_object {
     leaf name {
       description "Application name";
       type string {
         length "1 .. 63";
       }
     }
     uses apply-advanced;
     leaf description {
       description "Text description of application";
       type string {
         length "1 .. 900";
       }
     }
     list term {
       key name;
       ordered-by user;
       description "Define individual application protocols";
       max-elements 8;
       uses term_object;
     }
     leaf application-protocol {
       description "Application protocol type";
       type enumeration {
         enum "bootp" {
           description "Bootstrap protocol";
         }
         enum "dce-rpc" {
           description "DCE RPC";
         }
         enum "dce-rpc-portmap" {
           description "DCE RPC portmap";
         }
         enum "dns" {
           description "Domain Name Service";
         }
         enum "exec" {
           description "Remote Execution Protocol";
         }
         enum "ftp" {
           description "File Transfer Protocol";
         }
         enum "ftp-data" {
           description "File Transfer Protocol Data Session";
         }
         enum "gprs-gtp-c" {
           description "GPRS Tunneling Control Plane";
         }
         enum "gprs-gtp-u" {
           description "GPRS Tunneling User Plane";
         }
         enum "gprs-gtp-v0" {
           description "GPRS Tunneling Version 0";
         }
         enum "gprs-sctp" {
           description "GPRS Stream Control Protocol";
         }
         enum "h323" {
           description "H.323";
         }
         enum "icmp" {
           description "ICMP";
         }
         enum "icmpv6" {
           description "ICMPv6";
         }
         enum "ignore" {
           description "Ignore application type";
         }
         enum "iiop" {
           description "Internet Inter-ORB Protocol";
         }
         enum "ike-esp-nat" {
           description "IKE/ESP with NAT";
         }
         enum "ip" {
           description "IP";
         }
         enum "login" {
           description "Login";
         }
         enum "mgcp-ca" {
           description "MGCP-CA";
         }
         enum "mgcp-ua" {
           description "MGCP-UA";
         }
         enum "ms-rpc" {
           description "Microsoft RPC";
         }
         enum "netbios" {
           description "NetBIOS";
         }
         enum "netshow" {
           description "NetShow";
         }
         enum "none" {
           description "None";
         }
         enum "pptp" {
           description "Point-to-Point Tunneling Protocol";
         }
         enum "q931" {
           description "Q.931";
         }
         enum "ras" {
           description "RAS";
         }
         enum "realaudio" {
           description "RealAudio";
         }
         enum "rpc" {
           description "RPC";
         }
         enum "rpc-portmap" {
           description "RPC portmap";
         }
         enum "rsh" {
           description "Remote Shell";
         }
         enum "rtsp" {
           description "Real Time Streaming Protocol";
         }
         enum "sccp" {
           description "Skinny Client Control Protocol";
         }
         enum "sip" {
           description "Session Initiation Protocol";
         }
         enum "shell" {
           description "Shell";
         }
         enum "snmp" {
           description "SNMP";
         }
         enum "sqlnet" {
           description "SQLNet";
         }
         enum "sqlnet-v2" {
           description "Oracle SQL*Net Version 2";
         }
         enum "sun-rpc" {
           description "Sun Microsystems RPC";
         }
         enum "talk" {
           description "Talk Program";
         }
         enum "tftp" {
           description "Trivial File Transfer Protocol";
         }
         enum "traceroute" {
           description "Traceroute";
         }
         enum "http" {
           description "Hypertext Transfer Protocol";
         }
         enum "winframe" {
           description "WinFrame";
         }
         enum "https" {
           description "Hypertext Transfer Protocol";
         }
         enum "imap" {
           description "Internet Mail Access Protocol";
         }
         enum "smtp" {
           description "Simple Mail Transfer Protocol";
         }
         enum "ssh" {
           description "Secure Shell Protocol";
         }
         enum "telnet" {
           description "Telnet Protocol";
         }
         enum "twamp" {
           description "Two Way Active Meaurement Protocol";
         }
       }
     }
     leaf protocol {
       description "Match IP protocol type";
       type string;
     }
     leaf source-port {
       description "Match TCP/UDP source port";
       type string;
     }
     leaf destination-port {
       description "Match TCP/UDP destination port";
       type string;
     }
     leaf ether-type {
       description "Match ether type";
       type string {
       }
     }
     leaf icmp-type {
       description "Match ICMP message type";
       type string;
     }
     leaf icmp6-type {
       description "Match ICMP6 message type";
       type string;
     }
     leaf icmp-code {
       description "Match ICMP message code";
       type string;
     }
     leaf icmp6-code {
       description "Match ICMP6 message code";
       type string;
     }
     leaf rpc-program-number {
       description "Match range of RPC program numbers";
       type string {
       }
     }
     leaf uuid {
       description "Match universal unique identifier for DCE RPC objects";
       type string {
       }
     }
     leaf inactivity-timeout {
       description "Application-specific inactivity timeout";
       units "seconds";
       type string;
     }
     choice dns-choice {
       case case_1 {
         leaf do-not-translate-AAAA-query-to-A-query {
           description "Knob to control the translation of AAAA query to A query";
           type empty;
         }
       }
       case case_2 {
         leaf do-not-translate-A-query-to-AAAA-query {
           description "Knob to control the translation of A query to AAAA query";
           type empty;
         }
       }
     }
   }
   grouping application_set_object {
     leaf name {
       description "Application set name";
       type string {
         length "1 .. 63";
       }
     }
     uses apply-advanced;
     leaf description {
       description "Text description of application set";
       type string {
         length "1 .. 900";
       }
     }
     list application {
       key name;
       ordered-by user;
       description "Application to be included in the set";
       leaf name {
         description "Application name";
         type string {
           length "1 .. 63";
         }
       }
       uses apply-advanced;
     }
     list application-set {
       key name;
       ordered-by user;
       description "Define an application-set";
       leaf name {
         description "Define an application-set name";
         type string {
           length "1 .. 63";
         }
       }
       uses apply-advanced;
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping appqoe-probe-params {
     description "Active probe parameters";
     uses apply-advanced;
     container data-fill {
       description "Probe Data Payload content";
       uses apply-advanced;
       leaf fill {
         description "Repetitive payload string ";
         type string {
           length "1 .. 63";
         }
       }
     }
     container data-size {
       presence "enable data-size";
       description "Probe data size";
       uses apply-advanced;
       leaf size {
         description "Data Payload size of probe packet";
         type union {
           type string {
             pattern "<.*>|$.*";
           }
           type uint32 {
             range "4 .. 256";
           }
         }
       }
     }
     container probe-interval {
       presence "enable probe-interval";
       description "Time interval between 2 consecutive probes";
       uses apply-advanced;
       leaf interval {
         description "Interval value in sec";
         default "5";
         type union {
           type string {
             pattern "<.*>|$.*";
           }
           type uint32 {
             range "1 .. 30";
           }
         }
       }
     }
     container probe-count {
       presence "enable probe-count";
       description "Minimum number of samples to be collected to evaluate SLA measurement";
       uses apply-advanced;
       leaf count {
         description "Sample count";
         default "100";
         type union {
           type string {
             pattern "<.*>|$.*";
           }
           type uint32 {
             range "1 .. 1000";
           }
         }
       }
     }
     container burst-size {
       presence "enable burst-size";
       description "Number of probes out of probe count to be sent as a burst";
       uses apply-advanced;
       leaf size {
         description "Burst size";
         default "10";
         type union {
           type string {
             pattern "<.*>|$.*";
           }
           type uint32 {
             range "1 .. 100";
           }
         }
       }
     }
     container sla-export-interval {
       description "Enabled time based SLA exporting";
       uses apply-advanced;
       leaf interval {
         description "Interval (sec)";
         type union {
           type string {
             pattern "<.*>|$.*";
           }
           type uint32 {
             range "60 .. 600";
           }
         }
       }
     }
     container dscp-code-points {
       description "Mapping of code point aliases to bit strings";
       uses apply-advanced;
       leaf dscp {
         description "DSCP";
         type string;
       }
     }
   }
   grouping appqoe-probe-path {
     description "Set probe path details";
     uses apply-advanced;
     container local {
       description "Local node's info";
       presence "enable local";
       uses appqoe-node;
     }
     container remote {
       description "Remote node's info";
       presence "enable remote";
       uses appqoe-node;
     }
   }
   grouping appqoe-node {
     description "Set node info";
     uses apply-advanced;
     container ip-address {
       presence "enable ip-address";
       description "Set IP address";
       uses apply-advanced;
       leaf ip_address {
         description "IP address";
         type jt:ipv4addr;
       }
     }
   }
   grouping appqoe_sla_metric_profile {
     description "Metric Name";
     uses apply-advanced;
     container delay-round-trip {
       presence "enable delay-round-trip";
       description "Maximum acceptable delay";
       uses apply-advanced;
       leaf delay-val {
         description "Delay value(micor-sec)";
         type union {
           type string {
             pattern "<.*>|$.*";
           }
           type uint32 {
             range "0 .. 60000000";
           }
         }
       }
     }
     container jitter {
       presence "enable jitter";
       description "Maximum acceptable jitter";
       uses apply-advanced;
       leaf jitter-val {
         description "Jitter value(micro-sec)";
         type union {
           type string {
             pattern "<.*>|$.*";
           }
           type uint32 {
             range "0 .. 60000000";
           }
         }
       }
     }
     container jitter-type {
       presence "enable jitter-type";
       description "Type of Jitter";
       uses apply-advanced;
       leaf type {
         description "Jitter Type";
         type enumeration {
           enum "two-way-jitter" {
             description "Two-way-jitter-type";
           }
           enum "egress-jitter" {
             description "Egress-jitter-type";
           }
           enum "ingress-jitter" {
             description "Ingress-jitter-type";
           }
         }
       }
     }
     container packet-loss {
       presence "enable packet-loss";
       description "Maximum acceptable packet-loss";
       uses apply-advanced;
       leaf loss {
         description "Packet loss percentage";
         type union {
           type string {
             pattern "<.*>|$.*";
           }
           type uint32 {
             range "1 .. 100";
           }
         }
       }
     }
     container match {
       presence "enable match";
       description "Type of SLA match";
       uses apply-advanced;
       leaf sla_match {
         type enumeration {
           enum "any-one" {
             description "Match any one strings";
           }
           enum "all" {
             description "Match all metrics";
           }
         }
       }
     }
   }
   grouping arp-interface-type {
     description "Logical interface on which to configure ARP aging timer";
     leaf name {
       description "Interface name";
       type union {
         type jt:interface-name;
         type string {
           pattern "<.*>|$.*";
         }
       }
     }
     uses apply-advanced;
     leaf aging-timer {
       description "Change the ARP aging time value";
       units "minutes";
       type union {
         type string {
           pattern "<.*>|$.*";
         }
         type uint32 {
           range "1 .. 600000";
         }
       }
     }
   }
   grouping authentication-source-type {
     description "Configure user-identification authentication-source";
     leaf name {
       description "User-identification authentication-source name";
       type enumeration {
         enum "local-authentication-table" {
           description "Local-authentication-table, default priority is 100.";
         }
         enum "unified-access-control" {
           description "Unified-access-control, default priority is 200.";
         }
         enum "firewall-authentication" {
           description "Firewall-authentication, default priority is 150.";
         }
         enum "active-directory-authentication-table" {
           description "Active-directory-authentication-table, default priority is 125.";
         }
         enum "aruba-clearpass" {
           description "ClearPass-authentication-table, default priority is 110.";
         }
       }
     }
     uses apply-advanced;
     choice authentication-source-option {
       case case_1 {
         leaf priority {
           description "Larger number means lower priority, 0 for disable";
           type union {
             type string {
               pattern "<.*>|$.*";
             }
             type uint16 {
               range "0 .. 65535";
             }
           }
         }
       }
     }
   }
   grouping av-fallback-settings {
     description "Anti-virus fallback settings";
     uses apply-advanced;
     leaf default {
       description "Default action";
       type enumeration {
         enum "permit" {
         }
         enum "log-and-permit" {
         }
         enum "block" {
         }
       }
     }
     leaf content-size {
       description "Fallback action for over content size";
       type enumeration {
         enum "permit" {
         }
         enum "log-and-permit" {
         }
         enum "block" {
         }
       }
     }
     leaf engine-not-ready {
       description "Fallback action for engine not ready";
       type enumeration {
         enum "permit" {
         }
         enum "log-and-permit" {
         }
         enum "block" {
         }
       }
     }
     leaf timeout {
       description "Fallback action for engine scan timeout";
       type enumeration {
         enum "permit" {
         }
         enum "log-and-permit" {
         }
         enum "block" {
         }
       }
     }
     leaf out-of-resources {
       description "Fallback action for out of resources";
       type enumeration {
         enum "permit" {
         }
         enum "log-and-permit" {
         }
         enum "block" {
         }
       }
     }
     leaf too-many-requests {
       description "Fallback action for requests exceed engine limit";
       type enumeration {
         enum "permit" {
         }
         enum "log-and-permit" {
         }
         enum "block" {
         }
       }
     }
     leaf decompress-err {
       description "Fallback action for decompress error";
       type enumeration {
         enum "permit" {
         }
         enum "log-and-permit" {
         }
         enum "block" {
         }
       }
     }
   }
   grouping banner-object {
     uses apply-advanced;
     container banner {
       description "Banners that are prompted during authentication";
       uses apply-advanced;
       leaf login {
         description "The message that will be displayed before login";
         type string {
           length "1 .. 250";
         }
       }
       leaf success {
         description "The message that will be displayed on successful login";
         type string {
           length "1 .. 250";
         }
       }
       leaf fail {
         description "The message that will be displayed after failed user login";
         type string {
           length "1 .. 250";
         }
       }
     }
   }
   grouping bridge_filter {
     description "Define a BRIDGE firewall filter";
     leaf name {
       description "Filter name";
       type string {
       }
     }
     uses apply-advanced;
     leaf-list accounting-profile {
       ordered-by user;
       description "Accounting profile name";
       type string;
     }
     leaf interface-specific {
       description "Defined counters are interface specific";
       type empty;
     }
     leaf physical-interface-filter {
       description "Filter is physical interface filter";
       type empty;
     }
     list term {
       key name;
       ordered-by user;
       description "Define a firewall term";
       leaf name {
         description "Term name";
         type string {
         }
       }
       uses apply-advanced;
       leaf filter {
         description "Filter to include";
         type string {
         }
       }
       container from {
         description "Define match criteria";
         uses apply-advanced;
         choice interface-group_choice {
           case case_1 {
             leaf-list interface-group {
               ordered-by user;
               description "Range of values";
               type string;
             }
           }
           case case_2 {
             leaf-list interface-group-except {
               ordered-by user;
               description "Range of values";
               type string;
             }
           }
         }
         choice ether-type_choice {
           case case_1 {
             leaf-list ether-type {
               ordered-by user;
               type string;
             }
           }
           case case_2 {
             leaf-list ether-type-except {
               ordered-by user;
               type string;
             }
           }
         }
         choice vlan-ether-type_choice {
           case case_1 {
             leaf-list vlan-ether-type {
               ordered-by user;
               type string;
             }
           }
           case case_2 {
             leaf-list vlan-ether-type-except {
               ordered-by user;
               type string;
             }
           }
         }
         list destination-mac-address {
           key name;
           ordered-by user;
           description "Destination MAC address";
           uses firewall_mac_addr_object;
         }
         list source-mac-address {
           key name;
           ordered-by user;
           description "Source MAC address";
           uses firewall_mac_addr_object;
         }
         choice forwarding-class_choice {
           case case_1 {
             leaf-list forwarding-class {
               ordered-by user;
               description "String name";
               type string {
               }
             }
           }
           case case_2 {
             leaf-list forwarding-class-except {
               ordered-by user;
               description "String name";
               type string {
               }
             }
           }
         }
         choice loss-priority_choice {
           case case_1 {
           }
           case case_2 {
           }
         }
         choice learn-vlan-id_choice {
           case case_1 {
           }
           case case_2 {
           }
         }
         choice learn-vlan-1p-priority_choice {
           case case_1 {
           }
           case case_2 {
           }
         }
         choice user-vlan-id_choice {
           case case_1 {
           }
           case case_2 {
           }
         }
         choice user-vlan-1p-priority_choice {
           case case_1 {
           }
           case case_2 {
           }
         }
         choice learn-vlan-dei_choice {
           case case_1 {
           }
           case case_2 {
           }
         }
         choice traffic-type_choice {
           case case_1 {
           }
           case case_2 {
           }
         }
         choice ip-protocol_choice {
           case case_1 {
           }
           case case_2 {
           }
         }
         choice dscp_choice {
           case case_1 {
           }
           case case_2 {
           }
         }
         choice ip-precedence_choice {
           case case_1 {
           }
           case case_2 {
           }
         }
         choice source-port_choice {
           case case_1 {
           }
           case case_2 {
           }
         }
         choice destination-port_choice {
           case case_1 {
           }
           case case_2 {
           }
         }
         choice port_choice {
           case case_1 {
           }
           case case_2 {
           }
         }
         choice icmp-type_choice {
           case case_1 {
           }
           case case_2 {
           }
         }
         choice icmp-code_choice {
           case case_1 {
           }
           case case_2 {
           }
         }
         list interface {
           key name;
           ordered-by user;
           description "Match interface name";
           uses match_interface_object;
         }
         list interface-set {
           key name;
           ordered-by user;
           description "Match interface in set";
           uses match_interface_set_object;
         }
         choice ipv6-next-header_choice {
           case case_1 {
           }
           case case_2 {
           }
         }
         choice ipv6-payload-protocol_choice {
           case case_1 {
           }
           case case_2 {
           }
         }
         choice ipv6-traffic-class_choice {
           case case_1 {
           }
           case case_2 {
           }
         }
         choice policy-map_choice {
           case case_1 {
             leaf-list policy-map {
               ordered-by user;
               description "String name";
               type string {
                 length "1 .. 64";
               }
             }
           }
           case case_2 {
             leaf-list policy-map-except {
               ordered-by user;
               description "String name";
               type string {
                 length "1 .. 64";
               }
             }
           }
         }
         choice isid_choice {
           case case_1 {
           }
           case case_2 {
           }
         }
         choice isid-priority-code-point_choice {
           case case_1 {
           }
           case case_2 {
           }
         }
         choice isid-dei_choice {
           case case_1 {
           }
           case case_2 {
           }
         }
       }
       container then {
         description "Action to take if the 'from' condition is matched";
         uses apply-advanced;
         choice policer-choice {
           case case_1 {
             leaf policer {
               description "Name of policer to use to rate-limit traffic";
               type string {
               }
             }
           }
           case case_2 {
             container three-color-policer {
               description "Police the packet using a three-color-policer";
               uses apply-advanced;
               choice type-choice {
                 case case_1 {
                   leaf single-rate {
                     description "Name of single-rate three-color policer to use to rate-limit traffic";
                     type string {
                     }
                   }
                 }
                 case case_2 {
                   leaf single-packet-rate {
                     description "Name of single-packet-rate three-color policer to use to rate-limit traffic";
                     type string {
                     }
                   }
                 }
                 case case_3 {
                   leaf two-rate {
                     description "Name of two-rate three-color policer to use to rate-limit traffic";
                     type string {
                     }
                   }
                 }
                 case case_4 {
                   leaf two-packet-rate {
                     description "Name of two-packet-rate three-color policer to use to rate-limit traffic";
                     type string {
                     }
                   }
                 }
               }
             }
           }
           case case_3 {
           }
         }
         choice policy-map-choice {
           case case_1 {
             leaf clear-policy-map {
               description "Clear the policy marking";
               type empty;
             }
           }
           case case_2 {
             leaf policy-map {
               description "Policy map action";
               type string {
               }
             }
           }
         }
         leaf count {
           description "Count the packet in the named counter";
           type string {
           }
         }
         leaf loss-priority {
           description "Packet's loss priority";
           type enumeration {
             enum "low" {
               description "Loss priority low";
             }
             enum "high" {
               description "Loss priority high";
             }
             enum "medium-low" {
               description "Loss priority medium-low";
             }
             enum "medium-high" {
               description "Loss priority medium-high";
             }
           }
         }
         leaf forwarding-class {
           description "Classify packet to forwarding class";
           type string {
           }
         }
         choice designation {
           case case_1 {
             leaf accept {
               description "Accept the packet";
               type empty;
             }
           }
           case case_2 {
             leaf discard {
               description "Discard the packet";
               type empty;
             }
           }
           case case_3 {
             leaf next {
               description "Continue to next term in a filter";
               type enumeration {
                 enum "term" {
                   description "Continue to next term in a filter";
                 }
               }
             }
           }
         }
         leaf port-mirror-instance {
           description "Port-mirror the packet to specified instance";
           type string {
           }
         }
         leaf port-mirror {
           description "Port-mirror the packet";
           type empty;
         }
         container forwarding-policy {
           description "Specify forwarding policy for extended port";
           uses apply-advanced;
           leaf uplink-select {
             description "Specify port group for uplink selection";
             type string;
           }
         }
       }
     }
   }
   grouping category-list-type {
     description "Configure category-list object";
     leaf name {
       description "Configure name of category-list object";
       type string {
         length "1 .. 59";
       }
     }
     uses apply-advanced;
     leaf-list value {
       ordered-by user;
       description "Configure value of category-list object";
       type string;
     }
   }
   grouping ccc_filter {
     description "Define a CCC firewall filter";
     leaf name {
       description "Filter name";
       type string {
       }
     }
     uses apply-advanced;
     leaf-list accounting-profile {
       ordered-by user;
       description "Accounting profile name";
       type string;
     }
     leaf interface-specific {
       description "Any counters defined will be interface specific";
       type empty;
     }
     leaf physical-interface-filter {
       description "Filter is physical interface filter";
       type empty;
     }
     list term {
       key name;
       ordered-by user;
       description "Define a firewall term";
       leaf name {
         description "Term name";
         type string {
         }
       }
       uses apply-advanced;
       leaf filter {
         description "Filter to include";
         type string {
         }
       }
       container from {
         description "Define match criteria";
         uses apply-advanced;
         choice interface-group_choice {
           case case_1 {
             leaf-list interface-group {
               ordered-by user;
               description "Range of values";
               type string;
             }
           }
           case case_2 {
             leaf-list interface-group-except {
               ordered-by user;
               description "Range of values";
               type string;
             }
           }
         }
         choice forwarding-class_choice {
           case case_1 {
             leaf-list forwarding-class {
               ordered-by user;
               description "String name";
               type string {
               }
             }
           }
           case case_2 {
             leaf-list forwarding-class-except {
               ordered-by user;
               description "String name";
               type string {
               }
             }
           }
         }
         choice loss-priority_choice {
           case case_1 {
           }
           case case_2 {
           }
         }
         choice learn-vlan-1p-priority_choice {
           case case_1 {
           }
           case case_2 {
           }
         }
         choice user-vlan-1p-priority_choice {
           case case_1 {
           }
           case case_2 {
           }
         }
         choice dscp_choice {
           case case_1 {
           }
           case case_2 {
           }
         }
         choice ip-precedence_choice {
           case case_1 {
           }
           case case_2 {
           }
         }
         choice ip-protocol_choice {
           case case_1 {
           }
           case case_2 {
           }
         }
         choice icmp-type_choice {
           case case_1 {
           }
           case case_2 {
           }
         }
         choice icmp-code_choice {
           case case_1 {
           }
           case case_2 {
           }
         }
         choice source-port_choice {
           case case_1 {
           }
           case case_2 {
           }
         }
         choice destination-port_choice {
           case case_1 {
           }
           case case_2 {
           }
         }
         choice policy-map_choice {
           case case_1 {
             leaf-list policy-map {
               ordered-by user;
               description "String name";
               type string {
                 length "1 .. 64";
               }
             }
           }
           case case_2 {
             leaf-list policy-map-except {
               ordered-by user;
               description "String name";
               type string {
                 length "1 .. 64";
               }
             }
           }
         }
         choice user-vlan-id_choice {
           case case_1 {
           }
           case case_2 {
           }
         }
       }
       container then {
         description "Action to take if the 'from' condition is matched";
         uses apply-advanced;
         choice policer-choice {
           case case_1 {
             leaf policer {
               description "Name of policer to use to rate-limit traffic";
               type string {
               }
             }
           }
           case case_2 {
             container three-color-policer {
               description "Police the packet using a three-color-policer";
               uses apply-advanced;
               choice type-choice {
                 case case_1 {
                   leaf single-rate {
                     description "Name of single-rate three-color policer to use to rate-limit traffic";
                     type string {
                     }
                   }
                 }
                 case case_2 {
                   leaf single-packet-rate {
                     description "Name of single-packet-rate three-color policer to use to rate-limit traffic";
                     type string {
                     }
                   }
                 }
                 case case_3 {
                   leaf two-rate {
                     description "Name of two-rate three-color policer to use to rate-limit traffic";
                     type string {
                     }
                   }
                 }
                 case case_4 {
                   leaf two-packet-rate {
                     description "Name of two-packet-rate three-color policer to use to rate-limit traffic";
                     type string {
                     }
                   }
                 }
               }
             }
           }
           case case_3 {
           }
         }
         choice policy-map-choice {
           case case_1 {
             leaf clear-policy-map {
               description "Clear the policy marking";
               type empty;
             }
           }
           case case_2 {
             leaf policy-map {
               description "Policy map action";
               type string {
               }
             }
           }
         }
         leaf count {
           description "Count the packet in the named counter";
           type string {
           }
         }
         leaf loss-priority {
           description "Packet's loss priority";
           type enumeration {
             enum "low" {
               description "Loss priority low";
             }
             enum "high" {
               description "Loss priority high";
             }
             enum "medium-low" {
               description "Loss priority medium-low";
             }
             enum "medium-high" {
               description "Loss priority medium-high";
             }
           }
         }
         leaf forwarding-class {
           description "Classify packet to forwarding class";
           type string {
           }
         }
         leaf port-mirror-instance {
           description "Port-mirror the packet to the specified instance";
           type string {
           }
         }
         leaf port-mirror {
           description "Port-mirror the packet";
           type empty;
         }
         leaf packet-mode {
           description "Bypass flow mode for the packet";
           type empty;
         }
         choice designation {
           case case_1 {
           }
           case case_2 {
             leaf accept {
               description "Accept the packet";
               type empty;
             }
           }
           case case_3 {
             leaf discard {
               description "Discard the packet";
               type empty;
             }
           }
           case case_4 {
             leaf next {
               description "Continue to next term in a filter";
               type enumeration {
                 enum "term" {
                   description "Continue to next term in a filter";
                 }
               }
             }
           }
         }
       }
     }
   }
   grouping certificate-object {
     leaf name {
       description "Simple name to identify this certificate";
       type string;
     }
     uses apply-advanced;
     leaf certificate {
       description "Certificate and private key string";
       type string;
     }
   }
   grouping cflowd_sampling_inet_lr_inst_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       type union {
         type string {
           pattern "<.*>|$.*";
         }
         type uint8 {
           range "0 .. 63";
         }
       }
     }
     leaf forwarding-class {
       description "Forwarding-class for exported jflow packets, applicable only for inline-jflow";
       type string {
         length "1 .. 64";
       }
     }
     leaf routing-instance {
       description "Name of routing instance on which flow collector is reachable";
       type string;
     }
     leaf autonomous-system-type {
       description "Type of autonomous system number to export";
       default "origin";
       type enumeration {
         enum "origin" {
           description "Export origin-AS numbers";
         }
         enum "peer" {
           description "Export peer-AS numbers";
         }
       }
     }
     container aggregation {
       description "Aggregations to perform for exported flows (version 8 only)";
       uses aggregation_type;
     }
     choice local-dump-choice {
       leaf local-dump {
         description "Dump cflowd records to log file before exporting";
         type empty;
       }
       leaf no-local-dump {
         description "Don't dump cflowd records to log file before exporting";
         type empty;
       }
     }
     leaf source-address {
       description "Source IPv4 address for cflowd packets";
       type jt:ipv4addr;
     }
     container version9 {
       presence "enable version9";
       description "Export data in version 9 format";
       uses apply-advanced;
       container template {
         description "Template configuration";
         uses apply-advanced;
         leaf template-name {
           description "Template name";
           type string;
         }
       }
     }
     container version-ipfix {
       presence "enable version-ipfix";
       description "Export data in version ipfix format";
       status deprecated;
       uses apply-advanced;
       container template {
         description "Template configuration";
         uses apply-advanced;
         leaf template-name {
           description "Template name";
           type string;
         }
       }
     }
   }
   grouping aggregation_type {
     uses apply-advanced;
     leaf autonomous-system {
       description "Aggregate by autonomous system number";
       type empty;
     }
     leaf protocol-port {
       description "Aggregate by protocol and port number";
       type empty;
     }
     leaf source-prefix {
       description "Aggregate by source prefix";
       type empty;
     }
     leaf destination-prefix {
       description "Aggregate by destination prefix";
       type empty;
     }
     container source-destination-prefix {
       presence "enable source-destination-prefix";
       description "Aggregate by source and destination prefix";
       uses apply-advanced;
       leaf caida-compliant {
         description "Compatible with Caida record format for prefix aggregation (v8)";
         type empty;
       }
     }
   }
   grouping cflowd_sampling_inet_lr_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       type union {
         type string {
           pattern "<.*>|$.*";
         }
         type uint8 {
           range "0 .. 63";
         }
       }
     }
     leaf forwarding-class {
       description "Forwarding-class for exported jflow packets, applicable only for inline-jflow";
       type string {
         length "1 .. 64";
       }
     }
     leaf routing-instance {
       description "Name of routing instance on which flow collector is reachable";
       type string;
     }
     leaf autonomous-system-type {
       description "Type of autonomous system number to export";
       default "origin";
       type enumeration {
         enum "origin" {
           description "Export origin-AS numbers";
         }
         enum "peer" {
           description "Export peer-AS numbers";
         }
       }
     }
     container aggregation {
       description "Aggregations to perform for exported flows (version 8 only)";
       uses aggregation_type;
     }
     choice local-dump-choice {
       leaf local-dump {
         description "Dump cflowd records to log file before exporting";
         type empty;
       }
       leaf no-local-dump {
         description "Don't dump cflowd records to log file before exporting";
         type empty;
       }
     }
     leaf source-address {
       description "Source IPv4 address for cflowd packets";
       type jt:ipv4addr;
     }
     container version9 {
       presence "enable version9";
       description "Export data in version 9 format";
       uses apply-advanced;
       container template {
         description "Template configuration";
         uses apply-advanced;
         leaf template-name {
           description "Template name";
           type string;
         }
       }
     }
     container version-ipfix {
       presence "enable version-ipfix";
       description "Export data in version ipfix format";
       status deprecated;
       uses apply-advanced;
       container template {
         description "Template configuration";
         uses apply-advanced;
         leaf template-name {
           description "Template name";
           type string;
         }
       }
     }
   }
   grouping cflowd_sampling_mpls_lr_inst_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       type union {
         type string {
           pattern "<.*>|$.*";
         }
         type uint8 {
           range "0 .. 63";
         }
       }
     }
     leaf forwarding-class {
       description "Forwarding-class for exported jflow packets, applicable only for inline-jflow";
       type string {
         length "1 .. 64";
       }
     }
     leaf routing-instance {
       description "Name of routing instance on which flow collector is reachable";
       type string;
     }
     leaf autonomous-system-type {
       description "Type of autonomous system number to export";
       default "origin";
       type enumeration {
         enum "origin" {
           description "Export origin-AS numbers";
         }
         enum "peer" {
           description "Export peer-AS numbers";
         }
       }
     }
     container aggregation {
       description "Aggregations to perform for exported flows (version 8 only)";
       uses aggregation_type;
     }
     choice local-dump-choice {
       leaf local-dump {
         description "Dump cflowd records to log file before exporting";
         type empty;
       }
       leaf no-local-dump {
         description "Don't dump cflowd records to log file before exporting";
         type empty;
       }
     }
     leaf source-address {
       description "Source IPv4 address for cflowd packets";
       type jt:ipv4addr;
     }
     container version-ipfix {
       presence "enable version-ipfix";
       description "Export data in version ipfix format";
       uses apply-advanced;
       container template {
         description "Template configuration";
         uses apply-advanced;
         leaf template-name {
           description "Template name";
           type string;
         }
       }
     }
   }
   grouping cflowd_sampling_mpls_lr_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       type union {
         type string {
           pattern "<.*>|$.*";
         }
         type uint8 {
           range "0 .. 63";
         }
       }
     }
     leaf forwarding-class {
       description "Forwarding-class for exported jflow packets, applicable only for inline-jflow";
       type string {
         length "1 .. 64";
       }
     }
     leaf routing-instance {
       description "Name of routing instance on which flow collector is reachable";
       type string;
     }
     leaf autonomous-system-type {
       description "Type of autonomous system number to export";
       default "origin";
       type enumeration {
         enum "origin" {
           description "Export origin-AS numbers";
         }
         enum "peer" {
           description "Export peer-AS numbers";
         }
       }
     }
     container aggregation {
       description "Aggregations to perform for exported flows (version 8 only)";
       uses aggregation_type;
     }
     choice local-dump-choice {
       leaf local-dump {
         description "Dump cflowd records to log file before exporting";
         type empty;
       }
       leaf no-local-dump {
         description "Don't dump cflowd records to log file before exporting";
         type empty;
       }
     }
     leaf source-address {
       description "Source IPv4 address for cflowd packets";
       type jt:ipv4addr;
     }
     container version-ipfix {
       presence "enable version-ipfix";
       description "Export data in version ipfix format";
       uses apply-advanced;
       container template {
         description "Template configuration";
         uses apply-advanced;
         leaf template-name {
           description "Template name";
           type string;
         }
       }
     }
   }
   grouping clients-object {
     leaf name {
       description "Client config name";
       type string {
         length "1 .. 31";
       }
     }
     uses apply-advanced;
     list remote-protected-resources {
       key name;
       ordered-by user;
       description "IP/mask of remote protected resources";
       leaf name {
         description "IP/mask of remote protected resources";
         type jt:ipv4prefix-mandatory;
       }
     }
     list remote-exceptions {
       key name;
       ordered-by user;
       description "Ip/mask of exceptions being passthru";
       leaf name {
         description "Ip/mask of exceptions being passthru";
         type jt:ipv4prefix-mandatory;
       }
     }
     leaf ipsec-vpn {
       description "IPSec VPN assigned to remote access client";
       type string;
     }
     list user {
       key name;
       description "Remote IPSec VPN users";
       leaf name {
         description "User name";
         type string;
       }
       uses apply-advanced;
     }
     list user-groups {
       key name;
       description "Remote IPSec VPN usergroups";
       leaf name {
         description "Usergroup name";
         type string;
       }
       uses apply-advanced;
     }
   }
   grouping command-list-type {
     description "Configure command-list object";
     leaf name {
       description "Configure name of command-list object";
       type string {
         length "1 .. 29";
       }
     }
     uses apply-advanced;
     leaf-list value {
       ordered-by user;
       description "Configure value of command-list object";
       type string {
         length "1 .. 64";
       }
     }
   }
   grouping content-filtering-feature {
     description "Content-filtering feature";
     uses apply-advanced;
     list profile {
       key name;
       ordered-by user;
       description "Content filtering profile";
       leaf name {
         description "Content-filtering feature profile name";
         type string {
           length "1 .. 29";
         }
       }
       uses apply-advanced;
       leaf permit-command {
         description "Permit command list";
         type string;
       }
       leaf block-command {
         description "Block command list";
         type string;
       }
       leaf block-extension {
         description "Block extension list";
         type string;
       }
       container block-mime {
         presence "enable block-mime";
         description "Content-filtering feature block MIME";
         uses apply-advanced;
         leaf list {
           description "Block MIME list";
           type string;
         }
         leaf exception {
           description "Exception of block MIME list";
           type string;
         }
       }
       container block-content-type {
         description "Content-filtering feature block content type";
         uses apply-advanced;
         leaf activex {
           description "Block activex";
           type empty;
         }
         leaf java-applet {
           description "Block Java-applet";
           type empty;
         }
         leaf exe {
           description "Block Windows/dos exe file";
           type empty;
         }
         leaf zip {
           description "Block zip file";
           type empty;
         }
         leaf http-cookie {
           description "Block HTTP cookie";
           type empty;
         }
       }
       container notification-options {
         presence "enable notification-options";
         description "Notification options";
         uses apply-advanced;
         leaf type {
           description "Notification options type";
           type enumeration {
             enum "protocol-only" {
               description "Notification in protocol level";
             }
             enum "message" {
               description "Notification in message";
             }
           }
         }
         choice notify-mail-sender-choice {
           leaf notify-mail-sender {
             description "Notifiy mail sender";
             type empty;
           }
           leaf no-notify-mail-sender {
             description "Don't notifiy mail sender";
             type empty;
           }
         }
         leaf custom-message {
           description "Custom notification message";
           type string {
             length "1 .. 512";
           }
         }
       }
     }
   }
   grouping custom-attack-group-type {
     description "Define custom attack group";
     leaf name {
       description "Custom attack group name";
       type string;
     }
     uses apply-advanced;
     leaf attack-group-description {
       description "Attack group description in xml format";
       status deprecated;
       type string;
     }
     leaf-list group-members {
       ordered-by user;
       description "List of attacks/attack groups belonging to this group";
       type string;
     }
   }
   grouping custom-attack-type {
     description "Define custom attack";
     leaf name {
       description "Custom attack name";
       type string {
       }
     }
     uses apply-advanced;
     leaf attack-description {
       description "Attack description in xml format";
       status deprecated;
       type string;
     }
     leaf recommended-action {
       description "Recommended Action";
       type enumeration {
         enum "none" {
           description "No action";
         }
         enum "ignore" {
           description "No further inspection on the flow";
         }
         enum "drop-packet" {
           description "Drop the packet";
         }
         enum "drop" {
           description "Drop the packet and subsequent packets of the flow";
         }
         enum "close-client" {
           description "Reset the client side";
         }
         enum "close-server" {
           description "Reset the server side";
         }
         enum "close" {
           description "Reset both client and server";
         }
       }
     }
     leaf severity {
       description "Select the severity that matches the lethality of this attack on your network";
       type enumeration {
         enum "info" {
           description "Provide information of attack when it matches.";
         }
         enum "warning" {
           description "Issue a warning when attack matches.";
         }
         enum "minor" {
           description "The attack is a  minor one.";
         }
         enum "major" {
           description "The attack is a major one.";
         }
         enum "critical" {
           description "The attack is a critical one.";
         }
       }
     }
     container time-binding {
       description "Time binding params";
       leaf count {
         description "Number of times this attack is to be triggered";
         type union {
           type uint32;
           type string {
             pattern "<.*>|$.*";
           }
         }
       }
       leaf scope {
         description "Scope within which the count occurs";
         type enumeration {
           enum "peer" {
             description "If the attack is between a single source and single destination";
           }
           enum "source" {
             description "If the attack is from one source and multiple destination";
           }
           enum "destination" {
             description "If the attack is from multiple sources to one destination";
           }
         }
       }
     }
     container attack-type {
       description "Type of attack";
       uses apply-advanced;
       container signature {
         description "Signature based attack";
         uses apply-advanced;
         container protocol-binding {
           description "Protocol binding over which attack will be detected";
           uses apply-advanced;
           choice protocol {
             case case_1 {
               container tcp {
                 presence "enable tcp";
                 description "Attack is for TCP packets only";
                 uses apply-advanced;
                 list minimum-port {
                   key name;
                   ordered-by user;
                   description "Multiple sets of (single port/port ranges) can be specified";
                   uses port-range;
                 }
               }
             }
             case case_2 {
               container udp {
                 presence "enable udp";
                 description "Attack is for UDP packets only";
                 uses apply-advanced;
                 list minimum-port {
                   key name;
                   ordered-by user;
                   description "Either single port or port ranges can be specified";
                   uses port-range;
                 }
               }
             }
             case case_3 {
               container rpc {
                 presence "enable rpc";
                 description "Attack is for RPC packets only";
                 uses apply-advanced;
                 leaf program-number {
                   description "RPC Program Number";
                   type union {
                     type uint32;
                     type string {
                       pattern "<.*>|$.*";
                     }
                   }
                 }
               }
             }
             case case_4 {
               leaf icmp {
                 description "Attack is for ICMP packets only";
                 type empty;
               }
             }
             case case_5 {
               leaf icmpv6 {
                 description "Attack is for ICMPv6 packets only";
                 type empty;
               }
             }
             case case_6 {
               container ip {
                 presence "enable ip";
                 description "Attack is for all IP based packets";
                 uses apply-advanced;
                 leaf protocol-number {
                   description "Transport layer protocol number";
                   type union {
                     type string {
                       pattern "<.*>|$.*";
                     }
                     type uint32 {
                       range "0 .. 139";
                     }
                   }
                 }
               }
             }
             case case_7 {
               container ipv6 {
                 presence "enable ipv6";
                 description "Attack is for all IPv6 based packets";
                 uses apply-advanced;
                 leaf protocol-number {
                   description "Transport layer protocol number";
                   type union {
                     type string {
                       pattern "<.*>|$.*";
                     }
                     type uint32 {
                       range "0 .. 139";
                     }
                   }
                 }
               }
             }
             case case_8 {
               leaf application {
                 description "Application name";
                 type string;
               }
             }
             case case_9 {
               leaf nested-application {
                 description "Nested application name";
                 status deprecated;
                 type string;
               }
             }
           }
         }
         leaf context {
           description "Context";
           type string;
         }
         leaf pattern {
           description "Pattern is the signature of the attack you want to detect";
           type string {
             length "0 .. 511";
           }
         }
         leaf pattern-pcre {
           description "Attack signature pattern in PCRE format";
           type string {
             length "0 .. 511";
           }
         }
         leaf regexp {
           description "Regular expression used for matching repetition of patterns";
           type string {
             length "0 .. 511";
           }
         }
         leaf negate {
           description "Trigger the attack if condition is not met";
           type empty;
         }
         leaf direction {
           description "Connection direction of the attack";
           type enumeration {
             enum "client-to-server" {
               description "Client to Server";
             }
             enum "server-to-client" {
               description "Server to Client";
             }
             enum "any" {
               description "Any direction";
             }
           }
         }
         leaf shellcode {
           description "Specify shellcode flag for this attack";
           type enumeration {
             enum "intel" {
               description "Detect shellcode for intel platforms";
             }
             enum "sparc" {
               description "Detect shellcode for sparc platforms";
             }
             enum "all" {
               description "Detect shellcode for both intel and sparc platforms";
             }
             enum "no-shellcode" {
               description "Do not detect shellcode";
             }
           }
         }
         container protocol {
           description "Protocol header matches";
           uses apply-advanced;
           container ipv4 {
             description "IPv4 protocol parameters";
             uses apply-advanced;
             container tos {
               presence "enable tos";
               description "Type of Service";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container ihl {
               presence "enable ihl";
               description "Header length in words";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 15";
                   }
                 }
               }
             }
             container total-length {
               presence "enable total-length";
               description "Total Length of IP datagram";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container identification {
               presence "enable identification";
               description "Fragment Identification";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container ip-flags {
               presence "enable ip-flags";
               description "IP Flag bits";
               choice rb-choice {
                 leaf rb {
                   description "Reserved bit";
                   type empty;
                 }
                 leaf no-rb {
                   description "Don't reserved bit";
                   type empty;
                 }
               }
               choice mf-choice {
                 leaf mf {
                   description "More Fragment bit";
                   type empty;
                 }
                 leaf no-mf {
                   description "Don't more Fragment bit";
                   type empty;
                 }
               }
               choice df-choice {
                 leaf df {
                   description "Don't Fragment bit";
                   type empty;
                 }
                 leaf no-df {
                   description "Don't don't Fragment bit";
                   type empty;
                 }
               }
             }
             container ttl {
               presence "enable ttl";
               description "Time to live";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container protocol {
               presence "enable protocol";
               description "Transport layer protocol";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container source {
               presence "enable source";
               description "Source IP-address/Hostname";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type jt:ipv4addr;
               }
             }
             container destination {
               presence "enable destination";
               description "Destination IP-address/Hostname";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type jt:ipv4addr;
               }
             }
             container checksum-validate {
               presence "enable checksum-validate";
               description "Validate checksum field against calculated checksum";
               leaf match {
                 description "Match condition";
                 type enumeration {
                   enum "equal" {
                     description "Match when checksum field in packet is exact match";
                   }
                   enum "greater-than" {
                     description "Match when checksum field in packet is greater";
                   }
                   enum "less-than" {
                     description "Match when checksum field in packet is less";
                   }
                   enum "not-equal" {
                     description "Match when checksum field in packet is not exact match";
                   }
                 }
               }
               leaf value {
                 description "Match value";
                 default "0";
                 type union {
                   type string {
                     pattern "<.*>|$.*";
                   }
                   type uint32 {
                     range "0 .. 65535";
                   }
                 }
               }
             }
           }
           container ipv6 {
             description "IPv6 protocol parameters";
             uses apply-advanced;
             container traffic-class {
               presence "enable traffic-class";
               description "Traffic class. Similar to TOS in IPv4";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container payload-length {
               presence "enable payload-length";
               description "Length of the payload in the IPv6 datagram";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container flow-label {
               presence "enable flow-label";
               description "Flow label identification";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 1048575";
                   }
                 }
               }
             }
             container hop-limit {
               presence "enable hop-limit";
               description "Hop limit";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container next-header {
               presence "enable next-header";
               description "The header following the basic IPv6 header";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container source {
               presence "enable source";
               description "Source IP-address or hostname";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type jt:ipv6addr;
               }
             }
             container destination {
               presence "enable destination";
               description "Destination IP-address or hostname";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type jt:ipv6addr;
               }
             }
             container extension-header {
               description "IPv6 Extension headers";
               uses apply-advanced;
               container routing-header {
                 presence "enable routing-header";
                 description "IPv6 Routing extension header";
                 uses apply-advanced;
                 container header-type {
                   description "Routing header type";
                   uses apply-advanced;
                   leaf match {
                     description "Match condition";
                     type enumeration {
                       enum "equal" {
                         description "Match when value in packet is exact match";
                       }
                       enum "greater-than" {
                         description "Match when value in packet is greater";
                       }
                       enum "less-than" {
                         description "Match when value in packet is less";
                       }
                       enum "not-equal" {
                         description "Match when value in packet is not exact match";
                       }
                     }
                   }
                   leaf value {
                     description "Match value";
                     type union {
                       type string {
                         pattern "<.*>|$.*";
                       }
                       type uint32 {
                         range "0 .. 255";
                       }
                     }
                   }
                 }
               }
               container destination-option {
                 description "IPv6 Destination option extension header";
                 uses apply-advanced;
                 container option-type {
                   description "Destination option header type";
                   uses apply-advanced;
                   leaf match {
                     description "Match condition";
                     type enumeration {
                       enum "equal" {
                         description "Match when value in packet is exact match";
                       }
                       enum "greater-than" {
                         description "Match when value in packet is greater";
                       }
                       enum "less-than" {
                         description "Match when value in packet is less";
                       }
                       enum "not-equal" {
                         description "Match when value in packet is not exact match";
                       }
                     }
                   }
                   leaf value {
                     description "Match value";
                     type union {
                       type string {
                         pattern "<.*>|$.*";
                       }
                       type uint32 {
                         range "0 .. 255";
                       }
                     }
                   }
                 }
                 container home-address {
                   description "IPv6 Home address of the mobile node";
                   uses apply-advanced;
                   leaf match {
                     description "Match condition";
                     type enumeration {
                       enum "equal" {
                         description "Match when value in packet is exact match";
                       }
                       enum "greater-than" {
                         description "Match when value in packet is greater";
                       }
                       enum "less-than" {
                         description "Match when value in packet is less";
                       }
                       enum "not-equal" {
                         description "Match when value in packet is not exact match";
                       }
                     }
                   }
                   leaf value {
                     description "Match value";
                     type jt:ipv6addr;
                   }
                 }
               }
             }
           }
           container tcp {
             description "TCP protocol parameters";
             uses apply-advanced;
             container source-port {
               presence "enable source-port";
               description "Source port";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container destination-port {
               presence "enable destination-port";
               description "Destination port";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container sequence-number {
               presence "enable sequence-number";
               description "Sequence Number";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 4294967295";
                   }
                 }
               }
             }
             container ack-number {
               presence "enable ack-number";
               description "Acknowledgement Number";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 4294967295";
                   }
                 }
               }
             }
             container header-length {
               presence "enable header-length";
               description "Header Length in words";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 15";
                   }
                 }
               }
             }
             container reserved {
               presence "enable reserved";
               description "Three reserved bits";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 7";
                   }
                 }
               }
             }
             container window-size {
               presence "enable window-size";
               description "Window Size";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container urgent-pointer {
               presence "enable urgent-pointer";
               description "Urgent Pointer";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container tcp-flags {
               presence "enable tcp-flags";
               description "TCP header flags";
               choice r1-choice {
                 leaf r1 {
                   description "Set Reserverd bit 1";
                   type empty;
                 }
                 leaf no-r1 {
                   description "Don't set Reserverd bit 1";
                   type empty;
                 }
               }
               choice r2-choice {
                 leaf r2 {
                   description "Set Reserved bit 2";
                   type empty;
                 }
                 leaf no-r2 {
                   description "Don't set Reserved bit 2";
                   type empty;
                 }
               }
               choice urg-choice {
                 leaf urg {
                   description "Set Urgent bit";
                   type empty;
                 }
                 leaf no-urg {
                   description "Don't set Urgent bit";
                   type empty;
                 }
               }
               choice ack-choice {
                 leaf ack {
                   description "Set Acknowledge bit";
                   type empty;
                 }
                 leaf no-ack {
                   description "Don't set Acknowledge bit";
                   type empty;
                 }
               }
               choice psh-choice {
                 leaf psh {
                   description "Set Push bit";
                   type empty;
                 }
                 leaf no-psh {
                   description "Don't set Push bit";
                   type empty;
                 }
               }
               choice rst-choice {
                 leaf rst {
                   description "Set Reset bit";
                   type empty;
                 }
                 leaf no-rst {
                   description "Don't set Reset bit";
                   type empty;
                 }
               }
               choice syn-choice {
                 leaf syn {
                   description "Set SYN bit";
                   type empty;
                 }
                 leaf no-syn {
                   description "Don't set SYN bit";
                   type empty;
                 }
               }
               choice fin-choice {
                 leaf fin {
                   description "Set FINish bit";
                   type empty;
                 }
                 leaf no-fin {
                   description "Don't set FINish bit";
                   type empty;
                 }
               }
             }
             container option {
               presence "enable option";
               description "Kind";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container data-length {
               presence "enable data-length";
               description "Size of IP datagram subtracted by TCP header length";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "2 .. 255";
                   }
                 }
               }
             }
             container window-scale {
               presence "enable window-scale";
               description "Window scale";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container mss {
               presence "enable mss";
               description "Maximum Segment Size";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container checksum-validate {
               presence "enable checksum-validate";
               description "Validate checksum field against calculated checksum";
               leaf match {
                 description "Match condition";
                 type enumeration {
                   enum "equal" {
                     description "Match when checksum field in packet is exact match";
                   }
                   enum "greater-than" {
                     description "Match when checksum field in packet is greater";
                   }
                   enum "less-than" {
                     description "Match when checksum field in packet is less";
                   }
                   enum "not-equal" {
                     description "Match when checksum field in packet is not exact match";
                   }
                 }
               }
               leaf value {
                 description "Match value";
                 default "0";
                 type union {
                   type string {
                     pattern "<.*>|$.*";
                   }
                   type uint32 {
                     range "0 .. 65535";
                   }
                 }
               }
             }
           }
           container udp {
             description "UDP protocol parameters";
             uses apply-advanced;
             container source-port {
               presence "enable source-port";
               description "Source port";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container destination-port {
               presence "enable destination-port";
               description "Destination port";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container data-length {
               presence "enable data-length";
               description "Size of IP datagram subtracted by UDP header length";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container checksum-validate {
               presence "enable checksum-validate";
               description "Validate checksum field against calculated checksum";
               leaf match {
                 description "Match condition";
                 type enumeration {
                   enum "equal" {
                     description "Match when checksum field in packet is exact match";
                   }
                   enum "greater-than" {
                     description "Match when checksum field in packet is greater";
                   }
                   enum "less-than" {
                     description "Match when checksum field in packet is less";
                   }
                   enum "not-equal" {
                     description "Match when checksum field in packet is not exact match";
                   }
                 }
               }
               leaf value {
                 description "Match value";
                 default "0";
                 type union {
                   type string {
                     pattern "<.*>|$.*";
                   }
                   type uint32 {
                     range "0 .. 65535";
                   }
                 }
               }
             }
           }
           container icmp {
             description "ICMP protocol parameters";
             uses apply-advanced;
             container type {
               presence "enable type";
               description "Type";
               uses apply-advanced;
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container code {
               presence "enable code";
               description "Code";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container identification {
               presence "enable identification";
               description "Identifier in echo request/reply";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container sequence-number {
               presence "enable sequence-number";
               description "Sequence Number";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container data-length {
               presence "enable data-length";
               description "Size of IP datagram subtracted by ICMP header length";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container checksum-validate {
               presence "enable checksum-validate";
               description "Validate checksum field against calculated checksum";
               leaf match {
                 description "Match condition";
                 type enumeration {
                   enum "equal" {
                     description "Match when checksum field in packet is exact match";
                   }
                   enum "greater-than" {
                     description "Match when checksum field in packet is greater";
                   }
                   enum "less-than" {
                     description "Match when checksum field in packet is less";
                   }
                   enum "not-equal" {
                     description "Match when checksum field in packet is not exact match";
                   }
                 }
               }
               leaf value {
                 description "Match value";
                 default "0";
                 type union {
                   type string {
                     pattern "<.*>|$.*";
                   }
                   type uint32 {
                     range "0 .. 65535";
                   }
                 }
               }
             }
           }
           container icmpv6 {
             description "ICMPv6 protocol parameters";
             uses apply-advanced;
             container type {
               presence "enable type";
               description "Type";
               uses apply-advanced;
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container code {
               presence "enable code";
               description "Code";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container identification {
               presence "enable identification";
               description "Identifier in echo request/reply";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container sequence-number {
               presence "enable sequence-number";
               description "Sequence number";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container data-length {
               presence "enable data-length";
               description "Size of IPv6 datagram subtracted by ICMPv6 header length";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container checksum-validate {
               presence "enable checksum-validate";
               description "Validate checksum field against calculated checksum";
               leaf match {
                 description "Match condition";
                 type enumeration {
                   enum "equal" {
                     description "Match when checksum field in packet is exact match";
                   }
                   enum "greater-than" {
                     description "Match when checksum field in packet is greater";
                   }
                   enum "less-than" {
                     description "Match when checksum field in packet is less";
                   }
                   enum "not-equal" {
                     description "Match when checksum field in packet is not exact match";
                   }
                 }
               }
               leaf value {
                 description "Match value";
                 default "0";
                 type union {
                   type string {
                     pattern "<.*>|$.*";
                   }
                   type uint32 {
                     range "0 .. 65535";
                   }
                 }
               }
             }
           }
         }
       }
       container anomaly {
         description "Protocol anomaly";
         uses apply-advanced;
         leaf service {
           description "Service name";
           type string;
         }
         leaf test {
           description "Protocol anomaly condition to be checked";
           type string;
         }
         leaf direction {
           description "Direction";
           type enumeration {
             enum "client-to-server" {
               description "From Client to Server";
             }
             enum "server-to-client" {
               description "From Server to Client";
             }
             enum "any" {
               description "Any direction";
             }
           }
         }
         leaf shellcode {
           description "Specify shellcode flag for this attack";
           type enumeration {
             enum "intel" {
               description "Detect shellcode for intel platforms";
             }
             enum "sparc" {
               description "Detect shellcode for sparc platforms";
             }
             enum "all" {
               description "Detect shellcode for both intel and sparc platforms";
             }
             enum "no-shellcode" {
               description "Do not detect shellcode";
             }
           }
         }
       }
       container chain {
         description "Chain attack";
         uses apply-advanced;
         container protocol-binding {
           description "Protocol binding over which attack will be detected";
           uses apply-advanced;
           choice protocol {
             case case_1 {
               container tcp {
                 presence "enable tcp";
                 description "Attack is for TCP packets only";
                 uses apply-advanced;
                 list minimum-port {
                   key name;
                   ordered-by user;
                   description "Multiple sets of (single port/port ranges) can be specified";
                   uses port-range;
                 }
               }
             }
             case case_2 {
               container udp {
                 presence "enable udp";
                 description "Attack is for UDP packets only";
                 uses apply-advanced;
                 list minimum-port {
                   key name;
                   ordered-by user;
                   description "Either single port or port ranges can be specified";
                   uses port-range;
                 }
               }
             }
             case case_3 {
               container rpc {
                 presence "enable rpc";
                 description "Attack is for RPC packets only";
                 uses apply-advanced;
                 leaf program-number {
                   description "RPC Program Number";
                   type union {
                     type uint32;
                     type string {
                       pattern "<.*>|$.*";
                     }
                   }
                 }
               }
             }
             case case_4 {
               leaf icmp {
                 description "Attack is for ICMP packets only";
                 type empty;
               }
             }
             case case_5 {
               leaf icmpv6 {
                 description "Attack is for ICMPv6 packets only";
                 type empty;
               }
             }
             case case_6 {
               container ip {
                 presence "enable ip";
                 description "Attack is for all IP based packets";
                 uses apply-advanced;
                 leaf protocol-number {
                   description "Transport layer protocol number";
                   type union {
                     type string {
                       pattern "<.*>|$.*";
                     }
                     type uint32 {
                       range "0 .. 139";
                     }
                   }
                 }
               }
             }
             case case_7 {
               container ipv6 {
                 presence "enable ipv6";
                 description "Attack is for all IPv6 based packets";
                 uses apply-advanced;
                 leaf protocol-number {
                   description "Transport layer protocol number";
                   type union {
                     type string {
                       pattern "<.*>|$.*";
                     }
                     type uint32 {
                       range "0 .. 139";
                     }
                   }
                 }
               }
             }
             case case_8 {
               leaf application {
                 description "Application name";
                 type string;
               }
             }
             case case_9 {
               leaf nested-application {
                 description "Nested application name";
                 status deprecated;
                 type string;
               }
             }
           }
         }
         leaf scope {
           description "Scope of the attack";
           type enumeration {
             enum "session" {
               description "Allow matches across transactions within the same session";
             }
             enum "transaction" {
               description "Allow matches in single transactions within the same session";
             }
           }
         }
         leaf order {
           description "Attacks should match in the order in which they are defined";
           type empty;
         }
         leaf reset {
           description "Repeat match should generate a new alert";
           type empty;
         }
         leaf expression {
           description "Boolean Expression";
           type string;
         }
         list member {
           key name;
           ordered-by user;
           description "List of member attacks.";
           uses chain-member-type;
         }
       }
     }
   }
   grouping chain-member-type {
     description "Chain member";
     leaf name {
       description "Custom attack name";
       type string;
     }
     uses apply-advanced;
     container attack-type {
       presence "enable attack-type";
       description "Type of attack";
       uses apply-advanced;
       container signature {
         description "Signature based attack";
         uses apply-advanced;
         leaf context {
           description "Context";
           type string;
         }
         leaf pattern {
           description "Pattern is the signature of the attack you want to detect";
           type string {
             length "0 .. 511";
           }
         }
         leaf pattern-pcre {
           description "Attack signature pattern in PCRE format";
           type string {
             length "0 .. 511";
           }
         }
         leaf regexp {
           description "Regular expression used for matching repetition of patterns";
           type string {
             length "0 .. 511";
           }
         }
         leaf negate {
           description "Trigger the attack if condition is not met";
           type empty;
         }
         leaf direction {
           description "Connection direction of the attack";
           type enumeration {
             enum "client-to-server" {
               description "Client to Server";
             }
             enum "server-to-client" {
               description "Server to Client";
             }
             enum "any" {
               description "Any direction";
             }
           }
         }
         leaf shellcode {
           description "Specify shellcode flag for this attack";
           type enumeration {
             enum "intel" {
               description "Detect shellcode for intel platforms";
             }
             enum "sparc" {
               description "Detect shellcode for sparc platforms";
             }
             enum "all" {
               description "Detect shellcode for both intel and sparc platforms";
             }
             enum "no-shellcode" {
               description "Do not detect shellcode";
             }
           }
         }
         container protocol {
           description "Protocol header matches";
           uses apply-advanced;
           container ipv4 {
             description "IPv4 protocol parameters";
             uses apply-advanced;
             container tos {
               presence "enable tos";
               description "Type of Service";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container ihl {
               presence "enable ihl";
               description "Header length in words";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 15";
                   }
                 }
               }
             }
             container total-length {
               presence "enable total-length";
               description "Total Length of IP datagram";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container identification {
               presence "enable identification";
               description "Fragment Identification";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container ip-flags {
               presence "enable ip-flags";
               description "IP Flag bits";
               choice rb-choice {
                 leaf rb {
                   description "Reserved bit";
                   type empty;
                 }
                 leaf no-rb {
                   description "Don't reserved bit";
                   type empty;
                 }
               }
               choice mf-choice {
                 leaf mf {
                   description "More Fragment bit";
                   type empty;
                 }
                 leaf no-mf {
                   description "Don't more Fragment bit";
                   type empty;
                 }
               }
               choice df-choice {
                 leaf df {
                   description "Don't Fragment bit";
                   type empty;
                 }
                 leaf no-df {
                   description "Don't don't Fragment bit";
                   type empty;
                 }
               }
             }
             container ttl {
               presence "enable ttl";
               description "Time to live";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container protocol {
               presence "enable protocol";
               description "Transport layer protocol";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container source {
               presence "enable source";
               description "Source IP-address/Hostname";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type jt:ipv4addr;
               }
             }
             container destination {
               presence "enable destination";
               description "Destination IP-address/Hostname";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type jt:ipv4addr;
               }
             }
             container checksum-validate {
               presence "enable checksum-validate";
               description "Validate checksum field against calculated checksum";
               leaf match {
                 description "Match condition";
                 type enumeration {
                   enum "equal" {
                     description "Match when checksum field in packet is exact match";
                   }
                   enum "greater-than" {
                     description "Match when checksum field in packet is greater";
                   }
                   enum "less-than" {
                     description "Match when checksum field in packet is less";
                   }
                   enum "not-equal" {
                     description "Match when checksum field in packet is not exact match";
                   }
                 }
               }
               leaf value {
                 description "Match value";
                 default "0";
                 type union {
                   type string {
                     pattern "<.*>|$.*";
                   }
                   type uint32 {
                     range "0 .. 65535";
                   }
                 }
               }
             }
           }
           container ipv6 {
             description "IPv6 protocol parameters";
             uses apply-advanced;
             container traffic-class {
               presence "enable traffic-class";
               description "Traffic class. Similar to TOS in IPv4";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container payload-length {
               presence "enable payload-length";
               description "Length of the payload in the IPv6 datagram";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container flow-label {
               presence "enable flow-label";
               description "Flow label identification";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 1048575";
                   }
                 }
               }
             }
             container hop-limit {
               presence "enable hop-limit";
               description "Hop limit";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container next-header {
               presence "enable next-header";
               description "The header following the basic IPv6 header";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container source {
               presence "enable source";
               description "Source IP-address or hostname";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type jt:ipv6addr;
               }
             }
             container destination {
               presence "enable destination";
               description "Destination IP-address or hostname";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type jt:ipv6addr;
               }
             }
             container extension-header {
               description "IPv6 Extension headers";
               uses apply-advanced;
               container routing-header {
                 presence "enable routing-header";
                 description "IPv6 Routing extension header";
                 uses apply-advanced;
                 container header-type {
                   description "Routing header type";
                   uses apply-advanced;
                   leaf match {
                     description "Match condition";
                     type enumeration {
                       enum "equal" {
                         description "Match when value in packet is exact match";
                       }
                       enum "greater-than" {
                         description "Match when value in packet is greater";
                       }
                       enum "less-than" {
                         description "Match when value in packet is less";
                       }
                       enum "not-equal" {
                         description "Match when value in packet is not exact match";
                       }
                     }
                   }
                   leaf value {
                     description "Match value";
                     type union {
                       type string {
                         pattern "<.*>|$.*";
                       }
                       type uint32 {
                         range "0 .. 255";
                       }
                     }
                   }
                 }
               }
               container destination-option {
                 description "IPv6 Destination option extension header";
                 uses apply-advanced;
                 container option-type {
                   description "Destination option header type";
                   uses apply-advanced;
                   leaf match {
                     description "Match condition";
                     type enumeration {
                       enum "equal" {
                         description "Match when value in packet is exact match";
                       }
                       enum "greater-than" {
                         description "Match when value in packet is greater";
                       }
                       enum "less-than" {
                         description "Match when value in packet is less";
                       }
                       enum "not-equal" {
                         description "Match when value in packet is not exact match";
                       }
                     }
                   }
                   leaf value {
                     description "Match value";
                     type union {
                       type string {
                         pattern "<.*>|$.*";
                       }
                       type uint32 {
                         range "0 .. 255";
                       }
                     }
                   }
                 }
                 container home-address {
                   description "IPv6 Home address of the mobile node";
                   uses apply-advanced;
                   leaf match {
                     description "Match condition";
                     type enumeration {
                       enum "equal" {
                         description "Match when value in packet is exact match";
                       }
                       enum "greater-than" {
                         description "Match when value in packet is greater";
                       }
                       enum "less-than" {
                         description "Match when value in packet is less";
                       }
                       enum "not-equal" {
                         description "Match when value in packet is not exact match";
                       }
                     }
                   }
                   leaf value {
                     description "Match value";
                     type jt:ipv6addr;
                   }
                 }
               }
             }
           }
           container tcp {
             description "TCP protocol parameters";
             uses apply-advanced;
             container source-port {
               presence "enable source-port";
               description "Source port";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container destination-port {
               presence "enable destination-port";
               description "Destination port";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container sequence-number {
               presence "enable sequence-number";
               description "Sequence Number";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 4294967295";
                   }
                 }
               }
             }
             container ack-number {
               presence "enable ack-number";
               description "Acknowledgement Number";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 4294967295";
                   }
                 }
               }
             }
             container header-length {
               presence "enable header-length";
               description "Header Length in words";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 15";
                   }
                 }
               }
             }
             container reserved {
               presence "enable reserved";
               description "Three reserved bits";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 7";
                   }
                 }
               }
             }
             container window-size {
               presence "enable window-size";
               description "Window Size";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container urgent-pointer {
               presence "enable urgent-pointer";
               description "Urgent Pointer";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container tcp-flags {
               presence "enable tcp-flags";
               description "TCP header flags";
               choice r1-choice {
                 leaf r1 {
                   description "Set Reserverd bit 1";
                   type empty;
                 }
                 leaf no-r1 {
                   description "Don't set Reserverd bit 1";
                   type empty;
                 }
               }
               choice r2-choice {
                 leaf r2 {
                   description "Set Reserved bit 2";
                   type empty;
                 }
                 leaf no-r2 {
                   description "Don't set Reserved bit 2";
                   type empty;
                 }
               }
               choice urg-choice {
                 leaf urg {
                   description "Set Urgent bit";
                   type empty;
                 }
                 leaf no-urg {
                   description "Don't set Urgent bit";
                   type empty;
                 }
               }
               choice ack-choice {
                 leaf ack {
                   description "Set Acknowledge bit";
                   type empty;
                 }
                 leaf no-ack {
                   description "Don't set Acknowledge bit";
                   type empty;
                 }
               }
               choice psh-choice {
                 leaf psh {
                   description "Set Push bit";
                   type empty;
                 }
                 leaf no-psh {
                   description "Don't set Push bit";
                   type empty;
                 }
               }
               choice rst-choice {
                 leaf rst {
                   description "Set Reset bit";
                   type empty;
                 }
                 leaf no-rst {
                   description "Don't set Reset bit";
                   type empty;
                 }
               }
               choice syn-choice {
                 leaf syn {
                   description "Set SYN bit";
                   type empty;
                 }
                 leaf no-syn {
                   description "Don't set SYN bit";
                   type empty;
                 }
               }
               choice fin-choice {
                 leaf fin {
                   description "Set FINish bit";
                   type empty;
                 }
                 leaf no-fin {
                   description "Don't set FINish bit";
                   type empty;
                 }
               }
             }
             container option {
               presence "enable option";
               description "Kind";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container data-length {
               presence "enable data-length";
               description "Size of IP datagram subtracted by TCP header length";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "2 .. 255";
                   }
                 }
               }
             }
             container window-scale {
               presence "enable window-scale";
               description "Window scale";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container mss {
               presence "enable mss";
               description "Maximum Segment Size";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container checksum-validate {
               presence "enable checksum-validate";
               description "Validate checksum field against calculated checksum";
               leaf match {
                 description "Match condition";
                 type enumeration {
                   enum "equal" {
                     description "Match when checksum field in packet is exact match";
                   }
                   enum "greater-than" {
                     description "Match when checksum field in packet is greater";
                   }
                   enum "less-than" {
                     description "Match when checksum field in packet is less";
                   }
                   enum "not-equal" {
                     description "Match when checksum field in packet is not exact match";
                   }
                 }
               }
               leaf value {
                 description "Match value";
                 default "0";
                 type union {
                   type string {
                     pattern "<.*>|$.*";
                   }
                   type uint32 {
                     range "0 .. 65535";
                   }
                 }
               }
             }
           }
           container udp {
             description "UDP protocol parameters";
             uses apply-advanced;
             container source-port {
               presence "enable source-port";
               description "Source port";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container destination-port {
               presence "enable destination-port";
               description "Destination port";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container data-length {
               presence "enable data-length";
               description "Size of IP datagram subtracted by UDP header length";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container checksum-validate {
               presence "enable checksum-validate";
               description "Validate checksum field against calculated checksum";
               leaf match {
                 description "Match condition";
                 type enumeration {
                   enum "equal" {
                     description "Match when checksum field in packet is exact match";
                   }
                   enum "greater-than" {
                     description "Match when checksum field in packet is greater";
                   }
                   enum "less-than" {
                     description "Match when checksum field in packet is less";
                   }
                   enum "not-equal" {
                     description "Match when checksum field in packet is not exact match";
                   }
                 }
               }
               leaf value {
                 description "Match value";
                 default "0";
                 type union {
                   type string {
                     pattern "<.*>|$.*";
                   }
                   type uint32 {
                     range "0 .. 65535";
                   }
                 }
               }
             }
           }
           container icmp {
             description "ICMP protocol parameters";
             uses apply-advanced;
             container type {
               presence "enable type";
               description "Type";
               uses apply-advanced;
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container code {
               presence "enable code";
               description "Code";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container identification {
               presence "enable identification";
               description "Identifier in echo request/reply";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container sequence-number {
               presence "enable sequence-number";
               description "Sequence Number";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container data-length {
               presence "enable data-length";
               description "Size of IP datagram subtracted by ICMP header length";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container checksum-validate {
               presence "enable checksum-validate";
               description "Validate checksum field against calculated checksum";
               leaf match {
                 description "Match condition";
                 type enumeration {
                   enum "equal" {
                     description "Match when checksum field in packet is exact match";
                   }
                   enum "greater-than" {
                     description "Match when checksum field in packet is greater";
                   }
                   enum "less-than" {
                     description "Match when checksum field in packet is less";
                   }
                   enum "not-equal" {
                     description "Match when checksum field in packet is not exact match";
                   }
                 }
               }
               leaf value {
                 description "Match value";
                 default "0";
                 type union {
                   type string {
                     pattern "<.*>|$.*";
                   }
                   type uint32 {
                     range "0 .. 65535";
                   }
                 }
               }
             }
           }
           container icmpv6 {
             description "ICMPv6 protocol parameters";
             uses apply-advanced;
             container type {
               presence "enable type";
               description "Type";
               uses apply-advanced;
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container code {
               presence "enable code";
               description "Code";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container identification {
               presence "enable identification";
               description "Identifier in echo request/reply";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container sequence-number {
               presence "enable sequence-number";
               description "Sequence number";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container data-length {
               presence "enable data-length";
               description "Size of IPv6 datagram subtracted by ICMPv6 header length";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container checksum-validate {
               presence "enable checksum-validate";
               description "Validate checksum field against calculated checksum";
               leaf match {
                 description "Match condition";
                 type enumeration {
                   enum "equal" {
                     description "Match when checksum field in packet is exact match";
                   }
                   enum "greater-than" {
                     description "Match when checksum field in packet is greater";
                   }
                   enum "less-than" {
                     description "Match when checksum field in packet is less";
                   }
                   enum "not-equal" {
                     description "Match when checksum field in packet is not exact match";
                   }
                 }
               }
               leaf value {
                 description "Match value";
                 default "0";
                 type union {
                   type string {
                     pattern "<.*>|$.*";
                   }
                   type uint32 {
                     range "0 .. 65535";
                   }
                 }
               }
             }
           }
         }
       }
       container anomaly {
         description "Protocol anomaly";
         uses apply-advanced;
         leaf test {
           description "Protocol anomaly condition to be checked";
           type string;
         }
         leaf direction {
           description "Direction";
           type enumeration {
             enum "client-to-server" {
               description "From Client to Server";
             }
             enum "server-to-client" {
               description "From Server to Client";
             }
             enum "any" {
               description "Any direction";
             }
           }
         }
         leaf shellcode {
           description "Specify shellcode flag for this attack";
           type enumeration {
             enum "intel" {
               description "Detect shellcode for intel platforms";
             }
             enum "sparc" {
               description "Detect shellcode for sparc platforms";
             }
             enum "all" {
               description "Detect shellcode for both intel and sparc platforms";
             }
             enum "no-shellcode" {
               description "Do not detect shellcode";
             }
           }
         }
       }
     }
   }
   grouping custom-message-type {
     description "Configure custom-message object";
     leaf name {
       description "Configure name of custom-message object";
       type string {
         length "1 .. 59";
       }
     }
     uses apply-advanced;
     leaf type {
       description "Type of custom message";
       type enumeration {
         enum "redirect-url" {
           description "Redirect URL";
         }
         enum "user-message" {
           description "User message";
         }
       }
     }
     leaf content {
       description "Content of custom message";
       type string {
         length "1 .. 1024";
       }
     }
   }
   grouping default-anti-spam-feature {
     description "Anti-spam feature";
     uses apply-advanced;
     leaf type {
       description "Anti-spam type";
       type enumeration {
         enum "sbl" {
           description "Anti-spam sophos sbl";
         }
         enum "anti-spam-none" {
         }
       }
     }
     leaf address-whitelist {
       description "Anti-spam whitelist";
       type string;
     }
     leaf address-blacklist {
       description "Anti-spam blacklist";
       type string;
     }
     container traceoptions {
       description "Trace options for anti-spam feature";
       uses anti-spam-traceoptions;
     }
     container sbl {
       description "SBL settings";
       presence "enable sbl";
       uses default-sbl-type;
     }
   }
   grouping anti-spam-traceoptions {
     description "Trace options for anti-spam  feature";
     uses apply-advanced;
     list flag {
       key name;
       ordered-by user;
       description "Trace options for anti-spam feature flag";
       leaf name {
         description "Trace options for anti-spam feature flag name";
         type enumeration {
           enum "manager" {
             description "Trace anti-spam manager information";
           }
           enum "sbl" {
             description "Trace SBL server information";
           }
           enum "all" {
             description "Enable trace all anti-spam trace options";
           }
         }
       }
     }
   }
   grouping default-anti-virus-feature {
     description "Anti-virus feature";
     uses apply-advanced;
     container mime-whitelist {
       description "Anti-virus MIME whitelist";
       uses apply-advanced;
       leaf list {
         description "MIME list";
         type string;
       }
       leaf exception {
         description "Exception settings for MIME white list";
         type string;
       }
     }
     leaf url-whitelist {
       description "Anti-virus URL white list";
       type string;
     }
     leaf type {
       description "Anti-virus engine type";
       default "anti-virus-none";
       type enumeration {
         enum "sophos-engine" {
           description "Anti-virus sophos-engine";
         }
         enum "avira-engine" {
           description "Anti-virus avira-engine";
         }
         enum "anti-virus-none" {
         }
       }
     }
     container scan-options {
       presence "enable scan-options";
       description "Anti-virus scan options";
       uses apply-advanced;
       choice pre-detection-choice {
         leaf pre-detection {
           description "Anti-virus Pre-Detection";
           type empty;
         }
         leaf no-pre-detection {
           description "Don't anti-virus Pre-Detection";
           type empty;
         }
       }
       choice uri-check-choice {
         leaf uri-check {
           description "Anti-virus uri-check";
           type empty;
         }
         leaf no-uri-check {
           description "Don't anti-virus uri-check";
           type empty;
         }
       }
       leaf content-size-limit {
         description "Content size limit";
         type string;
       }
       leaf timeout {
         description "Scan engine timeout";
         units "seconds";
         type union {
           type string {
             pattern "<.*>|$.*";
           }
           type uint32 {
             range "1 .. 1800";
           }
         }
       }
       leaf decompress-layer-limit {
         description "Decompress layer limit";
         type union {
           type string {
             pattern "<.*>|$.*";
           }
           type uint32 {
             range "0 .. 10";
           }
         }
       }
     }
     container trickling {
       description "Anti-virus trickling";
       presence "enable trickling";
       uses anti-virus-trickling;
     }
     container notification-options {
       description "Anti-virus notification options";
       presence "enable notification-options";
       uses anti-virus-notification-options;
     }
     container fallback-options {
       description "Anti-virus fallback options";
       presence "enable fallback-options";
       uses av-fallback-settings;
     }
     container traceoptions {
       description "Trace options for anti-virus feature";
       uses anti-virus-traceoptions;
     }
     container avira-engine {
       description "Anti-virus Avira-engine";
       uses apply-advanced;
       container pattern-update {
         description "Anti-virus avira-engine pattern update";
         presence "enable pattern-update";
         uses anti-virus-pattern-update;
       }
     }
     container sophos-engine {
       description "Anti-virus sophos-engine";
       uses apply-advanced;
       container server {
         description "SAV and Anti-Spam first hop DNS server";
         uses apply-advanced;
         leaf ip {
           description "SAV and Anti-Spam first hop DNS server ip";
           type jt:ipaddr;
         }
         leaf routing-instance {
           description "Routing instance name";
           type string;
         }
       }
       leaf sxl-timeout {
         description "Sxl sophos anti-virus engine timeout";
         default "2";
         units "seconds";
         type union {
           type string {
             pattern "<.*>|$.*";
           }
           type uint32 {
             range "1 .. 5";
           }
         }
       }
       leaf sxl-retry {
         description "Sxl sophos anti-virus engine query retry (number of times)";
         default "1";
         type union {
           type string {
             pattern "<.*>|$.*";
           }
           type uint32 {
             range "0 .. 5";
           }
         }
       }
       container pattern-update {
         description "Anti-virus sophos-engine pattern update";
         presence "enable pattern-update";
         uses anti-virus-pattern-update;
       }
       container fallback-options {
         description "Anti-virus sophos-engine fallback options";
         presence "enable fallback-options";
         status deprecated;
         uses av-fallback-settings;
       }
       container scan-options {
         description "Anti-virus sophos-engine scan options";
         presence "enable scan-options";
         status deprecated;
         uses default-sophos-scan-options;
       }
       container trickling {
         description "Anti-virus trickling";
         presence "enable trickling";
         status deprecated;
         uses anti-virus-trickling;
       }
       container notification-options {
         description "Anti-virus notification options";
         presence "enable notification-options";
         status deprecated;
         uses anti-virus-notification-options;
       }
     }
   }
   grouping default-content-filtering-feature {
     description "Content-filtering feature";
     uses apply-advanced;
     leaf type {
       description "Content-filtering type";
       default "local";
       type enumeration {
         enum "local" {
           description "Content-filtering local";
         }
         enum "content-filtering-none" {
         }
       }
     }
     container traceoptions {
       description "Trace options for content-filtering feature";
       uses content-filtering-traceoptions;
     }
     leaf permit-command {
       description "Permit command list";
       type string;
     }
     leaf block-command {
       description "Block command list";
       type string;
     }
     leaf block-extension {
       description "Block extension list";
       type string;
     }
     container block-mime {
       presence "enable block-mime";
       description "Content-filtering feature block MIME";
       uses apply-advanced;
       leaf list {
         description "Block MIME list";
         type string;
       }
       leaf exception {
         description "Exception of block MIME list";
         type string;
       }
     }
     container block-content-type {
       description "Content-filtering feature block content type";
       uses apply-advanced;
       leaf activex {
         description "Block activex";
         type empty;
       }
       leaf java-applet {
         description "Block Java-applet";
         type empty;
       }
       leaf exe {
         description "Block Windows/dos exe file";
         type empty;
       }
       leaf zip {
         description "Block zip file";
         type empty;
       }
       leaf http-cookie {
         description "Block HTTP cookie";
         type empty;
       }
     }
     container notification-options {
       presence "enable notification-options";
       description "Notification options";
       uses apply-advanced;
       leaf type {
         description "Notification options type";
         type enumeration {
           enum "protocol-only" {
             description "Notification in protocol level";
           }
           enum "message" {
             description "Notification in message";
           }
         }
       }
       choice notify-mail-sender-choice {
         leaf notify-mail-sender {
           description "Notifiy mail sender";
           type empty;
         }
         leaf no-notify-mail-sender {
           description "Don't notifiy mail sender";
           type empty;
         }
       }
       leaf custom-message {
         description "Custom notification message";
         type string {
           length "1 .. 512";
         }
       }
     }
   }
   grouping content-filtering-traceoptions {
     description "Trace options for content-filtering feature";
     uses apply-advanced;
     list flag {
       key name;
       ordered-by user;
       description "Trace options for content-filtering feature flag";
       leaf name {
         description "Trace options for content-filtering feature flag name";
         type enumeration {
           enum "basic" {
             description "Trace content-filtering basic information";
           }
           enum "detail" {
             description "Trace content-filtering detail information";
           }
           enum "all" {
             description "Enable trace all content-filtering trace options";
           }
         }
       }
     }
   }
   grouping default-sbl-type {
     description "SBL type";
     uses apply-advanced;
     choice sbl-default-server-choice {
       leaf sbl-default-server {
         description "Default SBL server";
         type empty;
       }
       leaf no-sbl-default-server {
         description "Don't default SBL server";
         type empty;
       }
     }
     leaf spam-action {
       description "Anti-spam actions";
       default "tag-subject";
       type enumeration {
         enum "block" {
           description "Block e-mail";
         }
         enum "tag-header" {
           description "Tag header of e-mail";
         }
         enum "tag-subject" {
           description "Tag subject of e-mail";
         }
       }
     }
     leaf custom-tag-string {
       description "Custom tag string";
       type string {
         length "1 .. 512";
       }
     }
   }
   grouping default-sophos-scan-options {
     description "Anti-virus scan options";
     uses apply-advanced;
     choice uri-check-choice {
       leaf uri-check {
         description "Anti-virus uri-check";
         type empty;
       }
       leaf no-uri-check {
         description "Don't anti-virus uri-check";
         type empty;
       }
     }
     leaf content-size-limit {
       description "Content size limit";
       default "10000";
       type string;
     }
     leaf timeout {
       description "Scan engine timeout";
       units "seconds";
       type union {
         type string {
           pattern "<.*>|$.*";
         }
         type uint32 {
           range "1 .. 1800";
         }
       }
     }
   }
   grouping default-webfilter-feature {
     description "Web-filtering feature settings";
     uses apply-advanced;
     leaf url-whitelist {
       description "Configure custom URL for whitelist category";
       type string;
     }
     leaf url-blacklist {
       description "Configure custom URL for blacklist category";
       type string;
     }
     leaf http-reassemble {
       description "Reassemble HTTP request segments";
       type empty;
     }
     leaf http-persist {
       description "Check all HTTP request in a connection";
       type empty;
     }
     leaf type {
       description "Configure web-filtering engine type";
       default "web-filtering-none";
       type enumeration {
         enum "websense-redirect" {
         }
         enum "juniper-local" {
         }
         enum "juniper-enhanced" {
         }
         enum "web-filtering-none" {
         }
       }
     }
     container traceoptions {
       description "Trace options for web-filtering feature";
       uses web-filtering-traceoptions;
     }
     container websense-redirect {
       description "Configure web-filtering websense redirect engine";
       uses default-websense-type;
     }
     container juniper-local {
       description "Configure web-filtering juniper local engine";
       uses default-juniper-local-type;
     }
     container juniper-enhanced {
       description "Configure web-filtering juniper enhanced engine";
       uses default-juniper-enhanced-type;
     }
   }
   grouping default-juniper-enhanced-type {
     description "Juniper Enhanced";
     uses apply-advanced;
     container cache {
       presence "enable cache";
       uses apply-advanced;
       leaf timeout {
         description "Juniper enhanced cache timeout";
         default "1440";
         units "minutes";
         type union {
           type string {
             pattern "<.*>|$.*";
           }
           type uint32 {
             range "1 .. 1800";
           }
         }
       }
       leaf size {
         description "Juniper enhanced cache size";
         default "1024";
         units "kilobytes";
         type string;
       }
     }
     container server {
       description "Juniper enhanced server";
       presence "enable server";
       uses juniper-enhanced-server;
     }
     container reputation {
       presence "enable reputation";
       description "Customize reputation level";
       uses apply-advanced;
       leaf reputation-very-safe {
         description "Base-reputation-value";
         default "90";
         type union {
           type uint32;
           type string {
             pattern "<.*>|$.*";
           }
         }
       }
       leaf reputation-moderately-safe {
         description "Base-reputation-value";
         default "80";
         type union {
           type uint32;
           type string {
             pattern "<.*>|$.*";
           }
         }
       }
       leaf reputation-fairly-safe {
         description "Base-reputation-value";
         default "70";
         type union {
           type uint32;
           type string {
             pattern "<.*>|$.*";
           }
         }
       }
       leaf reputation-suspicious {
         description "Base-reputation-value";
         default "60";
         type union {
           type uint32;
           type string {
             pattern "<.*>|$.*";
           }
         }
       }
     }
     leaf query-type {
       description "Juniper enhanced query type";
       type enumeration {
         enum "url-ip" {
           description "Query category by URL and IP address";
         }
         enum "url" {
           description "Query category by URL only";
         }
       }
     }
     leaf base-filter {
       description "Juniper base filter";
       type string;
     }
     list category {
       key name;
       ordered-by user;
       description "Juniper enhanced category";
       uses juniper-enhanced-category-type;
     }
     container site-reputation-action {
       description "Juniper enhanced site reputation action";
       presence "enable site-reputation-action";
       uses juniper-enhanced-site-reputation-setting;
     }
     leaf default {
       description "Juniper enhanced profile default";
       type enumeration {
         enum "permit" {
           description "Permit action";
         }
         enum "block" {
           description "Block action";
         }
         enum "log-and-permit" {
           description "Log and permit action";
         }
         enum "quarantine" {
           description "Quarantine action";
         }
       }
     }
     leaf custom-block-message {
       description "Juniper enhanced custom block message sent to HTTP client";
       type string {
         length "1 .. 512";
       }
     }
     leaf quarantine-custom-message {
       description "Juniper enhanced quarantine custom message";
       type string {
         length "1 .. 512";
       }
     }
     container fallback-settings {
       description "Juniper enhanced fallback settings";
       presence "enable fallback-settings";
       uses web-filtering-fallback-setting;
     }
     leaf timeout {
       description "Juniper enhanced timeout";
       default "15";
       units "seconds";
       type union {
         type string {
           pattern "<.*>|$.*";
         }
         type uint32;
       }
     }
     leaf no-safe-search {
       description "Do not perform safe-search for Juniper enhanced protocol";
       type empty;
     }
     container block-message {
       description "Juniper enhanced block message settings";
       presence "enable block-message";
       uses web-filtering-block-message;
     }
     container quarantine-message {
       description "Juniper enhanced quarantine message settings";
       presence "enable quarantine-message";
       uses web-filtering-quarantine-message;
     }
   }
   grouping default-juniper-local-type {
     description "Juniper local";
     uses apply-advanced;
     leaf default {
       description "Juniper local profile default";
       type enumeration {
         enum "permit" {
           description "Permit action";
         }
         enum "block" {
           description "Block action";
         }
         enum "log-and-permit" {
           description "Log and permit action";
         }
       }
     }
     list category {
       key name;
       ordered-by user;
       description "Custom category";
       uses custom-category-type;
     }
     leaf custom-block-message {
       description "Juniper local custom block message";
       type string {
         length "1 .. 512";
       }
     }
     leaf quarantine-custom-message {
       description "Juniper local quarantine custom message";
       type string {
         length "1 .. 512";
       }
     }
     container block-message {
       description "Juniper local block message settings";
       presence "enable block-message";
       uses web-filtering-block-message;
     }
     container quarantine-message {
       description "Juniper local quarantine message settings";
       presence "enable quarantine-message";
       uses web-filtering-quarantine-message;
     }
     container fallback-settings {
       description "Juniper local fallback settings";
       presence "enable fallback-settings";
       uses web-filtering-fallback-setting;
     }
     leaf timeout {
       description "Juniper local timeout";
       default "15";
       units "seconds";
       type union {
         type string {
           pattern "<.*>|$.*";
         }
         type uint32 {
           range "1 .. 1800";
         }
       }
     }
   }
   grouping custom-category-type {
     description "Custom category type";
     leaf name {
       description "Name of custom category";
       type string {
         length "1 .. 59";
       }
     }
     uses apply-advanced;
     leaf action {
       description "Action to perform when web traffic matches category";
       type enumeration {
         enum "permit" {
         }
         enum "log-and-permit" {
         }
         enum "block" {
         }
         enum "quarantine" {
         }
       }
     }
     leaf custom-message {
       description "Custom message";
       type string;
     }
   }
   grouping default-websense-type {
     description "Websense redirect";
     uses apply-advanced;
     container server {
       description "Websense redirect server";
       presence "enable server";
       uses server;
     }
     list category {
       key name;
       ordered-by user;
       description "Custom category";
       uses custom-category-type;
     }
     leaf custom-block-message {
       description "Websense redirect custom block message";
       type string {
         length "1 .. 512";
       }
     }
     leaf quarantine-custom-message {
       description "Websense redirect quarantine custom message";
       type string {
         length "1 .. 512";
       }
     }
     container block-message {
       description "Websense redirect block message settings";
       presence "enable block-message";
       uses web-filtering-block-message;
     }
     container quarantine-message {
       description "Websense redirect quarantine message settings";
       presence "enable quarantine-message";
       uses web-filtering-quarantine-message;
     }
     container fallback-settings {
       description "Websense redirect fallback settings";
       presence "enable fallback-settings";
       uses web-filtering-fallback-setting;
     }
     leaf timeout {
       description "Websense redirect timeout";
       default "15";
       units "seconds";
       type union {
         type string {
           pattern "<.*>|$.*";
         }
         type uint32 {
           range "1 .. 1800";
         }
       }
     }
     leaf sockets {
       description "Websense redirect sockets number";
       default "32";
       type union {
         type string {
           pattern "<.*>|$.*";
         }
         type uint32 {
           range "1 .. 32";
         }
       }
     }
     leaf account {
       description "Websense redirect account";
       type string {
         length "1 .. 28";
       }
     }
   }
   grouping dhcp-attribute-type {
     uses apply-advanced;
     container option-match {
       description "Match";
       uses apply-advanced;
       container option-82 {
         uses apply-advanced;
         list circuit-id {
           key name;
           ordered-by user;
           description "Circuit ID portion of the option 82";
           leaf name {
             type string;
           }
           leaf range {
             description "Range name";
             type string;
           }
         }
         list remote-id {
           key name;
           ordered-by user;
           description "Remote ID portion of the option 82";
           leaf name {
             type string;
           }
           leaf range {
             description "Range name";
             type string;
           }
         }
       }
     }
     leaf maximum-lease-time {
       description "Maximum lease time advertised to clients";
       units "seconds";
       type string;
     }
     leaf next-server {
       description "Next server that clients need to contact";
       type jt:ipv4addr;
     }
     leaf server-identifier {
       description "Server Identifier - IP address value";
       type jt:ipv4addr;
     }
     leaf grace-period {
       description "Grace period for leases";
       units "seconds";
       type union {
         type uint32;
         type string {
           pattern "<.*>|$.*";
         }
       }
     }
     leaf domain-name {
       description "Domain name advertised to clients";
       type string {
       }
     }
     list name-server {
       key name;
       ordered-by user;
       description "Domain name servers available to the client";
       leaf name {
         description "DNS server's IPv4 address";
         type jt:ipv4addr;
       }
       uses apply-advanced;
     }
     list wins-server {
       key name;
       ordered-by user;
       description "WINS name servers";
       leaf name {
         description "WINS server's IPv4 address";
         type jt:ipv4addr;
       }
       uses apply-advanced;
     }
     list router {
       key name;
       ordered-by user;
       description "Routers advertised to clients";
       leaf name {
         description "Router's IPv4 address";
         type jt:ipv4addr;
       }
       uses apply-advanced;
     }
     leaf boot-file {
       description "Boot filename advertised to clients";
       type string;
     }
     leaf boot-server {
       description "Boot server advertised to clients";
       type string {
       }
     }
     leaf tftp-server {
       description "TFTP server IP address advertised to clients";
       type jt:ipv4addr;
     }
     container sip-server {
       description "SIP servers to clients";
       uses apply-advanced;
       list name {
         key name;
         ordered-by user;
         description "SIP server domain name available to clients";
         leaf name {
           description "SIP server name";
           type string;
         }
         uses apply-advanced;
       }
       list ip-address {
         key name;
         ordered-by user;
         description "SIP servers list of IPv4 addresses available to the client";
         leaf name {
           description "SIP server's IPv4 address";
           type jt:ipv4addr;
         }
         uses apply-advanced;
       }
     }
     leaf netbios-node-type {
       description "Type of NETBIOS node advertised to clients";
       type enumeration {
         enum "b-node" {
           description "Broadcast node";
         }
         enum "p-node" {
           description "Peer-to-peer node";
         }
         enum "m-node" {
           description "Mixed Node";
         }
         enum "h-node" {
           description "Hybrid node";
         }
       }
     }
     leaf sip-server-domain-name {
       description "SIP server domain name available to clients";
       type string {
       }
     }
     list sip-server-address {
       key name;
       ordered-by user;
       description "SIP Servers list of IPv6 addresses available to the client";
       leaf name {
         description "SIP Server's IPv6 address";
         type jt:ipv6addr;
       }
       uses apply-advanced;
     }
     list dns-server {
       key name;
       ordered-by user;
       description "Domain name servers available to the client";
       leaf name {
         description "DNS server's IPv6 address";
         type jt:ipv6addr;
       }
       uses apply-advanced;
     }
     leaf propagate-settings {
       description "Interface name for propagating TCP/IP Settings to pool";
       type string;
     }
     leaf-list propagate-ppp-settings {
       ordered-by user;
       description "PPP interface name for propagating DNS/WINS settings";
       type union {
         type jt:interface-name;
         type string {
           pattern "<.*>|$.*";
         }
       }
       max-elements 8;
     }
     list option {
       key name;
       ordered-by user;
       description "DHCP option";
       leaf name {
         description "DHCP option identifier code";
         type union {
           type uint32;
           type string {
             pattern "<.*>|$.*";
           }
         }
       }
       choice option-type-choice {
         case case_1 {
           leaf flag {
             description "Boolean flag value";
             type enumeration {
               enum "true" {
                 description "True value";
               }
               enum "false" {
                 description "False value";
               }
               enum "on" {
                 description "On value";
               }
               enum "off" {
                 description "Off value";
               }
             }
           }
         }
         case case_2 {
           leaf byte {
             description "Unsigned 8-bit value";
             type union {
               type uint8;
               type string {
                 pattern "<.*>|$.*";
               }
             }
           }
         }
         case case_3 {
           leaf short {
             description "Signed 16-bit numeric value";
             type union {
               type int16;
               type string {
                 pattern "<.*>|$.*";
               }
             }
           }
         }
         case case_4 {
           leaf unsigned-short {
             description "Unsigned 16-bit numeric value";
             type union {
               type uint16;
               type string {
                 pattern "<.*>|$.*";
               }
             }
           }
         }
         case case_5 {
           leaf integer {
             description "Signed 32-bit numeric value";
             type union {
               type int32;
               type string {
                 pattern "<.*>|$.*";
               }
             }
           }
         }
         case case_6 {
           leaf unsigned-integer {
             description "Unsigned 32-bit numeric value";
             type union {
               type uint32;
               type string {
                 pattern "<.*>|$.*";
               }
             }
           }
         }
         case case_7 {
           leaf hex-string {
             description "Hexadecimal string";
             type string {
               length "1 .. 510";
             }
           }
         }
         case case_8 {
           leaf string {
             description "Character string value";
             type string {
               length "1 .. 254";
             }
           }
         }
         case case_9 {
           leaf ip-address {
             description "IP address value";
             type jt:ipv4addr;
           }
         }
         case case_10 {
           leaf ipv6-address {
             description "IPV6 address value";
             type jt:ipv6addr;
           }
         }
         case case_11 {
           container array {
             presence "enable array";
             description "Array of values";
             uses apply-advanced;
             choice option-type-array-choice {
               case case_1 {
                 leaf-list flag {
                   ordered-by user;
                   description "Array of boolean flag values";
                   type enumeration {
                     enum "true" {
                       description "True value";
                     }
                     enum "false" {
                       description "False value";
                     }
                     enum "on" {
                       description "On value";
                     }
                     enum "off" {
                       description "Off value";
                     }
                   }
                 }
               }
               case case_2 {
                 leaf-list byte {
                   ordered-by user;
                   description "Array of unsigned 8-bit values";
                   type union {
                     type uint8;
                     type string {
                       pattern "<.*>|$.*";
                     }
                   }
                 }
               }
               case case_3 {
                 leaf-list short {
                   ordered-by user;
                   description "Array of signed 16-bit numeric values";
                   type union {
                     type int16;
                     type string {
                       pattern "<.*>|$.*";
                     }
                   }
                 }
               }
               case case_4 {
                 leaf-list unsigned-short {
                   ordered-by user;
                   description "Array of 16-bit numeric values";
                   type union {
                     type uint16;
                     type string {
                       pattern "<.*>|$.*";
                     }
                   }
                 }
               }
               case case_5 {
                 leaf-list integer {
                   ordered-by user;
                   description "Array of signed 32-bit numeric values";
                   type union {
                     type int32;
                     type string {
                       pattern "<.*>|$.*";
                     }
                   }
                 }
               }
               case case_6 {
                 leaf-list unsigned-integer {
                   ordered-by user;
                   description "Array of unsigned 32-bit numeric values";
                   type union {
                     type uint32;
                     type string {
                       pattern "<.*>|$.*";
                     }
                   }
                 }
               }
               case case_7 {
                 leaf-list hex-string {
                   ordered-by user;
                   description "Hexadecimal string";
                   type string {
                     length "1 .. 510";
                   }
                 }
               }
               case case_8 {
                 leaf-list string {
                   ordered-by user;
                   description "Array of character string values";
                   type string {
                     length "1 .. 254";
                   }
                 }
               }
               case case_9 {
                 leaf-list ip-address {
                   ordered-by user;
                   description "Array of IP address values";
                   type jt:ipv4addr;
                 }
               }
               case case_10 {
                 leaf-list ipv6-address {
                   ordered-by user;
                   description "Array of IPv6 address values";
                   type jt:ipv6addr;
                 }
               }
             }
           }
         }
       }
     }
     leaf valid-lifetime {
       description "Valid lifetime advertised to clients";
       units "seconds";
       type string;
     }
     leaf preferred-lifetime {
       description "Preferred lifetime advertised to clients";
       units "seconds";
       type string;
     }
     leaf t1-percentage {
       description "T1 time as percentage of preferred lifetime or max lease";
       units "percent";
       type union {
         type string {
           pattern "<.*>|$.*";
         }
         type uint32 {
           range "0 .. 100";
         }
       }
     }
     leaf t2-percentage {
       description "T2 time as percentage of preferred lifetime or max lease";
       units "percent";
       type union {
         type string {
           pattern "<.*>|$.*";
         }
         type uint32 {
           range "0 .. 100";
         }
       }
     }
     leaf exclude-prefix-len {
       description "Length of IPv6 prefix to be excluded from delegated prefix";
       type union {
         type string {
           pattern "<.*>|$.*";
         }
         type uint32 {
           range "1 .. 128";
         }
       }
     }
     leaf t1-renewal-time {
       description "T1 renewal time";
       units "seconds";
       type union {
         type uint32;
         type string {
           pattern "<.*>|$.*";
         }
       }
     }
     leaf t2-rebinding-time {
       description "T2 rebinding time";
       units "seconds";
       type union {
         type uint32;
         type string {
           pattern "<.*>|$.*";
         }
       }
     }
   }
   grouping dynamic-attack-group-type {
     description "Define dynamic attack group";
     leaf name {
       description "Name of the dynamic attack group";
       type string;
     }
     uses apply-advanced;
     leaf attack-group-description {
       description "Filter name/value in xml format";
       status deprecated;
       type string;
     }
     container filters {
       description "Configure filters";
       uses apply-advanced;
       container direction {
         presence "enable direction";
         description "Direction of attack";
         uses apply-advanced;
         leaf expression {
           description "Boolean AND/OR to be used for values";
           default "or";
           type enumeration {
             enum "and" {
               description "AND values together (recommended if 'exclude-*' values are set)";
             }
             enum "or" {
               description "OR values together";
             }
           }
         }
         leaf-list values {
           ordered-by user;
           description "Values for direction field";
           type enumeration {
             enum "client-to-server" {
               description "Select attacks from client to server";
             }
             enum "server-to-client" {
               description "Select attacks from server to client";
             }
             enum "any" {
               description "Select attacks which are in any direction";
             }
             enum "exclude-client-to-server" {
               description "Filter out attacks from client to server";
             }
             enum "exclude-server-to-client" {
               description "Filter out attacks from server to client";
             }
             enum "exclude-any" {
               description "Filter out attacks which are in any direction";
             }
           }
         }
       }
       container severity {
         presence "enable severity";
         description "Severity of attack";
         uses apply-advanced;
         leaf-list values {
           ordered-by user;
           description "Values for severity field";
           type enumeration {
             enum "info" {
               description "Provide information of attack when it matches.";
             }
             enum "warning" {
               description "Issue a warning when attack matches.";
             }
             enum "minor" {
               description "The attack is a minor one.";
             }
             enum "major" {
               description "The attack is a major one.";
             }
             enum "critical" {
               description "The attack is a critical one.";
             }
           }
         }
       }
       container type {
         presence "enable type";
         description "Type of attack";
         uses apply-advanced;
         leaf-list values {
           ordered-by user;
           description "Values for type field";
           type enumeration {
             enum "signature" {
               description "Signature based attacks";
             }
             enum "anomaly" {
               description "Protocol anomalies";
             }
           }
         }
       }
       choice recommended-choice {
         leaf recommended {
           description "Recommended flag";
           type empty;
         }
         leaf no-recommended {
           description "Don't recommended flag";
           type empty;
         }
       }
       container performance {
         presence "enable performance";
         description "Performance of attack";
         uses apply-advanced;
         leaf-list values {
           ordered-by user;
           description "Values for performance field";
           type enumeration {
             enum "unknown" {
               description "Performance level unknown";
             }
             enum "fast" {
               description "Fast performance";
             }
             enum "normal" {
               description "Normal performance";
             }
             enum "slow" {
               description "Slow performance";
             }
           }
         }
       }
       container category {
         presence "enable category";
         description "Category of attack";
         uses apply-advanced;
         leaf-list values {
           ordered-by user;
           description "Values for category field";
           type string;
         }
       }
       container service {
         presence "enable service";
         description "Service/Application of attack";
         uses apply-advanced;
         leaf-list values {
           ordered-by user;
           description "Values for service field";
           type string;
         }
       }
       container false-positives {
         presence "enable false-positives";
         description "False positive field in attack";
         uses apply-advanced;
         leaf-list values {
           ordered-by user;
           description "Values for false-positives field";
           type enumeration {
             enum "unknown" {
               description "Unknown information";
             }
             enum "rarely" {
               description "Rare false positives occurrence";
             }
             enum "occasionally" {
               description "Ocassional false positives occurrence";
             }
             enum "frequently" {
               description "Frequent false positives occurrence";
             }
           }
         }
       }
       list vendor {
         key name;
         ordered-by user;
         description "Vendor/Product the attack belongs to";
         uses vendor-object;
       }
       container file-type {
         presence "enable file-type";
         description "File type the attack is valid for";
         uses apply-advanced;
         leaf-list values {
           ordered-by user;
           description "Values for file-type field";
           type string;
         }
       }
       container vulnerability-type {
         presence "enable vulnerability-type";
         description "Vulnariability type of attack";
         uses apply-advanced;
         leaf-list values {
           ordered-by user;
           description "Values for vulnariability-type field";
           type string;
         }
       }
       list cvss-score {
         key name;
         ordered-by user;
         description "CVSS score of Attack ";
         leaf name {
           description "Match condition of CVSS score";
           type enumeration {
             enum "greater-than" {
               description "Match when cvss score is greater";
             }
             enum "less-than" {
               description "Match when cvss score is less";
             }
           }
         }
         uses apply-advanced;
         leaf value {
           description "Match value";
           type decimal64 {
             fraction-digits 2;
             range "0 .. 10";
           }
         }
       }
       list age-of-attack {
         key name;
         ordered-by user;
         description "Age of an Attack ";
         leaf name {
           description "Match condition of Age of Attack";
           type enumeration {
             enum "greater-than" {
               description "Match when Age of Attack is greater";
             }
             enum "less-than" {
               description "Match when Age of Attack is less";
             }
           }
         }
         uses apply-advanced;
         leaf value {
           description "Match value";
           type union {
             type string {
               pattern "<.*>|$.*";
             }
             type uint32 {
               range "1 .. 100";
             }
           }
         }
       }
     }
   }
   grouping dynamic-dhcp-attribute-type {
     uses apply-advanced;
     leaf maximum-lease-time {
       description "Maximum lease time advertised to clients";
       units "seconds";
       type string;
     }
     leaf valid-lifetime {
       description "Preferred lifetime";
       units "seconds";
       type string;
     }
     leaf preferred-lifetime {
       description "Preferred lifetime";
       units "seconds";
       type string;
     }
     list dns-server {
       key name;
       ordered-by user;
       description "Domain name servers available to the client";
       leaf name {
         description "DNS server's IPv6 address";
         type jt:ipv6addr;
       }
       uses apply-advanced;
     }
     leaf t1-percentage {
       description "T1 time as percentage of preferred lifetime advertised to clients";
       units "percent";
       type union {
         type string {
           pattern "<.*>|$.*";
         }
         type uint32 {
           range "0 .. 100";
         }
       }
     }
     leaf t2-percentage {
       description "T2 time as percentage of preferred lifetime advertised to clients";
       units "percent";
       type union {
         type string {
           pattern "<.*>|$.*";
         }
         type uint32 {
           range "0 .. 100";
         }
       }
     }
   }
   grouping e2e-action-profile {
     leaf name {
       description "Name of the action profile";
       type string {
         length "1 .. 64";
       }
     }
     uses apply-advanced;
     leaf preserve-trace-order {
       description "Preserve trace order (has performance overhead)";
       type empty;
     }
     leaf record-pic-history {
       description "Record the PIC(s) in which the packet has been processed";
       type empty;
     }
     list event {
       key name;
       ordered-by user;
       uses e2e-event;
     }
     list module {
       key name;
       ordered-by user;
       uses e2e-module;
     }
   }
   grouping e2e-event {
     leaf name {
       description "Name of the event";
       type enumeration {
         enum "np-ingress" {
           description "NP ingress";
         }
         enum "np-egress" {
           description "NP egress";
         }
         enum "mac-ingress" {
           description "SRX1K/3K IOC Mac ingress";
         }
         enum "mac-egress" {
           description "SRX1K/3K IOC Mac egress";
         }
         enum "lbt" {
           description "Load-Balance-Thread";
         }
         enum "pot" {
           description "Packet-Order-Thread";
         }
         enum "jexec" {
           description "JExec";
         }
         enum "lt-enter" {
           description "LT(Logical Tunnel) enter";
         }
         enum "lt-leave" {
           description "LT(Logical Tunnel) leave";
         }
       }
     }
     uses apply-advanced;
     leaf trace {
       description "Trace action";
       type empty;
     }
     leaf count {
       description "Count action";
       type empty;
     }
     leaf packet-summary {
       description "Packet summary action";
       type empty;
     }
     leaf packet-dump {
       description "Packet dump action";
       type empty;
     }
   }
   grouping e2e-module {
     leaf name {
       description "Name of the module";
       type enumeration {
         enum "flow" {
           description "Flow module";
         }
       }
     }
     uses apply-advanced;
     list flag {
       key name;
       ordered-by user;
       description "Events and other information to include in trace output";
       leaf name {
         type enumeration {
           enum "all" {
             description "All flow trace";
           }
         }
       }
     }
   }
   grouping end-to-end-debug-filter {
     description "End to end debug packer filter settings";
     leaf name {
       description "Name of the filter";
       type string {
         length "1 .. 64";
       }
     }
     uses apply-advanced;
     leaf action-profile {
       description "Actions to take with this filter";
       type string;
     }
     leaf protocol {
       description "Match IP protocol type";
       type string;
     }
     leaf source-prefix {
       description "Source IPv4/IPv6 address prefix";
       type jt:ipprefix;
     }
     leaf destination-prefix {
       description "Destination IPv4/IPv6 address prefix";
       type jt:ipprefix;
     }
     leaf source-port {
       description "Match TCP/UDP source port";
       type string;
     }
     leaf destination-port {
       description "Match TCP/UDP destination port";
       type string;
     }
     leaf interface {
       description "Logical interface";
       type union {
         type jt:interface-name;
         type string {
           pattern "<.*>|$.*";
         }
       }
     }
   }
   grouping es_filter {
     leaf name {
       description "Filter name";
       type string {
       }
     }
     uses apply-advanced;
     leaf interface-specific {
       description "Defined counters are interface specific";
       type empty;
     }
     list term {
       key name;
       ordered-by user;
       description "Define a firewall term";
       leaf name {
         description "Term name";
         type string {
         }
       }
       uses apply-advanced;
       container from {
         description "Define match criteria";
         uses apply-advanced;
         list interface {
           key name;
           ordered-by user;
           description "Match interface name";
           uses match_interface_object;
         }
         list source-mac-address {
           key name;
           ordered-by user;
           description "Match MAC source address";
           uses firewall_mac_addr_object;
         }
         list destination-mac-address {
           key name;
           ordered-by user;
           description "Match MAC destination address";
           uses firewall_mac_addr_object;
         }
         choice ether-type_choice {
           case case_1 {
             leaf-list ether-type {
               ordered-by user;
               type string;
             }
           }
           case case_2 {
             leaf-list ether-type-except {
               ordered-by user;
               type string;
             }
           }
         }
         choice l2-encap-type_choice {
           case case_1 {
             leaf-list l2-encap-type {
               ordered-by user;
               type string;
             }
           }
           case case_2 {
             leaf-list l2-encap-type-except {
               ordered-by user;
               type string;
             }
           }
         }
         choice vlan_choice {
           case case_1 {
           }
           case case_2 {
           }
         }
         choice dot1q-tag_choice {
           case case_1 {
           }
           case case_2 {
           }
         }
         choice dot1q-user-priority_choice {
           case case_1 {
           }
           case case_2 {
           }
         }
         list address {
           key name;
           ordered-by user;
           description "Match IP source or destination address";
           uses firewall_addr_object;
         }
         choice dscp_choice {
           case case_1 {
             leaf-list dscp {
               ordered-by user;
               type string;
             }
           }
           case case_2 {
             leaf-list dscp-except {
               ordered-by user;
               type string;
             }
           }
         }
         choice precedence_choice {
           case case_1 {
           }
           case case_2 {
           }
         }
         choice ip-options_choice {
           case case_1 {
             leaf-list ip-options {
               ordered-by user;
               type enumeration {
                 enum "any" {
                   description "Any IP option";
                 }
               }
             }
           }
           case case_2 {
             leaf-list ip-options-except {
               ordered-by user;
               type enumeration {
                 enum "any" {
                   description "Any IP option";
                 }
               }
             }
           }
         }
         leaf fragment-flags {
           description "Match fragment flags (in symbolic or hex formats) - (Ingress only)";
           type string;
         }
         leaf is-fragment {
           description "Match if packet is a fragment";
           type empty;
         }
         choice protocol_choice {
           case case_1 {
           }
           case case_2 {
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice port_choice {
           case case_1 {
             leaf-list port {
               ordered-by user;
               type string;
             }
           }
           case case_2 {
             leaf-list port-except {
               ordered-by user;
               type string;
             }
           }
         }
         leaf tcp-flags {
           description "Match TCP flags (in symbolic or hex formats)";
           type string;
         }
         leaf tcp-initial {
           description "Match initial packet of a TCP connection";
           type empty;
         }
         leaf tcp-established {
           description "Match packet of an established TCP connection";
           type empty;
         }
         choice icmp-type_choice {
           case case_1 {
             leaf-list icmp-type {
               ordered-by user;
               type string;
             }
           }
           case case_2 {
             leaf-list icmp-type-except {
               ordered-by user;
               type string;
             }
           }
         }
         choice icmp-code_choice {
           case case_1 {
             leaf-list icmp-code {
               ordered-by user;
               type string;
             }
           }
           case case_2 {
             leaf-list icmp-code-except {
               ordered-by user;
               type string;
             }
           }
         }
         list source-prefix-list {
           key name;
           ordered-by user;
           description "Match IP source prefixes in named list";
           uses firewall_prefix_list;
         }
         list destination-prefix-list {
           key name;
           ordered-by user;
           description "Match IP destination prefixes in named list";
           uses firewall_prefix_list;
         }
         choice ip-protocol_choice {
           case case_1 {
           }
           case case_2 {
           }
         }
         choice ip-precedence_choice {
           case case_1 {
           }
           case case_2 {
           }
         }
         choice ipv6-next-header_choice {
           case case_1 {
           }
           case case_2 {
           }
         }
         choice ipv6-payload-protocol_choice {
           case case_1 {
           }
           case case_2 {
           }
         }
         choice ipv6-traffic-class_choice {
           case case_1 {
           }
           case case_2 {
           }
         }
         choice interface-group_choice {
           case case_1 {
           }
           case case_2 {
           }
         }
         choice vlan-ether-type_choice {
           case case_1 {
           }
           case case_2 {
           }
         }
         choice loss-priority_choice {
           case case_1 {
           }
           case case_2 {
           }
         }
         choice learn-vlan-id_choice {
           case case_1 {
           }
           case case_2 {
           }
         }
         choice learn-vlan-1p-priority_choice {
           case case_1 {
           }
           case case_2 {
           }
         }
         choice learn-vlan-dei_choice {
           case case_1 {
           }
           case case_2 {
           }
         }
         choice user-vlan-id_choice {
           case case_1 {
           }
           case case_2 {
           }
         }
         choice user-vlan-1p-priority_choice {
           case case_1 {
           }
           case case_2 {
           }
         }
         choice traffic-type_choice {
           case case_1 {
           }
           case case_2 {
           }
         }
         choice isid_choice {
           case case_1 {
           }
           case case_2 {
           }
         }
         choice isid-priority-code-point_choice {
           case case_1 {
           }
           case case_2 {
           }
         }
         choice isid-dei_choice {
           case case_1 {
           }
           case case_2 {
           }
         }
         choice forwarding-class_choice {
           case case_1 {
             leaf-list forwarding-class {
               ordered-by user;
               description "String name";
               type string {
               }
             }
           }
           case case_2 {
             leaf-list forwarding-class-except {
               ordered-by user;
               description "String name";
               type string {
               }
             }
           }
         }
         choice arp-type_choice {
           case case_1 {
           }
         }
         container ip-version {
           description "Define IP version";
           uses apply-advanced;
           container ipv4 {
             description "Define L3/L4 match items to match IPv4 packets";
             uses apply-advanced;
             list address {
               key name;
               ordered-by user;
               description "Match IP source or destination address";
               uses firewall_addr_object;
             }
             choice dscp_choice {
               case case_1 {
                 leaf-list dscp {
                   ordered-by user;
                   type string;
                 }
               }
               case case_2 {
                 leaf-list dscp-except {
                   ordered-by user;
                   type string;
                 }
               }
             }
             choice precedence_choice {
               case case_1 {
               }
               case case_2 {
               }
             }
             choice ip-options_choice {
               case case_1 {
                 leaf-list ip-options {
                   ordered-by user;
                   type enumeration {
                     enum "any" {
                       description "Any IP option";
                     }
                   }
                 }
               }
               case case_2 {
                 leaf-list ip-options-except {
                   ordered-by user;
                   type enumeration {
                     enum "any" {
                       description "Any IP option";
                     }
                   }
                 }
               }
             }
             leaf fragment-flags {
               description "Match fragment flags (in symbolic or hex formats) - (Ingress only)";
               type string;
             }
             leaf is-fragment {
               description "Match if packet is a fragment";
               type empty;
             }
             choice protocol_choice {
               case case_1 {
               }
               case case_2 {
               }
             }
             choice source-port_choice {
               case case_1 {
                 leaf-list source-port {
                   ordered-by user;
                   type string;
                 }
               }
               case case_2 {
                 leaf-list source-port-except {
                   ordered-by user;
                   type string;
                 }
               }
             }
             choice destination-port_choice {
               case case_1 {
                 leaf-list destination-port {
                   ordered-by user;
                   type string;
                 }
               }
               case case_2 {
                 leaf-list destination-port-except {
                   ordered-by user;
                   type string;
                 }
               }
             }
             choice port_choice {
               case case_1 {
                 leaf-list port {
                   ordered-by user;
                   type string;
                 }
               }
               case case_2 {
                 leaf-list port-except {
                   ordered-by user;
                   type string;
                 }
               }
             }
             leaf tcp-flags {
               description "Match TCP flags (in symbolic or hex formats) - (Ingress only)";
               type string;
             }
             leaf tcp-initial {
               description "Match initial packet of a TCP connection - (Ingress only)";
               type empty;
             }
             leaf tcp-established {
               description "Match packet of an established TCP connection";
               type empty;
             }
             choice icmp-type_choice {
               case case_1 {
                 leaf-list icmp-type {
                   ordered-by user;
                   type string;
                 }
               }
               case case_2 {
                 leaf-list icmp-type-except {
                   ordered-by user;
                   type string;
                 }
               }
             }
             choice icmp-code_choice {
               case case_1 {
                 leaf-list icmp-code {
                   ordered-by user;
                   type string;
                 }
               }
               case case_2 {
                 leaf-list icmp-code-except {
                   ordered-by user;
                   type string;
                 }
               }
             }
             list source-prefix-list {
               key name;
               ordered-by user;
               description "Match IP source prefixes in named list";
               uses firewall_prefix_list;
             }
             list destination-prefix-list {
               key name;
               ordered-by user;
               description "Match IP destination prefixes in named list";
               uses firewall_prefix_list;
             }
             choice ip-protocol_choice {
               case case_1 {
               }
               case case_2 {
               }
             }
             choice ip-precedence_choice {
               case case_1 {
               }
               case case_2 {
               }
             }
           }
           container ipv6 {
             description "Define L3/L4 match items to match IPv6 packets";
             uses apply-advanced;
             choice traffic-class_choice {
               case case_1 {
                 leaf-list traffic-class {
                   ordered-by user;
                   type string;
                 }
               }
               case case_2 {
                 leaf-list traffic-class-except {
                   ordered-by user;
                   type string;
                 }
               }
             }
             choice next-header_choice {
               case case_1 {
                 leaf-list next-header {
                   ordered-by user;
                   type string;
                 }
               }
               case case_2 {
                 leaf-list next-header-except {
                   ordered-by user;
                   type string;
                 }
               }
             }
             choice payload-protocol_choice {
               case case_1 {
               }
               case case_2 {
               }
             }
             choice source-port_choice {
               case case_1 {
                 leaf-list source-port {
                   ordered-by user;
                   type string;
                 }
               }
               case case_2 {
                 leaf-list source-port-except {
                   ordered-by user;
                   type string;
                 }
               }
             }
             choice destination-port_choice {
               case case_1 {
                 leaf-list destination-port {
                   ordered-by user;
                   type string;
                 }
               }
               case case_2 {
                 leaf-list destination-port-except {
                   ordered-by user;
                   type string;
                 }
               }
             }
             choice port_choice {
               case case_1 {
                 leaf-list port {
                   ordered-by user;
                   type string;
                 }
               }
               case case_2 {
                 leaf-list port-except {
                   ordered-by user;
                   type string;
                 }
               }
             }
             choice extension-header_choice {
               case case_1 {
               }
               case case_2 {
               }
             }
             leaf tcp-flags {
               description "Match TCP flags (in symbolic or hex formats)";
               type string;
             }
             leaf tcp-initial {
               description "Match initial packet of a TCP connection";
               type empty;
             }
             leaf tcp-established {
               description "Match packet of an established TCP connection";
               type empty;
             }
             choice icmp-type_choice {
               case case_1 {
                 leaf-list icmp-type {
                   ordered-by user;
                   type string;
                 }
               }
               case case_2 {
                 leaf-list icmp-type-except {
                   ordered-by user;
                   type string;
                 }
               }
             }
             choice icmp-code_choice {
               case case_1 {
                 leaf-list icmp-code {
                   ordered-by user;
                   type string;
                 }
               }
               case case_2 {
                 leaf-list icmp-code-except {
                   ordered-by user;
                   type string;
                 }
               }
             }
             list source-prefix-list {
               key name;
               ordered-by user;
               description "Match IP source prefixes in named list";
               uses firewall_prefix_list;
             }
             list destination-prefix-list {
               key name;
               ordered-by user;
               description "Match IP destination prefixes in named list";
               uses firewall_prefix_list;
             }
           }
         }
       }
       container then {
         description "Action to take if the 'from' condition is matched";
         uses apply-advanced;
         choice designation {
           case case_1 {
             leaf accept {
               description "Accept the packet";
               type empty;
             }
           }
           case case_2 {
             leaf discard {
               description "Discard the packet";
               type empty;
             }
           }
           case case_3 {
             leaf next {
               description "Continue to next term in a filter";
               type enumeration {
                 enum "term" {
                   description "Continue to next term in a filter";
                 }
               }
             }
           }
         }
         leaf log {
           description "Log the packet";
           type empty;
         }
         leaf syslog {
           description "System log (syslog) information about the packet";
           type empty;
         }
         leaf forwarding-class {
           description "Classify packet to forwarding class";
           type string {
           }
         }
         leaf analyzer {
           description "Name of analyzer - (Ingress only)";
           type string {
           }
         }
         leaf port-mirror-instance {
           description "Port-mirror the packet to specified instance";
           type string {
           }
         }
         leaf port-mirror {
           description "Port-mirror the packet";
           type empty;
         }
         leaf loss-priority {
           description "Packet's loss priority";
           type enumeration {
             enum "low" {
               description "Loss priority low";
             }
             enum "high" {
               description "Loss priority high";
             }
             enum "medium-low" {
               description "Loss priority medium-low";
             }
             enum "medium-high" {
               description "Loss priority medium-high";
             }
           }
         }
         leaf count {
           description "Count the packet in the named counter";
           type string {
           }
         }
         choice policer-choice {
           case case_1 {
             leaf policer {
               description "Name of policer to use to rate-limit traffic";
               type string {
               }
             }
           }
           case case_2 {
             container three-color-policer {
               description "Police the packet using a three-color-policer";
               uses apply-advanced;
               choice type-choice {
                 case case_1 {
                   leaf single-rate {
                     description "Name of single-rate three-color policer to use to rate-limit traffic";
                     type string {
                     }
                   }
                 }
                 case case_2 {
                   leaf single-packet-rate {
                     description "Name of single-packet-rate three-color policer to use to rate-limit traffic";
                     type string {
                     }
                   }
                 }
                 case case_3 {
                   leaf two-rate {
                     description "Name of two-rate three-color policer to use to rate-limit traffic";
                     type string {
                     }
                   }
                 }
                 case case_4 {
                   leaf two-packet-rate {
                     description "Name of two-packet-rate three-color policer to use to rate-limit traffic";
                     type string {
                     }
                   }
                 }
               }
             }
           }
           case case_3 {
           }
         }
         leaf vlan {
           description "Name of VLAN - (Ingress only)";
           type string;
         }
       }
     }
   }
   grouping extension-list-type {
     description "Configure extension-list object";
     leaf name {
       description "Configure name of extension-list object";
       type string {
         length "1 .. 29";
       }
     }
     uses apply-advanced;
     leaf-list value {
       ordered-by user;
       description "Configure value of extension-list object";
       type string {
         length "1 .. 29";
       }
     }
   }
   grouping firewall_addr_object {
     leaf name {
       description "Prefix to match";
       type jt:ipv4prefix;
     }
     leaf except {
       description "Match address not in this prefix";
       type empty;
     }
   }
   grouping firewall_flexible_match {
     description "Define a flexible match";
     leaf name {
       description "Flex match template name";
       type string {
       }
     }
     uses apply-advanced;
     leaf match-start {
       description "Start point to match in packet";
       type enumeration {
         enum "layer-2" {
           description "Layer-2 match start";
         }
         enum "layer-3" {
           description "Layer-3 match start";
         }
         enum "layer-4" {
           description "Layer-4 match start";
         }
         enum "payload" {
           description "Payload match start";
         }
       }
     }
     leaf byte-offset {
       description "Byte offset after the match start point";
       type union {
         type uint32;
         type string {
           pattern "<.*>|$.*";
         }
       }
     }
     leaf bit-offset {
       description "Bit offset after the (match-start + byte) offset";
       type union {
         type string {
           pattern "<.*>|$.*";
         }
         type uint32 {
           range "0 .. 7";
         }
       }
     }
     leaf bit-length {
       description "Length of the data to be matched in bits, not needed for string input";
       type union {
         type string {
           pattern "<.*>|$.*";
         }
         type uint32 {
           range "1 .. 128";
         }
       }
     }
   }
   grouping firewall_mac_addr_object {
     leaf name {
       description "MAC address to match";
       type jt:mac-addr-prefix;
     }
     leaf except {
       description "Match MAC address not in this range";
       type empty;
     }
   }
   grouping firewall_policer {
     description "Define a policer";
     leaf name {
       description "Policer name";
       type string {
       }
     }
     uses apply-advanced;
     leaf filter-specific {
       description "Policer is filter-specific";
       type empty;
     }
     leaf logical-interface-policer {
       description "Policer is logical interface policer";
       type empty;
     }
     leaf physical-interface-policer {
       description "Policer is physical interface policer";
       type empty;
     }
     choice exceeding {
       case case_1 {
         container if-exceeding {
           presence "enable if-exceeding";
           description "Define rate limits";
           uses apply-advanced;
           choice bandwidth {
             case case_1 {
               leaf bandwidth-limit {
                 description "Bandwidth limit";
                 units "bits per second";
                 type string;
               }
             }
             case case_2 {
               leaf bandwidth-percent {
                 description "Bandwidth limit in percentage";
                 units "percent";
                 type union {
                   type string {
                     pattern "<.*>|$.*";
                   }
                   type uint32 {
                     range "1 .. 100";
                   }
                 }
               }
             }
           }
           leaf burst-size-limit {
             description "Burst size limit";
             units "bytes";
             type string;
           }
         }
       }
       case case_2 {
       }
     }
     container then {
       description "Action to take if the rate limits are exceeded";
       uses apply-advanced;
       leaf discard {
         description "Discard the packet";
         type empty;
       }
       leaf loss-priority {
         description "Packet's loss priority";
         type enumeration {
           enum "low" {
             description "Loss priority low";
           }
           enum "high" {
             description "Loss priority high";
           }
           enum "medium-low" {
             description "Loss priority medium-low";
           }
           enum "medium-high" {
             description "Loss priority medium-high";
           }
         }
       }
       leaf forwarding-class {
         description "Classify packet to forwarding class";
         type string {
         }
       }
       leaf out-of-profile {
         description "Discard packets only if both congested and over threshold";
         type empty;
       }
     }
   }
   grouping firewall_prefix_list {
     leaf name {
       description "Prefix list to match";
       type string;
     }
     leaf except {
       description "Match addresses not in this prefix list";
       type empty;
     }
   }
   grouping flow-filter-type {
     description "Flow filter settings";
     leaf name {
       description "Name of the filter";
       type string {
         length "1 .. 63";
       }
     }
     uses apply-advanced;
     leaf protocol {
       description "Match IP protocol type";
       type string;
     }
     leaf source-prefix {
       description "Source IP address prefix";
       type jt:ipprefix;
     }
     leaf destination-prefix {
       description "Destination IP address prefix";
       type jt:ipprefix;
     }
     leaf conn-tag {
       description "Session connection tag";
       type union {
         type string {
           pattern "<.*>|$.*";
         }
         type uint32 {
           range "0 .. 4294967295";
         }
       }
     }
     leaf logical-system {
       description "Logical system";
       type string {
         length "1 .. 63";
       }
     }
     leaf source-port {
       description "Match TCP/UDP source port";
       type string;
     }
     leaf destination-port {
       description "Match TCP/UDP destination port";
       type string;
     }
     leaf interface {
       description "Source logical interface";
       type union {
         type jt:interface-name;
         type string {
           pattern "<.*>|$.*";
         }
       }
     }
   }
   grouping httpd_dvpn_traceoptions_type {
     description "Trace options for dynamic-vpn process";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Area of HTTPD process to enable debugging output";
       leaf name {
         type enumeration {
           enum "all" {
             description "Trace all areas";
           }
         }
       }
     }
   }
   grouping icap-profile-object {
     leaf name {
       description "ICAP service profile name";
       type string {
         length "1 .. 63";
       }
     }
     uses apply-advanced;
     list server {
       key name;
       ordered-by user;
       description "Configure service redirection server";
       max-elements 16;
       uses icap-redir-server;
     }
     container http {
       description "ICAP methods switch";
       uses http-redirect-object;
     }
     container fallback-option {
       description "Failure event actions";
       uses icap-redirect-fallback;
     }
     leaf timeout {
       description "Server response timeout in milliseconds";
       default "500";
       type union {
         type string {
           pattern "<.*>|$.*";
         }
         type uint16 {
           range "100 .. 50000";
         }
       }
     }
   }
   grouping http-redirect-object {
     uses apply-advanced;
     leaf redirect-request {
       description "Enable redirect service on HTTP request";
       type empty;
     }
     leaf redirect-response {
       description "Enable redirect service on HTTP response";
       type empty;
     }
   }
   grouping icap-redir-server {
     leaf name {
       description "Server name";
       type string {
         length "1 .. 63";
       }
     }
     uses apply-advanced;
     container authorization {
       description "User authentication";
       uses apply-advanced;
       leaf authorization-type {
         description "Authentication type. 'Basic' by default";
         type string {
           length "1 .. 127";
         }
       }
       container credentials {
         description "Credentials text";
         choice credentials-choice {
           case case_1 {
             leaf ascii {
               description "ASCII string";
               type string {
                 length "1 .. 511";
               }
             }
           }
           case case_2 {
             leaf base64 {
               description "Base64 string";
               type string {
                 length "1 .. 511";
               }
             }
           }
         }
       }
     }
     leaf host {
       description "Host name/IP address";
       type string {
         length "1 .. 255";
       }
     }
     leaf port {
       description "Server listening port";
       default "1344";
       type union {
         type string {
           pattern "<.*>|$.*";
         }
         type uint16 {
           range "1025 .. 65535";
         }
       }
     }
     leaf reqmod-uri {
       description "REQMOD option resource identifier";
       type string {
         length "0 .. 1023";
       }
     }
     leaf respmod-uri {
       description "RESPMOD option resource identifier";
       type string {
         length "0 .. 1023";
       }
     }
     container routing-instance {
       description "Routing instance";
       leaf ri-name {
         description "Routing instance name";
         type string {
           length "1 .. 127";
         }
       }
     }
     leaf sockets {
       description "Number of connections to create";
       default "8";
       type union {
         type string {
           pattern "<.*>|$.*";
         }
         type uint8 {
           range "1 .. 64";
         }
       }
     }
     leaf tls-profile {
       description "TLS profile";
       type string {
         length "1 .. 63";
       }
     }
   }
   grouping icap-redirect-fallback {
     uses apply-advanced;
     leaf timeout {
       description "Request timeout action";
       default "permit";
       type enumeration {
         enum "permit" {
           description "Direct permit action";
         }
         enum "log-permit" {
           description "Log then permit action";
         }
         enum "block" {
           description "Block action";
         }
       }
     }
     leaf connectivity {
       description "Connection-related failure action";
       default "permit";
       type enumeration {
         enum "permit" {
           description "Direct permit action";
         }
         enum "log-permit" {
           description "Log then permit action";
         }
         enum "block" {
           description "Block action";
         }
       }
     }
     leaf default-action {
       description "Default failure action";
       default "permit";
       type enumeration {
         enum "permit" {
           description "Direct permit action";
         }
         enum "log-permit" {
           description "Log then permit action";
         }
         enum "block" {
           description "Block action";
         }
       }
     }
   }
   grouping icap-redirect-traceoptions {
     description "ICAP redirect traceoptions";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Trace flags";
       leaf name {
         type enumeration {
           enum "all" {
             description "Trace everything";
           }
           enum "icap-redirect-re" {
             description "Trace events on RE side";
           }
           enum "icap-redirect-control" {
             description "Trace events on PFE-ukernel side";
           }
           enum "icap-redirect-connection" {
             description "Trace ICAP server connection events";
           }
           enum "icap-redirect-protocol" {
             description "Trace redirect packet events";
           }
         }
       }
     }
   }
   grouping idp-policy-type {
     leaf name {
       description "IDP policy name";
       type string;
     }
     container rulebase-ips {
       description "IPS rulebase";
       uses apply-advanced;
       list rule {
         key name;
         ordered-by user;
         description "Configure IPS rule";
         leaf name {
           description "Rule name";
           type string;
         }
         uses apply-advanced;
         leaf description {
           description "Rule description";
           type string;
         }
         container match {
           description "Rule match criteria";
           uses apply-advanced;
           leaf from-zone {
             description "Match from zone";
             default "any";
             type string;
           }
           choice source {
             case case_1 {
               leaf-list source-address {
                 ordered-by user;
                 description "Match source address";
                 type string;
               }
             }
             case case_2 {
               leaf-list source-except {
                 ordered-by user;
                 description "Don't match source address";
                 type string;
               }
             }
             case case_3 {
             }
             case case_4 {
             }
           }
           leaf to-zone {
             description "Match to zone";
             default "any";
             type string;
           }
           choice destination {
             case case_1 {
               leaf-list destination-address {
                 ordered-by user;
                 description "Match destination address";
                 type string;
               }
             }
             case case_2 {
               leaf-list destination-except {
                 ordered-by user;
                 description "Don't match destination address";
                 type string;
               }
             }
             case case_3 {
             }
             case case_4 {
             }
           }
           leaf application {
             description "Specify application or application-set name to match";
             type string;
           }
           container attacks {
             description "Match attack objects";
             uses apply-advanced;
             leaf-list custom-attacks {
               ordered-by user;
               description "Custom attacks";
               type string;
             }
             leaf-list custom-attack-groups {
               ordered-by user;
               description "Custom attack groups";
               type string;
             }
             leaf-list dynamic-attack-groups {
               ordered-by user;
               description "Dynamic attack groups";
               type string;
             }
             leaf-list predefined-attacks {
               ordered-by user;
               description "Predefined attacks";
               type string;
             }
             leaf-list predefined-attack-groups {
               ordered-by user;
               description "Predefined attack groups";
               type string;
             }
           }
         }
         container then {
           uses apply-advanced;
           container action {
             choice action {
               case case_1 {
                 leaf no-action {
                   description "No action";
                   type empty;
                 }
               }
               case case_2 {
                 leaf ignore-connection {
                   description "Ignore";
                   type empty;
                 }
               }
               case case_3 {
                 container mark-diffserv {
                   description "Mark differentiated services codepoint (DSCP)";
                   uses apply-advanced;
                   leaf codepoint {
                     description "Codepoint value";
                     type union {
                       type string {
                         pattern "<.*>|$.*";
                       }
                       type uint32 {
                         range "0 .. 63";
                       }
                     }
                   }
                 }
               }
               case case_4 {
                 container class-of-service {
                   description "Classification of traffic based on class-of-service";
                   uses apply-advanced;
                   leaf forwarding-class {
                     description "Forwarding class for outgoing packets";
                     type string {
                     }
                   }
                   leaf dscp-code-point {
                     description "Differentiated services code point value";
                     type union {
                       type string {
                         pattern "<.*>|$.*";
                       }
                       type uint32 {
                         range "0 .. 63";
                       }
                     }
                   }
                 }
               }
               case case_5 {
                 leaf drop-packet {
                   description "Drop packet";
                   type empty;
                 }
               }
               case case_6 {
                 leaf drop-connection {
                   description "Drop connection";
                   type empty;
                 }
               }
               case case_7 {
                 leaf close-client {
                   description "Close client";
                   type empty;
                 }
               }
               case case_8 {
                 leaf close-server {
                   description "Close server";
                   type empty;
                 }
               }
               case case_9 {
                 leaf close-client-and-server {
                   description "Close client and server";
                   type empty;
                 }
               }
               case case_10 {
                 leaf recommended {
                   description "Recommended";
                   type empty;
                 }
               }
             }
           }
           container ip-action {
             uses apply-advanced;
             choice ip-action {
               case case_1 {
                 leaf ip-notify {
                   description "Notify about future traffic";
                   type empty;
                 }
               }
               case case_2 {
                 leaf ip-close {
                   description "Close future connections";
                   type empty;
                 }
               }
               case case_3 {
                 leaf ip-block {
                   description "Block future connections";
                   type empty;
                 }
               }
             }
             leaf target {
               type enumeration {
                 enum "service" {
                   description "Match source, destination, dst-port and protocol";
                 }
                 enum "source-zone-address" {
                   description "Match source-zone and source-address";
                 }
                 enum "source-address" {
                   description "Match source";
                 }
                 enum "destination-address" {
                   description "Match destination";
                 }
                 enum "zone-service" {
                   description "Match source-zone, destination, dst-port, protocol";
                 }
                 enum "source-zone" {
                   description "Match source-zone";
                 }
               }
             }
             leaf log {
               description "Log IP action taken";
               type empty;
             }
             leaf log-create {
               description "Log IP action creation";
               type empty;
             }
             leaf timeout {
               description "Number of seconds IP action should remain effective";
               type union {
                 type string {
                   pattern "<.*>|$.*";
                 }
                 type uint32 {
                   range "0 .. 64800";
                 }
               }
             }
             leaf refresh-timeout {
               description "Refresh timeout when future connections match installed ip-action filter";
               type empty;
             }
           }
           container notification {
             presence "enable notification";
             description "Configure notification/logging options";
             uses apply-advanced;
             container log-attacks {
               presence "enable log-attacks";
               description "Enable attack logging";
               uses apply-advanced;
               leaf alert {
                 description "Set alert flag in attack log";
                 type empty;
               }
             }
             container packet-log {
               presence "enable packet-log";
               uses apply-advanced;
               leaf pre-attack {
                 description "No of packets to capture before attack";
                 default "1";
                 type union {
                   type string {
                     pattern "<.*>|$.*";
                   }
                   type uint32 {
                     range "1 .. 255";
                   }
                 }
               }
               leaf post-attack {
                 description "No of packets to capture after attack";
                 type union {
                   type string {
                     pattern "<.*>|$.*";
                   }
                   type uint32 {
                     range "0 .. 255";
                   }
                 }
               }
               leaf post-attack-timeout {
                 description "Timeout (seconds) after attack before stopping packet capture";
                 default "5";
                 type union {
                   type string {
                     pattern "<.*>|$.*";
                   }
                   type uint32 {
                     range "0 .. 1800";
                   }
                 }
               }
             }
           }
           leaf severity {
             description "Set rule severity level";
             type enumeration {
               enum "info" {
               }
               enum "warning" {
               }
               enum "minor" {
               }
               enum "major" {
               }
               enum "critical" {
               }
             }
           }
         }
         leaf terminal {
           description "Set/Unset terminal flag";
           type empty;
         }
       }
     }
     container rulebase-exempt {
       description "Exempt rulebase";
       uses apply-advanced;
       list rule {
         key name;
         ordered-by user;
         description "Configure exempt rule";
         leaf name {
           description "Rule name";
           type string;
         }
         uses apply-advanced;
         leaf description {
           description "Rule description";
           type string;
         }
         container match {
           description "Rule match criteria";
           uses apply-advanced;
           leaf from-zone {
             description "Match from zone";
             default "any";
             type string;
           }
           choice source {
             case case_1 {
               leaf-list source-address {
                 ordered-by user;
                 description "Match source address";
                 type string;
               }
             }
             case case_2 {
               leaf-list source-except {
                 ordered-by user;
                 description "Don't match source address";
                 type string;
               }
             }
             case case_3 {
             }
             case case_4 {
             }
           }
           leaf to-zone {
             description "Match to zone";
             default "any";
             type string;
           }
           choice destination {
             case case_1 {
               leaf-list destination-address {
                 ordered-by user;
                 description "Match destination address";
                 type string;
               }
             }
             case case_2 {
               leaf-list destination-except {
                 ordered-by user;
                 description "Don't match destination address";
                 type string;
               }
             }
             case case_3 {
             }
             case case_4 {
             }
           }
           container attacks {
             description "Match attack objects";
             uses apply-advanced;
             leaf-list custom-attacks {
               ordered-by user;
               description "Custom attacks";
               type string;
             }
             leaf-list custom-attack-groups {
               ordered-by user;
               description "Custom attack groups";
               type string;
             }
             leaf-list dynamic-attack-groups {
               ordered-by user;
               description "Dynamic attack groups";
               type string;
             }
             leaf-list predefined-attacks {
               ordered-by user;
               description "Predefined attacks";
               type string;
             }
             leaf-list predefined-attack-groups {
               ordered-by user;
               description "Predefined attack groups";
               type string;
             }
           }
         }
       }
     }
   }
   grouping idpd-traceoptions-type {
     description "Trace options for idpd";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Events and other information to include in trace output";
       leaf name {
         description "Flag name to include in trace output";
         type enumeration {
           enum "all" {
             description "All events";
           }
         }
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
   }
   grouping ids-option-type {
     description "Configure screen object";
     leaf name {
       description "Screen object name";
       type string {
         length "1 .. 64";
       }
     }
     uses apply-advanced;
     leaf description {
       description "Text description of screen";
       type string {
         length "1 .. 900";
       }
     }
     leaf alarm-without-drop {
       description "Do not drop packet, only generate alarm";
       type empty;
     }
     leaf match-direction {
       description "Match direction";
       type enumeration {
         enum "input" {
           description "Match on input to interface";
         }
         enum "output" {
           description "Match on output from interface";
         }
         enum "input-output" {
           description "Match on input to or output from interface";
         }
       }
     }
     container aggregation {
       presence "enable aggregation";
       description "Configure the source and Destination prefix for a ids-option";
       uses apply-advanced;
       leaf source-prefix-mask {
         description "Source IPV4 prefix";
         type union {
           type string {
             pattern "<.*>|$.*";
           }
           type uint32 {
             range "1 .. 32";
           }
         }
       }
       leaf destination-prefix-mask {
         description "Destination IPV4 prefix";
         type union {
           type string {
             pattern "<.*>|$.*";
           }
           type uint32 {
             range "1 .. 32";
           }
         }
       }
       leaf source-prefix-v6-mask {
         description "Source IPV6 prefix";
         type union {
           type string {
             pattern "<.*>|$.*";
           }
           type uint32 {
             range "1 .. 128";
           }
         }
       }
       leaf destination-prefix-v6-mask {
         description "Destination IPV6 prefix";
         type union {
           type string {
             pattern "<.*>|$.*";
           }
           type uint32 {
             range "1 .. 128";
           }
         }
       }
     }
     container icmp {
       description "Configure ICMP ids options";
       uses apply-advanced;
       container ip-sweep {
         presence "enable ip-sweep";
         description "Configure ip sweep ids option";
         leaf threshold {
           description "Threshold";
           default "5000";
           units "microseconds in which 10 ICMP packets are detected";
           type union {
             type string {
               pattern "<.*>|$.*";
             }
             type uint32 {
               range "1000 .. 1000000";
             }
           }
         }
       }
       leaf fragment {
         description "Enable ICMP fragment ids option";
         type empty;
       }
       leaf large {
         description "Enable large ICMP packet (size > 1024) ids option";
         type empty;
       }
       container flood {
         presence "enable flood";
         description "Configure icmp flood ids option";
         leaf threshold {
           description "Threshold";
           default "1000";
           units "ICMP packets per second";
           type union {
             type string {
               pattern "<.*>|$.*";
             }
             type uint32;
           }
         }
       }
       leaf ping-death {
         description "Enable ping of death ids option";
         type empty;
       }
       leaf icmpv6-malformed {
         description "Enable icmpv6 malformed ids option";
         type empty;
       }
     }
     container ip {
       description "Configure IP layer ids options";
       uses apply-advanced;
       leaf bad-option {
         description "Enable ip with bad option ids option";
         type empty;
       }
       leaf record-route-option {
         description "Enable ip with record route option ids option";
         type empty;
       }
       leaf timestamp-option {
         description "Enable ip with timestamp option ids option";
         type empty;
       }
       leaf security-option {
         description "Enable ip with security option ids option";
         type empty;
       }
       leaf stream-option {
         description "Enable ip with stream option ids option";
         type empty;
       }
       leaf spoofing {
         description "Enable IP address spoofing ids option";
         type empty;
       }
       leaf source-route-option {
         description "Enable ip source route ids option";
         type empty;
       }
       leaf loose-source-route-option {
         description "Enable ip with loose source route ids option";
         type empty;
       }
       leaf strict-source-route-option {
         description "Enable ip with strict source route ids option";
         type empty;
       }
       leaf unknown-protocol {
         description "Enable ip unknown protocol ids option";
         type empty;
       }
       leaf block-frag {
         description "Enable ip fragment blocking ids option";
         type empty;
       }
       leaf tear-drop {
         description "Enable tear drop ids option";
         type empty;
       }
       container ipv6-extension-header {
         description "Configure ipv6 extension header ids option";
         uses apply-advanced;
         container hop-by-hop-header {
           presence "enable hop-by-hop-header";
           description "Enable ipv6 hop by hop option header ids option";
           uses apply-advanced;
           leaf jumbo-payload-option {
             description "Enable jumbo payload option ids option";
             type empty;
           }
           leaf router-alert-option {
             description "Enable router alert option ids option";
             type empty;
           }
           leaf quick-start-option {
             description "Enable quick start option ids option";
             type empty;
           }
           leaf CALIPSO-option {
             description "Enable Common Architecture Label ipv6 Security Option ids option";
             type empty;
           }
           leaf SMF-DPD-option {
             description "Enable Simplified Multicast Forwarding ipv6 Duplicate Packet Detection option ids option";
             type empty;
           }
           leaf RPL-option {
             description "Enable Routing Protocol for Low-power and Lossy networks option ids option";
             type empty;
           }
           list user-defined-option-type {
             key name;
             ordered-by user;
             description "User-defined option type range";
             max-elements 256;
             leaf name {
               description "User-defined option type low value";
               type union {
                 type string {
                   pattern "<.*>|$.*";
                 }
                 type uint32 {
                   range "1 .. 255";
                 }
               }
             }
             container to {
               description "Upper limit of option type range";
               uses apply-advanced;
               leaf type-high {
                 description "User-defined option type high value";
                 type union {
                   type string {
                     pattern "<.*>|$.*";
                   }
                   type uint32 {
                     range "1 .. 255";
                   }
                 }
               }
             }
           }
         }
         leaf routing-header {
           description "Enable ipv6 routing header ids option";
           type empty;
         }
         leaf fragment-header {
           description "Enable ipv6 fragment header ids option";
           type empty;
         }
         leaf ESP-header {
           description "Enable ipv6 Encapsulating Security Payload header ids option";
           type empty;
         }
         leaf AH-header {
           description "Enable ipv6 Authentication Header ids option";
           type empty;
         }
         leaf no-next-header {
           description "Enable ipv6 no next header ids option";
           type empty;
         }
         container destination-header {
           presence "enable destination-header";
           description "Enable ipv6 destination option header ids option";
           uses apply-advanced;
           leaf tunnel-encapsulation-limit-option {
             description "Enable tunnel encapsulation limit option ids option";
             type empty;
           }
           leaf home-address-option {
             description "Enable home address option ids option";
             type empty;
           }
           leaf ILNP-nonce-option {
             description "Enable Identifier-Locator Network Protocol Nonce option ids option";
             type empty;
           }
           leaf line-identification-option {
             description "Enable line identification option ids option";
             type empty;
           }
           list user-defined-option-type {
             key name;
             ordered-by user;
             description "User-defined option type range";
             max-elements 256;
             leaf name {
               description "User-defined option type low value";
               type union {
                 type string {
                   pattern "<.*>|$.*";
                 }
                 type uint32 {
                   range "1 .. 255";
                 }
               }
             }
             container to {
               description "Upper limit of option type range";
               uses apply-advanced;
               leaf type-high {
                 description "User-defined option type high value";
                 type union {
                   type string {
                     pattern "<.*>|$.*";
                   }
                   type uint32 {
                     range "1 .. 255";
                   }
                 }
               }
             }
           }
         }
         leaf shim6-header {
           description "Enable ipv6 shim header ids option";
           type empty;
         }
         leaf mobility-header {
           description "Enable ipv6 mobility header ids option";
           type empty;
         }
         leaf HIP-header {
           description "Enable ipv6 Host Identify Protocol header ids option";
           type empty;
         }
         list user-defined-header-type {
           key name;
           ordered-by user;
           description "User-defined header type range";
           max-elements 256;
           leaf name {
             description "User-defined header type low value";
             type union {
               type string {
                 pattern "<.*>|$.*";
               }
               type uint32 {
                 range "0 .. 255";
               }
             }
           }
           container to {
             description "Upper limit of header type range";
             uses apply-advanced;
             leaf type-high {
               description "User-defined header type high value";
               type union {
                 type string {
                   pattern "<.*>|$.*";
                 }
                 type uint32 {
                   range "0 .. 255";
                 }
               }
             }
           }
         }
       }
       leaf ipv6-extension-header-limit {
         description "Enable ipv6 extension header limit ids option";
         type union {
           type string {
             pattern "<.*>|$.*";
           }
           type uint32 {
             range "0 .. 32";
           }
         }
       }
       leaf ipv6-malformed-header {
         description "Enable ipv6 malformed header ids option";
         type empty;
       }
       container tunnel {
         description "Configure IP tunnel ids options";
         uses apply-advanced;
         leaf bad-inner-header {
           description "Enable IP tunnel bad inner header ids option";
           type empty;
         }
         container gre {
           description "Configure IP tunnel GRE ids option";
           uses apply-advanced;
           leaf gre-6in4 {
             description "Enable IP tunnel GRE 6in4 ids option";
             type empty;
           }
           leaf gre-4in6 {
             description "Enable IP tunnel GRE 4in6 ids option";
             type empty;
           }
           leaf gre-6in6 {
             description "Enable IP tunnel GRE 6in6 ids option";
             type empty;
           }
           leaf gre-4in4 {
             description "Enable IP tunnel GRE 4in4 ids option";
             type empty;
           }
         }
         container ip-in-udp {
           description "Configure IP tunnel IPinUDP ids option";
           uses apply-advanced;
           leaf teredo {
             description "Enable IP tunnel IPinUDP Teredo ids option";
             type empty;
           }
         }
         container ipip {
           description "Configure IP tunnel IPIP ids option";
           uses apply-advanced;
           leaf ipip-6to4relay {
             description "Enable IP tunnel IPIP 6to4 Relay ids option";
             type empty;
           }
           leaf ipip-6in4 {
             description "Enable IP tunnel IPIP 6in4 ids option";
             type empty;
           }
           leaf ipip-4in6 {
             description "Enable IP tunnel IPIP 4in6 ids option";
             type empty;
           }
           leaf ipip-4in4 {
             description "Enable IP tunnel IPIP 4in4 ids option";
             type empty;
           }
           leaf ipip-6in6 {
             description "Enable IP tunnel IPIP 6in6 ids option";
             type empty;
           }
           leaf ipip-6over4 {
             description "Enable IP tunnel IPIP 6over4 ids option";
             type empty;
           }
           leaf isatap {
             description "Enable IP tunnel IPIP ISATAP ids option";
             type empty;
           }
           leaf dslite {
             description "Enable IP tunnel IPIP DS-Lite ids option";
             type empty;
           }
         }
       }
     }
     container tcp {
       description "Configure TCP Layer ids options";
       uses apply-advanced;
       leaf syn-fin {
         description "Enable SYN and FIN bits set attack ids option";
         type empty;
       }
       leaf fin-no-ack {
         description "Enable Fin bit with no ACK bit ids option";
         type empty;
       }
       leaf tcp-no-flag {
         description "Enable TCP packet without flag ids option";
         type empty;
       }
       leaf syn-frag {
         description "Enable SYN fragment ids option";
         type empty;
       }
       container port-scan {
         presence "enable port-scan";
         description "Configure TCP port scan ids option";
         leaf threshold {
           description "Threshold";
           default "5000";
           units "microseconds in which 10 attack packets are detected";
           type union {
             type string {
               pattern "<.*>|$.*";
             }
             type uint32 {
               range "1000 .. 1000000";
             }
           }
         }
       }
       container syn-ack-ack-proxy {
         presence "enable syn-ack-ack-proxy";
         description "Configure syn-ack-ack proxy ids option";
         leaf threshold {
           description "Threshold";
           default "512";
           units "un-authenticated connections";
           type union {
             type string {
               pattern "<.*>|$.*";
             }
             type uint32 {
               range "1 .. 250000";
             }
           }
         }
       }
       container syn-flood {
         presence "enable syn-flood";
         description "Configure SYN flood ids option";
         uses apply-advanced;
         leaf alarm-threshold {
           description "Alarm threshold";
           default "512";
           units "requests per second";
           type union {
             type string {
               pattern "<.*>|$.*";
             }
             type uint32;
           }
         }
         leaf attack-threshold {
           description "Attack threshold";
           default "200";
           units "proxied requests per second";
           type union {
             type string {
               pattern "<.*>|$.*";
             }
             type uint32;
           }
         }
         leaf source-threshold {
           description "Source threshold";
           default "4000";
           units "SYN pps";
           type union {
             type string {
               pattern "<.*>|$.*";
             }
             type uint32;
           }
         }
         leaf destination-threshold {
           description "Destination threshold";
           default "4000";
           units "SYN pps";
           type union {
             type string {
               pattern "<.*>|$.*";
             }
             type uint32;
           }
         }
         leaf queue-size {
           description "Queue size";
           status deprecated;
           default "1024";
           units "proxied requests in queue";
           type union {
             type string {
               pattern "<.*>|$.*";
             }
             type uint32 {
               range "200 .. 20000";
             }
           }
         }
         leaf timeout {
           description "SYN flood ager timeout";
           default "20";
           units "seconds";
           type union {
             type string {
               pattern "<.*>|$.*";
             }
             type uint32 {
               range "1 .. 50";
             }
           }
         }
         list white-list {
           key name;
           description "Set of IP addresses that will not trigger a screen";
           max-elements 2;
           leaf name {
             description "White-list name";
             type string {
               length "1 .. 32";
             }
           }
           uses apply-advanced;
           leaf-list source-address {
             ordered-by user;
             description "Source address";
             type jt:ipprefix;
             max-elements 32;
           }
           leaf-list destination-address {
             ordered-by user;
             description "Destination address";
             type jt:ipprefix;
             max-elements 32;
           }
         }
       }
       leaf land {
         description "Enable land attack ids option";
         type empty;
       }
       leaf winnuke {
         description "Enable winnuke attack ids option";
         type empty;
       }
       container tcp-sweep {
         presence "enable tcp-sweep";
         description "Configure TCP sweep ids option";
         leaf threshold {
           description "Threshold";
           default "5000";
           units "microseconds in which 10 TCP packets are detected";
           type union {
             type string {
               pattern "<.*>|$.*";
             }
             type uint32 {
               range "1000 .. 1000000";
             }
           }
         }
       }
     }
     container udp {
       description "Configure UDP layer ids options";
       uses apply-advanced;
       container flood {
         presence "enable flood";
         description "Configure UDP flood ids option";
         uses apply-advanced;
         leaf threshold {
           description "Threshold";
           default "1000";
           units "UDP packets per second";
           type union {
             type string {
               pattern "<.*>|$.*";
             }
             type uint32;
           }
         }
         leaf-list white-list {
           ordered-by user;
           description "Configure UDP flood white list group name";
           type string;
           max-elements 2;
         }
       }
       container udp-sweep {
         presence "enable udp-sweep";
         description "Configure UDP sweep ids option";
         leaf threshold {
           description "Threshold";
           default "5000";
           units "microseconds in which 10 UDP packets are detected";
           type union {
             type string {
               pattern "<.*>|$.*";
             }
             type uint32 {
               range "1000 .. 1000000";
             }
           }
         }
       }
       container port-scan {
         presence "enable port-scan";
         description "Configure UDP port scan ids option";
         leaf threshold {
           description "Threshold";
           default "5000";
           units "microseconds in which 10 attack packets are detected";
           type union {
             type string {
               pattern "<.*>|$.*";
             }
             type uint32 {
               range "1000 .. 1000000";
             }
           }
         }
       }
     }
     container limit-session {
       description "Limit sessions";
       uses apply-advanced;
       leaf source-ip-based {
         description "Limit sessions from the same source IP";
         type union {
           type string {
             pattern "<.*>|$.*";
           }
           type uint32;
         }
       }
       leaf destination-ip-based {
         description "Limit sessions to the same destination IP";
         type union {
           type string {
             pattern "<.*>|$.*";
           }
           type uint32;
         }
       }
       container by-source {
         presence "enable by-source";
         description "Limit sessions from the same source IP or subnet";
         uses apply-advanced;
         leaf maximum-sessions {
           description "Limit sessions on the basis of maximum concurrent sessions";
           type union {
             type string {
               pattern "<.*>|$.*";
             }
             type uint32;
           }
         }
         leaf packet-rate {
           description "Limit sessions on the basis of packet rate";
           type union {
             type string {
               pattern "<.*>|$.*";
             }
             type uint32 {
               range "1 .. 4294967295";
             }
           }
         }
         leaf session-rate {
           description "Limit sessions on the basis of session rate";
           type union {
             type string {
               pattern "<.*>|$.*";
             }
             type uint32 {
               range "1 .. 4294967295";
             }
           }
         }
         container by-protocol {
           description "Limit sessions on the basis of protocol";
           presence "enable by-protocol";
           uses by-protocol-object-type;
         }
       }
       container by-destination {
         presence "enable by-destination";
         description "Limit sessions to the same destination IP or subnet";
         uses apply-advanced;
         leaf maximum-sessions {
           description "Limit sessions on the basis of maximum concurrent sessions";
           type union {
             type string {
               pattern "<.*>|$.*";
             }
             type uint32;
           }
         }
         leaf packet-rate {
           description "Limit sessions on the basis of packet rate";
           type union {
             type string {
               pattern "<.*>|$.*";
             }
             type uint32 {
               range "1 .. 4294967295";
             }
           }
         }
         leaf session-rate {
           description "Limit sessions on the basis of session rate";
           type union {
             type string {
               pattern "<.*>|$.*";
             }
             type uint32 {
               range "1 .. 4294967295";
             }
           }
         }
         container by-protocol {
           description "Limit sessions on the basis of protocol";
           presence "enable by-protocol";
           uses by-protocol-object-type;
         }
       }
     }
   }
   grouping by-protocol-object-type {
     description "Configure limit-session on the basis of protocol";
     uses apply-advanced;
     container tcp {
       description "Configure limit-session on the basis of TCP";
       presence "enable tcp";
       uses by-protocol-object-limit-type;
     }
     container udp {
       description "Configure limit-session on the basis of UDP";
       presence "enable udp";
       uses by-protocol-object-limit-type;
     }
     container icmp {
       description "Configure limit-session on the basis of ICMP";
       presence "enable icmp";
       uses by-protocol-object-limit-type;
     }
   }
   grouping by-protocol-object-limit-type {
     description "Configure the limit-session for each protocol";
     uses apply-advanced;
     leaf maximum-sessions {
       description "Limit sessions on the basis of maximum concurrent sessions";
       type union {
         type string {
           pattern "<.*>|$.*";
         }
         type uint32;
       }
     }
     leaf packet-rate {
       description "Limit sessions on the basis of packet rate";
       type union {
         type string {
           pattern "<.*>|$.*";
         }
         type uint32 {
           range "1 .. 4294967295";
         }
       }
     }
     leaf session-rate {
       description "Limit sessions on the basis of session rate";
       type union {
         type string {
           pattern "<.*>|$.*";
         }
         type uint32 {
           range "1 .. 4294967295";
         }
       }
     }
   }
   grouping ids-wlist-type {
     leaf name {
       description "White-list name";
       type string {
         length "1 .. 32";
       }
     }
     uses apply-advanced;
     leaf-list address {
       ordered-by user;
       description "Address";
       type jt:ipprefix;
       max-elements 32;
     }
   }
   grouping inet6_dialer_filter {
     description "Define an IPv6 dialer filter";
     leaf name {
       description "Filter name";
       type string {
       }
     }
     uses apply-advanced;
     leaf-list accounting-profile {
       ordered-by user;
       description "Accounting profile name";
       type string;
     }
     list term {
       key name;
       ordered-by user;
       description "Define a firewall term";
       leaf name {
         description "Term name";
         type string {
         }
       }
       uses apply-advanced;
       container from {
         description "Define match criteria";
         uses apply-advanced;
         list source-address {
           key name;
           ordered-by user;
           description "Match source address";
           uses firewall_addr6_object;
         }
         list destination-address {
           key name;
           ordered-by user;
           description "Match destination address";
           uses firewall_addr6_object;
         }
         list address {
           key name;
           ordered-by user;
           description "Match source or destination address";
           uses firewall_addr6_object;
         }
         list source-prefix-list {
           key name;
           ordered-by user;
           description "Match source prefixes in named list";
           uses firewall_prefix_list;
         }
         list destination-prefix-list {
           key name;
           ordered-by user;
           description "Match destination prefixes in named list";
           uses firewall_prefix_list;
         }
         list prefix-list {
           key name;
           ordered-by user;
           description "Match source or destination prefixes in named list";
           uses firewall_prefix_list;
         }
         choice packet-length_choice {
           case case_1 {
             leaf-list packet-length {
               ordered-by user;
               description "Range of values";
               type string;
             }
           }
           case case_2 {
             leaf-list packet-length-except {
               ordered-by user;
               description "Range of values";
               type string;
             }
           }
         }
         choice next-header_choice {
           case case_1 {
             leaf-list next-header {
               ordered-by user;
               type string;
             }
           }
           case case_2 {
             leaf-list next-header-except {
               ordered-by user;
               type string;
             }
           }
         }
         choice icmp-type_choice {
           case case_1 {
             leaf-list icmp-type {
               ordered-by user;
               type string;
             }
           }
           case case_2 {
             leaf-list icmp-type-except {
               ordered-by user;
               type string;
             }
           }
         }
         choice icmp-code_choice {
           case case_1 {
             leaf-list icmp-code {
               ordered-by user;
               type string;
             }
           }
           case case_2 {
             leaf-list icmp-code-except {
               ordered-by user;
               type string;
             }
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice port_choice {
           case case_1 {
             leaf-list port {
               ordered-by user;
               type string;
             }
           }
           case case_2 {
             leaf-list port-except {
               ordered-by user;
               type string;
             }
           }
         }
       }
       container then {
         description "Action to take if the 'from' condition is matched";
         uses apply-advanced;
         leaf log {
           description "Log the packet";
           type empty;
         }
         leaf syslog {
           description "System log (syslog) information about the packet";
           type empty;
         }
         leaf sample {
           description "Sample the packet";
           type empty;
         }
         choice designation {
           case case_1 {
             leaf note {
               description "Interested ISDN packet";
               type empty;
             }
           }
           case case_2 {
             leaf ignore {
               description "Non-interested ISDN packet";
               type empty;
             }
           }
         }
       }
     }
   }
   grouping firewall_addr6_object {
     leaf name {
       description "Prefix to match";
       type jt:ipv6prefix;
     }
     leaf except {
       description "Match address not in this prefix";
       type empty;
     }
   }
   grouping inet6_filter {
     description "Define an IPv6 firewall filter";
     leaf name {
       description "Filter name";
       type string {
       }
     }
     uses apply-advanced;
     leaf-list accounting-profile {
       ordered-by user;
       description "Accounting profile name";
       type string;
     }
     leaf interface-specific {
       description "Defined counters are interface specific";
       type empty;
     }
     leaf physical-interface-filter {
       description "Filter is physical interface filter";
       type empty;
     }
     list term {
       key name;
       ordered-by user;
       description "Define a firewall term";
       leaf name {
         description "Term name";
         type string {
         }
       }
       uses apply-advanced;
       leaf filter {
         description "Filter to include";
         type string {
         }
       }
       container from {
         description "Define match criteria";
         uses apply-advanced;
         choice destination-class_choice {
           case case_1 {
           }
           case case_2 {
           }
         }
         choice source-class_choice {
           case case_1 {
           }
           case case_2 {
           }
         }
         choice interface-group_choice {
           case case_1 {
             leaf-list interface-group {
               ordered-by user;
               description "Range of values";
               type string;
             }
           }
           case case_2 {
             leaf-list interface-group-except {
               ordered-by user;
               description "Range of values";
               type string;
             }
           }
         }
         list source-address {
           key name;
           ordered-by user;
           description "Match  source address";
           uses firewall_addr6_object;
         }
         list destination-address {
           key name;
           ordered-by user;
           description "Match destination address";
           uses firewall_addr6_object;
         }
         list address {
           key name;
           ordered-by user;
           description "Match source or destination address";
           uses firewall_addr6_object;
         }
         list source-prefix-list {
           key name;
           ordered-by user;
           description "Match source prefixes in named list";
           uses firewall_prefix_list;
         }
         list destination-prefix-list {
           key name;
           ordered-by user;
           description "Match destination prefixes in named list";
           uses firewall_prefix_list;
         }
         list prefix-list {
           key name;
           ordered-by user;
           description "Match source or destination prefixes in named list";
           uses firewall_prefix_list;
         }
         choice next-header_choice {
           case case_1 {
             leaf-list next-header {
               ordered-by user;
               type string;
             }
           }
           case case_2 {
             leaf-list next-header-except {
               ordered-by user;
               type string;
             }
           }
         }
         choice payload-protocol_choice {
           case case_1 {
           }
           case case_2 {
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice port_choice {
           case case_1 {
             leaf-list port {
               ordered-by user;
               type string;
             }
           }
           case case_2 {
             leaf-list port-except {
               ordered-by user;
               type string;
             }
           }
         }
         choice extension-header_choice {
           case case_1 {
           }
           case case_2 {
           }
         }
         choice packet-length_choice {
           case case_1 {
             leaf-list packet-length {
               ordered-by user;
               description "Range of values";
               type string {
               }
             }
           }
           case case_2 {
             leaf-list packet-length-except {
               ordered-by user;
               description "Range of values";
               type string {
               }
             }
           }
         }
         choice traffic-class_choice {
           case case_1 {
             leaf-list traffic-class {
               ordered-by user;
               type string;
             }
           }
           case case_2 {
             leaf-list traffic-class-except {
               ordered-by user;
               type string;
             }
           }
         }
         choice icmp-type_choice {
           case case_1 {
             leaf-list icmp-type {
               ordered-by user;
               type string;
             }
           }
           case case_2 {
             leaf-list icmp-type-except {
               ordered-by user;
               type string;
             }
           }
         }
         choice icmp-code_choice {
           case case_1 {
             leaf-list icmp-code {
               ordered-by user;
               type string;
             }
           }
           case case_2 {
             leaf-list icmp-code-except {
               ordered-by user;
               type string;
             }
           }
         }
         leaf tcp-initial {
           description "Match initial packet of a TCP connection";
           type empty;
         }
         leaf tcp-established {
           description "Match packet of an established TCP connection";
           type empty;
         }
         leaf tcp-flags {
           description "Match TCP flags (in symbolic or hex formats)";
           type string;
         }
         list interface {
           key name;
           ordered-by user;
           description "Match interface name";
           uses match_interface_object;
         }
         list interface-set {
           key name;
           ordered-by user;
           description "Match interface in set";
           uses match_interface_set_object;
         }
         choice forwarding-class_choice {
           case case_1 {
             leaf-list forwarding-class {
               ordered-by user;
               description "String name";
               type string {
               }
             }
           }
           case case_2 {
             leaf-list forwarding-class-except {
               ordered-by user;
               description "String name";
               type string {
               }
             }
           }
         }
         choice loss-priority_choice {
           case case_1 {
           }
           case case_2 {
           }
         }
         leaf service-filter-hit {
           description "Match if service-filter-hit is set";
           type empty;
         }
         choice hop-limit_choice {
           case case_1 {
           }
           case case_2 {
           }
         }
         choice gre-key_choice {
           case case_1 {
           }
           case case_2 {
           }
         }
         choice policy-map_choice {
           case case_1 {
             leaf-list policy-map {
               ordered-by user;
               description "String name";
               type string {
                 length "1 .. 64";
               }
             }
           }
           case case_2 {
             leaf-list policy-map-except {
               ordered-by user;
               description "String name";
               type string {
                 length "1 .. 64";
               }
             }
           }
         }
       }
       container then {
         description "Action to take if the 'from' condition is matched";
         uses apply-advanced;
         choice policer-choice {
           case case_1 {
             leaf policer {
               description "Name of policer to use to rate-limit traffic";
               type string {
               }
             }
           }
           case case_2 {
             container three-color-policer {
               description "Police the packet using a three-color-policer";
               uses apply-advanced;
               choice type-choice {
                 case case_1 {
                   leaf single-rate {
                     description "Name of single-rate three-color policer to use to rate-limit traffic";
                     type string {
                     }
                   }
                 }
                 case case_2 {
                   leaf single-packet-rate {
                     description "Name of single-packet-rate three-color policer to use to rate-limit traffic";
                     type string {
                     }
                   }
                 }
                 case case_3 {
                   leaf two-rate {
                     description "Name of two-rate three-color policer to use to rate-limit traffic";
                     type string {
                     }
                   }
                 }
                 case case_4 {
                   leaf two-packet-rate {
                     description "Name of two-packet-rate three-color policer to use to rate-limit traffic";
                     type string {
                     }
                   }
                 }
               }
             }
           }
           case case_3 {
           }
         }
         choice policy-map-choice {
           case case_1 {
             leaf clear-policy-map {
               description "Clear the policy marking";
               type empty;
             }
           }
           case case_2 {
             leaf policy-map {
               description "Policy map action";
               type string {
               }
             }
           }
         }
         choice inet6cnt {
           case case_1 {
           }
           case case_2 {
             leaf count {
               description "Count the packet in the named counter";
               type string {
               }
             }
           }
         }
         leaf service-accounting {
           description "Count the packets for service accounting";
           type empty;
         }
         leaf service-accounting-deferred {
           description "Count the packets for deferred service accounting";
           type empty;
         }
         leaf log {
           description "Log the packet";
           type empty;
         }
         leaf syslog {
           description "System log (syslog) information about the packet";
           type empty;
         }
         leaf sample {
           description "Sample the packet";
           type empty;
         }
         leaf port-mirror-instance {
           description "Port-mirror the packet to specified instance";
           type string {
           }
         }
         leaf loss-priority {
           description "Packet's loss priority";
           type enumeration {
             enum "low" {
               description "Loss priority low";
             }
             enum "high" {
               description "Loss priority high";
             }
             enum "medium-low" {
               description "Loss priority medium-low";
             }
             enum "medium-high" {
               description "Loss priority medium-high";
             }
           }
         }
         leaf forwarding-class {
           description "Classify packet to forwarding class";
           type string {
           }
         }
         leaf skip-services {
           description "Skip the services";
           type empty;
         }
         leaf service-filter-hit {
           description "Marked when packet processing by the current type of chained filters is done, the packet is directed to the next type of filters";
           type empty;
         }
         choice designation {
           case case_1 {
           }
           case case_2 {
           }
           case case_3 {
             leaf accept {
               description "Accept the packet";
               type empty;
             }
           }
           case case_4 {
             leaf discard {
               description "Discard the packet";
               type empty;
             }
           }
           case case_5 {
             leaf next {
               description "Continue to next term in a filter";
               type enumeration {
                 enum "term" {
                   description "Continue to next term in a filter";
                 }
               }
             }
           }
           case case_6 {
           }
           case case_7 {
             list logical-system {
               key logical-system-name;
               ordered-by user;
               description "Packets are directed to specified logical system";
               max-elements 1;
               leaf logical-system-name {
                 description "Name of logical system";
                 type string {
                 }
               }
               container routing-instance {
                 description "Packets are directed to specified routing instance";
                 leaf routing-instance-name {
                   description "Name of routing instance";
                   type string {
                   }
                 }
                 leaf topology {
                   description "Packets are directed to specified topology";
                   type string {
                   }
                 }
               }
               leaf topology {
                 description "Packets are directed to specified topology";
                 type string {
                 }
               }
             }
           }
           case case_8 {
             container routing-instance {
               description "Packets are directed to specified routing instance";
               leaf routing-instance-name {
                 description "Name of routing instance";
                 type string {
                 }
               }
               leaf topology {
                 description "Packets are directed to specified topology";
                 type string {
                 }
               }
             }
           }
           case case_9 {
             leaf topology {
               description "Packets are directed to specified topology";
               type string {
               }
             }
           }
           case case_10 {
           }
           case case_11 {
           }
           case case_12 {
             container reject {
               presence "enable reject";
               description "Reject the packet";
               choice style {
                 case case_1 {
                   leaf no-route {
                     description "Send ICMPv6 No Route message";
                     type empty;
                   }
                 }
                 case case_2 {
                   leaf administratively-prohibited {
                     description "Send ICMPv6 Administratively Prohibited message";
                     type empty;
                   }
                 }
                 case case_3 {
                   leaf beyond-scope {
                     description "Send ICMPv6 Beyond Scope of Source Address message";
                     type empty;
                   }
                 }
                 case case_4 {
                   leaf address-unreachable {
                     description "Send ICMPv6 Address Unreachable message";
                     type empty;
                   }
                 }
                 case case_5 {
                   leaf port-unreachable {
                     description "Send ICMPv6 Port Unreachable message";
                     type empty;
                   }
                 }
                 case case_6 {
                   leaf policy-failed {
                     description "Source address failed ingress/egress policy";
                     type empty;
                   }
                 }
                 case case_7 {
                   leaf reject-route {
                     description "Reject route to destination";
                     type empty;
                   }
                 }
                 case case_8 {
                   leaf tcp-reset {
                     description "Send TCP Reset message";
                     type empty;
                   }
                 }
                 case case_9 {
                   leaf network-unreachable {
                     description "Send ICMPv4 Network Unreachable message";
                     status deprecated;
                     type empty;
                   }
                 }
                 case case_10 {
                   leaf host-unreachable {
                     description "Send ICMPv4 Host Unreachable message";
                     status deprecated;
                     type empty;
                   }
                 }
                 case case_11 {
                   leaf protocol-unreachable {
                     description "Send ICMPv4 Protocol Unreachable message";
                     status deprecated;
                     type empty;
                   }
                 }
                 case case_12 {
                   leaf source-route-failed {
                     description "Send ICMPv4 Source Route Failed message";
                     status deprecated;
                     type empty;
                   }
                 }
                 case case_13 {
                   leaf network-unknown {
                     description "Send ICMPv4 Network Unknown message";
                     status deprecated;
                     type empty;
                   }
                 }
                 case case_14 {
                   leaf host-unknown {
                     description "Send ICMPv4 Host Unknown message";
                     status deprecated;
                     type empty;
                   }
                 }
                 case case_15 {
                   leaf source-host-isolated {
                     description "Send ICMPv4 Source Host Isolated message";
                     status deprecated;
                     type empty;
                   }
                 }
                 case case_16 {
                   leaf network-prohibited {
                     description "Send ICMPv4 Network Prohibited message";
                     status deprecated;
                     type empty;
                   }
                 }
                 case case_17 {
                   leaf host-prohibited {
                     description "Send ICMPv4 Host Prohibited message";
                     status deprecated;
                     type empty;
                   }
                 }
                 case case_18 {
                   leaf bad-network-tos {
                     description "Send ICMPv4 Bad Network ToS message";
                     status deprecated;
                     type empty;
                   }
                 }
                 case case_19 {
                   leaf bad-host-tos {
                     description "Send ICMPv4 Bad Host ToS message";
                     status deprecated;
                     type empty;
                   }
                 }
                 case case_20 {
                   leaf precedence-violation {
                     description "Send ICMPv4 Precedence Violation message";
                     status deprecated;
                     type empty;
                   }
                 }
                 case case_21 {
                   leaf precedence-cutoff {
                     description "Send ICMPv4 Precedence Cutoff message";
                     status deprecated;
                     type empty;
                   }
                 }
               }
             }
           }
         }
       }
     }
   }
   grouping inet6_fuf {
     leaf name {
       description "Name of fast update filter";
       type string {
       }
     }
     uses apply-advanced;
     leaf interface-specific {
       description "Defined counters are interface specific";
       type empty;
     }
     leaf-list match-order {
       ordered-by user;
       type enumeration {
         enum "next-header" {
           description "Include next header protocol in match set";
         }
         enum "payload-protocol" {
           description "Include payload protocol in match set";
         }
         enum "source-address" {
           description "Include source-address in match set";
         }
         enum "destination-address" {
           description "Include destination-address in match set";
         }
         enum "source-port" {
           description "Include source-port in match set";
         }
         enum "destination-port" {
           description "Include destination-port in match set";
         }
         enum "traffic-class" {
           description "Include traffic-class (DSCP) in match set";
         }
       }
     }
     list term {
       key name;
       ordered-by user;
       description "One or more firewall terms";
       leaf name {
         description "Term name";
         type string {
         }
       }
       uses apply-advanced;
       leaf only-at-create {
         description "Add term only when filter is first created.";
         type empty;
       }
       container from {
         description "Match criteria";
         uses apply-advanced;
         container source-address {
           description "Match source IP address";
           uses firewall_addr6_simple_object;
         }
         container destination-address {
           description "Match destination IP address";
           uses firewall_addr6_simple_object;
         }
         choice source-port_choice {
           case case_1 {
             container source-port {
               description "Match TCP/UDP source port";
               uses match_simple_port_value;
             }
           }
         }
         choice destination-port_choice {
           case case_1 {
             container destination-port {
               description "Match TCP/UDP destination port";
               uses match_simple_port_value;
             }
           }
         }
         choice next-header_choice {
           case case_1 {
             container next-header {
               description "Match next header protocol type";
               uses match_simple_protocol_value;
             }
           }
         }
         choice traffic-class_choice {
           case case_1 {
             container traffic-class {
               description "Match Differentiated Services (DiffServ) code point";
               uses match_simple_dscp_value;
             }
           }
         }
         leaf match-terms {
           description "Dynamically supplied list of match criteria";
           type string;
         }
       }
       container then {
         description "Action to take if the 'from' condition is matched";
         uses apply-advanced;
         choice policer-choice {
           case case_1 {
             leaf policer {
               description "Name of policer to use to rate-limit traffic";
               type string {
               }
             }
           }
         }
         leaf count {
           description "Count the packet in the named counter";
           type string {
           }
         }
         leaf service-accounting {
           description "Count the packets for service accounting";
           type empty;
         }
         leaf log {
           description "Log the packet";
           type empty;
         }
         leaf port-mirror {
           description "Port-mirror the packet";
           type empty;
         }
         leaf loss-priority {
           description "Packet's loss priority";
           type enumeration {
             enum "low" {
               description "Loss priority low";
             }
             enum "high" {
               description "Loss priority high";
             }
             enum "medium-low" {
               description "Loss priority medium-low";
             }
             enum "medium-high" {
               description "Loss priority medium-high";
             }
           }
         }
         leaf forwarding-class {
           description "Classify packet to forwarding class";
           type string {
           }
         }
         leaf action-terms {
           description "Dynamically supplied list of actions";
           type string;
         }
         choice designation {
           case case_1 {
             leaf accept {
               description "Accept the packet";
               type empty;
             }
           }
           case case_2 {
             leaf discard {
               description "Discard the packet";
               type empty;
             }
           }
           case case_3 {
             container routing-instance {
               description "Packets are directed to specified routing instance";
               leaf routing-instance-name {
                 description "Name of routing instance";
                 type string {
                 }
               }
               leaf topology {
                 description "Packets are directed to specified topology";
                 type string {
                 }
               }
             }
           }
         }
       }
     }
   }
   grouping firewall_addr6_simple_object {
     uses apply-advanced;
     leaf address {
       description "Prefix to match";
       type jt:ipv6prefix;
     }
   }
   grouping inet6_service_filter {
     leaf name {
       description "Filter name";
       type string {
       }
     }
     uses apply-advanced;
     list term {
       key name;
       ordered-by user;
       description "Service filter term";
       leaf name {
         description "Term name";
         type string {
         }
       }
       uses apply-advanced;
       container from {
         description "Match criteria";
         uses apply-advanced;
         choice interface-group_choice {
           case case_1 {
             leaf-list interface-group {
               ordered-by user;
               description "Range of values";
               type string;
             }
           }
           case case_2 {
             leaf-list interface-group-except {
               ordered-by user;
               description "Range of values";
               type string;
             }
           }
         }
         list source-address {
           key name;
           ordered-by user;
           description "Match  source address";
           uses firewall_addr6_object;
         }
         list destination-address {
           key name;
           ordered-by user;
           description "Match destination address";
           uses firewall_addr6_object;
         }
         list address {
           key name;
           ordered-by user;
           description "Match source or destination address";
           uses firewall_addr6_object;
         }
         list source-prefix-list {
           key name;
           ordered-by user;
           description "Match source prefixes in named list";
           uses firewall_prefix_list;
         }
         list destination-prefix-list {
           key name;
           ordered-by user;
           description "Match destination prefixes in named list";
           uses firewall_prefix_list;
         }
         list prefix-list {
           key name;
           ordered-by user;
           description "Match source or destination prefixes in named list";
           uses firewall_prefix_list;
         }
         choice next-header_choice {
           case case_1 {
             leaf-list next-header {
               ordered-by user;
               type string;
             }
           }
           case case_2 {
             leaf-list next-header-except {
               ordered-by user;
               type string;
             }
           }
         }
         choice payload-protocol_choice {
           case case_1 {
           }
           case case_2 {
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice port_choice {
           case case_1 {
             leaf-list port {
               ordered-by user;
               type string;
             }
           }
           case case_2 {
             leaf-list port-except {
               ordered-by user;
               type string;
             }
           }
         }
         choice extension-header_choice {
           case case_1 {
           }
           case case_2 {
           }
         }
         choice esp-spi_choice {
           case case_1 {
             leaf-list esp-spi {
               ordered-by user;
               description "Range of values";
               type string;
             }
           }
           case case_2 {
             leaf-list esp-spi-except {
               ordered-by user;
               description "Range of values";
               type string;
             }
           }
         }
         choice ah-spi_choice {
           case case_1 {
           }
           case case_2 {
           }
         }
         leaf tcp-flags {
           description "Match TCP flags (in symbolic or hex formats)";
           type string;
         }
         choice loss-priority_choice {
           case case_1 {
           }
           case case_2 {
           }
         }
         choice forwarding-class_choice {
           case case_1 {
             leaf-list forwarding-class {
               ordered-by user;
               description "String name";
               type string {
               }
             }
           }
           case case_2 {
             leaf-list forwarding-class-except {
               ordered-by user;
               description "String name";
               type string {
               }
             }
           }
         }
       }
       container then {
         description "Action to take if the 'from' condition is matched";
         uses apply-advanced;
         leaf count {
           description "Count the packet in the named counter";
           type string {
           }
         }
         leaf log {
           description "Log the packet";
           type empty;
         }
         leaf sample {
           description "Sample the packet";
           type empty;
         }
         leaf port-mirror {
           description "Port-mirror the packet";
           type empty;
         }
         choice designation {
           case case_1 {
             leaf service {
               description "Forward packets to service processing";
               type empty;
             }
           }
           case case_2 {
             leaf skip {
               description "Skip service processing";
               type empty;
             }
           }
           case case_3 {
           }
         }
       }
     }
   }
   grouping inet_dialer_filter {
     leaf name {
       description "Filter name";
       type string {
       }
     }
     uses apply-advanced;
     leaf-list accounting-profile {
       ordered-by user;
       description "Accounting profile name";
       type string;
     }
     list term {
       key name;
       ordered-by user;
       description "Define a firewall term";
       leaf name {
         description "Term name";
         type string {
         }
       }
       uses apply-advanced;
       container from {
         description "Define match criteria";
         uses apply-advanced;
         list source-address {
           key name;
           ordered-by user;
           description "Match IP source address";
           uses firewall_addr_object;
         }
         list destination-address {
           key name;
           ordered-by user;
           description "Match IP destination address";
           uses firewall_addr_object;
         }
         list address {
           key name;
           ordered-by user;
           description "Match IP source or destination address";
           uses firewall_addr_object;
         }
         list source-prefix-list {
           key name;
           ordered-by user;
           description "Match IP source prefixes in named list";
           uses firewall_prefix_list;
         }
         list destination-prefix-list {
           key name;
           ordered-by user;
           description "Match IP destination prefixes in named list";
           uses firewall_prefix_list;
         }
         list prefix-list {
           key name;
           ordered-by user;
           description "Match IP source or destination prefixes in named list";
           uses firewall_prefix_list;
         }
         choice packet-length_choice {
           case case_1 {
             leaf-list packet-length {
               ordered-by user;
               description "Range of values";
               type string {
               }
             }
           }
           case case_2 {
             leaf-list packet-length-except {
               ordered-by user;
               description "Range of values";
               type string {
               }
             }
           }
         }
         choice precedence_choice {
           case case_1 {
             leaf-list precedence {
               ordered-by user;
               type string;
             }
           }
           case case_2 {
             leaf-list precedence-except {
               ordered-by user;
               type string;
             }
           }
         }
         choice dscp_choice {
           case case_1 {
             leaf-list dscp {
               ordered-by user;
               type string;
             }
           }
           case case_2 {
             leaf-list dscp-except {
               ordered-by user;
               type string;
             }
           }
         }
         choice ip-options_choice {
           case case_1 {
             leaf-list ip-options {
               ordered-by user;
               type string;
             }
           }
           case case_2 {
             leaf-list ip-options-except {
               ordered-by user;
               type string;
             }
           }
         }
         leaf is-fragment {
           description "Match if packet is a fragment";
           type empty;
         }
         leaf first-fragment {
           description "Match if packet is the first fragment";
           type empty;
         }
         choice fragment-offset_choice {
           case case_1 {
             leaf-list fragment-offset {
               ordered-by user;
               description "Range of values";
               type string {
               }
             }
           }
           case case_2 {
             leaf-list fragment-offset-except {
               ordered-by user;
               description "Range of values";
               type string {
               }
             }
           }
         }
         leaf fragment-flags {
           description "Match fragment flags";
           type string;
         }
         choice protocol_choice {
           case case_1 {
             leaf-list protocol {
               ordered-by user;
               type string;
             }
           }
           case case_2 {
             leaf-list protocol-except {
               ordered-by user;
               type string;
             }
           }
         }
         choice ttl_choice {
           case case_1 {
             leaf-list ttl {
               ordered-by user;
               description "Range of values";
               type string {
               }
             }
           }
           case case_2 {
             leaf-list ttl-except {
               ordered-by user;
               description "Range of values";
               type string {
               }
             }
           }
         }
         choice icmp-type_choice {
           case case_1 {
             leaf-list icmp-type {
               ordered-by user;
               type string;
             }
           }
           case case_2 {
             leaf-list icmp-type-except {
               ordered-by user;
               type string;
             }
           }
         }
         choice icmp-code_choice {
           case case_1 {
             leaf-list icmp-code {
               ordered-by user;
               type string;
             }
           }
           case case_2 {
             leaf-list icmp-code-except {
               ordered-by user;
               type string;
             }
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice port_choice {
           case case_1 {
             leaf-list port {
               ordered-by user;
               type string;
             }
           }
           case case_2 {
             leaf-list port-except {
               ordered-by user;
               type string;
             }
           }
         }
         leaf tcp-initial {
           description "Match initial packet of a TCP connection";
           type empty;
         }
         leaf tcp-established {
           description "Match packet of an established TCP connection";
           type empty;
         }
         leaf tcp-flags {
           description "Match TCP flags (in symbolic or hex formats)";
           type string;
         }
         choice esp-spi_choice {
           case case_1 {
             leaf-list esp-spi {
               ordered-by user;
               description "Range of values";
               type string;
             }
           }
           case case_2 {
             leaf-list esp-spi-except {
               ordered-by user;
               description "Range of values";
               type string;
             }
           }
         }
         choice ah-spi_choice {
           case case_1 {
           }
           case case_2 {
           }
         }
       }
       container then {
         description "Action to take if the 'from' condition is matched";
         uses apply-advanced;
         leaf log {
           description "Log the packet";
           type empty;
         }
         leaf syslog {
           description "System log (syslog) information about the packet";
           type empty;
         }
         leaf sample {
           description "Sample the packet";
           type empty;
         }
         choice designation {
           case case_1 {
             leaf note {
               description "Interested ISDN packet";
               type empty;
             }
           }
           case case_2 {
             leaf ignore {
               description "Non-interested ISDN packet";
               type empty;
             }
           }
         }
       }
     }
   }
   grouping inet_filter {
     leaf name {
       description "Filter name";
       type string {
       }
     }
     uses apply-advanced;
     leaf-list accounting-profile {
       ordered-by user;
       description "Accounting profile name";
       type string;
     }
     leaf interface-specific {
       description "Defined counters are interface specific";
       type empty;
     }
     leaf physical-interface-filter {
       description "Filter is physical interface filter";
       type empty;
     }
     list term {
       key name;
       ordered-by user;
       description "Define a firewall term";
       leaf name {
         description "Term name";
         type string {
         }
       }
       uses apply-advanced;
       leaf filter {
         description "Filter to include";
         type string {
         }
       }
       container from {
         description "Define match criteria";
         uses apply-advanced;
         choice destination-class_choice {
           case case_1 {
           }
           case case_2 {
           }
         }
         choice source-class_choice {
           case case_1 {
           }
           case case_2 {
           }
         }
         choice interface-group_choice {
           case case_1 {
             leaf-list interface-group {
               ordered-by user;
               description "Range of values";
               type string;
             }
           }
           case case_2 {
             leaf-list interface-group-except {
               ordered-by user;
               description "Range of values";
               type string;
             }
           }
         }
         list source-address {
           key name;
           ordered-by user;
           description "Match IP source address";
           uses firewall_addr_object;
         }
         list destination-address {
           key name;
           ordered-by user;
           description "Match IP destination address";
           uses firewall_addr_object;
         }
         list address {
           key name;
           ordered-by user;
           description "Match IP source or destination address";
           uses firewall_addr_object;
         }
         list source-prefix-list {
           key name;
           ordered-by user;
           description "Match IP source prefixes in named list";
           uses firewall_prefix_list;
         }
         list destination-prefix-list {
           key name;
           ordered-by user;
           description "Match IP destination prefixes in named list";
           uses firewall_prefix_list;
         }
         list prefix-list {
           key name;
           ordered-by user;
           description "Match IP source or destination prefixes in named list";
           uses firewall_prefix_list;
         }
         choice packet-length_choice {
           case case_1 {
             leaf-list packet-length {
               ordered-by user;
               description "Range of values";
               type string {
               }
             }
           }
           case case_2 {
             leaf-list packet-length-except {
               ordered-by user;
               description "Range of values";
               type string {
               }
             }
           }
         }
         choice dscp_choice {
           case case_1 {
             leaf-list dscp {
               ordered-by user;
               type string;
             }
           }
           case case_2 {
             leaf-list dscp-except {
               ordered-by user;
               type string;
             }
           }
         }
         choice precedence_choice {
           case case_1 {
             leaf-list precedence {
               ordered-by user;
               type string;
             }
           }
           case case_2 {
             leaf-list precedence-except {
               ordered-by user;
               type string;
             }
           }
         }
         choice ip-options_choice {
           case case_1 {
             leaf-list ip-options {
               ordered-by user;
               type string;
             }
           }
           case case_2 {
             leaf-list ip-options-except {
               ordered-by user;
               type string;
             }
           }
         }
         leaf is-fragment {
           description "Match if packet is a fragment";
           type empty;
         }
         leaf first-fragment {
           description "Match if packet is the first fragment";
           type empty;
         }
         leaf service-filter-hit {
           description "Match if service-filter-hit is set";
           type empty;
         }
         choice fragment-offset_choice {
           case case_1 {
             leaf-list fragment-offset {
               ordered-by user;
               description "Range of values";
               type string {
               }
             }
           }
           case case_2 {
             leaf-list fragment-offset-except {
               ordered-by user;
               description "Range of values";
               type string {
               }
             }
           }
         }
         leaf fragment-flags {
           description "Match fragment flags (in symbolic or hex formats) - (Ingress only)";
           type string;
         }
         choice protocol_choice {
           case case_1 {
             leaf-list protocol {
               ordered-by user;
               type string;
             }
           }
           case case_2 {
             leaf-list protocol-except {
               ordered-by user;
               type string;
             }
           }
         }
         choice ttl_choice {
           case case_1 {
             leaf-list ttl {
               ordered-by user;
               description "Range of values";
               type string {
               }
             }
           }
           case case_2 {
             leaf-list ttl-except {
               ordered-by user;
               description "Range of values";
               type string {
               }
             }
           }
         }
         choice icmp-type_choice {
           case case_1 {
             leaf-list icmp-type {
               ordered-by user;
               type string;
             }
           }
           case case_2 {
             leaf-list icmp-type-except {
               ordered-by user;
               type string;
             }
           }
         }
         choice icmp-code_choice {
           case case_1 {
             leaf-list icmp-code {
               ordered-by user;
               type string;
             }
           }
           case case_2 {
             leaf-list icmp-code-except {
               ordered-by user;
               type string;
             }
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice port_choice {
           case case_1 {
             leaf-list port {
               ordered-by user;
               type string;
             }
           }
           case case_2 {
             leaf-list port-except {
               ordered-by user;
               type string;
             }
           }
         }
         leaf tcp-initial {
           description "Match initial packet of a TCP connection";
           type empty;
         }
         leaf tcp-established {
           description "Match packet of an established TCP connection";
           type empty;
         }
         leaf tcp-flags {
           description "Match TCP flags (in symbolic or hex formats)";
           type string;
         }
         choice esp-spi_choice {
           case case_1 {
             leaf-list esp-spi {
               ordered-by user;
               description "Range of values";
               type string;
             }
           }
           case case_2 {
             leaf-list esp-spi-except {
               ordered-by user;
               description "Range of values";
               type string;
             }
           }
         }
         choice ah-spi_choice {
           case case_1 {
           }
           case case_2 {
           }
         }
         list interface {
           key name;
           ordered-by user;
           description "Match interface name";
           uses match_interface_object;
         }
         list interface-set {
           key name;
           ordered-by user;
           description "Match interface in set";
           uses match_interface_set_object;
         }
         choice forwarding-class_choice {
           case case_1 {
             leaf-list forwarding-class {
               ordered-by user;
               description "String name";
               type string {
               }
             }
           }
           case case_2 {
             leaf-list forwarding-class-except {
               ordered-by user;
               description "String name";
               type string {
               }
             }
           }
         }
         choice loss-priority_choice {
           case case_1 {
           }
           case case_2 {
           }
         }
         choice rat-type_choice {
           case case_1 {
             leaf-list rat-type {
               ordered-by user;
               type string;
             }
           }
           case case_2 {
             leaf-list rat-type-except {
               ordered-by user;
               type string;
             }
           }
         }
         choice redirect-reason_choice {
           case case_1 {
             leaf-list redirect-reason {
               ordered-by user;
               type enumeration {
                 enum "aoc" {
                   description "Advice of Charge";
                 }
                 enum "aolb" {
                   description "Advice of Low Balance";
                 }
                 enum "dpi" {
                   description "Layer7 match required";
                 }
               }
             }
           }
           case case_2 {
             leaf-list redirect-reason-except {
               ordered-by user;
               type enumeration {
                 enum "aoc" {
                   description "Advice of Charge";
                 }
                 enum "aolb" {
                   description "Advice of Low Balance";
                 }
                 enum "dpi" {
                   description "Layer7 match required";
                 }
               }
             }
           }
         }
         choice gre-key_choice {
           case case_1 {
           }
           case case_2 {
           }
         }
         choice policy-map_choice {
           case case_1 {
             leaf-list policy-map {
               ordered-by user;
               description "String name";
               type string {
                 length "1 .. 64";
               }
             }
           }
           case case_2 {
             leaf-list policy-map-except {
               ordered-by user;
               description "String name";
               type string {
                 length "1 .. 64";
               }
             }
           }
         }
       }
       container then {
         description "Action to take if the 'from' condition is matched";
         uses apply-advanced;
         choice policer-choice {
           case case_1 {
             leaf policer {
               description "Name of policer to use to rate-limit traffic";
               type string {
               }
             }
           }
           case case_2 {
             container three-color-policer {
               description "Police the packet using a three-color-policer";
               uses apply-advanced;
               choice type-choice {
                 case case_1 {
                   leaf single-rate {
                     description "Name of single-rate three-color policer to use to rate-limit traffic";
                     type string {
                     }
                   }
                 }
                 case case_2 {
                   leaf single-packet-rate {
                     description "Name of single-packet-rate three-color policer to use to rate-limit traffic";
                     type string {
                     }
                   }
                 }
                 case case_3 {
                   leaf two-rate {
                     description "Name of two-rate three-color policer to use to rate-limit traffic";
                     type string {
                     }
                   }
                 }
                 case case_4 {
                   leaf two-packet-rate {
                     description "Name of two-packet-rate three-color policer to use to rate-limit traffic";
                     type string {
                     }
                   }
                 }
               }
             }
           }
           case case_3 {
           }
         }
         choice policy-map-choice {
           case case_1 {
             leaf clear-policy-map {
               description "Clear the policy marking";
               type empty;
             }
           }
           case case_2 {
             leaf policy-map {
               description "Policy map action";
               type string {
               }
             }
           }
         }
         choice inetcnt {
           case case_1 {
           }
           case case_2 {
             leaf count {
               description "Count the packet in the named counter";
               type string {
               }
             }
           }
         }
         leaf service-accounting {
           description "Count the packets for service accounting";
           type empty;
         }
         leaf skip-services {
           description "Skip the services";
           type empty;
         }
         leaf service-accounting-deferred {
           description "Count the packets for deferred service accounting";
           type empty;
         }
         leaf log {
           description "Log the packet";
           type empty;
         }
         leaf packet-mode {
           description "Bypass flow mode for the packet";
           type empty;
         }
         leaf syslog {
           description "System log (syslog) information about the packet";
           type empty;
         }
         leaf sample {
           description "Sample the packet";
           type empty;
         }
         leaf port-mirror-instance {
           description "Port-mirror the packet to specified instance";
           type string {
           }
         }
         leaf port-mirror {
           description "Port-mirror the packet";
           type empty;
         }
         leaf loss-priority {
           description "Packet's loss priority";
           type enumeration {
             enum "low" {
               description "Loss priority low";
             }
             enum "high" {
               description "Loss priority high";
             }
             enum "medium-low" {
               description "Loss priority medium-low";
             }
             enum "medium-high" {
               description "Loss priority medium-high";
             }
           }
         }
         leaf forwarding-class {
           description "Classify packet to forwarding class";
           type string {
           }
         }
         leaf service-filter-hit {
           description "Marked when packet processing by the current type of chained filters is done, the packet is directed to the next type of filters";
           type empty;
         }
         leaf virtual-channel {
           description "Set the output interface virtual channel";
           type string {
           }
         }
         choice designation {
           case case_1 {
             leaf accept {
               description "Accept the packet";
               type empty;
             }
           }
           case case_2 {
             container discard {
               presence "enable discard";
               description "Discard the packet";
               uses apply-advanced;
               leaf accounting {
                 description "Named discard collector for packet";
                 type string;
               }
             }
           }
           case case_3 {
             leaf next {
               description "Continue to next term in a filter";
               type enumeration {
                 enum "term" {
                   description "Continue to next term in a filter";
                 }
               }
             }
           }
           case case_4 {
             list logical-system {
               key logical-system-name;
               ordered-by user;
               description "Packets are directed to specified logical system";
               max-elements 1;
               leaf logical-system-name {
                 description "Name of logical system";
                 type string {
                 }
               }
               container routing-instance {
                 description "Packets are directed to specified routing instance";
                 leaf routing-instance-name {
                   description "Name of routing instance";
                   type string {
                   }
                 }
                 leaf topology {
                   description "Packets are directed to specified topology";
                   type string {
                   }
                 }
               }
               leaf topology {
                 description "Packets are directed to specified topology";
                 type string {
                 }
               }
             }
           }
           case case_5 {
             container routing-instance {
               description "Packets are directed to specified routing instance";
               leaf routing-instance-name {
                 description "Name of routing instance";
                 type string {
                 }
               }
               leaf topology {
                 description "Packets are directed to specified topology";
                 type string {
                 }
               }
             }
           }
           case case_6 {
             leaf topology {
               description "Packets are directed to specified topology";
               type string {
               }
             }
           }
           case case_7 {
           }
           case case_8 {
           }
           case case_9 {
           }
           case case_10 {
           }
           case case_11 {
           }
           case case_12 {
           }
           case case_13 {
             container reject {
               presence "enable reject";
               description "Reject the packet";
               choice style {
                 case case_1 {
                   leaf network-unreachable {
                     description "Send ICMP Network Unreachable message";
                     type empty;
                   }
                 }
                 case case_2 {
                   leaf host-unreachable {
                     description "Send ICMP Host Unreachable message";
                     type empty;
                   }
                 }
                 case case_3 {
                   leaf protocol-unreachable {
                     description "Send ICMP Protocol Unreachable message";
                     type empty;
                   }
                 }
                 case case_4 {
                   leaf port-unreachable {
                     description "Send ICMP Port Unreachable message";
                     type empty;
                   }
                 }
                 case case_5 {
                   leaf fragmentation-needed {
                     description "Send ICMP Fragmentation Needed message";
                     type empty;
                   }
                 }
                 case case_6 {
                   leaf source-route-failed {
                     description "Send ICMP Source Route Failed message";
                     type empty;
                   }
                 }
                 case case_7 {
                   leaf network-unknown {
                     description "Send ICMP Network Unknown message";
                     type empty;
                   }
                 }
                 case case_8 {
                   leaf host-unknown {
                     description "Send ICMP Host Unknown message";
                     type empty;
                   }
                 }
                 case case_9 {
                   leaf source-host-isolated {
                     description "Send ICMP Source Host Isolated message";
                     type empty;
                   }
                 }
                 case case_10 {
                   leaf network-prohibited {
                     description "Send ICMP Network Prohibited message";
                     type empty;
                   }
                 }
                 case case_11 {
                   leaf host-prohibited {
                     description "Send ICMP Host Prohibited message";
                     type empty;
                   }
                 }
                 case case_12 {
                   leaf bad-network-tos {
                     description "Send ICMP Bad Network ToS message";
                     type empty;
                   }
                 }
                 case case_13 {
                   leaf bad-host-tos {
                     description "Send ICMP Bad Host ToS message";
                     type empty;
                   }
                 }
                 case case_14 {
                   leaf administratively-prohibited {
                     description "Send ICMP Administratively Prohibited message";
                     type empty;
                   }
                 }
                 case case_15 {
                   leaf precedence-violation {
                     description "Send ICMP Precedence Violation message";
                     type empty;
                   }
                 }
                 case case_16 {
                   leaf precedence-cutoff {
                     description "Send ICMP Precedence Cutoff message";
                     type empty;
                   }
                 }
                 case case_17 {
                   leaf tcp-reset {
                     description "Send TCP Reset message";
                     type empty;
                   }
                 }
               }
             }
           }
           case case_14 {
           }
         }
         leaf prefix-action {
           description "Police or count packets using named prefix action";
           type string {
           }
         }
       }
     }
   }
   grouping inet_fuf {
     leaf name {
       description "Name of fast update filter";
       type string {
       }
     }
     uses apply-advanced;
     leaf interface-specific {
       description "Defined counters are interface specific";
       type empty;
     }
     leaf-list match-order {
       ordered-by user;
       type enumeration {
         enum "protocol" {
           description "Include IP protocol in match set";
         }
         enum "source-address" {
           description "Include source-address in match set";
         }
         enum "destination-address" {
           description "Include destination-address in match set";
         }
         enum "source-port" {
           description "Include source-port in match set";
         }
         enum "destination-port" {
           description "Include destination-port in match set";
         }
         enum "dscp" {
           description "Include Differentiated Services (DiffServ) code point in match set";
         }
       }
     }
     list term {
       key name;
       ordered-by user;
       description "One or more firewall terms";
       leaf name {
         description "Term name";
         type string {
         }
       }
       uses apply-advanced;
       leaf only-at-create {
         description "Add term only when filter is first created.";
         type empty;
       }
       container from {
         description "Match criteria";
         uses apply-advanced;
         container source-address {
           description "Match source IP address";
           uses firewall_addr_simple_object;
         }
         container destination-address {
           description "Match destination IP address";
           uses firewall_addr_simple_object;
         }
         choice source-port_choice {
           case case_1 {
             container source-port {
               description "Match TCP/UDP source port";
               uses match_simple_port_value;
             }
           }
         }
         choice destination-port_choice {
           case case_1 {
             container destination-port {
               description "Match TCP/UDP destination port";
               uses match_simple_port_value;
             }
           }
         }
         choice protocol_choice {
           case case_1 {
             container protocol {
               description "Match IP protocol type";
               uses match_simple_protocol_value;
             }
           }
         }
         choice dscp_choice {
           case case_1 {
             container dscp {
               description "Match Differentiated Services (DiffServ) code point";
               uses match_simple_dscp_value;
             }
           }
         }
         leaf match-terms {
           description "Dynamically supplied list of match criteria";
           type string;
         }
       }
       container then {
         description "Action to take if the 'from' condition is matched";
         uses apply-advanced;
         choice policer-choice {
           case case_1 {
             leaf policer {
               description "Name of policer to use to rate-limit traffic";
               type string {
               }
             }
           }
         }
         leaf count {
           description "Count the packet in the named counter";
           type string {
           }
         }
         leaf service-accounting {
           description "Count the packets for service accounting";
           type empty;
         }
         leaf log {
           description "Log the packet";
           type empty;
         }
         leaf port-mirror {
           description "Port-mirror the packet";
           type empty;
         }
         leaf loss-priority {
           description "Packet's loss priority";
           type enumeration {
             enum "low" {
               description "Loss priority low";
             }
             enum "high" {
               description "Loss priority high";
             }
             enum "medium-low" {
               description "Loss priority medium-low";
             }
             enum "medium-high" {
               description "Loss priority medium-high";
             }
           }
         }
         leaf forwarding-class {
           description "Classify packet to forwarding class";
           type string {
           }
         }
         leaf action-terms {
           description "Dynamically supplied list of actions";
           type string;
         }
         choice designation {
           case case_1 {
             leaf accept {
               description "Accept the packet";
               type empty;
             }
           }
           case case_2 {
             leaf discard {
               description "Discard the packet";
               type empty;
             }
           }
           case case_3 {
             container routing-instance {
               description "Packets are directed to specified routing instance";
               leaf routing-instance-name {
                 description "Name of routing instance";
                 type string {
                 }
               }
               leaf topology {
                 description "Packets are directed to specified topology";
                 type string {
                 }
               }
             }
           }
         }
       }
     }
   }
   grouping firewall_addr_simple_object {
     uses apply-advanced;
     leaf address {
       description "Prefix to match";
       type jt:ipv4prefix;
     }
   }
   grouping inet_service_filter {
     leaf name {
       description "Filter name";
       type string {
       }
     }
     uses apply-advanced;
     list term {
       key name;
       ordered-by user;
       description "Service filter term";
       leaf name {
         description "Term name";
         type string {
         }
       }
       uses apply-advanced;
       container from {
         description "Match criteria";
         uses apply-advanced;
         choice interface-group_choice {
           case case_1 {
             leaf-list interface-group {
               ordered-by user;
               description "Range of values";
               type string;
             }
           }
           case case_2 {
             leaf-list interface-group-except {
               ordered-by user;
               description "Range of values";
               type string;
             }
           }
         }
         list source-address {
           key name;
           ordered-by user;
           description "Match IP source address";
           uses firewall_addr_object;
         }
         list destination-address {
           key name;
           ordered-by user;
           description "Match IP destination address";
           uses firewall_addr_object;
         }
         list address {
           key name;
           ordered-by user;
           description "Match IP source or destination address";
           uses firewall_addr_object;
         }
         list source-prefix-list {
           key name;
           ordered-by user;
           description "Match IP source prefixes in named list";
           uses firewall_prefix_list;
         }
         list destination-prefix-list {
           key name;
           ordered-by user;
           description "Match IP destination prefixes in named list";
           uses firewall_prefix_list;
         }
         list prefix-list {
           key name;
           ordered-by user;
           description "Match IP source or destination prefixes in named list";
           uses firewall_prefix_list;
         }
         choice protocol_choice {
           case case_1 {
             leaf-list protocol {
               ordered-by user;
               type string;
             }
           }
           case case_2 {
             leaf-list protocol-except {
               ordered-by user;
               type string;
             }
           }
         }
         choice ip-options_choice {
           case case_1 {
             leaf-list ip-options {
               ordered-by user;
               type enumeration {
                 enum "any" {
                   description "Any IP option";
                 }
               }
             }
           }
           case case_2 {
             leaf-list ip-options-except {
               ordered-by user;
               type enumeration {
                 enum "any" {
                   description "Any IP option";
                 }
               }
             }
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice port_choice {
           case case_1 {
             leaf-list port {
               ordered-by user;
               type string;
             }
           }
           case case_2 {
             leaf-list port-except {
               ordered-by user;
               type string;
             }
           }
         }
         choice esp-spi_choice {
           case case_1 {
             leaf-list esp-spi {
               ordered-by user;
               description "Range of values";
               type string;
             }
           }
           case case_2 {
             leaf-list esp-spi-except {
               ordered-by user;
               description "Range of values";
               type string;
             }
           }
         }
         leaf is-fragment {
           description "Match if packet is a fragment";
           type empty;
         }
         leaf first-fragment {
           description "Match if packet is the first fragment";
           type empty;
         }
         choice fragment-offset_choice {
           case case_1 {
             leaf-list fragment-offset {
               ordered-by user;
               description "Range of values";
               type string {
               }
             }
           }
           case case_2 {
             leaf-list fragment-offset-except {
               ordered-by user;
               description "Range of values";
               type string {
               }
             }
           }
         }
         leaf fragment-flags {
           description "Match fragment flags";
           type string;
         }
         leaf tcp-flags {
           description "Match TCP flags (in symbolic or hex formats)";
           type string;
         }
         choice ah-spi_choice {
           case case_1 {
           }
           case case_2 {
           }
         }
         choice loss-priority_choice {
           case case_1 {
           }
           case case_2 {
           }
         }
         choice forwarding-class_choice {
           case case_1 {
             leaf-list forwarding-class {
               ordered-by user;
               description "String name";
               type string {
               }
             }
           }
           case case_2 {
             leaf-list forwarding-class-except {
               ordered-by user;
               description "String name";
               type string {
               }
             }
           }
         }
         choice redirect-reason_choice {
           case case_1 {
             leaf-list redirect-reason {
               ordered-by user;
               type enumeration {
                 enum "aoc" {
                   description "Advice of Charge";
                 }
                 enum "aolb" {
                   description "Advice of Low Balance";
                 }
                 enum "dpi" {
                   description "Layer7 match required";
                 }
               }
             }
           }
           case case_2 {
             leaf-list redirect-reason-except {
               ordered-by user;
               type enumeration {
                 enum "aoc" {
                   description "Advice of Charge";
                 }
                 enum "aolb" {
                   description "Advice of Low Balance";
                 }
                 enum "dpi" {
                   description "Layer7 match required";
                 }
               }
             }
           }
         }
       }
       container then {
         description "Action to take if the 'from' condition is matched";
         uses apply-advanced;
         leaf count {
           description "Count the packet in the named counter";
           type string {
           }
         }
         leaf log {
           description "Log the packet";
           type empty;
         }
         leaf sample {
           description "Sample the packet";
           type empty;
         }
         leaf port-mirror {
           description "Port-mirror the packet";
           type empty;
         }
         choice designation {
           case case_1 {
             leaf service {
               description "Forward packets to service processing";
               type empty;
             }
           }
           case case_2 {
             leaf skip {
               description "Skip service processing";
               type empty;
             }
           }
           case case_3 {
           }
         }
       }
     }
   }
   grouping inet_simple_filter {
     leaf name {
       description "Name of simple filter";
       type string {
       }
     }
     uses apply-advanced;
     leaf interface-specific {
       description "Defined counters are interface specific";
       status deprecated;
       type empty;
     }
     list term {
       key name;
       ordered-by user;
       description "One or more firewall terms";
       leaf name {
         description "Term name";
         type string {
         }
       }
       uses apply-advanced;
       container from {
         description "Match criteria";
         uses apply-advanced;
         container source-address {
           description "Source IP address";
           uses firewall_addr_simple_object;
         }
         container destination-address {
           description "Destination IP address";
           uses firewall_addr_simple_object;
         }
         choice protocol_choice {
           case case_1 {
             container protocol {
               description "Match IP protocol type";
               uses match_simple_protocol_value;
             }
           }
         }
         choice source-port_choice {
           case case_1 {
             container source-port {
               description "Match TCP/UDP source port";
               uses match_simple_port_value;
             }
           }
         }
         choice destination-port_choice {
           case case_1 {
             container destination-port {
               description "Match TCP/UDP destination port";
               uses match_simple_port_value;
             }
           }
         }
         choice forwarding-class_choice {
           case case_1 {
             leaf-list forwarding-class {
               ordered-by user;
               description "String name";
               type string {
               }
             }
           }
         }
       }
       container then {
         description "Action to take if the 'from' condition is matched";
         uses apply-advanced;
         choice policer-choice {
           case case_1 {
             leaf policer {
               description "Name of policer to use to rate-limit traffic";
               type string {
               }
             }
           }
           case case_2 {
             container three-color-policer {
               description "Police the packet using a three-color-policer";
               uses apply-advanced;
               choice type-choice {
                 case case_1 {
                   leaf single-rate {
                     description "Name of single-rate three-color policer to use to rate-limit traffic";
                     type string {
                     }
                   }
                 }
                 case case_2 {
                   leaf two-rate {
                     description "Name of two-rate three-color policer to use to rate-limit traffic";
                     type string {
                     }
                   }
                 }
               }
             }
           }
         }
         leaf loss-priority {
           description "Packet's loss priority";
           type enumeration {
             enum "low" {
               description "Low loss priority";
             }
             enum "medium-high" {
               description "Medium-high loss priority";
             }
             enum "medium-low" {
               description "Medium-low loss priority";
             }
             enum "high" {
               description "High loss priority";
             }
           }
         }
         leaf forwarding-class {
           description "Classify packet to forwarding class";
           type string {
           }
         }
         leaf discard {
           description "Discard the packet";
           type empty;
         }
         leaf accept {
           description "Accept the packet";
           type empty;
         }
       }
     }
   }
   grouping interface_set_type {
     leaf name {
       description "Interface set name";
       type string {
       }
     }
     uses apply-advanced;
     list interface-list {
       key name;
       ordered-by user;
       description "Interface list";
       leaf name {
         description "Interface name";
         type union {
           type jt:interface-wildcard;
           type string {
             pattern "<.*>|$.*";
           }
         }
       }
       uses apply-advanced;
     }
   }
   grouping jdhcp-local-server-type {
     uses apply-advanced;
     container dhcpv6 {
       description "DHCPv6 configuration";
       uses dhcpv6-local-server-type;
     }
     list pool-match-order {
       key name;
       ordered-by user;
       description "Define order of attribute matching for pool selection";
       leaf name {
         description "Match type";
         type enumeration {
           enum "external-authority" {
             description "External authority handles address selection";
           }
           enum "ip-address-first" {
             description "IP address used first to select a pool";
           }
           enum "option-82" {
             description "Option 82 used in matching of pool";
           }
           enum "option-82-strict" {
             description "Option 82 used in strict matching of pool";
           }
         }
       }
       uses apply-advanced;
     }
     container duplicate-clients-in-subnet {
       description "Allow duplicate clients in a subnet";
       uses jdhcp-duplicate-clients-in-subnet-type;
     }
     container forward-snooped-clients {
       description "Forward snooped (unicast) packets";
       choice interface-type {
         case case_1 {
           leaf configured-interfaces {
             description "Forward snooped (unicast) packets on configured interfaces";
             type empty;
           }
         }
         case case_2 {
           leaf non-configured-interfaces {
             description "Forward snooped (unicast) packets on non-configured interfaces";
             type empty;
           }
         }
         case case_3 {
           leaf all-interfaces {
             description "Forward snooped (unicast) packets on configured and non-configured interfaces";
             type empty;
           }
         }
       }
     }
     container overrides {
       description "DHCP override processing";
       presence "enable overrides";
       uses override-local-server-type;
     }
     leaf access-profile {
       description "Access profile to use for AAA services";
       type string {
         length "1 .. 128";
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container route-suppression {
       description "Suppress access-internal and/or destination route addition";
       uses dhcp-route-suppression-type;
     }
     list group {
       key name;
       ordered-by user;
       description "Define a DHCP local server group";
       uses dhcp-local-server-group;
     }
     list dual-stack-group {
       key name;
       description "Define a DHCP dual stack group";
       uses dhcp-local-server-dual-stack-group;
     }
     container lease-time-validation {
       presence "enable lease-time-validation";
       description "Configure lease time violation validation";
       uses apply-advanced;
       leaf lease-time-threshold {
         description "Threshold for lease time violation seconds";
         units "seconds";
         type union {
           type string {
             pattern "<.*>|$.*";
           }
           type uint32 {
             range "60 .. 2147483647";
           }
         }
       }
       container violation-action {
         description "Lease time validation violation action";
         choice violation-action-choice {
           case case_1 {
             leaf strict {
               description "Reject discover and renew";
               type empty;
             }
           }
           case case_2 {
             leaf override-lease {
               description "Override assigned lease time with threshold";
               type empty;
             }
           }
         }
       }
     }
     choice requested-ip-check {
       case case_1 {
         leaf requested-ip-network-match {
           description "Subnet to match server's address for active and giaddr for passive clients";
           default "8";
           type union {
             type string {
               pattern "<.*>|$.*";
             }
             type uint32 {
               range "0 .. 31";
             }
           }
         }
       }
       case case_2 {
         leaf requested-ip-interface-match {
           description "Use incoming-interface's subnet to check";
           type empty;
         }
       }
     }
     leaf no-snoop {
       description "Do not snoop DHCP packets";
       type empty;
     }
     container allow-leasequery {
       description "Allow DHCP leasequery";
       presence "enable allow-leasequery";
       uses server-leasequery-type;
     }
     container remote-id-mismatch {
       description "DHCP client remote-id mismatch";
       presence "enable remote-id-mismatch";
       uses dhcp-remote-id-mismatch-type;
     }
     container reauthenticate {
       description "DHCP client reauthenticate processing";
       leaf lease-renewal {
         description "Reauthenticate on each renew, rebind, DISCOVER or SOLICIT";
         type empty;
       }
       leaf remote-id-mismatch {
         description "Reauthenticate on remote-id mismatch for renew, rebind and re-negotiation";
         type empty;
       }
     }
     container allow-bulk-leasequery {
       description "Allow DHCP bulk leasequery";
       presence "enable allow-bulk-leasequery";
       uses server-bulk-leasequery-type;
     }
   }
   grouping dhcp-local-server-dual-stack-group {
     description "DHCP dual stack groups";
     leaf name {
       description "Dual stack group name";
       type string {
         length "1 .. 64";
       }
     }
     uses apply-advanced;
     container authentication {
       description "DHCP authentication";
       uses dual-stack-authentication-type;
     }
     leaf access-profile {
       description "Access profile to be used for jdhcpd";
       type string {
         length "1 .. 128";
       }
     }
     container dynamic-profile {
       description "Dynamic profile to use";
       uses dynamic-profile-type;
     }
     leaf service-profile {
       description "Dynamic profile to use for default service activation";
       type string {
         length "1 .. 128";
       }
     }
     leaf on-demand-address-allocation {
       description "Allocate addresses on demand";
       type empty;
     }
     container classification-key {
       description "Classification key for identifying dual stack household";
       uses classification-types;
     }
     container protocol-master {
       description "Select family as protocol master";
       uses jdhcp-dual-stack-protocol-mstr-type;
     }
     container liveness-detection {
       description "DHCP client liveness detection processing";
       uses dhcp-liveness-detection-dualstack-type;
     }
     container reauthenticate {
       description "DHCP client reauthenticate processing";
       leaf lease-renewal {
         description "Reauthenticate on each renew, rebind, DISCOVER or SOLICIT";
         type empty;
       }
       leaf remote-id-mismatch {
         description "Reauthenticate on remote-id mismatch for renew, rebind and re-negotiation";
         type empty;
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
   }
   grouping classification-types {
     description "Different mechanisms to identify a single household";
     uses apply-advanced;
     leaf mac-address {
       description "MAC address of client";
       type empty;
     }
     leaf circuit-id {
       description "Circuit-id as key";
       type empty;
     }
     leaf remote-id {
       description "Remote-id as key";
       type empty;
     }
   }
   grouping dhcp-liveness-detection-dualstack-type {
     description "DHCP client liveness detection processing";
     uses apply-advanced;
     container failure-action {
       description "Liveness detection failure action options";
       uses dhcp-liveness-detection-failure-action-type;
     }
     container method {
       description "Liveness detection method options";
       uses apply-advanced;
       choice method-choice {
         case case_1 {
           container layer2-liveness-detection {
             description "Address resolution options";
             uses dhcp-arp-nud-liveness-detection-type;
           }
         }
       }
     }
   }
   grouping dhcp-arp-nud-liveness-detection-type {
     description "Address Resolution detection options";
     uses apply-advanced;
     leaf transmit-interval {
       description "Transmit interval for address resolution";
       default "300";
       units "seconds";
       type union {
         type string {
           pattern "<.*>|$.*";
         }
         type uint32 {
           range "300 .. 1800";
         }
       }
     }
     leaf max-consecutive-retries {
       description "Retry attempts";
       default "3";
       type union {
         type string {
           pattern "<.*>|$.*";
         }
         type uint32 {
           range "3 .. 6";
         }
       }
     }
   }
   grouping dhcp-liveness-detection-failure-action-type {
     description "Liveness detection failure action options";
     uses apply-advanced;
     choice failure-action-type {
       case case_1 {
         leaf clear-binding {
           description "Clear the client binding";
           type empty;
         }
       }
       case case_2 {
         leaf clear-binding-if-interface-up {
           description "Clear the client binding only if the incoming interface is up";
           type empty;
         }
       }
       case case_3 {
         leaf log-only {
           description "Maintain the client binding and log the failure event";
           type empty;
         }
       }
     }
   }
   grouping dhcp-local-server-group {
     description "DHCP groups";
     leaf name {
       description "Group name";
       type string {
         length "1 .. 64";
       }
     }
     uses apply-advanced;
     container authentication {
       description "DHCP authentication";
       uses authentication-type;
     }
     container overrides {
       description "DHCP override processing";
       presence "enable overrides";
       uses override-local-server-type;
     }
     container dynamic-profile {
       description "Dynamic profile to use";
       uses dynamic-profile-type;
     }
     leaf access-profile {
       description "Access profile to use for AAA services";
       type string {
         length "1 .. 128";
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container route-suppression {
       description "Suppress access-internal and/or destination route addition";
       uses dhcp-route-suppression-type;
     }
     list interface {
       key name;
       description "One or more interfaces";
       leaf name {
         description "Interface name";
         type union {
           type jt:interface-name;
           type string {
             pattern "<.*>|$.*";
           }
         }
       }
       uses apply-advanced;
       leaf upto {
         description "Interface up to";
         type union {
           type jt:interface-name;
           type string {
             pattern "<.*>|$.*";
           }
         }
       }
       leaf exclude {
         description "Exclude this interface range";
         type empty;
       }
       container overrides {
         description "DHCP override processing";
         uses override-local-server-type;
       }
       container dynamic-profile {
         description "Dynamic profile to use";
         uses dynamic-profile-type;
       }
       leaf access-profile {
         description "Access profile to use for AAA services";
         type string {
           length "1 .. 128";
         }
       }
       container short-cycle-protection {
         description "Short cycle lockout configuration";
         leaf lockout-min-time {
           description "Short cycle lockout time in seconds";
           type union {
             type string {
               pattern "<.*>|$.*";
             }
             type uint32 {
               range "1 .. 86400";
             }
           }
         }
         leaf lockout-max-time {
           description "Short cycle lockout time in seconds";
           type union {
             type string {
               pattern "<.*>|$.*";
             }
             type uint32 {
               range "1 .. 86400";
             }
           }
         }
       }
     }
     container lease-time-validation {
       presence "enable lease-time-validation";
       description "Configure lease time violation validation";
       uses apply-advanced;
       leaf lease-time-threshold {
         description "Threshold for lease time violation seconds";
         units "seconds";
         type union {
           type string {
             pattern "<.*>|$.*";
           }
           type uint32 {
             range "60 .. 2147483647";
           }
         }
       }
       container violation-action {
         description "Lease time validation violation action";
         choice violation-action-choice {
           case case_1 {
             leaf strict {
               description "Reject discover and renew";
               type empty;
             }
           }
           case case_2 {
             leaf override-lease {
               description "Override assigned lease time with threshold";
               type empty;
             }
           }
         }
       }
     }
     container remote-id-mismatch {
       description "DHCP client remote-id mismatch";
       presence "enable remote-id-mismatch";
       uses dhcp-remote-id-mismatch-type;
     }
     container reauthenticate {
       description "DHCP client reauthenticate processing";
       leaf lease-renewal {
         description "Reauthenticate on each renew, rebind, DISCOVER or SOLICIT";
         type empty;
       }
       leaf remote-id-mismatch {
         description "Reauthenticate on remote-id mismatch for renew, rebind and re-negotiation";
         type empty;
       }
     }
   }
   grouping authentication-type {
     description "DHCP authentication";
     uses apply-advanced;
     leaf password {
       description "Username password to use";
       type string {
         length "1 .. 64";
       }
     }
     container username-include {
       description "Add username options";
       uses apply-advanced;
       leaf delimiter {
         description "Change delimiter/separator character";
         type string {
           length 1;
         }
       }
       leaf domain-name {
         description "Add domain name";
         type string {
           length "1 .. 64";
         }
       }
       leaf user-prefix {
         description "Add user defined prefix";
         type string {
           length "1 .. 64";
         }
       }
       leaf mac-address {
         description "Include MAC address";
         type empty;
       }
       container option-82 {
         presence "enable option-82";
         description "Include option 82";
         leaf circuit-id {
           description "Include option 82 circuit-id (sub option 1)";
           type empty;
         }
         leaf remote-id {
           description "Include option 82 remote-id (sub option 2)";
           type empty;
         }
       }
       leaf logical-system-name {
         description "Include logical system name";
         type empty;
       }
       leaf routing-instance-name {
         description "Include routing instance name";
         type empty;
       }
       leaf option-60 {
         description "Include option 60";
         type empty;
       }
       leaf circuit-type {
         description "Include circuit type";
         type empty;
       }
       leaf interface-name {
         description "Include interface name";
         type empty;
       }
       leaf interface-description {
         description "Include interface description";
         type enumeration {
           enum "device" {
             description "Add the device interface description";
           }
           enum "logical" {
             description "Add the logical interface description";
           }
         }
       }
       leaf vlan-tags {
         description "Include the vlan tag(s)";
         type empty;
       }
     }
   }
   grouping dhcp-remote-id-mismatch-type {
     description "DHCP client remote-id-mismatch processing";
     uses apply-advanced;
     leaf disconnect {
       description "Disconnect session on remote-id mismatch";
       type empty;
     }
   }
   grouping dhcp-route-suppression-type {
     uses apply-advanced;
     choice dhcp-route-suppression-choice {
       case case_1 {
         leaf access-internal {
           description "Suppress access-internal and destination route addition";
           type empty;
         }
       }
       case case_2 {
         leaf destination {
           description "Suppress destination route addition";
           type empty;
         }
       }
     }
   }
   grouping dhcpv6-local-server-type {
     uses apply-advanced;
     container authentication {
       description "DHCPv6 authentication";
       uses dhcpv6-authentication-type;
     }
     container liveness-detection {
       description "DHCPv6 client liveness detection processing";
       uses dhcpv6-liveness-detection-type;
     }
     container reconfigure {
       description "DHCPv6 reconfigure processing";
       presence "enable reconfigure";
       uses dhcpv6-reconfigure-type;
     }
     container dynamic-profile {
       description "Dynamic profile to use";
       uses dynamic-profile-type;
     }
     container forward-snooped-clients {
       description "Forward snooped (unicast) packets";
       choice interface-type {
         case case_1 {
           leaf configured-interfaces {
             description "Forward snooped (unicast) packets on configured interfaces";
             type empty;
           }
         }
         case case_2 {
           leaf non-configured-interfaces {
             description "Forward snooped (unicast) packets on non-configured interfaces";
             type empty;
           }
         }
         case case_3 {
           leaf all-interfaces {
             description "Forward snooped (unicast) packets on configured and non-configured interfaces";
             type empty;
           }
         }
       }
     }
     leaf service-profile {
       description "Dynamic profile to use for default service activation";
       type string {
         length "1 .. 128";
       }
     }
     leaf access-profile {
       description "Access profile to use for AAA services";
       type string {
         length "1 .. 128";
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container overrides {
       description "DHCPv6 override processing";
       presence "enable overrides";
       uses dhcpv6-override-local-server-type;
     }
     container route-suppression {
       description "Suppress access-internal and/or access route addition";
       uses dhcpv6-route-suppression-type;
     }
     list group {
       key name;
       ordered-by user;
       description "Define a DHCPv6 local server group";
       uses dhcpv6-local-server-group;
     }
     container lease-time-validation {
       presence "enable lease-time-validation";
       description "Configure lease time violation validation";
       uses apply-advanced;
       leaf lease-time-threshold {
         description "Threshold for lease time violation seconds";
         units "seconds";
         type union {
           type string {
             pattern "<.*>|$.*";
           }
           type uint32 {
             range "60 .. 2147483647";
           }
         }
       }
       container violation-action {
         description "Lease time validation violation action";
         choice violation-action-choice {
           case case_1 {
             leaf strict {
               description "Reject solicit and renew";
               type empty;
             }
           }
           case case_2 {
             leaf override-lease {
               description "Override assigned lease time with threshold";
               type empty;
             }
           }
         }
       }
     }
     choice requested-ip-check {
       case case_1 {
         leaf requested-ip-network-match {
           description "Subnet to match server's address for active and link-address for passive clients";
           default "16";
           type union {
             type string {
               pattern "<.*>|$.*";
             }
             type uint32 {
               range "0 .. 127";
             }
           }
         }
       }
       case case_2 {
         leaf requested-ip-interface-match {
           description "Use incoming-interface's subnet to check";
           type empty;
         }
       }
     }
     leaf no-snoop {
       description "Do not snoop DHCPV6 packets";
       type empty;
     }
     container server-duid-type {
       description "Define the DUID type to be used as the Server ID. Type supported is DUID-LL";
       uses duid-type;
     }
     container remote-id-mismatch {
       description "DHCP client remote-id mismatch";
       presence "enable remote-id-mismatch";
       uses dhcp-remote-id-mismatch-type;
     }
     container reauthenticate {
       description "DHCP client reauthenticate processing";
       leaf lease-renewal {
         description "Reauthenticate on each renew, rebind, DISCOVER or SOLICIT";
         type empty;
       }
       leaf remote-id-mismatch {
         description "Reauthenticate on remote-id mismatch for renew, rebind and re-negotiation";
         type empty;
       }
     }
     container allow-leasequery {
       description "Allow DHCPv6 leasequery";
       presence "enable allow-leasequery";
       uses server-leasequery-type;
     }
     container allow-bulk-leasequery {
       description "Allow DHCPv6 bulk leasequery";
       presence "enable allow-bulk-leasequery";
       uses server-bulk-leasequery-type;
     }
     container duplicate-clients {
       description "Allow duplicate clients";
       uses dhcpv6-duplicate-clients-type;
     }
     container dynamic-server {
       description "DHCPv6 dynamic server configuration";
       uses dhcpv6-dynamic-server-type;
     }
   }
   grouping dhcpv6-authentication-type {
     description "DHCPv6 authentication";
     uses apply-advanced;
     leaf password {
       description "Username password to use";
       type string {
         length "1 .. 64";
       }
     }
     container username-include {
       description "Add username options";
       uses apply-advanced;
       leaf delimiter {
         description "Change delimiter/separator character";
         type string {
           length 1;
         }
       }
       leaf domain-name {
         description "Add domain name";
         type string {
           length "1 .. 64";
         }
       }
       leaf user-prefix {
         description "Add user defined prefix";
         type string {
           length "1 .. 64";
         }
       }
       leaf mac-address {
         description "Include MAC address";
         type empty;
       }
       leaf client-id {
         description "Include client ID";
         type empty;
       }
       container relay-agent-remote-id {
         presence "enable relay-agent-remote-id";
         description "Include the relay agent remote ID";
         uses apply-advanced;
         choice relay-agent-remote-id-choice {
           case case_1 {
             leaf enterprise-id {
               description "Only use enterprise-id portion of option-37";
               status deprecated;
               type empty;
             }
           }
           case case_2 {
             leaf remote-id {
               description "Only use remote-id portion of option-37";
               status deprecated;
               type empty;
             }
           }
         }
       }
       leaf logical-system-name {
         description "Include logical system name";
         type empty;
       }
       leaf routing-instance-name {
         description "Include routing instance name";
         type empty;
       }
       leaf relay-agent-subscriber-id {
         description "Include the relay agent subscriber ID";
         type empty;
       }
       leaf relay-agent-interface-id {
         description "Include the relay agent interface ID";
         type empty;
       }
       leaf circuit-type {
         description "Include circuit type";
         type empty;
       }
       leaf interface-name {
         description "Include interface name";
         type empty;
       }
       leaf interface-description {
         description "Include interface description";
         type enumeration {
           enum "device" {
             description "Add the device interface description";
           }
           enum "logical" {
             description "Add the logical interface description";
           }
         }
       }
       leaf vlan-tags {
         description "Include the vlan tag(s)";
         type empty;
       }
     }
   }
   grouping dhcpv6-duplicate-clients-type {
     description "Allow duplicate clients";
     choice distinguish-with {
       case case_1 {
         leaf incoming-interface {
           description "Allow duplicate clients on different underlying interfaces";
           type empty;
         }
       }
     }
   }
   grouping dhcpv6-dynamic-server-type {
     uses apply-advanced;
     container overrides {
       description "DHCPv6 override processing";
       presence "enable overrides";
       uses dhcpv6-override-dynamic-server-type;
     }
     list group {
       key name;
       ordered-by user;
       description "Define a DHCPv6 dynamic server group";
       uses dhcpv6-dynamic-server-group;
     }
   }
   grouping dhcpv6-dynamic-server-group {
     description "DHCP dynamic server groups";
     leaf name {
       description "Group name";
       type string {
         length "1 .. 64";
       }
     }
     uses apply-advanced;
     leaf neighbor-discovery-router-advertisement {
       description "Designated NDRA pool for this group";
       type string {
         length "1 .. 64";
       }
     }
     container overrides {
       description "DHCP override processing";
       presence "enable overrides";
       uses dhcpv6-override-dynamic-server-type;
     }
     list interface {
       key name;
       description "One or more interfaces";
       leaf name {
         description "Interface name";
         type union {
           type jt:interface-name;
           type string {
             pattern "<.*>|$.*";
           }
         }
       }
       uses apply-advanced;
       container overrides {
         description "DHCP override processing";
         uses dhcpv6-override-dynamic-server-type;
       }
     }
   }
   grouping dhcpv6-liveness-detection-type {
     description "DHCPv6 client liveness detection processing";
     uses apply-advanced;
     container failure-action {
       description "Liveness detection failure action options";
       uses dhcp-liveness-detection-failure-action-type;
     }
     container method {
       description "Liveness detection method options";
       uses apply-advanced;
       choice method-choice {
         case case_1 {
           container bfd {
             description "Bidirectional Forwarding Detection (BFD) options";
             uses dhcp-bfd-liveness-detection-type;
           }
         }
         case case_2 {
           container layer2-liveness-detection {
             description "Neighbor discovery options";
             uses dhcp-arp-nud-liveness-detection-type;
           }
         }
       }
     }
   }
   grouping dhcp-bfd-liveness-detection-type {
     description "Bidirectional Forwarding Detection (BFD) options";
     uses apply-advanced;
     leaf version {
       description "BFD protocol version number";
       default "automatic";
       type enumeration {
         enum "0" {
           description "BFD version 0 (deprecated)";
         }
         enum "1" {
           description "BFD version 1";
         }
         enum "automatic" {
           description "Choose BFD version automatically";
         }
       }
     }
     leaf minimum-interval {
       description "Minimum transmit and receive interval";
       units "milliseconds";
       type union {
         type string {
           pattern "<.*>|$.*";
         }
         type uint32 {
           range "30000 .. 255000";
         }
       }
     }
     leaf minimum-transmit-interval {
       description "Minimum transmit interval";
       status deprecated;
       units "milliseconds";
       type union {
         type string {
           pattern "<.*>|$.*";
         }
         type uint32 {
           range "30000 .. 255000";
         }
       }
     }
     leaf minimum-receive-interval {
       description "Minimum receive interval";
       units "milliseconds";
       type union {
         type string {
           pattern "<.*>|$.*";
         }
         type uint32 {
           range "30000 .. 255000";
         }
       }
     }
     leaf multiplier {
       description "Detection time multiplier";
       default "3";
       type union {
         type string {
           pattern "<.*>|$.*";
         }
         type uint32 {
           range "1 .. 255";
         }
       }
     }
     choice adaptation-choice {
       case case_1 {
         leaf no-adaptation {
           description "Disable adaptation";
           type empty;
         }
       }
     }
     container transmit-interval {
       description "Transmit-interval options";
       uses apply-advanced;
       leaf minimum-interval {
         description "Minimum transmit interval";
         units "milliseconds";
         type union {
           type string {
             pattern "<.*>|$.*";
           }
           type uint32 {
             range "30000 .. 255000";
           }
         }
       }
       leaf threshold {
         description "High transmit interval triggering a trap";
         units "milliseconds";
         type union {
           type uint32;
           type string {
             pattern "<.*>|$.*";
           }
         }
       }
     }
     container detection-time {
       description "Detection-time options";
       uses apply-advanced;
       leaf threshold {
         description "High detection-time triggering a trap";
         units "milliseconds";
         type union {
           type uint32;
           type string {
             pattern "<.*>|$.*";
           }
         }
       }
     }
     leaf session-mode {
       description "BFD single-hop or multihop session-mode";
       default "automatic";
       type enumeration {
         enum "automatic" {
           description "Choose session-mode automatically";
         }
         enum "single-hop" {
           description "Use single-hop";
         }
         enum "multihop" {
           description "Use multihop";
         }
       }
     }
     leaf holddown-interval {
       description "Time to hold the session-UP notification to the client";
       default "0";
       units "milliseconds";
       type union {
         type string {
           pattern "<.*>|$.*";
         }
         type uint32 {
           range "0 .. 255000";
         }
       }
     }
   }
   grouping dhcpv6-local-server-group {
     description "DHCP groups";
     leaf name {
       description "Group name";
       type string {
         length "1 .. 64";
       }
     }
     uses apply-advanced;
     container authentication {
       description "DHCP authentication";
       uses dhcpv6-authentication-type;
     }
     container liveness-detection {
       description "DHCPv6 client liveness detection processing";
       uses dhcpv6-liveness-detection-type;
     }
     container reconfigure {
       description "DHCPv6 reconfigure processing";
       presence "enable reconfigure";
       uses dhcpv6-reconfigure-type;
     }
     container dynamic-profile {
       description "Dynamic profile to use";
       uses dynamic-profile-type;
     }
     leaf service-profile {
       description "Dynamic profile to use for default service activation";
       type string {
         length "1 .. 128";
       }
     }
     leaf access-profile {
       description "Access profile to use for AAA services";
       type string {
         length "1 .. 128";
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container overrides {
       description "DHCP override processing";
       presence "enable overrides";
       uses dhcpv6-override-local-server-type;
     }
     container route-suppression {
       description "Suppress access-internal and/or access route addition";
       uses dhcpv6-route-suppression-type;
     }
     list interface {
       key name;
       description "One or more interfaces";
       leaf name {
         description "Interface name";
         type union {
           type jt:interface-name;
           type string {
             pattern "<.*>|$.*";
           }
         }
       }
       uses apply-advanced;
       leaf upto {
         description "Interface up to";
         type union {
           type jt:interface-name;
           type string {
             pattern "<.*>|$.*";
           }
         }
       }
       leaf exclude {
         description "Exclude this interface range";
         type empty;
       }
       leaf trace {
         description "Enable tracing for this interface";
         type empty;
       }
       container overrides {
         description "DHCP override processing";
         uses dhcpv6-override-local-server-type;
       }
       container dynamic-profile {
         description "Dynamic profile to use";
         uses dynamic-profile-type;
       }
       leaf service-profile {
         description "Dynamic profile to use for default service activation";
         type string {
           length "1 .. 128";
         }
       }
       leaf access-profile {
         description "Access profile to use for AAA services";
         type string {
           length "1 .. 128";
         }
       }
       container short-cycle-protection {
         description "Short cycle lockout configuration";
         leaf lockout-min-time {
           description "Short cycle lockout time in seconds";
           type union {
             type string {
               pattern "<.*>|$.*";
             }
             type uint32 {
               range "1 .. 86400";
             }
           }
         }
         leaf lockout-max-time {
           description "Short cycle lockout time in seconds";
           type union {
             type string {
               pattern "<.*>|$.*";
             }
             type uint32 {
               range "1 .. 86400";
             }
           }
         }
       }
     }
     container lease-time-validation {
       presence "enable lease-time-validation";
       description "Configure lease time violation validation";
       uses apply-advanced;
       leaf lease-time-threshold {
         description "Threshold for lease time violation seconds";
         units "seconds";
         type union {
           type string {
             pattern "<.*>|$.*";
           }
           type uint32 {
             range "60 .. 2147483647";
           }
         }
       }
       container violation-action {
         description "Lease time validation violation action";
         choice violation-action-choice {
           case case_1 {
             leaf strict {
               description "Reject solicit and renew";
               type empty;
             }
           }
           case case_2 {
             leaf override-lease {
               description "Override assigned lease time with threshold";
               type empty;
             }
           }
         }
       }
     }
     container remote-id-mismatch {
       description "DHCP client remote-id mismatch";
       presence "enable remote-id-mismatch";
       uses dhcp-remote-id-mismatch-type;
     }
     container reauthenticate {
       description "DHCP client reauthenticate processing";
       leaf lease-renewal {
         description "Reauthenticate on each renew, rebind, DISCOVER or SOLICIT";
         type empty;
       }
       leaf remote-id-mismatch {
         description "Reauthenticate on remote-id mismatch for renew, rebind and re-negotiation";
         type empty;
       }
     }
   }
   grouping dhcpv6-override-dynamic-server-type {
     description "DHCP override processing";
     uses apply-advanced;
     leaf interface-client-limit {
       description "Limit the number of clients allowed on an interface";
       type union {
         type string {
           pattern "<.*>|$.*";
         }
         type uint32 {
           range "1 .. 500000";
         }
       }
     }
     leaf rapid-commit {
       description "Enable rapid commit processing";
       type empty;
     }
     container process-inform {
       presence "enable process-inform";
       description "Process INFORMATION request PDUs";
       uses apply-advanced;
       leaf pool {
         description "Pool name for family inet6";
         type string {
           length "1 .. 64";
         }
       }
     }
     leaf delegated-pool {
       description "Delegated pool name for inet6";
       type string {
         length "1 .. 64";
       }
     }
     leaf ia-na-pool {
       description "IA_NA pool name for inet6";
       type string {
         length "1 .. 64";
       }
     }
   }
   grouping dhcpv6-override-local-server-type {
     description "DHCP override processing";
     uses apply-advanced;
     leaf interface-client-limit {
       description "Limit the number of clients allowed on an interface";
       type union {
         type string {
           pattern "<.*>|$.*";
         }
         type uint32 {
           range "1 .. 500000";
         }
       }
     }
     leaf rapid-commit {
       description "Enable rapid commit processing";
       type empty;
     }
     container client-negotiation-match {
       description "Use secondary match criteria for SOLICIT PDU";
       choice match-with {
         case case_1 {
           leaf incoming-interface {
             description "Use incoming interface";
             type empty;
           }
         }
       }
     }
     container process-inform {
       presence "enable process-inform";
       description "Process INFORMATION request PDUs";
       uses apply-advanced;
       leaf pool {
         description "Pool name for family inet6";
         type string {
           length "1 .. 64";
         }
       }
     }
     container delay-advertise {
       description "Filter options for dhcp-server";
       presence "enable delay-advertise";
       uses dhcpv6-filter-option;
     }
     leaf delegated-pool {
       description "Delegated pool name for inet6";
       type string {
         length "1 .. 64";
       }
     }
     leaf multi-address-embedded-option-response {
       description "If the client requests multiple addresses place the options in each address";
       type empty;
     }
     leaf always-process-option-request-option {
       description "Always process option even after address allocation failure";
       type empty;
     }
     leaf delete-binding-on-renegotiation {
       description "Delete binding on renegotiation";
       type empty;
     }
     leaf top-level-status-code {
       description "A top level status code option rather than encapsulated in IA for NoAddrsAvail in Advertise PDUs";
       type empty;
     }
     leaf always-add-option-dns-server {
       description "Add option-23, DNS recursive name server in Advertise and Reply";
       type empty;
     }
     leaf asymmetric-lease-time {
       description "Use a reduced lease time for the client. In seconds";
       units "seconds";
       type union {
         type string {
           pattern "<.*>|$.*";
         }
         type uint32 {
           range "600 .. 86400";
         }
       }
     }
     leaf asymmetric-prefix-lease-time {
       description "Use a reduced prefix lease time for the client. In seconds";
       units "seconds";
       type union {
         type string {
           pattern "<.*>|$.*";
         }
         type uint32 {
           range "600 .. 86400";
         }
       }
     }
     leaf protocol-attributes {
       description "DHCPv6 attributes to use as defined under access protocol-attributes";
       type string {
         length "1 .. 64";
       }
     }
     leaf dual-stack {
       description "Dual stack group to use";
       type string {
         length "1 .. 64";
       }
     }
   }
   grouping dhcpv6-filter-option {
     description "Generic DHCPv6 filter processing";
     uses apply-advanced;
     leaf delay-time {
       description "Time delay between solicit and advertise";
       default "3";
       units "seconds";
       type union {
         type string {
           pattern "<.*>|$.*";
         }
         type uint32 {
           range "1 .. 30";
         }
       }
     }
     container based-on {
       description "Option number";
       uses apply-advanced;
       container option-18 {
         presence "enable option-18";
         description "Option 18";
         uses apply-advanced;
         container equals {
           description "Generic option equals";
           uses server-v6-option-ascii-hex;
         }
         container not-equals {
           description "Generic option not equals";
           uses server-v6-option-ascii-hex;
         }
         container starts-with {
           description "Generic option starts-with";
           uses server-v6-option-ascii-hex;
         }
       }
       container option-37 {
         presence "enable option-37";
         description "Option 37";
         uses apply-advanced;
         container equals {
           description "Generic option equals";
           uses server-v6-option-ascii-hex;
         }
         container not-equals {
           description "Generic option not equals";
           uses server-v6-option-ascii-hex;
         }
         container starts-with {
           description "Generic option starts-with";
           uses server-v6-option-ascii-hex;
         }
       }
       container option-15 {
         presence "enable option-15";
         description "Option 15";
         uses apply-advanced;
         container equals {
           description "Generic option equals";
           uses server-v6-option-ascii-hex;
         }
         container not-equals {
           description "Generic option not equals";
           uses server-v6-option-ascii-hex;
         }
         container starts-with {
           description "Generic option starts-with";
           uses server-v6-option-ascii-hex;
         }
       }
       container option-16 {
         presence "enable option-16";
         description "Option 16";
         uses apply-advanced;
         container equals {
           description "Generic option equals";
           uses server-v6-option-ascii-hex;
         }
         container not-equals {
           description "Generic option not equals";
           uses server-v6-option-ascii-hex;
         }
         container starts-with {
           description "Generic option starts-with";
           uses server-v6-option-ascii-hex;
         }
       }
     }
   }
   grouping dhcpv6-reconfigure-type {
     description "DHCPv6 reconfigure processing";
     uses apply-advanced;
     leaf strict {
       description "Only allow packets containing Reconfigure Accept Option";
       type empty;
     }
     leaf clear-on-abort {
       description "Delete client on reconfiguration abort";
       type empty;
     }
     leaf attempts {
       description "Number of reconfigure attempts before aborting";
       type union {
         type string {
           pattern "<.*>|$.*";
         }
         type uint32 {
           range "1 .. 10";
         }
       }
     }
     leaf timeout {
       description "Initial timeout value for retry";
       type union {
         type string {
           pattern "<.*>|$.*";
         }
         type uint32 {
           range "1 .. 10";
         }
       }
     }
     leaf token {
       description "Reconfigure token";
       type string {
         length "1 .. 244";
       }
     }
     container trigger {
       description "DHCP reconfigure trigger";
       uses reconfigure-trigger-type;
     }
     leaf support-option-pd-exclude {
       description "Request prefix exclude option in reconfigure message";
       type empty;
     }
   }
   grouping dhcpv6-route-suppression-type {
     description "Suppress access-internal and/or access route addition";
     leaf access {
       description "Suppress access route addition";
       type empty;
     }
     leaf access-internal {
       description "Suppress access-internal route addition";
       type empty;
     }
   }
   grouping dual-stack-authentication-type {
     description "DHCP dual stack authentication";
     uses apply-advanced;
     leaf password {
       description "Username password to use";
       type string {
         length "1 .. 64";
       }
     }
     container username-include {
       description "Add username options";
       uses apply-advanced;
       leaf delimiter {
         description "Change delimiter/separator character";
         type string {
           length 1;
         }
       }
       leaf domain-name {
         description "Add domain name";
         type string {
           length "1 .. 64";
         }
       }
       leaf user-prefix {
         description "Add user defined prefix";
         type string {
           length "1 .. 64";
         }
       }
       leaf mac-address {
         description "Include MAC address";
         type empty;
       }
       leaf relay-agent-remote-id {
         description "Include the relay agent remote ID";
         type empty;
       }
       leaf logical-system-name {
         description "Include logical system name";
         type empty;
       }
       leaf routing-instance-name {
         description "Include routing instance name";
         type empty;
       }
       leaf relay-agent-interface-id {
         description "Include the relay agent interface ID";
         type empty;
       }
       leaf interface-name {
         description "Include interface name";
         type empty;
       }
       leaf interface-description {
         description "Include interface description";
         type enumeration {
           enum "device" {
             description "Add the device interface description";
           }
           enum "logical" {
             description "Add the logical interface description";
           }
         }
       }
       leaf circuit-type {
         description "Include circuit type";
         type empty;
       }
       leaf vlan-tags {
         description "Include the vlan tag(s)";
         type empty;
       }
     }
   }
   grouping duid-type {
     uses apply-advanced;
     leaf duid_ll {
       description "Link Layer Address based DUID ";
       type empty;
     }
   }
   grouping dynamic-profile-type {
     description "Dynamic profile to use";
     uses apply-advanced;
     leaf dynamic-profile {
       description "Dynamic profile to use";
       type string {
         length "1 .. 80";
       }
     }
     choice dynamic-profile-type-choice {
       case case_1 {
         leaf use-primary {
           description "Dynamic profile to use on the primary interface";
           type string {
             length "1 .. 80";
           }
         }
       }
       case case_2 {
         container aggregate-clients {
           presence "enable aggregate-clients";
           description "Aggregate client profiles";
           uses apply-advanced;
           choice aggregate-type {
             case case_1 {
               leaf merge {
                 description "Merge the client dynamic profiles";
                 type empty;
               }
             }
             case case_2 {
               leaf replace {
                 description "Replace client dynamic profiles";
                 type empty;
               }
             }
           }
         }
       }
     }
   }
   grouping jdhcp-dual-stack-protocol-mstr-type {
     description "Select family as protocol master";
     choice addr-fam {
       case case_1 {
         leaf inet {
           description "INET family has protocol master behavior";
           type empty;
         }
       }
       case case_2 {
         leaf inet6 {
           description "INET6 family has protocol master behavior";
           type empty;
         }
       }
     }
   }
   grouping jdhcp-duplicate-clients-in-subnet-type {
     description "Allow duplicate clients in a subnet";
     choice distinguish-with {
       case case_1 {
         leaf incoming-interface {
           description "Allow duplicate clients on different interfaces in a subnet";
           type empty;
         }
       }
       case case_2 {
         leaf option-82 {
           description "Allow duplicate clients using different option-82 options in a subnet";
           type empty;
         }
       }
     }
   }
   grouping jdhcp-relay-type {
     description "Dynamic Host Configuration Protocol relay configuration";
     uses apply-advanced;
     leaf duplicate-clients-on-interface {
       description "Allow duplicate clients on different interfaces in a subnet";
       status deprecated;
       type empty;
     }
     container duplicate-clients-in-subnet {
       description "Allow duplicate clients in a subnet";
       uses jdhcp-duplicate-clients-in-subnet-type;
     }
     container dhcpv6 {
       description "DHCPv6 configuration";
       uses dhcpv6-relay-type;
     }
     leaf arp-inspection {
       description "Enable Dynamic ARP Inspection";
       type empty;
     }
     container forward-snooped-clients {
       description "Forward snooped (unicast) packets";
       choice interface-type {
         case case_1 {
           leaf configured-interfaces {
             description "Forward snooped (unicast) packets on configured interfaces";
             type empty;
           }
         }
         case case_2 {
           leaf non-configured-interfaces {
             description "Forward snooped (unicast) packets on non-configured interfaces";
             type empty;
           }
         }
         case case_3 {
           leaf all-interfaces {
             description "Forward snooped (unicast) packets on configured and non-configured interfaces";
             type empty;
           }
         }
       }
     }
     container authentication {
       description "DHCP authentication";
       uses authentication-type;
     }
     container liveness-detection {
       description "DHCP client liveness detection processing";
       uses dhcp-liveness-detection-type;
     }
     container dynamic-profile {
       description "Dynamic profile to use";
       uses dynamic-profile-type;
     }
     leaf service-profile {
       description "Dynamic profile to use for default service activation";
       type string {
         length "1 .. 128";
       }
     }
     leaf access-profile {
       description "Access profile to use for AAA services";
       type string {
         length "1 .. 128";
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container overrides {
       description "DHCP override processing";
       presence "enable overrides";
       uses override-type;
     }
     container relay-option {
       description "DHCP option processing";
       presence "enable relay-option";
       uses dhcp-generic-v4-option;
     }
     container server-match {
       description "Server match processing";
       uses apply-advanced;
       container default-action {
         description "Server match default action";
         presence "enable default-action";
         uses server-match-action-choice;
       }
       list address {
         key name;
         ordered-by user;
         description "Server address";
         leaf name {
           description "Server address for matching";
           type jt:ipv4prefix;
         }
         uses apply-advanced;
         choice server-match-action-choice {
           case case_1 {
             leaf forward-only {
               description "Forward without subscriber services when a match is made";
               type empty;
             }
           }
           case case_2 {
             leaf create-relay-entry {
               description "Create relay entry and allow subscriber services";
               type empty;
             }
           }
         }
       }
     }
     container relay-option-60 {
       description "DHCP option-60 processing";
       presence "enable relay-option-60";
       status deprecated;
       uses relay-option-60-type-top;
     }
     container relay-option-82 {
       description "DHCP option-82 processing";
       presence "enable relay-option-82";
       uses relay-option-82-type;
     }
     container forward-only {
       description "Forward DHCP packets without creating binding";
       presence "enable forward-only";
       uses forward-only-to-rc-type;
     }
     leaf description {
       description "Text description of servers";
       type string;
     }
     leaf maximum-hop-count {
       description "Maximum number of hops per packet";
       type union {
         type string {
           pattern "<.*>|$.*";
         }
         type uint32 {
           range "1 .. 16";
         }
       }
     }
     leaf minimum-wait-time {
       description "Minimum number of seconds before requests are forwarded";
       type union {
         type string {
           pattern "<.*>|$.*";
         }
         type uint32 {
           range "0 .. 30000";
         }
       }
     }
     leaf client-response-ttl {
       description "IP time-to-live value to set in responses to client";
       type union {
         type string {
           pattern "<.*>|$.*";
         }
         type uint32 {
           range "1 .. 255";
         }
       }
     }
     leaf source-ip-change {
       description "Use address of egress interface as source ip";
       type empty;
     }
     leaf forward-only-replies {
       description "Forward-only replies from server to appropriate logical-system:routing-instance based on options";
       type empty;
     }
     container server-group {
       description "Define a DHCP server group";
       uses server-group-type;
     }
     container active-server-group {
       description "Name of DHCP server group";
       uses dhcpv4-gbl-active-sg-type;
     }
     container route-suppression {
       description "Suppress access-internal and/or destination route addition";
       uses dhcp-route-suppression-type;
     }
     list group {
       key name;
       ordered-by user;
       description "Define a DHCP group";
       uses dhcp-group;
     }
     list dual-stack-group {
       key name;
       description "Define a DHCP dual stack group";
       uses dhcp-dual-stack-group;
     }
     leaf no-snoop {
       description "Do not snoop DHCP packets";
       type empty;
     }
     leaf server-response-time {
       description "Number of seconds in a period of activity between the last server response and an unaswered request";
       default "0";
       type union {
         type uint32;
         type string {
           pattern "<.*>|$.*";
         }
       }
     }
     container lease-time-validation {
       presence "enable lease-time-validation";
       description "Configure lease time violation validation";
       uses apply-advanced;
       leaf lease-time-threshold {
         description "Threshold for lease time violation in seconds";
         units "seconds";
         type union {
           type string {
             pattern "<.*>|$.*";
           }
           type uint32 {
             range "60 .. 2147483647";
           }
         }
       }
       container violation-action {
         description "Lease time validation violation action";
         leaf drop {
           description "Drop dhcpv4 offer and ack packets";
           type empty;
         }
       }
     }
     container leasequery {
       description "DHCP leasequery configuration";
       presence "enable leasequery";
       uses relay-leasequery-type;
     }
     container bulk-leasequery {
       description "DHCP bulk leasequery configuration";
       presence "enable bulk-leasequery";
       uses relay-bulk-leasequery-v4-type;
     }
     container remote-id-mismatch {
       description "DHCP client remote-id mismatch";
       presence "enable remote-id-mismatch";
       uses dhcp-remote-id-mismatch-type;
     }
   }
   grouping dhcp-dual-stack-group {
     description "DHCP dual stack groups";
     leaf name {
       description "Dual stack group name";
       type string {
         length "1 .. 64";
       }
     }
     uses apply-advanced;
     container authentication {
       description "DHCP authentication";
       uses dual-stack-authentication-type;
     }
     leaf service-profile {
       description "Dynamic profile to use for default service activation";
       type string {
         length "1 .. 128";
       }
     }
     leaf access-profile {
       description "Access profile to be used for jdhcpd";
       type string {
         length "1 .. 128";
       }
     }
     container dynamic-profile {
       description "Dynamic profile to use";
       uses dynamic-profile-type;
     }
     container liveness-detection {
       description "DHCP client liveness detection processing";
       uses dhcp-liveness-detection-dualstack-type;
     }
     container relay-agent-interface-id {
       description "Interface-id option processing";
       presence "enable relay-agent-interface-id";
       uses v6-relay-option-interface-id-type;
     }
     container relay-agent-remote-id {
       description "Remote-id option processing";
       presence "enable relay-agent-remote-id";
       uses v6-relay-option-remote-id-type;
     }
     container classification-key {
       description "Classification key for identifying dual stack household";
       uses classification-types;
     }
     container protocol-master {
       description "Select family as protocol master";
       uses jdhcp-dual-stack-protocol-mstr-type;
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
   }
   grouping dhcp-generic-v4-option {
     description "Generic DHCP options processing";
     uses apply-advanced;
     leaf option-number {
       description "Option number";
       status deprecated;
       type enumeration {
         enum "60" {
           description "Option 60";
           status deprecated;
         }
         enum "77" {
           description "Option 77";
           status deprecated;
         }
       }
     }
     container equals {
       description "Generic option equals";
       status deprecated;
       uses relay-v4-option-ascii-hex;
     }
     container default-action {
       description "Generic option default action";
       status deprecated;
       uses dhcp-v4-option-default-action;
     }
     container starts-with {
       description "Generic option starts with";
       status deprecated;
       uses relay-v4-option-ascii-hex;
     }
     container option-60 {
       description "Add option 60 processing";
       presence "enable option-60";
       uses dhcp-generic-v4-option-type;
     }
     container option-77 {
       description "Add option 77 processing";
       presence "enable option-77";
       uses dhcp-generic-v4-option-type;
     }
     list option-order {
       key name;
       ordered-by user;
       description "Options precedence order";
       leaf name {
         description "Option number";
         type enumeration {
           enum "60" {
             description "Option 60";
           }
           enum "77" {
             description "Option 77";
           }
         }
       }
       uses apply-advanced;
     }
   }
   grouping dhcp-generic-v4-option-type {
     uses apply-advanced;
     container equals {
       description "Generic option equals";
       uses relay-v4-option-ascii-hex;
     }
     container default-action {
       description "Generic option default action";
       uses dhcp-v4-option-default-action;
     }
     container starts-with {
       description "Generic option starts with";
       uses relay-v4-option-ascii-hex;
     }
   }
   grouping dhcp-group {
     description "DHCP groups";
     leaf name {
       description "Group name";
       type string {
         length "1 .. 64";
       }
     }
     uses apply-advanced;
     container active-server-group {
       description "Name of DHCP server group";
       uses dhcpv4-gp-active-sg-type;
     }
     container authentication {
       description "DHCP authentication";
       uses authentication-type;
     }
     container liveness-detection {
       description "DHCP client liveness detection processing";
       uses dhcp-liveness-detection-type;
     }
     container dynamic-profile {
       description "Dynamic profile to use";
       uses dynamic-profile-type;
     }
     leaf service-profile {
       description "Dynamic profile to use for default service activation";
       type string {
         length "1 .. 128";
       }
     }
     leaf access-profile {
       description "Access profile to use for AAA services";
       type string {
         length "1 .. 128";
       }
     }
     container overrides {
       description "DHCP override processing";
       presence "enable overrides";
       uses override-type;
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container server-match {
       description "Server match processing";
       uses apply-advanced;
       container default-action {
         description "Server match default action";
         presence "enable default-action";
         uses server-match-action-choice;
       }
       list address {
         key name;
         ordered-by user;
         description "Server address";
         leaf name {
           description "Server address for matching";
           type jt:ipv4prefix;
         }
         uses apply-advanced;
         choice server-match-action-choice {
           case case_1 {
             leaf forward-only {
               description "Forward without subscriber services when a match is made";
               type empty;
             }
           }
           case case_2 {
             leaf create-relay-entry {
               description "Create relay entry and allow subscriber services";
               type empty;
             }
           }
         }
       }
     }
     container relay-option {
       description "DHCP option processing";
       presence "enable relay-option";
       uses dhcp-generic-v4-option;
     }
     container relay-option-60 {
       description "DHCP option-60 processing";
       presence "enable relay-option-60";
       status deprecated;
       uses relay-option-60-type-group;
     }
     container relay-option-82 {
       description "DHCP option-82 processing";
       presence "enable relay-option-82";
       uses relay-option-82-type;
     }
     container forward-only {
       description "Forward DHCP packets without creating binding";
       presence "enable forward-only";
       uses forward-only-to-rc-type;
     }
     container route-suppression {
       description "Suppress access-internal and/or destination route addition";
       uses dhcp-route-suppression-type;
     }
     leaf description {
       description "Text description of servers";
       type string;
     }
     leaf maximum-hop-count {
       description "Maximum number of hops per packet";
       type union {
         type string {
           pattern "<.*>|$.*";
         }
         type uint32 {
           range "1 .. 16";
         }
       }
     }
     leaf minimum-wait-time {
       description "Minimum number of seconds before requests are forwarded";
       type union {
         type string {
           pattern "<.*>|$.*";
         }
         type uint32 {
           range "0 .. 30000";
         }
       }
     }
     leaf client-response-ttl {
       description "IP time-to-live value to set in responses to client";
       type union {
         type string {
           pattern "<.*>|$.*";
         }
         type uint32 {
           range "1 .. 255";
         }
       }
     }
     leaf source-ip-change {
       description "Use address of egress interface as source ip";
       type empty;
     }
     list interface {
       key name;
       description "One or more interfaces";
       leaf name {
         description "Interface name";
         type union {
           type jt:interface-name;
           type string {
             pattern "<.*>|$.*";
           }
         }
       }
       uses apply-advanced;
       leaf upto {
         description "Interface up to";
         type union {
           type jt:interface-name;
           type string {
             pattern "<.*>|$.*";
           }
         }
       }
       leaf exclude {
         description "Exclude this interface range";
         type empty;
       }
       container overrides {
         description "DHCP override processing";
         uses override-type;
       }
       container dynamic-profile {
         description "Dynamic profile to use";
         uses dynamic-profile-type;
       }
       leaf service-profile {
         description "Dynamic profile to use for default service activation";
         type string {
           length "1 .. 128";
         }
       }
       leaf access-profile {
         description "Access profile to use for AAA services";
         type string {
           length "1 .. 128";
         }
       }
       container short-cycle-protection {
         description "Short cycle lockout configuration";
         leaf lockout-min-time {
           description "Short cycle lockout time in seconds";
           type union {
             type string {
               pattern "<.*>|$.*";
             }
             type uint32 {
               range "1 .. 86400";
             }
           }
         }
         leaf lockout-max-time {
           description "Short cycle lockout time in seconds";
           type union {
             type string {
               pattern "<.*>|$.*";
             }
             type uint32 {
               range "1 .. 86400";
             }
           }
         }
       }
     }
     container remote-id-mismatch {
       description "DHCP client remote-id mismatch";
       presence "enable remote-id-mismatch";
       uses dhcp-remote-id-mismatch-type;
     }
     container lease-time-validation {
       presence "enable lease-time-validation";
       description "Configure lease time violation validation";
       uses apply-advanced;
       leaf lease-time-threshold {
         description "Threshold for lease time violation in seconds";
         units "seconds";
         type union {
           type string {
             pattern "<.*>|$.*";
           }
           type uint32 {
             range "60 .. 2147483647";
           }
         }
       }
       container violation-action {
         description "Lease time validation violation action";
         leaf drop {
           description "Drop dhcpv4 offer and ack packets";
           type empty;
         }
       }
     }
   }
   grouping dhcp-liveness-detection-type {
     description "DHCP client liveness detection processing";
     uses apply-advanced;
     container failure-action {
       description "Liveness detection failure action options";
       uses dhcp-liveness-detection-failure-action-type;
     }
     container method {
       description "Liveness detection method options";
       uses apply-advanced;
       choice method-choice {
         case case_1 {
           container bfd {
             description "Bidirectional Forwarding Detection (BFD) options";
             uses dhcp-bfd-liveness-detection-type;
           }
         }
         case case_2 {
           container layer2-liveness-detection {
             description "Address resolution options";
             uses dhcp-arp-nud-liveness-detection-type;
           }
         }
       }
     }
   }
   grouping dhcp-v4-option-default-action {
     description "Default action";
     uses apply-advanced;
     choice server-group-choice {
       case case_1 {
         leaf relay-server-group {
           description "Name of DHCP relay server group when match is made";
           type string {
             length "1 .. 64";
           }
         }
       }
       case case_2 {
         leaf local-server-group {
           description "Name of DHCP local server group when match is made";
           type string {
             length "1 .. 64";
           }
         }
       }
       case case_3 {
         leaf drop {
           description "Discard when a match is made";
           type empty;
         }
       }
       case case_4 {
         leaf forward-only {
           description "Forward without subscriber services when a match is made";
           type empty;
         }
       }
     }
   }
   grouping dhcpv4-gbl-active-sg-type {
     leaf active-server-group {
       description "Name of DHCP server group";
       type string {
         length "1 .. 64";
       }
     }
     leaf allow-server-change {
       description "Accept DHCP-ACK from any server in this group";
       type empty;
     }
   }
   grouping dhcpv4-gp-active-sg-type {
     leaf active-server-group {
       description "Name of DHCP server group";
       type string {
         length "1 .. 64";
       }
     }
     leaf allow-server-change {
       description "Accept DHCP-ACK from any server in this group";
       type empty;
     }
   }
   grouping dhcpv6-relay-type {
     description "DHCPv6 relay configuration";
     uses apply-advanced;
     container authentication {
       description "DHCPv6 authentication";
       uses dhcpv6-authentication-type;
     }
     container liveness-detection {
       description "DHCPv6 client liveness detection processing";
       uses dhcpv6-liveness-detection-type;
     }
     container dynamic-profile {
       description "Dynamic profile to use";
       uses dynamic-profile-type;
     }
     leaf service-profile {
       description "Dynamic profile to use for default service activation";
       type string {
         length "1 .. 128";
       }
     }
     leaf access-profile {
       description "Access profile to use for AAA services";
       type string {
         length "1 .. 128";
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container overrides {
       description "DHCPv6 override processing";
       presence "enable overrides";
       uses dhcpv6-override-relay-type;
     }
     container relay-option {
       description "DHCPv6 option processing";
       presence "enable relay-option";
       uses dhcp-generic-v6-option;
     }
     container server-match {
       description "Server match processing";
       uses apply-advanced;
       container default-action {
         description "Server match default action";
         uses server-match-action-choice;
       }
       container duid {
         description "Match duid processing";
         uses apply-advanced;
         container equals {
           description "Duid equals";
           uses server-match-v6-ascii-hex;
         }
         container starts-with {
           description "Duid starts with";
           uses server-match-v6-ascii-hex;
         }
       }
       list address {
         key name;
         ordered-by user;
         description "Server ipv6 address";
         leaf name {
           description "Server ipv6 address for matching";
           type jt:ipv6prefix;
         }
         uses apply-advanced;
         choice server-match-action-choice {
           case case_1 {
             leaf forward-only {
               description "Forward without subscriber services when a match is made";
               type empty;
             }
           }
           case case_2 {
             leaf create-relay-entry {
               description "Create relay entry and allow subscriber services";
               type empty;
             }
           }
         }
       }
     }
     leaf relay-agent-option-79 {
       description "Add the client MAC address to the Relay Forward header.";
       type empty;
     }
     container vendor-specific-information {
       description "DHCPv6 option 17 vendor-specific processing";
       uses jdhcp-vendor-specific-type;
     }
     container forward-only {
       description "Forward DHCPv6 packets without creating binding";
       presence "enable forward-only";
       uses forward-only-to-rc-type;
     }
     leaf forward-only-replies {
       description "Forward-only replies from server to appropriate logical-system:routing-instance based on options";
       type empty;
     }
     container forward-snooped-clients {
       description "Forward snooped (unicast) packets";
       choice interface-type {
         case case_1 {
           leaf configured-interfaces {
             description "Forward snooped (unicast) packets on configured interfaces";
             type empty;
           }
         }
         case case_2 {
           leaf non-configured-interfaces {
             description "Forward snooped (unicast) packets on non-configured interfaces";
             type empty;
           }
         }
         case case_3 {
           leaf all-interfaces {
             description "Forward snooped (unicast) packets on configured and non-configured interfaces";
             type empty;
           }
         }
       }
     }
     container route-suppression {
       description "Suppress access-internal and/or access route addition";
       uses dhcpv6-route-suppression-type;
     }
     list group {
       key name;
       ordered-by user;
       description "Define a DHCPv6 relay group";
       uses dhcpv6-relay-group;
     }
     container relay-agent-interface-id {
       description "DHCPv6 interface-id option processing";
       presence "enable relay-agent-interface-id";
       uses v6-relay-option-interface-id-type;
     }
     container relay-agent-remote-id {
       description "DHCPv6 remote-id option processing";
       presence "enable relay-agent-remote-id";
       uses v6-relay-option-remote-id-type;
     }
     container server-group {
       description "Define a DHCPv6 server group";
       uses v6-server-group-type;
     }
     container active-server-group {
       description "Name of DHCPv6 server group";
       uses dhcpv6-gbl-active-sg-type;
     }
     leaf server-response-time {
       description "Number of seconds in a period of activity between the last server response and an unaswered request";
       default "0";
       type union {
         type uint32;
         type string {
           pattern "<.*>|$.*";
         }
       }
     }
     container lease-time-validation {
       presence "enable lease-time-validation";
       description "Configure lease time violation validation";
       uses apply-advanced;
       leaf lease-time-threshold {
         description "Threshold for lease time violation in seconds";
         units "seconds";
         type union {
           type string {
             pattern "<.*>|$.*";
           }
           type uint32 {
             range "60 .. 2147483647";
           }
         }
       }
       container violation-action {
         description "Lease time validation violation action";
         leaf drop {
           description "Drop dhcpv6 advertise and reply packets";
           type empty;
         }
       }
     }
     leaf no-snoop {
       description "Do not snoop DHCPV6 packets";
       type empty;
     }
     container leasequery {
       description "DHCPv6 leasequery configuration";
       presence "enable leasequery";
       uses relay-leasequery-type;
     }
     container bulk-leasequery {
       description "DHCPv6 bulk leasequery configuration";
       presence "enable bulk-leasequery";
       uses relay-bulk-leasequery-v6-type;
     }
     container remote-id-mismatch {
       description "DHCP client remote-id mismatch";
       presence "enable remote-id-mismatch";
       uses dhcp-remote-id-mismatch-type;
     }
     container duplicate-clients {
       description "Allow duplicate clients";
       uses dhcpv6-duplicate-clients-type;
     }
   }
   grouping dhcp-generic-v6-option {
     description "Generic DHCPv6 options processing";
     uses apply-advanced;
     leaf option-number {
       description "Option number";
       status deprecated;
       type enumeration {
         enum "15" {
           description "Option 15";
           status deprecated;
         }
         enum "16" {
           description "Option 16";
           status deprecated;
         }
       }
     }
     container equals {
       description "Generic option equals";
       status deprecated;
       uses relay-v6-option-ascii-hex;
     }
     container default-action {
       description "Generic option default action";
       status deprecated;
       uses dhcp-v6-option-default-action;
     }
     container starts-with {
       description "Generic option starts with";
       status deprecated;
       uses relay-v6-option-ascii-hex;
     }
     container option-15 {
       description "Add option 15 processing";
       presence "enable option-15";
       uses dhcp-generic-v6-option-type;
     }
     container option-16 {
       description "Add option 16 processing";
       presence "enable option-16";
       uses dhcp-generic-v6-option-type;
     }
     list option-order {
       key name;
       ordered-by user;
       description "Options precedence order";
       leaf name {
         description "Option number";
         type enumeration {
           enum "15" {
             description "Option 15";
           }
           enum "16" {
             description "Option 16";
           }
         }
       }
       uses apply-advanced;
     }
   }
   grouping dhcp-generic-v6-option-type {
     uses apply-advanced;
     container equals {
       description "Generic option equals";
       uses relay-v6-option-ascii-hex;
     }
     container default-action {
       description "Generic option default action";
       uses dhcp-v6-option-default-action;
     }
     container starts-with {
       description "Generic option starts with";
       uses relay-v6-option-ascii-hex;
     }
   }
   grouping dhcp-v6-option-default-action {
     description "Default action";
     uses apply-advanced;
     choice server-group-choice {
       case case_1 {
         leaf relay-server-group {
           description "Name of DHCP relay server group when match is made";
           type string {
             length "1 .. 64";
           }
         }
       }
       case case_2 {
         leaf drop {
           description "Discard when a match is made";
           type empty;
         }
       }
       case case_3 {
         leaf forward-only {
           description "Forward without subscriber services when a match is made";
           type empty;
         }
       }
     }
   }
   grouping dhcpv6-gbl-active-sg-type {
     uses apply-advanced;
     leaf active-server-group {
       description "Name of DHCPv6 server group";
       type string {
         length "1 .. 64";
       }
     }
   }
   grouping dhcpv6-override-relay-type {
     description "DHCPv6 relay override processing";
     uses apply-advanced;
     choice allow-snooped-clients-choice {
       leaf allow-snooped-clients {
         description "Allow client creation from snooped PDUs";
         type empty;
       }
       leaf no-allow-snooped-clients {
         description "Don't allow client creation from snooped PDUs";
         type empty;
       }
     }
     leaf delay-authentication {
       description "Delay subscriber authentication in DHCP protocol processing until request packet";
       type empty;
     }
     leaf interface-client-limit {
       description "Limit the number of clients allowed on an interface";
       type union {
         type string {
           pattern "<.*>|$.*";
         }
         type uint32 {
           range "1 .. 500000";
         }
       }
     }
     leaf dual-stack {
       description "Dual stack group to use.";
       type string {
         length "1 .. 64";
       }
     }
     leaf no-bind-on-request {
       description "Do not bind if stray DHCPv6 RENEW, REBIND is received";
       type empty;
     }
     container client-negotiation-match {
       description "Use secondary match criteria for SOLICIT PDU";
       choice match-with {
         case case_1 {
           leaf incoming-interface {
             description "Use incoming interface";
             type empty;
           }
         }
       }
     }
     leaf send-release-on-delete {
       description "Always send RELEASE to the server when a binding is deleted";
       type empty;
     }
     leaf always-process-option-request-option {
       description "Always process option even after address allocation failure";
       type empty;
     }
     leaf relay-source {
       description "Interface for relay source";
       type union {
         type jt:interface-name;
         type string {
           pattern "<.*>|$.*";
         }
       }
     }
     leaf delete-binding-on-renegotiation {
       description "Delete binding on renegotiation";
       type empty;
     }
     leaf asymmetric-lease-time {
       description "Use a reduced lease time for the client. In seconds";
       units "seconds";
       type union {
         type string {
           pattern "<.*>|$.*";
         }
         type uint32 {
           range "600 .. 86400";
         }
       }
     }
     leaf asymmetric-prefix-lease-time {
       description "Use a reduced prefix lease time for the client. In seconds";
       units "seconds";
       type union {
         type string {
           pattern "<.*>|$.*";
         }
         type uint32 {
           range "600 .. 86400";
         }
       }
     }
   }
   grouping dhcpv6-relay-group {
     description "DHCPv6 groups";
     leaf name {
       description "Group name";
       type string {
         length "1 .. 64";
       }
     }
     uses apply-advanced;
     container active-server-group {
       description "Name of DHCPv6 server group";
       uses dhcpv6-gp-active-sg-type;
     }
     list dual-stack-group {
       key name;
       description "Define a DHCP dual stack group";
       uses dhcp-dual-stack-group;
     }
     container authentication {
       description "DHCPv6 authentication";
       uses dhcpv6-authentication-type;
     }
     container liveness-detection {
       description "DHCPv6 client liveness detection processing";
       uses dhcpv6-liveness-detection-type;
     }
     container dynamic-profile {
       description "Dynamic profile to use";
       uses dynamic-profile-type;
     }
     leaf service-profile {
       description "Dynamic profile to use for default service activation";
       type string {
         length "1 .. 128";
       }
     }
     leaf access-profile {
       description "Access profile to use for AAA services";
       type string {
         length "1 .. 128";
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container overrides {
       description "DHCPv6 override processing";
       presence "enable overrides";
       uses dhcpv6-override-relay-type;
     }
     container relay-option {
       description "DHCPv6 option processing";
       presence "enable relay-option";
       uses dhcp-generic-v6-option;
     }
     container vendor-specific-information {
       description "DHCPv6 option 17 vendor-specific processing";
       uses jdhcp-vendor-specific-type;
     }
     container forward-only {
       description "Forward DHCPv6 packets without creating binding";
       presence "enable forward-only";
       uses forward-only-to-rc-type;
     }
     container relay-agent-interface-id {
       description "DHCPv6 interface-id option processing";
       presence "enable relay-agent-interface-id";
       uses v6-relay-option-interface-id-type;
     }
     container relay-agent-remote-id {
       description "DHCPv6 remote-id option processing";
       presence "enable relay-agent-remote-id";
       uses v6-relay-option-remote-id-type;
     }
     container route-suppression {
       description "Suppress access-internal and/or access route addition";
       uses dhcpv6-route-suppression-type;
     }
     leaf relay-agent-option-79 {
       description "Add the client MAC address to the Relay Forward header.";
       type empty;
     }
     list interface {
       key name;
       description "One or more interfaces";
       leaf name {
         description "Interface name";
         type union {
           type jt:interface-name;
           type string {
             pattern "<.*>|$.*";
           }
         }
       }
       uses apply-advanced;
       leaf upto {
         description "Interface up to";
         type union {
           type jt:interface-name;
           type string {
             pattern "<.*>|$.*";
           }
         }
       }
       leaf exclude {
         description "Exclude this interface range";
         type empty;
       }
       leaf trace {
         description "Enable tracing for this interface";
         type empty;
       }
       container overrides {
         description "DHCPv6 override processing";
         uses dhcpv6-override-relay-type;
       }
       container dynamic-profile {
         description "Dynamic profile to use";
         uses dynamic-profile-type;
       }
       leaf service-profile {
         description "Dynamic profile to use for default service activation";
         type string {
           length "1 .. 128";
         }
       }
       leaf access-profile {
         description "Access profile to use for AAA services";
         type string {
           length "1 .. 128";
         }
       }
       container short-cycle-protection {
         description "Short cycle lockout configuration";
         leaf lockout-min-time {
           description "Short cycle lockout time in seconds";
           type union {
             type string {
               pattern "<.*>|$.*";
             }
             type uint32 {
               range "1 .. 86400";
             }
           }
         }
         leaf lockout-max-time {
           description "Short cycle lockout time in seconds";
           type union {
             type string {
               pattern "<.*>|$.*";
             }
             type uint32 {
               range "1 .. 86400";
             }
           }
         }
       }
     }
     container lease-time-validation {
       presence "enable lease-time-validation";
       description "Configure lease time violation validation";
       uses apply-advanced;
       leaf lease-time-threshold {
         description "Threshold for lease time violation in seconds";
         units "seconds";
         type union {
           type string {
             pattern "<.*>|$.*";
           }
           type uint32 {
             range "60 .. 2147483647";
           }
         }
       }
       container violation-action {
         description "Lease time validation violation action";
         leaf drop {
           description "Drop dhcpv6 advertise and reply packets";
           type empty;
         }
       }
     }
     container remote-id-mismatch {
       description "DHCP client remote-id mismatch";
       presence "enable remote-id-mismatch";
       uses dhcp-remote-id-mismatch-type;
     }
     container server-match {
       description "Server match processing";
       uses apply-advanced;
       container default-action {
         description "Server match default action";
         uses server-match-action-choice;
       }
       container duid {
         description "Match duid processing";
         uses apply-advanced;
         container equals {
           description "Duid equals";
           uses server-match-v6-ascii-hex;
         }
         container starts-with {
           description "Duid starts with";
           uses server-match-v6-ascii-hex;
         }
       }
       list address {
         key name;
         ordered-by user;
         description "Server ipv6 address";
         leaf name {
           description "Server ipv6 address for matching";
           type jt:ipv6prefix;
         }
         uses apply-advanced;
         choice server-match-action-choice {
           case case_1 {
             leaf forward-only {
               description "Forward without subscriber services when a match is made";
               type empty;
             }
           }
           case case_2 {
             leaf create-relay-entry {
               description "Create relay entry and allow subscriber services";
               type empty;
             }
           }
         }
       }
     }
   }
   grouping dhcpv6-gp-active-sg-type {
     uses apply-advanced;
     leaf active-server-group {
       description "Name of DHCPv6 server group";
       type string {
         length "1 .. 64";
       }
     }
   }
   grouping forward-only-to-rc-type {
     description "Forward DHCP packets without creating binding";
     uses apply-advanced;
     leaf logical-system {
       default "current";
       type string;
     }
     leaf routing-instance {
       default "current";
       type string;
     }
   }
   grouping jdhcp-vendor-specific-type {
     description "Add vendor-specific option processing";
     uses apply-advanced;
     leaf host-name {
       description "Add router host name";
       type empty;
     }
     leaf location {
       description "Add location information expressed as interface name format";
       type empty;
     }
   }
   grouping jsf_application_traffic_control_rule_set_type {
     description "Define service application traffic rule-set reference";
     uses apply-advanced;
     leaf rule-set {
       description "Service rule-set name";
       type string {
         length "1 .. 64";
       }
     }
   }
   grouping jsscd-static-subscribers-type {
     uses apply-advanced;
     container access-profile {
       description "Access profile reference";
       uses jsscd-access-profile-type;
     }
     container dynamic-profile {
       description "Dynamic profile reference";
       uses jsscd-dynamic-profile-type;
     }
     container service-profile {
       description "Dynamic profile to use for default service activation";
       uses jsscd-service-profile-type;
     }
     container authentication {
       description "Static Subscriber Client authentication";
       uses jsscd-authentication-type;
     }
     list group {
       key name;
       ordered-by user;
       description "Static Subscriber Client group configuration";
       uses jsscd-group-type;
     }
     leaf auto-login {
       description "Auto login the operator logged-out static subscribers";
       type empty;
     }
     leaf baseline-stats {
       description "Baseline the statistics for static subscribers";
       type empty;
     }
     list interface {
       key name;
       description "One or more interfaces";
       leaf name {
         description "Interface name";
         type union {
           type jt:interface-unit;
           type string {
             pattern "<.*>|$.*";
           }
         }
       }
       uses apply-advanced;
       container subscriber-ip-address {
         description "Assigned IP address to report externally";
         uses apply-advanced;
         leaf address {
           description "IPv4 address";
           type jt:ipv4addr;
         }
       }
       container subscriber-ipv6-address {
         description "Assigned IPv6 address to report externally";
         uses apply-advanced;
         leaf address {
           description "IPv6 Address or Prefix";
           type jt:ipv6prefix;
         }
       }
     }
   }
   grouping jsscd-access-profile-type {
     description "Access profile for static subscribers";
     uses apply-advanced;
     leaf access-profile-name {
       description "Profile name";
       type string;
     }
   }
   grouping jsscd-authentication-type {
     description "Static Subscriber Client authentication";
     uses apply-advanced;
     leaf password {
       description "Username password to use";
       type jt:unreadable;
     }
     container username-include {
       description "Add username options";
       uses apply-advanced;
       leaf delimiter {
         description "Change delimiter/separator character";
         type string {
           length 1;
         }
       }
       leaf domain-name {
         description "Add domain name";
         type string {
           length "1 .. 64";
         }
       }
       leaf user-prefix {
         description "Add user defined prefix";
         type string {
           length "1 .. 64";
         }
       }
       leaf interface {
         description "Include interface name";
         type empty;
       }
       leaf logical-system-name {
         description "Include logical system name";
         type empty;
       }
       leaf routing-instance-name {
         description "Include routing instance name";
         type empty;
       }
       leaf vlan-tags {
         description "Include vlan tag(s)";
         type empty;
       }
     }
   }
   grouping jsscd-dynamic-profile-type {
     description "Dynamic profile to use";
     uses apply-advanced;
     leaf dynamic-profile-name {
       description "Dynamic profile to use";
       type string {
         length "1 .. 80";
       }
     }
     container aggregate-clients {
       presence "enable aggregate-clients";
       description "Aggregate client profiles";
       uses apply-advanced;
       choice aggregate-type {
         case case_1 {
           leaf merge {
             description "Merge the client dynamic profiles";
             type empty;
           }
         }
         case case_2 {
           leaf replace {
             description "Replace client dynamic profiles";
             type empty;
           }
         }
       }
     }
   }
   grouping jsscd-group-type {
     leaf name {
       description "Group name";
       type string {
         length "1 .. 64";
       }
     }
     uses apply-advanced;
     container service-profile {
       description "Dynamic profile to use for default service activation";
       uses jsscd-service-profile-type;
     }
     container access-profile {
       description "Access profile reference";
       uses jsscd-access-profile-type;
     }
     container dynamic-profile {
       description "Dynamic profile reference";
       uses jsscd-dynamic-profile-type;
     }
     container authentication {
       description "Static Subscriber Client authentication";
       uses jsscd-authentication-type;
     }
     list interface {
       key name;
       description "One or more interfaces";
       leaf name {
         description "Interface name";
         type union {
           type jt:interface-unit;
           type string {
             pattern "<.*>|$.*";
           }
         }
       }
       leaf upto {
         description "Interface up to";
         type union {
           type jt:interface-unit;
           type string {
             pattern "<.*>|$.*";
           }
         }
       }
       leaf exclude {
         description "Exclude this interface range";
         type empty;
       }
     }
     leaf auto-login {
       description "Auto login the operator logged-out static subscribers";
       type empty;
     }
   }
   grouping jsscd-service-profile-type {
     description "Service profile for static subscribers";
     uses apply-advanced;
     leaf service-profile-name {
       description "Service profile name";
       type string {
         length "1 .. 80";
       }
     }
   }
   grouping juniper-bridge-domains {
     description "Bridge domains";
     leaf name {
       description "Bridge domain name";
       type string {
       }
     }
     uses apply-advanced;
     leaf description {
       description "Text description of bridge domain";
       type string {
       }
     }
     leaf domain-type {
       description "Type of bridge domain";
       type enumeration {
         enum "bridge" {
           description "Forwarding instance";
         }
       }
     }
     choice vlan_choice {
       case case_1 {
         leaf vlan-id {
           description "IEEE 802.1q VLAN identifier for bridging domain";
           type string;
         }
       }
       case case_2 {
         container vlan-tags {
           presence "enable vlan-tags";
           description "IEEE 802.1q VLAN tags for bridging domain";
           leaf outer {
             description "[tpid.]vlan-id, tpid format is 0xNNNN and is optional";
             type string {
             }
           }
           leaf inner {
             description "[tpid.]vlan-id, tpid format is 0xNNNN and is optional";
             type string {
             }
           }
         }
       }
       case case_3 {
         leaf-list vlan-id-list {
           description "Create bridge-domain for each of the vlan-id specified in the vlan-id-list";
           type jt:vlan-range;
         }
       }
     }
     leaf-list isid-list {
       ordered-by user;
       description "Create bridge-domain for isid (Valid isid:256..16777214)";
       type string;
     }
     leaf vlan-id-scope-local {
       description "Enable the scope of vlan-id local to avoid transmitting vlan tagged packets";
       type empty;
     }
     leaf service-id {
       description "Service id required if bridge-domain is of type MC-AE and vlan-id all or vlan-id none or vlan-tags";
       type union {
         type string {
           pattern "<.*>|$.*";
         }
         type uint32 {
           range "1 .. 65535";
         }
       }
     }
     leaf domain-id {
       description "Domain-id for auto derived Route Target";
       type union {
         type string {
           pattern "<.*>|$.*";
         }
         type uint32 {
           range "1 .. 15";
         }
       }
     }
     leaf no-local-switching {
       description "Disable local switching within CE-facing interfaces";
       type empty;
     }
     leaf mcae-mac-synchronize {
       description "Enable IRB MAC synchronization in this bridge domain";
       type empty;
     }
     leaf mcae-mac-flush {
       description "Enable MCAE MAC flush in a/s mode for a bridge domain on MCAE link up";
       type empty;
     }
     leaf no-irb-layer-2-copy {
       description "Disable transmission of layer-2 copy of packets of irb routing-interface";
       type empty;
     }
     leaf no-arp-suppression {
       description "Disable suppression of ARP/NDP for EVPN";
       type empty;
     }
     leaf enable-mac-move-action {
       description "Enable blocking action due to mac-move in this Bridge Domain";
       type empty;
     }
     list interface {
       key name;
       ordered-by user;
       description "Interface name for this bridge domain";
       leaf name {
         type string;
       }
       uses apply-advanced;
       leaf protect-interface {
         description "Name of protect interface";
         type union {
           type jt:interface-name;
           type string {
             pattern "<.*>|$.*";
           }
         }
       }
     }
     leaf routing-interface {
       description "Routing interface name for this bridge-domain";
       type union {
         type jt:interface-unit;
         type string {
           pattern "<.*>|$.*";
         }
       }
     }
     container forwarding-options {
       description "Forwarding options configuration";
       uses juniper-bridge-forwarding-options;
     }
     container multicast-snooping-options {
       description "Multicast snooping option configuration";
       uses juniper-multicast-snooping-options;
     }
     container bridge-options {
       description "Bridge domain configuration";
       uses juniper-protocols-bd;
     }
     container protocols {
       presence "enable protocols";
       uses apply-advanced;
       container igmp-snooping {
         description "IGMP snooping configuration";
         presence "enable igmp-snooping";
         uses juniper-bd-protocols-igmp-snooping;
       }
       container mld-snooping {
         description "MLD snooping configuration";
         presence "enable mld-snooping";
         uses juniper-bd-protocols-mld-snooping;
       }
     }
     container vxlan {
       uses apply-advanced;
       leaf ovsdb-managed {
         description "Bridge-domain is managed remotely via VXLAN OVSDB Controller";
         type empty;
       }
       leaf vni {
         description "VXLAN identifier";
         type union {
           type string {
             pattern "<.*>|$.*";
           }
           type uint32 {
             range "0 .. 16777214";
           }
         }
       }
       leaf multicast-group {
         description "Multicast group registered for VXLAN segment";
         type jt:ipv4addr;
       }
       leaf encapsulate-inner-vlan {
         description "Retain inner VLAN in the packet";
         type empty;
       }
       leaf decapsulate-accept-inner-vlan {
         description "Accept VXLAN packets with inner VLAN";
         type empty;
       }
       leaf unreachable-vtep-aging-timer {
         description "Unreachable VXLAN tunnel endpoint removal timer";
         units "seconds";
         type union {
           type string {
             pattern "<.*>|$.*";
           }
           type uint16 {
             range "300 .. 1800";
           }
         }
       }
       leaf ingress-node-replication {
         description "Enable ingress node replication";
         type empty;
       }
     }
     leaf isolated-vlan {
       description "Isolated VLAN ID for private vlan bridge domain";
       type union {
         type string {
           pattern "<.*>|$.*";
         }
         type uint32 {
           range "1 .. 4094";
         }
       }
     }
     leaf-list community-vlans {
       description "List of Community VLANs for private vlan bridge domain";
       type jt:vlan-range;
     }
     container proxy-mac {
       description "Proxy MAC settings";
       uses apply-advanced;
       leaf irb {
         description "Reply with virtual-gateway MAC or IRB MAC";
         type empty;
       }
       leaf proxy-mac-address {
         description "Reply with configured MAC for all requests";
         type jt:mac-unicast;
       }
     }
   }
   grouping juniper-bd-protocols-igmp-snooping {
     description "IGMP snooping options";
     uses apply-advanced;
     container traceoptions {
       description "Trace options for IGMP Snooping";
       uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "packets" {
               description "Trace all IGMP packets";
             }
             enum "query" {
               description "Trace IGMP membership query messages";
             }
             enum "report" {
               description "Trace membership report messages";
             }
             enum "leave" {
               description "Trace leave group messages (IGMPv2 only)";
             }
             enum "group" {
               description "Trace group operations";
             }
             enum "client-notification" {
               description "Trace notifications";
             }
             enum "host-notification" {
               description "Trace host notifications";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     leaf query-interval {
       description "When to send host query messages";
       default "125";
       units "seconds";
       type union {
         type string {
           pattern "<.*>|$.*";
         }
         type uint32 {
           range "1 .. 1024";
         }
       }
     }
     container l2-querier {
       description "Enable L2 querier mode";
       uses apply-advanced;
       leaf source-address {
         description "Source IP address to use for L2 querier";
         type jt:ipv4addr;
       }
     }
     leaf query-response-interval {
       description "How long to wait for a host query response";
       default "10";
       units "seconds";
       type string {
       }
     }
     leaf query-last-member-interval {
       description "When to send group query messages";
       default "1";
       units "seconds";
       type string {
       }
     }
     leaf robust-count {
       description "Expected packet loss on a subnet";
       default "2";
       type union {
         type string {
           pattern "<.*>|$.*";
         }
         type uint32 {
           range "2 .. 10";
         }
       }
     }
     leaf learn-pim-router {
       description "Learn PIM router interfaces from PIM hellos";
       type empty;
     }
     leaf immediate-leave {
       description "Enable immediate group leave on interfaces";
       type empty;
     }
     container proxy {
       presence "enable proxy";
       description "Enable proxy mode";
       uses apply-advanced;
       leaf source-address {
         description "Source IP address to use for proxy";
         type jt:ipv4addr;
       }
       leaf irb {
         description "Proxy IGMP reports to IRB";
         type empty;
       }
     }
     list interface {
       key name;
       ordered-by user;
       description "Interface options for IGMP";
       leaf name {
         description "Interface name";
         type union {
           type jt:interface-name;
           type string {
             pattern "<.*>|$.*";
           }
         }
       }
       uses apply-advanced;
       leaf multicast-router-interface {
         description "Enabling multicast-router-interface on the interface";
         type empty;
       }
       leaf immediate-leave {
         description "Enable immediate group leave on interfaces";
         type empty;
       }
       leaf host-only-interface {
         description "Enable interfaces to be treated as host-side interfaces";
         type empty;
       }
       leaf group-limit {
         description "Maximum number of (source,group) per interface";
         type union {
           type string {
             pattern "<.*>|$.*";
           }
           type uint16 {
             range "1 .. 65535";
           }
         }
       }
       container static {
         description "Static group or source membership";
         uses apply-advanced;
         list group {
           key name;
           ordered-by user;
           description "IP multicast group address";
           leaf name {
             description "IP multicast group address";
             type jt:ipv4addr;
           }
           uses apply-advanced;
           list source {
             key name;
             ordered-by user;
             description "IP multicast source address";
             leaf name {
               description "Source address of IP multicast data";
               type jt:ipv4addr;
             }
             uses apply-advanced;
           }
         }
       }
     }
     list pseudowire-remote-address {
       key name;
       ordered-by user;
       description "Pseudowire interface options for IGMP";
       leaf name {
         description "Pseudowire endpoint address";
         type jt:ipv4addr;
       }
       uses apply-advanced;
       leaf multicast-router-interface {
         description "Enabling multicast-router-interface on the interface";
         type empty;
       }
       leaf immediate-leave {
         description "Enable immediate group leave on interfaces";
         type empty;
       }
     }
     list vlan {
       key name;
       ordered-by user;
       description "Vlan options";
       leaf name {
         description "VLAN name";
         type string {
           length "1 .. 64";
         }
       }
       uses apply-advanced;
       leaf query-interval {
         description "When to send host query messages";
         units "seconds";
         type union {
           type string {
             pattern "<.*>|$.*";
           }
           type uint32 {
             range "1 .. 1024";
           }
         }
       }
       leaf query-response-interval {
         description "How long to wait for a host query response";
         units "seconds";
         type string {
         }
       }
       leaf query-last-member-interval {
         description "When to send group query messages";
         units "seconds";
         type string {
         }
       }
       leaf robust-count {
         description "Expected packet loss on a subnet";
         type union {
           type string {
             pattern "<.*>|$.*";
           }
           type uint32 {
             range "2 .. 10";
           }
         }
       }
       leaf immediate-leave {
         description "Enable immediate group leave on interfaces";
         type empty;
       }
       container proxy {
         presence "enable proxy";
         description "Enable proxy mode";
         uses apply-advanced;
         leaf source-address {
           description "Source IP address to use for proxy";
           type jt:ipv4addr;
         }
       }
       list interface {
         key name;
         ordered-by user;
         description "Interface options for IGMP";
         leaf name {
           description "Interface name";
           type union {
             type jt:interface-name;
             type string {
               pattern "<.*>|$.*";
             }
           }
         }
         uses apply-advanced;
         leaf multicast-router-interface {
           description "Enabling multicast-router-interface on the interface";
           type empty;
         }
         leaf immediate-leave {
           description "Enable immediate group leave on interfaces";
           type empty;
         }
         leaf host-only-interface {
           description "Enable interfaces to be treated as host-side interfaces";
           type empty;
         }
         leaf group-limit {
           description "Maximum number of (source,group) per interface";
           type union {
             type string {
               pattern "<.*>|$.*";
             }
             type uint16 {
               range "1 .. 65535";
             }
           }
         }
         container static {
           description "Static group or source membership";
           uses apply-advanced;
           list group {
             key name;
             ordered-by user;
             description "IP multicast group address";
             leaf name {
               description "IP multicast group address";
               type jt:ipv4addr;
             }
             uses apply-advanced;
             list source {
               key name;
               ordered-by user;
               description "IP multicast source address";
               leaf name {
                 description "Source address of IP multicast data";
                 type jt:ipv4addr;
               }
               uses apply-advanced;
             }
           }
         }
       }
       list pseudowire-remote-address {
         key name;
         ordered-by user;
         description "Pseudowire interface options for IGMP";
         leaf name {
           description "Pseudowire endpoint address";
           type jt:ipv4addr;
         }
         uses apply-advanced;
         leaf multicast-router-interface {
           description "Enabling multicast-router-interface on the interface";
           type empty;
         }
         leaf immediate-leave {
           description "Enable immediate group leave on interfaces";
           type empty;
         }
       }
       list qualified-vlan {
         key name;
         ordered-by user;
         description "VLAN options for qualified-learning";
         leaf name {
           description "VLAN ID of the learning-domain";
           type union {
             type string {
               pattern "<.*>|$.*";
             }
             type uint32 {
               range "0 .. 1023";
             }
           }
         }
         uses apply-advanced;
         leaf query-interval {
           description "When to send host query messages";
           units "seconds";
           type union {
             type string {
               pattern "<.*>|$.*";
             }
             type uint32 {
               range "1 .. 1024";
             }
           }
         }
         leaf query-response-interval {
           description "How long to wait for a host query response";
           units "seconds";
           type string {
           }
         }
         leaf query-last-member-interval {
           description "When to send group query messages";
           units "seconds";
           type string {
           }
         }
         leaf robust-count {
           description "Expected packet loss on a subnet";
           type union {
             type string {
               pattern "<.*>|$.*";
             }
             type uint32 {
               range "2 .. 10";
             }
           }
         }
         leaf immediate-leave {
           description "Enable immediate group leave on interfaces";
           type empty;
         }
         container proxy {
           presence "enable proxy";
           description "Enable proxy mode";
           uses apply-advanced;
           leaf source-address {
             description "Source IP address to use for proxy";
             type jt:ipv4addr;
           }
         }
         list interface {
           key name;
           ordered-by user;
           description "Interface options for IGMP";
           leaf name {
             description "Interface name";
             type union {
               type jt:interface-name;
               type string {
                 pattern "<.*>|$.*";
               }
             }
           }
           uses apply-advanced;
           leaf multicast-router-interface {
             description "Enabling multicast-router-interface on the interface";
             type empty;
           }
           leaf immediate-leave {
             description "Enable immediate group leave on interfaces";
             type empty;
           }
           leaf host-only-interface {
             description "Enable interfaces to be treated as host-side interfaces";
             type empty;
           }
           leaf group-limit {
             description "Maximum number of (source,group) per interface";
             type union {
               type string {
                 pattern "<.*>|$.*";
               }
               type uint16 {
                 range "1 .. 65535";
               }
             }
           }
           container static {
             description "Static group or source membership";
             uses apply-advanced;
             list group {
               key name;
               ordered-by user;
               description "IP multicast group address";
               leaf name {
                 description "IP multicast group address";
                 type jt:ipv4addr;
               }
               uses apply-advanced;
               list source {
                 key name;
                 ordered-by user;
                 description "IP multicast source address";
                 leaf name {
                   description "Source address of IP multicast data";
                   type jt:ipv4addr;
                 }
                 uses apply-advanced;
               }
             }
           }
         }
         list pseudowire-remote-address {
           key name;
           ordered-by user;
           description "Pseudowire interface options for IGMP";
           leaf name {
             description "Pseudowire endpoint address";
             type jt:ipv4addr;
           }
           uses apply-advanced;
           leaf multicast-router-interface {
             description "Enabling multicast-router-interface on the interface";
             type empty;
           }
           leaf immediate-leave {
             description "Enable immediate group leave on interfaces";
             type empty;
           }
         }
       }
     }
   }
   grouping juniper-bd-protocols-mld-snooping {
     description "MLD snooping options";
     uses apply-advanced;
     container traceoptions {
       description "Trace options for MLD Snooping";
       uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "packets" {
               description "Trace all MLD packets";
             }
             enum "query" {
               description "Trace MLD membership query messages";
             }
             enum "report" {
               description "Trace membership report messages";
             }
             enum "leave" {
               description "Trace leave group messages (MLDv2 only)";
             }
             enum "group" {
               description "Trace group operations";
             }
             enum "client-notification" {
               description "Trace notifications";
             }
             enum "host-notification" {
               description "Trace host notifications";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     leaf query-interval {
       description "When to send host query messages";
       default "125";
       units "seconds";
       type union {
         type string {
           pattern "<.*>|$.*";
         }
         type uint32 {
           range "1 .. 1024";
         }
       }
     }
     container l2-querier {
       description "Enable L2 querier mode";
       uses apply-advanced;
       leaf source-address {
         description "Source IP address to use for L2 querier";
         type jt:ipv6addr;
       }
     }
     leaf query-response-interval {
       description "How long to wait for a host query response";
       default "10";
       units "seconds";
       type string {
       }
     }
     leaf query-last-member-interval {
       description "When to send group query messages";
       default "1";
       units "seconds";
       type string {
       }
     }
     leaf robust-count {
       description "Expected packet loss on a subnet";
       default "2";
       type union {
         type string {
           pattern "<.*>|$.*";
         }
         type uint32 {
           range "2 .. 10";
         }
       }
     }
     leaf immediate-leave {
       description "Enable immediate group leave on interfaces";
       type empty;
     }
     container proxy {
       presence "enable proxy";
       description "Enable proxy mode";
       uses apply-advanced;
       leaf source-address {
         description "Source IP address to use for proxy";
         type jt:ipv6addr;
       }
       leaf irb {
         description "Proxy IGMP reports to IRB";
         type empty;
       }
     }
     leaf evpn-ssm-reports-only {
       description "Accept and process only <s,g> reports of SSM groups";
       type empty;
     }
     list interface {
       key name;
       ordered-by user;
       description "Interface options for MLD";
       leaf name {
         description "Interface name";
         type union {
           type jt:interface-name;
           type string {
             pattern "<.*>|$.*";
           }
         }
       }
       uses apply-advanced;
       leaf multicast-router-interface {
         description "Enabling multicast-router-interface on the interface";
         type empty;
       }
       leaf immediate-leave {
         description "Enable immediate group leave on interfaces";
         type empty;
       }
       leaf host-only-interface {
         description "Enable interfaces to be treated as host-side interfaces";
         type empty;
       }
       leaf group-limit {
         description "Maximum number of (source,group) per interface";
         type union {
           type string {
             pattern "<.*>|$.*";
           }
           type uint16 {
             range "1 .. 65535";
           }
         }
       }
       container static {
         description "Static group or source membership";
         uses apply-advanced;
         list group {
           key name;
           ordered-by user;
           description "IP multicast group address";
           leaf name {
             description "IP multicast group address";
             type jt:ipv6addr;
           }
           uses apply-advanced;
           list source {
             key name;
             ordered-by user;
             description "IP multicast source address";
             leaf name {
               description "Source address of IP multicast data";
               type jt:ipv6addr;
             }
             uses apply-advanced;
           }
         }
       }
     }
     list pseudowire-remote-address {
       key name;
       ordered-by user;
       description "Pseudowire interface options for MLD";
       leaf name {
         description "Pseudowire endpoint address";
         type jt:ipv4addr;
       }
       uses apply-advanced;
       leaf multicast-router-interface {
         description "Enabling multicast-router-interface on the interface";
         type empty;
       }
       leaf immediate-leave {
         description "Enable immediate group leave on interfaces";
         type empty;
       }
     }
     list vlan {
       key name;
       ordered-by user;
       description "Vlan options";
       leaf name {
         description "Vlan of the bridge-domain";
         type string {
           length "1 .. 64";
         }
       }
       uses apply-advanced;
       leaf query-interval {
         description "When to send host query messages";
         units "seconds";
         type union {
           type string {
             pattern "<.*>|$.*";
           }
           type uint32 {
             range "1 .. 1024";
           }
         }
       }
       leaf query-response-interval {
         description "How long to wait for a host query response";
         units "seconds";
         type string {
         }
       }
       leaf query-last-member-interval {
         description "When to send group query messages";
         units "seconds";
         type string {
         }
       }
       leaf robust-count {
         description "Expected packet loss on a subnet";
         type union {
           type string {
             pattern "<.*>|$.*";
           }
           type uint32 {
             range "2 .. 10";
           }
         }
       }
       leaf immediate-leave {
         description "Enable immediate group leave on interfaces";
         type empty;
       }
       container proxy {
         presence "enable proxy";
         description "Enable proxy mode";
         uses apply-advanced;
         leaf source-address {
           description "Source IP address to use for proxy";
           type jt:ipv6addr;
         }
       }
       leaf evpn-ssm-reports-only {
         description "Accept and process only <s,g> reports of SSM groups";
         type empty;
       }
       list interface {
         key name;
         ordered-by user;
         description "Interface options for MLD";
         leaf name {
           description "Interface name";
           type union {
             type jt:interface-name;
             type string {
               pattern "<.*>|$.*";
             }
           }
         }
         uses apply-advanced;
         leaf multicast-router-interface {
           description "Enabling multicast-router-interface on the interface";
           type empty;
         }
         leaf immediate-leave {
           description "Enable immediate group leave on interfaces";
           type empty;
         }
         leaf host-only-interface {
           description "Enable interfaces to be treated as host-side interfaces";
           type empty;
         }
         leaf group-limit {
           description "Maximum number of (source,group) per interface";
           type union {
             type string {
               pattern "<.*>|$.*";
             }
             type uint16 {
               range "1 .. 65535";
             }
           }
         }
         container static {
           description "Static group or source membership";
           uses apply-advanced;
           list group {
             key name;
             ordered-by user;
             description "IP multicast group address";
             leaf name {
               description "IP multicast group address";
               type jt:ipv6addr;
             }
             uses apply-advanced;
             list source {
               key name;
               ordered-by user;
               description "IP multicast source address";
               leaf name {
                 description "Source address of IP multicast data";
                 type jt:ipv6addr;
               }
               uses apply-advanced;
             }
           }
         }
       }
       list pseudowire-remote-address {
         key name;
         ordered-by user;
         description "Pseudowire interface options for MLD";
         leaf name {
           description "Pseudowire endpoint address";
           type jt:ipv4addr;
         }
         uses apply-advanced;
         leaf multicast-router-interface {
           description "Enabling multicast-router-interface on the interface";
           type empty;
         }
         leaf immediate-leave {
           description "Enable immediate group leave on interfaces";
           type empty;
         }
       }
       list qualified-vlan {
         key name;
         ordered-by user;
         description "VLAN options for qualified-learning";
         leaf name {
           description "VLAN ID of the learning-domain";
           type union {
             type string {
               pattern "<.*>|$.*";
             }
             type uint32 {
               range "0 .. 1023";
             }
           }
         }
         uses apply-advanced;
         leaf query-interval {
           description "When to send host query messages";
           units "seconds";
           type union {
             type string {
               pattern "<.*>|$.*";
             }
             type uint32 {
               range "1 .. 1024";
             }
           }
         }
         leaf query-response-interval {
           description "How long to wait for a host query response";
           units "seconds";
           type string {
           }
         }
         leaf query-last-member-interval {
           description "When to send group query messages";
           units "seconds";
           type string {
           }
         }
         leaf robust-count {
           description "Expected packet loss on a subnet";
           type union {
             type string {
               pattern "<.*>|$.*";
             }
             type uint32 {
               range "2 .. 10";
             }
           }
         }
         leaf immediate-leave {
           description "Enable immediate group leave on interfaces";
           type empty;
         }
         container proxy {
           presence "enable proxy";
           description "Enable proxy mode";
           uses apply-advanced;
           leaf source-address {
             description "Source IP address to use for proxy";
             type jt:ipv6addr;
           }
         }
         leaf evpn-ssm-reports-only {
           description "Accept and process only <s,g> reports of SSM groups";
           type empty;
         }
         list interface {
           key name;
           ordered-by user;
           description "Interface options for MLD";
           leaf name {
             description "Interface name";
             type union {
               type jt:interface-name;
               type string {
                 pattern "<.*>|$.*";
               }
             }
           }
           uses apply-advanced;
           leaf multicast-router-interface {
             description "Enabling multicast-router-interface on the interface";
             type empty;
           }
           leaf immediate-leave {
             description "Enable immediate group leave on interfaces";
             type empty;
           }
           leaf host-only-interface {
             description "Enable interfaces to be treated as host-side interfaces";
             type empty;
           }
           leaf group-limit {
             description "Maximum number of (source,group) per interface";
             type union {
               type string {
                 pattern "<.*>|$.*";
               }
               type uint16 {
                 range "1 .. 65535";
               }
             }
           }
           container static {
             description "Static group or source membership";
             uses apply-advanced;
             list group {
               key name;
               ordered-by user;
               description "IP multicast group address";
               leaf name {
                 description "IP multicast group address";
                 type jt:ipv6addr;
               }
               uses apply-advanced;
               list source {
                 key name;
                 ordered-by user;
                 description "IP multicast source address";
                 leaf name {
                   description "Source address of IP multicast data";
                   type jt:ipv6addr;
                 }
                 uses apply-advanced;
               }
             }
           }
         }
         list pseudowire-remote-address {
           key name;
           ordered-by user;
           description "Pseudowire interface options for MLD";
           leaf name {
             description "Pseudowire endpoint address";
             type jt:ipv4addr;
           }
           uses apply-advanced;
           leaf multicast-router-interface {
             description "Enabling multicast-router-interface on the interface";
             type empty;
           }
           leaf immediate-leave {
             description "Enable immediate group leave on interfaces";
             type empty;
           }
         }
       }
     }
   }
   grouping juniper-bridge-forwarding-options {
     uses apply-advanced;
     container filter {
       description "Filtering for bridge forwarding table";
       uses apply-advanced;
       leaf input {
         description "Name of input filter to apply for forwarded packets";
         type string;
       }
     }
     container flood {
       description "Filtering for bridge flood table";
       uses apply-advanced;
       leaf input {
         description "Name of input filter to apply for bridge flood packets";
         type string;
       }
     }
     container dhcp-relay {
       description "Dynamic Host Configuration Protocol relay configuration";
       status deprecated;
       uses jdhcp-relay-type;
     }
     container dhcp-security {
       description "Dynamic ARP Inspection configuration";
       presence "enable dhcp-security";
       uses jdhcp-security-type;
     }
   }
   grouping jdhcp-security-type {
     description "DHCP access security configuration";
     uses apply-advanced;
     leaf no-dhcp-snooping {
       description "Disable dhcp snooping";
       type empty;
     }
     leaf arp-inspection {
       description "Enable dynamic ARP inspection";
       type empty;
     }
     leaf ip-source-guard {
       description "Enable IP source guard";
       type empty;
     }
     leaf no-dhcpv6-snooping {
       description "Disable DHCPv6 snooping";
       type empty;
     }
     leaf neighbor-discovery-inspection {
       description "Enable neighbor discovery inspection";
       type empty;
     }
     leaf ipv6-source-guard {
       description "Enable IPv6 source guard";
       type empty;
     }
     leaf light-weight-dhcpv6-relay {
       description "Enable light weight dhcpv6 relay";
       type empty;
     }
     list group {
       key name;
       ordered-by user;
       description "Define a DHCP security group for overriding defaults";
       uses ds-group;
     }
     container option-82 {
       description "DHCP option-82 processing for snooped packets";
       presence "enable option-82";
       uses security-option-82-type;
     }
     container dhcpv6-options {
       description "DHCPv6 option processing for snooped packets";
       presence "enable dhcpv6-options";
       uses security-dhcpv6-options-type;
     }
   }
   grouping ds-group {
     description "DHCP security groups";
     leaf name {
       description "Group name";
       type string {
         length "1 .. 64";
       }
     }
     uses apply-advanced;
     container overrides {
       description "DHCP override processing";
       presence "enable overrides";
       uses ds-override-type;
     }
     list interface {
       key name;
       description "One or more interfaces";
       leaf name {
         description "Interface name";
         type union {
           type jt:interface-name;
           type string {
             pattern "<.*>|$.*";
           }
         }
       }
       uses apply-advanced;
       list static-ip {
         key name;
         ordered-by user;
         description "Static IP address configuration";
         uses ip-mac-static;
       }
       list static-ipv6 {
         key name;
         ordered-by user;
         description "Static IPv6 address configuration";
         uses ipv6-mac-static;
       }
     }
   }
   grouping ds-override-type {
     description "Dynamic ARP Inspection override processing";
     uses apply-advanced;
     leaf trusted {
       description "Make this trusted group of interfaces";
       type empty;
     }
     leaf untrusted {
       description "Make this untrusted group of interfaces";
       type empty;
     }
     leaf no-option82 {
       description "Make this group of interfaces not to add option82";
       type empty;
     }
     leaf no-option37 {
       description "Make this group of interfaces not to add option37";
       type empty;
     }
     leaf no-option18 {
       description "Make this group of interfaces not to add option18";
       type empty;
     }
     leaf no-option16 {
       description "Make this group of interfaces not to add option16";
       type empty;
     }
     leaf no-option79 {
       description "Make this group of interfaces not to add option79";
       type empty;
     }
     leaf no-dhcpv6-options {
       description "Make this group of interfaces not to add any DHCPv6 options";
       type empty;
     }
   }
   grouping ip-mac-static {
     leaf name {
       description "IP address";
       type jt:ipaddr;
     }
     leaf mac {
       description "MAC address";
       type jt:mac-addr;
     }
   }
   grouping ipv6-mac-static {
     leaf name {
       description "IP address";
       type jt:ipv6addr;
     }
     leaf mac {
       description "MAC address";
       type jt:mac-addr;
     }
   }
   grouping juniper-def-rtb-switch-options {
     description "Bridge option configuration";
     uses apply-advanced;
     container mac-table-size {
       description "Size of MAC address forwarding table";
       uses apply-advanced;
       leaf limit {
         description "Maximum number of MAC addresses";
         type union {
           type string {
             pattern "<.*>|$.*";
           }
           type uint32;
         }
       }
       leaf packet-action {
         description "Action when MAC limit is reached";
         type enumeration {
           enum "none" {
             description "Forward the packet";
           }
           enum "drop" {
             description "Drop packets and do not learn. Default is forward";
           }
         }
       }
     }
     container mac-ip-table-size {
       description "Size of MAC+IP bindings table";
       uses apply-advanced;
       leaf limit {
         description "Maximum number of MAC+IP bindings";
         type union {
           type string {
             pattern "<.*>|$.*";
           }
           type uint32;
         }
       }
     }
     container interface-mac-limit {
       description "Maximum MAC address learned per interface";
       uses apply-advanced;
       leaf limit {
         description "Maximum number of MAC addresses per interface";
         type union {
           type string {
             pattern "<.*>|$.*";
           }
           type uint32;
         }
       }
       leaf packet-action {
         description "Action when MAC limit is reached";
         type enumeration {
           enum "none" {
             description "Forward the packet";
           }
           enum "drop" {
             description "Drop packets and do not learn. Default is forward";
           }
           enum "log" {
             description "Do not drop the packet but generate an alarm, an SNMP trap or a system log entry";
           }
           enum "shutdown" {
             description "Disable the interface and generate an alarm, an SNMP trap or a system log entry";
           }
           enum "drop-and-log" {
             description "Drop the packet and generate an alarm, an SNMP trap or a system log entry";
           }
         }
       }
     }
     container interface-mac-ip-limit {
       description "Maximum MAC+IP bindings learned per interface";
       uses apply-advanced;
       leaf limit {
         description "Maximum number of MAC+IP bindings per interface";
         type union {
           type string {
             pattern "<.*>|$.*";
           }
           type uint32;
         }
       }
     }
     container mac-notification {
       presence "enable mac-notification";
       description "MAC notification options";
       uses apply-advanced;
       leaf notification-interval {
         description "Interval for sending MAC notifications";
         default "30";
         units "seconds";
         type union {
           type string {
             pattern "<.*>|$.*";
           }
           type uint32 {
             range "1 .. 60";
           }
         }
       }
     }
     leaf mac-table-aging-time {
       description "Delay for discarding MAC address if no updates are received";
       units "seconds";
       type union {
         type string {
           pattern "<.*>|$.*";
         }
         type uint32;
       }
     }
     leaf no-mac-learning {
       description "Disable dynamic MAC address learning";
       type empty;
     }
     leaf no-normalization {
       description "Disable vlan id normalization for interfaces";
       type empty;
     }
     leaf mac-statistics {
       description "Enable MAC address statistics";
       type empty;
     }
     container mib {
       presence "enable mib";
       description "Snmp mib options";
       uses apply-advanced;
       container dot1q-mib {
         presence "enable dot1q-mib";
         description "Dot1q MIB configuration options";
         uses apply-advanced;
         leaf port-list {
           description "Port list for staticegressports and staticuntaggedports MIB";
           type enumeration {
             enum "bit-map" {
               description "Port list is represented in bit-map format";
             }
             enum "string" {
               description "Port list is represented in string format";
             }
           }
         }
       }
     }
     container static-rvtep-mac {
       description "Configure Static MAC and remote VxLAN tunnel endpoint entries";
       uses apply-advanced;
       list mac {
         key "mac_addr remote-vtep";
         description "Unicast MAC address";
         leaf mac_addr {
           type jt:mac-unicast;
         }
         leaf remote-vtep {
           description "Configure static remote VXLAN tunnel endpoints";
           type jt:ipaddr;
         }
       }
     }
     leaf service-id {
       description "Service ID required if multi-chassis AE is part of a bridge-domain";
       type union {
         type string {
           pattern "<.*>|$.*";
         }
         type uint32 {
           range "1 .. 65535";
         }
       }
     }
     leaf ovsdb-managed {
       description "All vxlan bridge domains in routing instance are remote managed";
       type empty;
     }
     container vtep-source-interface {
       description "Source layer-3 IFL for VXLAN";
       leaf interface-name {
         type union {
           type jt:interface-name;
           type string {
             pattern "<.*>|$.*";
           }
         }
       }
       choice family {
         case case_1 {
           container inet {
             presence "enable inet";
             description "IPv4 source";
             uses apply-advanced;
           }
         }
         case case_2 {
           container inet6 {
             presence "enable inet6";
             description "IPv6 source";
             uses apply-advanced;
           }
         }
       }
     }
     container voip {
       description "Voice-over-IP configuration";
       uses apply-advanced;
       list interface {
         key name;
         ordered-by user;
         description "Enable voice over IP on this port";
         leaf name {
           type string;
         }
         uses apply-advanced;
         leaf vlan {
           description "VLAN for voice over IP";
           type string {
           }
         }
         leaf forwarding-class {
           description "Forwarding class";
           type string {
           }
         }
       }
     }
     container unknown-unicast-forwarding {
       description "Set interface for forwarding of unknown unicast packets";
       uses apply-advanced;
       list vlan {
         key name;
         description "VLAN for the unknown unicast packets";
         leaf name {
           description "VLAN name or VLAN Tag (1..4095)";
           type string {
           }
         }
         uses apply-advanced;
         leaf interface {
           description "Interface to send unknown unicast packets for the VLAN";
           type union {
             type jt:interface-name;
             type string {
               pattern "<.*>|$.*";
             }
           }
         }
       }
     }
     container route-distinguisher {
       description "Route distinguisher for this instance";
       leaf rd-type {
         description "Number in (16 bit:32 bit) or (32 bit 'L':16 bit) or (IP address:16 bit) format";
         type string {
         }
       }
     }
     leaf-list vrf-import {
       ordered-by user;
       description "Import policy for VRF instance RIBs";
       type jt:policy-algebra;
     }
     leaf-list vrf-export {
       ordered-by user;
       description "Export policy for VRF instance RIBs";
       type jt:policy-algebra;
     }
     container vrf-target {
       description "VRF target community configuration";
       uses apply-advanced;
       leaf community {
         description "Target community to use in import and export";
         type string {
         }
       }
       leaf import {
         description "Target community to use when filtering on import";
         type string {
         }
       }
       leaf export {
         description "Target community to use when marking routes on export";
         type string {
         }
       }
       container auto {
         description "Auto derive import and export target community from BGP AS & L2";
         presence "enable auto";
         uses juniper-def-rtb-auto-import-as;
       }
     }
     container vtep-remote-interface {
       description "Remote VTEP interface";
       uses apply-advanced;
       list remote-ip {
         key name;
         ordered-by user;
         description "Remote VTEP IP address";
         leaf name {
           description "IP address";
           type jt:ipv4addr;
         }
         uses apply-advanced;
         leaf dynamic-profile {
           description "Define associate dynamic profile";
           type string;
         }
       }
       container default {
         description "To all remote vtep interface";
         uses apply-advanced;
         leaf dynamic-profile {
           description "Define associate dynamic profile";
           type string;
         }
       }
     }
     list interface {
       key name;
       ordered-by user;
       description "Interface for configuring bridge-options";
       leaf name {
         description "Interface name";
         type union {
           type jt:interface-name;
           type string {
             pattern "<.*>|$.*";
           }
         }
       }
       uses apply-advanced;
       container interface-mac-limit {
         description "Maximum number of MAC addresses learned on the interface";
         uses apply-advanced;
         leaf limit {
           description "Maximum number of MAC addresses per interface";
           type union {
             type string {
               pattern "<.*>|$.*";
             }
             type uint32;
           }
         }
         leaf disable {
           description "Disable interface for interface-mac-limit";
           type empty;
         }
         leaf packet-action {
           description "Action when MAC limit is reached";
           type enumeration {
             enum "none" {
               description "Forward the packet";
             }
             enum "drop" {
               description "Drop packets and do not learn. Default is forward";
             }
             enum "log" {
               description "Do not drop the packet but generate an alarm, an SNMP trap or a system log entry";
             }
             enum "shutdown" {
               description "Disable the interface and generate an alarm, an SNMP trap or a system log entry";
             }
             enum "drop-and-log" {
               description "Drop the packet and generate an alarm, an SNMP trap or a system log entry";
             }
           }
         }
       }
       container interface-mac-ip-limit {
         description "Maximum number of MAC+IP bindings learned on the interface";
         uses apply-advanced;
         leaf limit {
           description "Maximum number of MAC+IP bindings per interface";
           type union {
             type string {
               pattern "<.*>|$.*";
             }
             type uint32;
           }
         }
       }
       leaf no-mac-learning {
         description "Disable dynamic MAC address learning";
         type empty;
       }
       leaf mac-pinning {
         description "Enable MAC pinning";
         type empty;
       }
       leaf no-mac-notification {
         description "Disable mac notification on this interface";
         type empty;
       }
     }
     leaf-list remote-vtep-list {
       description "Configure static remote VXLAN tunnel endpoints";
       type jt:ipaddr;
       max-elements 1024;
     }
     leaf interface-shutdown-action {
       description "Interface shutdown mode for Storm-Control/Mac-Limit/Mac-Move-limit scenario";
       type enumeration {
         enum "soft-shutdown" {
           description "Soft-shutdown restricts data-packets while control-packets are still received";
         }
         enum "hard-shutdown" {
           description "Hard-shutdown restricts all packets, port will not be operational";
         }
       }
     }
     leaf-list remote-vtep-v6-list {
       description "Configurate static IPv6 remote VXLAN tunnel endpoints";
       type jt:ipv6addr;
       max-elements 1024;
     }
     container redundant-trunk-group {
       description "Redundant trunk group";
       uses apply-advanced;
       list group {
         key name;
         ordered-by user;
         description "Name of Redundant trunk group";
         leaf name {
           description "RTG name";
           type string {
             length "1 .. 63";
           }
         }
         uses apply-advanced;
         leaf preempt-cutover-timer {
           description "Hold timer for primary interface before preempting secondary interface";
           units "seconds";
           type union {
             type string {
               pattern "<.*>|$.*";
             }
             type uint16 {
               range "1 .. 600";
             }
           }
         }
         leaf description {
           description "Text description of the RTG";
           type string {
             length "1 .. 127";
           }
         }
         list interface {
           key name;
           description "Interfaces that are part of this redundant trunk group";
           leaf name {
             description "Interface name";
             type union {
               type jt:interface-name;
               type string {
                 pattern "<.*>|$.*";
               }
             }
           }
           uses apply-advanced;
           leaf primary {
             description "Set Primary Redundant Trunk Group interface";
             type empty;
           }
         }
       }
     }
   }
   grouping juniper-def-rtb-auto-import-as {
     uses apply-advanced;
     list import-as {
       key name;
       description "AS to auto import for a list of VNI ids";
       leaf name {
         description " Autonomous system number in plain number or 'higher 16bits'.'Lower 16 bits' (asdot notation) format";
         type string {
         }
       }
       uses apply-advanced;
       leaf-list vni-list {
         description "List of VNI identifiers or all";
         type string;
       }
     }
   }
   grouping juniper-enhanced-category-type {
     description "Juniper enhanced category type";
     leaf name {
       description "Name of Juniper enhanced category";
       type string {
         length "1 .. 59";
       }
     }
     uses apply-advanced;
     leaf action {
       description "Action to perform when web traffic matches category";
       type enumeration {
         enum "permit" {
         }
         enum "log-and-permit" {
         }
         enum "block" {
         }
         enum "quarantine" {
         }
       }
     }
     leaf custom-message {
       description "Custom message";
       type string;
     }
   }
   grouping juniper-enhanced-server {
     description "Server handling categorization requests";
     uses apply-advanced;
     leaf host {
       description "Server host IP address or string host name";
       type string;
     }
     leaf port {
       description "Server port";
       type union {
         type string {
           pattern "<.*>|$.*";
         }
         type uint16 {
           range "1 .. 65535";
         }
       }
     }
     leaf proxy-profile {
       description "Proxy profile";
       type string {
         length "1 .. 64";
       }
     }
     leaf routing-instance {
       description "Routing instance name";
       type string;
     }
   }
   grouping juniper-enhanced-site-reputation-setting {
     description "Juniper enhanced site reputation settings";
     uses apply-advanced;
     leaf very-safe {
       description "Action when site reputation is very safe";
       type enumeration {
         enum "permit" {
         }
         enum "log-and-permit" {
         }
         enum "block" {
         }
         enum "quarantine" {
         }
       }
     }
     leaf moderately-safe {
       description "Action when site reputation is moderately safe";
       type enumeration {
         enum "permit" {
         }
         enum "log-and-permit" {
         }
         enum "block" {
         }
         enum "quarantine" {
         }
       }
     }
     leaf fairly-safe {
       description "Action when site reputation is fairly safe";
       type enumeration {
         enum "permit" {
         }
         enum "log-and-permit" {
         }
         enum "block" {
         }
         enum "quarantine" {
         }
       }
     }
     leaf suspicious {
       description "Action when site reputation is suspicious";
       type enumeration {
         enum "permit" {
         }
         enum "log-and-permit" {
         }
         enum "block" {
         }
         enum "quarantine" {
         }
       }
     }
     leaf harmful {
       description "Action when site reputation is harmful";
       type enumeration {
         enum "permit" {
         }
         enum "log-and-permit" {
         }
         enum "block" {
         }
         enum "quarantine" {
         }
       }
     }
   }
   grouping juniper-multicast-snooping-options {
     uses apply-advanced;
     container options {
       description "Miscellaneous options";
       uses apply-advanced;
       container syslog {
         description "Set system logging level";
         uses apply-advanced;
         container level {
           description "Logging level";
           leaf emergency {
             description "Emergency level";
             type empty;
           }
           leaf alert {
             description "Alert level";
             type empty;
           }
           leaf critical {
             description "Critical level";
             type empty;
           }
           leaf error {
             description "Error level";
             type empty;
           }
           leaf warning {
             description "Warning level";
             type empty;
           }
           leaf notice {
             description "Notice level";
             type empty;
           }
           leaf info {
             description "Informational level";
             type empty;
           }
           leaf debug {
             description "Debugging level";
             type empty;
           }
         }
         leaf upto {
           description "Log up to a particular logging level";
           type enumeration {
             enum "emergency" {
               description "Emergency level";
             }
             enum "alert" {
               description "Alert level";
             }
             enum "critical" {
               description "Critical level";
             }
             enum "error" {
               description "Error level";
             }
             enum "warning" {
               description "Warning level";
             }
             enum "notice" {
               description "Notice level";
             }
             enum "info" {
               description "Informational level";
             }
             enum "debug" {
               description "Debugging level";
             }
           }
         }
         leaf mark {
           description "Periodically mark the trace file";
           units "seconds";
           type union {
             type int32;
             type string {
               pattern "<.*>|$.*";
             }
           }
         }
       }
     }
     container traceoptions {
       description "Multicast snooping trace options";
       uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "parse" {
               description "Trace configuration parsing";
             }
             enum "config-internal" {
               description "Trace configuration internals";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf disable {
           description "Disable this trace flag";
           type empty;
         }
       }
     }
     container forwarding-cache {
       description "Multicast forwarding cache";
       uses apply-advanced;
       container threshold {
         description "Threshold";
         uses apply-advanced;
         leaf suppress {
           description "Suppress threshold";
           type union {
             type string {
               pattern "<.*>|$.*";
             }
             type uint32 {
               range "1 .. 200000";
             }
           }
         }
         leaf reuse {
           description "Reuse threshold";
           type union {
             type string {
               pattern "<.*>|$.*";
             }
             type uint32 {
               range "1 .. 200000";
             }
           }
         }
       }
     }
     leaf-list flood-groups {
       ordered-by user;
       description "Groups for which the traffic will be flooded";
       type jt:ipaddr;
     }
     container host-outbound-traffic {
       description "Host generated protocol packets";
       uses apply-advanced;
       leaf forwarding-class {
         description "Forwarding class name";
         type string {
         }
       }
       leaf dot1p {
         description "Dot1p bits";
         type union {
           type string {
             pattern "<.*>|$.*";
           }
           type uint32 {
             range "0 .. 7";
           }
         }
       }
     }
     container graceful-restart {
       description "Configure graceful restart attributes";
       uses apply-advanced;
       choice enable-disable {
         case case_1 {
           leaf disable {
             description "Disable graceful restart";
             type empty;
           }
         }
       }
       leaf restart-duration {
         description "Maximum time for graceful restart to finish";
         default "180";
         units "seconds";
         type union {
           type string {
             pattern "<.*>|$.*";
           }
           type uint32 {
             range "0 .. 300";
           }
         }
       }
     }
     leaf ignore-stp-topology-change {
       description "Don't process stp topology change";
       type empty;
     }
     container multichassis-lag-replicate-state {
       presence "enable multichassis-lag-replicate-state";
       description "Enable multichassis lag replication";
       uses apply-advanced;
       leaf suppress-report {
         description "Enable mclag report suppression";
         type empty;
       }
     }
     leaf nexthop-hold-time {
       description "Nexthop hold time in milliseconds";
       units "milliseconds";
       type union {
         type string {
           pattern "<.*>|$.*";
         }
         type uint32 {
           range "1 .. 1000";
         }
       }
     }
   }
   grouping juniper-policy-options {
     description "Define a redundancy policy";
     uses apply-advanced;
     container satellite-policies {
       description "Satellite Policy configuration";
       uses satellite-policy-options;
     }
     list prefix-list {
       key name;
       ordered-by user;
       description "Define a named set of address prefixes";
       leaf name {
         description "Prefix list name";
         type string;
       }
       uses apply-advanced;
       list prefix-list-item {
         key name;
         uses prefix_list_items;
       }
       leaf apply-path {
         description "Apply IP prefixes from a configuration statement";
         type string;
       }
     }
     list route-filter-list {
       key name;
       ordered-by user;
       description "Define a named set of route-filter address prefixes";
       leaf name {
         description "Route filter list name";
         type string;
       }
       uses apply-advanced;
       list rf_list {
         key "address choice-ident choice-value";
         ordered-by user;
         uses route_filter_list_items;
       }
     }
     list source-address-filter-list {
       key name;
       ordered-by user;
       description "Define a named set of source address filter address prefixes";
       leaf name {
         description "Source address filter list name";
         type string;
       }
       uses apply-advanced;
       list saf_list {
         key "address choice-ident choice-value";
         ordered-by user;
         uses source_address_filter_list_items;
       }
     }
     list mac-list {
       key name;
       ordered-by user;
       description "Define a named set of mac addresses";
       leaf name {
         description "MAc Address list name";
         type string;
       }
       uses apply-advanced;
       list mac-addr-list-item {
         key name;
         uses mac_addr_list_items;
       }
     }
     list vsi-policy {
       key name;
       ordered-by user;
       description "Define a named set of VSI policies";
       leaf name {
         description "VSI policy name";
         type string;
       }
       uses apply-advanced;
       container from {
         description "Conditions to match the VSI policy";
         uses apply-advanced;
         list vsi-manager {
           key "vsi-manager-id vsi-type vsi-version vsi-instance";
           ordered-by user;
           description "VSI manager";
           leaf vsi-manager-id {
             description "VSI manager ID";
             type union {
               type string {
                 pattern "<.*>|$.*";
               }
               type uint32 {
                 range "1 .. 255";
               }
             }
           }
           leaf vsi-type {
             description "VSI type";
             type union {
               type string {
                 pattern "<.*>|$.*";
               }
               type uint32 {
                 range "1 .. 16777216";
               }
             }
           }
           leaf vsi-version {
             description "VSI version";
             type union {
               type string {
                 pattern "<.*>|$.*";
               }
               type uint32 {
                 range "1 .. 255";
               }
             }
           }
           leaf vsi-instance {
             description "VSI instance";
             type string;
           }
           uses apply-advanced;
         }
       }
       container then {
         description "Actions to take if 'from' conditions match";
         uses apply-advanced;
         leaf filter {
           description "Filter name";
           type string;
         }
       }
     }
     leaf skip-then-actions {
       description "Skip 'then' actions and allow route actions in 'from'";
       type empty;
     }
     list policy-statement {
       key name;
       description "Routing policy";
       leaf name {
         description "Name to identify a policy filter";
         type string;
       }
       uses apply-advanced;
       container defaults {
         description "Policy default behaviour";
         uses apply-advanced;
         container route-filter {
           description "Set route filter behaviour";
           choice scope-choice {
             case case_1 {
               leaf no-walkup {
                 description "Route filter walk up disable";
                 type empty;
               }
             }
             case case_2 {
               leaf walkup {
                 description "Route filter walk up enable";
                 type empty;
               }
             }
           }
         }
       }
       list term {
         key name;
         ordered-by user;
         description "Policy term";
         leaf name {
           type string;
         }
         uses apply-advanced;
         container from {
           description "Conditions to match the source of a route";
           uses apply-advanced;
           leaf instance {
             description "Routing protocol instance";
             type string;
           }
           leaf instance-any {
             description "Any routing protocol instance";
             type empty;
           }
           leaf-list instance-list {
             description "A list of routing protocol instances";
             type string;
           }
           leaf family {
             type enumeration {
               enum "inet" {
                 description "IPv4 family";
               }
               enum "inet-vpn" {
                 description "IPv4-VPN family";
               }
               enum "inet6" {
                 description "IPv6 family";
               }
               enum "inet6-vpn" {
                 description "IPv6-VPN family";
               }
               enum "iso-vpn" {
                 description "ISO-VPN family";
               }
               enum "iso" {
                 description "ISO family";
               }
               enum "evpn" {
                 description "EVPN family";
               }
               enum "inet-mvpn" {
                 description "IPv4 Multicast VPN family";
               }
               enum "inet6-mvpn" {
                 description "IPv6 Multicast VPN family";
               }
               enum "inet-mdt" {
                 description "IPv4 MDT Signaling family";
               }
               enum "route-target" {
                 description "Local route target VPN family";
               }
               enum "traffic-engineering" {
                 description "Traffic Engineering family";
               }
             }
           }
           leaf-list protocol {
             ordered-by user;
             description "Protocol from which route was learned";
             type enumeration {
               enum "aggregate" {
                 description "Aggregate routes";
               }
               enum "bgp" {
                 description "BGP";
               }
               enum "direct" {
                 description "Directly connected routes";
               }
               enum "dvmrp" {
                 description "Distance Vector Multicast Routing Protocol";
               }
               enum "isis" {
                 description "Intermediate System-to-Intermediate System";
               }
               enum "esis" {
                 description "End System-to-Intermediate System";
               }
               enum "l-isis" {
                 description "Labelled ISIS";
               }
               enum "l2circuit" {
                 description "Layer 2 circuits";
               }
               enum "l2vpn" {
                 description "Layer 2 MPLS virtual private networks";
               }
               enum "local" {
                 description "Local system addresses";
               }
               enum "ospf" {
                 description "Open Shortest Path First";
               }
               enum "ospf2" {
                 description "Open Shortest Path First Version 2";
               }
               enum "ospf3" {
                 description "Open Shortest Path First Version 3";
               }
               enum "l-ospf" {
                 description "Labelled OSPF";
               }
               enum "pim" {
                 description "Protocol Independent Multicast";
               }
               enum "rip" {
                 description "Routing Information Protocol";
               }
               enum "ripng" {
                 description "Routing Information Protocol next generation";
               }
               enum "static" {
                 description "Statically defined addresses";
               }
               enum "arp" {
                 description "Addresses learned from ARP";
               }
               enum "frr" {
                 description "Addresses created by Host Fast Re-route";
               }
               enum "mpls" {
                 description "Multiprotocol Label Switching";
               }
               enum "ldp" {
                 description "Label Distribution Protocol";
               }
               enum "rsvp" {
                 description "Resource Reservation Protocol";
               }
               enum "msdp" {
                 description "Multicast Source Discovery Protocol";
               }
               enum "route-target" {
                 description "Local route target VPN membership";
               }
               enum "access" {
                 description "Access server routes";
               }
               enum "access-internal" {
                 description "Internal routes to directly connected clients";
               }
               enum "anchor" {
                 description "Anchor routes connected to UEs";
               }
               enum "bgp-static" {
                 description "BGP static routes";
               }
               enum "vpls" {
                 description "Virtual Private LAN Service";
               }
               enum "evpn" {
                 description "Ethernet VPN Service";
               }
               enum "spring-te" {
                 description "SPRING Traffic-Engineered";
               }
               enum "bgp-ls-epe" {
                 description "Addresses created by BGP-LS egress TE";
               }
               enum "rift" {
                 description "RIFT routes";
               }
             }
           }
           leaf rib {
             description "Routing table";
             type string;
           }
           leaf-list neighbor {
             ordered-by user;
             description "Neighboring router";
             type jt:ipaddr;
           }
           leaf-list next-hop {
             ordered-by user;
             description "Next-hop router";
             type jt:ipaddr;
           }
           leaf-list interface {
             ordered-by user;
             description "Interface name or address";
             type union {
               type jt:ipaddr-or-interface;
               type string {
                 pattern "<.*>|$.*";
               }
             }
           }
           leaf area {
             description "OSPF area identifier";
             type jt:areaid;
           }
           leaf-list as-path {
             ordered-by user;
             description "Name of AS path regular expression (BGP only)";
             type string;
           }
           leaf-list as-path-group {
             ordered-by user;
             description "Name of AS path group (BGP only)";
             type string;
           }
           leaf origin {
             description "BGP origin attribute";
             type enumeration {
               enum "igp" {
                 description "Path originated in the local IGP";
               }
               enum "egp" {
                 description "Path originated in another AS";
               }
               enum "incomplete" {
                 description "Path was learned by some other means";
               }
             }
           }
           leaf-list community {
             ordered-by user;
             description "BGP community";
             type string;
           }
           leaf level {
             description "IS-IS level";
             type union {
               type uint32;
               type string {
                 pattern "<.*>|$.*";
               }
             }
           }
           container external {
             presence "enable external";
             description "External route";
             uses apply-advanced;
             leaf type {
               description "OSPF external metric type";
               type union {
                 type string {
                   pattern "<.*>|$.*";
                 }
                 type int32 {
                   range "1 .. 2";
                 }
               }
             }
           }
           leaf validation-database {
             description "Name to identify a validation-state";
             type enumeration {
               enum "valid" {
                 description "Match for valid database validation-state";
               }
               enum "invalid" {
                 description "Match for invalid database validation-state";
               }
               enum "unknown" {
                 description "Match for unknown database validation-state";
               }
             }
           }
           leaf metric {
             description "Metric value";
             type union {
               type uint32;
               type string {
                 pattern "<.*>|$.*";
               }
             }
           }
           leaf metric2 {
             description "Metric value 2";
             type union {
               type uint32;
               type string {
                 pattern "<.*>|$.*";
               }
             }
           }
           leaf metric3 {
             description "Metric value 3";
             type union {
               type uint32;
               type string {
                 pattern "<.*>|$.*";
               }
             }
           }
           leaf metric4 {
             description "Metric value 4";
             type union {
               type uint32;
               type string {
                 pattern "<.*>|$.*";
               }
             }
           }
           leaf-list tag {
             ordered-by user;
             description "Tag string";
             type union {
               type uint32;
               type string {
                 pattern "<.*>|$.*";
               }
             }
           }
           leaf tag2 {
             description "Tag string 2";
             type union {
               type uint32;
               type string {
                 pattern "<.*>|$.*";
               }
             }
           }
           leaf preference {
             description "Preference value";
             type union {
               type uint32;
               type string {
                 pattern "<.*>|$.*";
               }
             }
           }
           leaf preference2 {
             description "Preference value 2";
             type union {
               type uint32;
               type string {
                 pattern "<.*>|$.*";
               }
             }
           }
           leaf color {
             description "Color (preference) value";
             type union {
               type uint32;
               type string {
                 pattern "<.*>|$.*";
               }
             }
           }
           leaf color2 {
             description "Color (preference) value 2";
             type union {
               type uint32;
               type string {
                 pattern "<.*>|$.*";
               }
             }
           }
           leaf local-preference {
             description "Local preference associated with a route";
             type union {
               type uint32;
               type string {
                 pattern "<.*>|$.*";
               }
             }
           }
           leaf-list policy {
             ordered-by user;
             description "Name of policy to evaluate";
             type jt:policy-algebra;
           }
           list route-filter {
             key "address choice-ident choice-value";
             ordered-by user;
             description "List of routes to match";
             uses control_route_filter_type;
           }
           list source-address-filter {
             key "address choice-ident choice-value";
             ordered-by user;
             description "List of source addresses to match";
             uses control_source_address_filter_type;
           }
           list prefix-list {
             key name;
             ordered-by user;
             description "List of prefix-lists of routes to match";
             uses control_prefix_list_type;
           }
           list prefix-list-filter {
             key "list_name choice-ident choice-value";
             ordered-by user;
             description "List of prefix-list-filters to match";
             uses control_prefix_list_filter_type;
           }
           list rtf-prefix-list {
             key name;
             ordered-by user;
             description "List of rtf-prefix-lists of routes to match";
             uses control_rtf_prefix_list_type;
           }
           list route-filter-list {
             key name;
             ordered-by user;
             description "List of route-filter-lists of routes to match";
             uses control_route_filter_list_type;
           }
           list source-address-filter-list {
             key name;
             ordered-by user;
             description "List of source-address-filter-lists of routes to match";
             uses control_source_address_filter_list_type;
           }
           container multicast-scope {
             description "Multicast scope to match";
             choice scope-choice {
               case case_1 {
                 leaf node-local {
                   description "Node-local scope";
                   type empty;
                 }
               }
               case case_2 {
                 leaf link-local {
                   description "Link-local scope";
                   type empty;
                 }
               }
               case case_3 {
                 leaf site-local {
                   description "Site-local scope";
                   type empty;
                 }
               }
               case case_4 {
                 leaf organization-local {
                   description "Organization-local scope";
                   type empty;
                 }
               }
               case case_5 {
                 leaf global {
                   description "Global scope";
                   type empty;
                 }
               }
               case case_6 {
                 leaf scope_value {
                   description "Scope value";
                   type union {
                     type string {
                       pattern "<.*>|$.*";
                     }
                     type uint32 {
                       range "0 .. 15";
                     }
                   }
                 }
               }
             }
             choice scope-operator {
               case case_1 {
                 leaf orhigher {
                   description "Match higher values";
                   type empty;
                 }
               }
               case case_2 {
                 leaf orlower {
                   description "Match lower values";
                   type empty;
                 }
               }
             }
           }
           leaf aggregate-contributor {
             description "Match more specifics of an aggregate";
             type empty;
           }
           leaf state {
             description "Route state";
             type enumeration {
               enum "active" {
                 description "Active route";
               }
               enum "inactive" {
                 description "Inactive route";
               }
             }
           }
           leaf route-type {
             description "Route type";
             type enumeration {
               enum "internal" {
                 description "Internal route";
               }
               enum "external" {
                 description "External route";
               }
             }
           }
           leaf-list nlri-route-type {
             ordered-by user;
             description "Route type from NLRI";
             type union {
               type string {
                 pattern "<.*>|$.*";
               }
               type uint32 {
                 range "1 .. 10";
               }
             }
           }
           leaf next-hop-type {
             description "Next-hop type";
             type enumeration {
               enum "merged" {
                 description "Merged next hop";
               }
             }
           }
           leaf-list condition {
             ordered-by user;
             description "Condition to match on";
             type string;
           }
           list community-count {
             key name;
             ordered-by user;
             description "Number of BGP communities";
             uses community_count_type;
           }
           list as-path-unique-count {
             key name;
             ordered-by user;
             description "Number of unique BGP ASes excluding confederations";
             uses as-path-unique-count-type;
           }
           list as-path-calc-length {
             key name;
             ordered-by user;
             description "Number of BGP ASes excluding confederations";
             uses as-path-calc-length-type;
           }
           container traffic-engineering {
             presence "enable traffic-engineering";
             description "Traffic-Engineering related parameters";
             uses apply-advanced;
             leaf-list protocol {
               ordered-by user;
               description "Protocol that originated the entry";
               type enumeration {
                 enum "direct" {
                   description "Directly originated";
                 }
                 enum "ospf" {
                   description "OSPF originated";
                 }
                 enum "isis-level-1" {
                   description "ISIS level-1 originated";
                 }
                 enum "isis-level-2" {
                   description "ISIS level-2 originated";
                 }
                 enum "static" {
                   description "Statically originated";
                 }
                 enum "unknown" {
                   description "Originated by unknown sources";
                 }
               }
             }
             container node {
               presence "enable node";
               description "Node-related parameters";
               uses apply-advanced;
               leaf as {
                 description "AS number";
                 type string {
                 }
               }
               leaf node-type {
                 description "Real or pseudo-node";
                 type enumeration {
                   enum "router" {
                     description "Real node";
                   }
                   enum "pseudo-node" {
                     description "Pseudo-node";
                   }
                 }
               }
               leaf router-id {
                 description "IP prefix to match the router-id against";
                 type jt:ipprefix;
               }
               leaf sys-id {
                 description "ISO address of the node";
                 type jt:sysid;
               }
             }
             container ipv4-prefix {
               presence "enable ipv4-prefix";
               description "IPV4 prefix-related parameters";
               uses apply-advanced;
               leaf as {
                 description "AS number";
                 type string {
                 }
               }
               leaf router-id {
                 description "IP prefix to match the router-id against";
                 type jt:ipprefix;
               }
               leaf prefix {
                 description "IP prefix to match against";
                 type jt:ipprefix;
               }
               leaf sys-id {
                 description "ISO address of the node";
                 type jt:sysid;
               }
             }
             container link {
               presence "enable link";
               description "Link-related parameters";
               uses apply-advanced;
               container from {
                 description "Specify parameter of the 'from' side";
                 uses apply-advanced;
                 leaf as {
                   description "AS number";
                   type string {
                   }
                 }
                 leaf router-id {
                   description "IP prefix to match the router-id against";
                   type jt:ipprefix;
                 }
                 leaf sys-id {
                   description "System-ID of the node";
                   type jt:sysid;
                 }
                 leaf node-type {
                   description "Type of the node";
                   type enumeration {
                     enum "router" {
                       description "Real node";
                     }
                     enum "pseudo-node" {
                       description "Pseudo-node";
                     }
                   }
                 }
                 leaf link-address {
                   description "IP prefix to match the link address against";
                   type jt:ipprefix;
                 }
               }
               container to {
                 description "Specify parameters of the 'to' side";
                 uses apply-advanced;
                 leaf as {
                   description "AS number";
                   type string {
                   }
                 }
                 leaf router-id {
                   description "IP prefix to match the router-id against";
                   type jt:ipprefix;
                 }
                 leaf sys-id {
                   description "System-ID of the node";
                   type jt:sysid;
                 }
                 leaf node-type {
                   description "Type of the node";
                   type enumeration {
                     enum "router" {
                       description "Real node";
                     }
                     enum "pseudo-node" {
                       description "Pseudo-node";
                     }
                   }
                 }
                 leaf link-address {
                   description "IP prefix to match the link address against";
                   type jt:ipprefix;
                 }
               }
             }
           }
           leaf-list route-distinguisher {
             ordered-by user;
             description "Name of the route-distinguisher";
             type string;
           }
         }
         container to {
           description "Conditions to match the destination of a route";
           uses apply-advanced;
           leaf instance {
             description "Routing protocol instance";
             type string;
           }
           leaf instance-any {
             description "Any routing protocol instance";
             type empty;
           }
           leaf-list instance-list {
             description "A list of routing protocol instances";
             type string;
           }
           leaf family {
             type enumeration {
               enum "inet" {
                 description "IPv4 family";
               }
               enum "inet-vpn" {
                 description "IPv4-VPN family";
               }
               enum "inet6" {
                 description "IPv6 family";
               }
               enum "inet6-vpn" {
                 description "IPv6-VPN family";
               }
               enum "iso-vpn" {
                 description "ISO-VPN family";
               }
               enum "iso" {
                 description "ISO family";
               }
               enum "evpn" {
                 description "EVPN family";
               }
               enum "inet-mvpn" {
                 description "IPv4 Multicast VPN family";
               }
               enum "inet6-mvpn" {
                 description "IPv6 Multicast VPN family";
               }
               enum "inet-mdt" {
                 description "IPv4 MDT Signaling family";
               }
               enum "route-target" {
                 description "Local route target VPN family";
               }
               enum "traffic-engineering" {
                 description "Traffic Engineering family";
               }
             }
           }
           leaf-list protocol {
             ordered-by user;
             description "Protocol from which route was learned";
             type enumeration {
               enum "aggregate" {
                 description "Aggregate routes";
               }
               enum "bgp" {
                 description "BGP";
               }
               enum "direct" {
                 description "Directly connected routes";
               }
               enum "dvmrp" {
                 description "Distance Vector Multicast Routing Protocol";
               }
               enum "isis" {
                 description "Intermediate System-to-Intermediate System";
               }
               enum "esis" {
                 description "End System-to-Intermediate System";
               }
               enum "l-isis" {
                 description "Labelled ISIS";
               }
               enum "l2circuit" {
                 description "Layer 2 circuits";
               }
               enum "l2vpn" {
                 description "Layer 2 MPLS virtual private networks";
               }
               enum "local" {
                 description "Local system addresses";
               }
               enum "ospf" {
                 description "Open Shortest Path First";
               }
               enum "ospf2" {
                 description "Open Shortest Path First Version 2";
               }
               enum "ospf3" {
                 description "Open Shortest Path First Version 3";
               }
               enum "l-ospf" {
                 description "Labelled OSPF";
               }
               enum "pim" {
                 description "Protocol Independent Multicast";
               }
               enum "rip" {
                 description "Routing Information Protocol";
               }
               enum "ripng" {
                 description "Routing Information Protocol next generation";
               }
               enum "static" {
                 description "Statically defined addresses";
               }
               enum "arp" {
                 description "Addresses learned from ARP";
               }
               enum "frr" {
                 description "Addresses created by Host Fast Re-route";
               }
               enum "mpls" {
                 description "Multiprotocol Label Switching";
               }
               enum "ldp" {
                 description "Label Distribution Protocol";
               }
               enum "rsvp" {
                 description "Resource Reservation Protocol";
               }
               enum "msdp" {
                 description "Multicast Source Discovery Protocol";
               }
               enum "route-target" {
                 description "Local route target VPN membership";
               }
               enum "access" {
                 description "Access server routes";
               }
               enum "access-internal" {
                 description "Internal routes to directly connected clients";
               }
               enum "anchor" {
                 description "Anchor routes connected to UEs";
               }
               enum "bgp-static" {
                 description "BGP static routes";
               }
               enum "vpls" {
                 description "Virtual Private LAN Service";
               }
               enum "evpn" {
                 description "Ethernet VPN Service";
               }
               enum "spring-te" {
                 description "SPRING Traffic-Engineered";
               }
               enum "bgp-ls-epe" {
                 description "Addresses created by BGP-LS egress TE";
               }
               enum "rift" {
                 description "RIFT routes";
               }
             }
           }
           leaf rib {
             description "Routing table";
             type string;
           }
           leaf-list neighbor {
             ordered-by user;
             description "Neighboring router";
             type jt:ipaddr;
           }
           leaf-list next-hop {
             ordered-by user;
             description "Next-hop router";
             type jt:ipaddr;
           }
           leaf-list interface {
             ordered-by user;
             description "Interface name or address";
             type union {
               type jt:ipaddr-or-interface;
               type string {
                 pattern "<.*>|$.*";
               }
             }
           }
           leaf area {
             description "OSPF area identifier";
             type jt:areaid;
           }
           leaf-list as-path {
             ordered-by user;
             description "Name of AS path regular expression (BGP only)";
             type string;
           }
           leaf-list as-path-group {
             ordered-by user;
             description "Name of AS path group (BGP only)";
             type string;
           }
           leaf origin {
             description "BGP origin attribute";
             type enumeration {
               enum "igp" {
                 description "Path originated in the local IGP";
               }
               enum "egp" {
                 description "Path originated in another AS";
               }
               enum "incomplete" {
                 description "Path was learned by some other means";
               }
             }
           }
           leaf-list community {
             ordered-by user;
             description "BGP community";
             type string;
           }
           leaf level {
             description "IS-IS level";
             type union {
               type uint32;
               type string {
                 pattern "<.*>|$.*";
               }
             }
           }
           container external {
             presence "enable external";
             description "External route";
             uses apply-advanced;
             leaf type {
               description "OSPF external metric type";
               type union {
                 type string {
                   pattern "<.*>|$.*";
                 }
                 type int32 {
                   range "1 .. 2";
                 }
               }
             }
           }
           leaf validation-database {
             description "Name to identify a validation-state";
             type enumeration {
               enum "valid" {
                 description "Match for valid database validation-state";
               }
               enum "invalid" {
                 description "Match for invalid database validation-state";
               }
               enum "unknown" {
                 description "Match for unknown database validation-state";
               }
             }
           }
           leaf metric {
             description "Metric value";
             type union {
               type uint32;
               type string {
                 pattern "<.*>|$.*";
               }
             }
           }
           leaf metric2 {
             description "Metric value 2";
             type union {
               type uint32;
               type string {
                 pattern "<.*>|$.*";
               }
             }
           }
           leaf metric3 {
             description "Metric value 3";
             type union {
               type uint32;
               type string {
                 pattern "<.*>|$.*";
               }
             }
           }
           leaf metric4 {
             description "Metric value 4";
             type union {
               type uint32;
               type string {
                 pattern "<.*>|$.*";
               }
             }
           }
           leaf-list tag {
             ordered-by user;
             description "Tag string";
             type union {
               type uint32;
               type string {
                 pattern "<.*>|$.*";
               }
             }
           }
           leaf tag2 {
             description "Tag string 2";
             type union {
               type uint32;
               type string {
                 pattern "<.*>|$.*";
               }
             }
           }
           leaf preference {
             description "Preference value";
             type union {
               type uint32;
               type string {
                 pattern "<.*>|$.*";
               }
             }
           }
           leaf preference2 {
             description "Preference value 2";
             type union {
               type uint32;
               type string {
                 pattern "<.*>|$.*";
               }
             }
           }
           leaf color {
             description "Color (preference) value";
             type union {
               type uint32;
               type string {
                 pattern "<.*>|$.*";
               }
             }
           }
           leaf color2 {
             description "Color (preference) value 2";
             type union {
               type uint32;
               type string {
                 pattern "<.*>|$.*";
               }
             }
           }
           leaf local-preference {
             description "Local preference associated with a route";
             type union {
               type uint32;
               type string {
                 pattern "<.*>|$.*";
               }
             }
           }
           leaf-list policy {
             ordered-by user;
             description "Name of policy to evaluate";
             type jt:policy-algebra;
           }
         }
         container then {
           description "Actions to take if 'from' and 'to' conditions match";
           uses apply-advanced;
           container metric {
             description "Metric value";
             uses apply-advanced;
             choice metric_action {
               case case_1 {
                 leaf metric {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
               case case_4 {
                 container igp {
                   presence "enable igp";
                   description "Track the IGP metric (BGP only)";
                   leaf metric_offset {
                     description "Metric offset for MED";
                     type union {
                       type int32;
                       type string {
                         pattern "<.*>|$.*";
                       }
                     }
                   }
                 }
               }
               case case_5 {
                 container minimum-igp {
                   presence "enable minimum-igp";
                   description "Track the minimum IGP metric (BGP only)";
                   leaf metric_offset {
                     description "Metric offset for MED";
                     type union {
                       type int32;
                       type string {
                         pattern "<.*>|$.*";
                       }
                     }
                   }
                 }
               }
               case case_6 {
                 container expression {
                   description "Calculate value based on route metric and metric2";
                   uses metric_expression_type;
                 }
               }
               case case_7 {
                 leaf aigp {
                   description "Use aigp, if it exists, to set the IGP metric";
                   type empty;
                 }
               }
             }
           }
           container metric2 {
             description "Metric value 2";
             uses apply-advanced;
             choice metric_action {
               case case_1 {
                 leaf metric2 {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
             }
           }
           container metric3 {
             description "Metric value 3";
             uses apply-advanced;
             choice metric_action {
               case case_1 {
                 leaf metric3 {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
             }
           }
           container metric4 {
             description "Metric value 4";
             uses apply-advanced;
             choice metric_action {
               case case_1 {
                 leaf metric4 {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
             }
           }
           container tag {
             description "Tag string";
             uses apply-advanced;
             choice metric_action {
               case case_1 {
                 leaf tag {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
             }
           }
           container tag2 {
             description "Tag string 2";
             uses apply-advanced;
             choice metric_action {
               case case_1 {
                 leaf tag2 {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
             }
           }
           container preference {
             description "Preference value";
             uses apply-advanced;
             choice metric_action {
               case case_1 {
                 leaf preference {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
             }
           }
           container preference2 {
             description "Preference value 2";
             uses apply-advanced;
             choice metric_action {
               case case_1 {
                 leaf preference2 {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
             }
           }
           container color {
             description "Color (preference) value";
             uses apply-advanced;
             choice metric_action {
               case case_1 {
                 leaf color {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
             }
           }
           container color2 {
             description "Color (preference) value 2";
             uses apply-advanced;
             choice metric_action {
               case case_1 {
                 leaf color2 {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
             }
           }
           container local-preference {
             description "Local preference associated with a route";
             uses apply-advanced;
             choice metric_action {
               case case_1 {
                 leaf local-preference {
                   type union {
                     type uint32;
                     type string {
                       pattern "<.*>|$.*";
                     }
                   }
                 }
               }
               case case_2 {
                 leaf add {
                   description "Add constant to attribute";
                   type union {
                     type uint32;
                     type string {
                       pattern "<.*>|$.*";
                     }
                   }
                 }
               }
               case case_3 {
                 leaf subtract {
                   description "Subtract constant from attribute";
                   type union {
                     type uint32;
                     type string {
                       pattern "<.*>|$.*";
                     }
                   }
                 }
               }
             }
           }
           leaf priority {
             description "Set priority for route installation";
             type enumeration {
               enum "high" {
                 description "Set priority to high";
               }
               enum "medium" {
                 description "Set priority to medium";
               }
               enum "low" {
                 description "Set priority to low";
               }
             }
           }
           container prefix-segment {
             description "Set prefix segment attributes";
             leaf index {
               description "Set prefix segment index ";
               type union {
                 type string {
                   pattern "<.*>|$.*";
                 }
                 type uint32 {
                   range "0 .. 199999";
                 }
               }
             }
             leaf node-segment {
               description "Set node segment flag for this prefix segment";
               type empty;
             }
           }
           leaf label-allocation {
             description "Set label allocation mode";
             type enumeration {
               enum "per-table" {
                 description "Set per-table label allocation mode";
               }
               enum "per-nexthop" {
                 description "Set per-nexthop label allocation mode";
               }
               enum "per-table-localize" {
                 description "Set per-table-localize label allocation mode";
               }
             }
           }
           container add-path {
             description "Set BGP add-path attributes";
             leaf send-count {
               description "Number of add-paths sent";
               type union {
                 type string {
                   pattern "<.*>|$.*";
                 }
                 type uint32 {
                   range "2 .. 64";
                 }
               }
             }
           }
           leaf validation-state {
             description "Set validation-state of a route";
             type enumeration {
               enum "valid" {
                 description "Set validaton-state to valid";
               }
               enum "invalid" {
                 description "Set validation-state to invalid";
               }
               enum "unknown" {
                 description "Set validation-state to unknown";
               }
             }
           }
           leaf origin {
             description "BGP path origin";
             type enumeration {
               enum "igp" {
                 description "Path originated in the local IGP";
               }
               enum "egp" {
                 description "Path originated in another AS";
               }
               enum "incomplete" {
                 description "Path was learned by some other means";
               }
             }
           }
           container aigp-originate {
             presence "enable aigp-originate";
             description "Originate a BGP AIGP attribute";
             leaf distance {
               description "AIGP distance";
               type union {
                 type uint32;
                 type string {
                   pattern "<.*>|$.*";
                 }
               }
             }
           }
           container aigp-adjust {
             description "Adjust a BGP AIGP attribute";
             choice math-op {
               case case_1 {
                 leaf add {
                   type empty;
                 }
               }
               case case_2 {
                 leaf subtract {
                   type empty;
                 }
               }
               case case_3 {
                 leaf multiply {
                   type empty;
                 }
               }
               case case_4 {
                 leaf divide {
                   type empty;
                 }
               }
             }
             choice adjust-value {
               case case_1 {
                 leaf user-value {
                   description "Adjustment value";
                   type union {
                     type uint64;
                     type string {
                       pattern "<.*>|$.*";
                     }
                   }
                 }
               }
               case case_2 {
                 leaf distance-to-protocol-nexthop {
                   description "Metric2";
                   type empty;
                 }
               }
             }
           }
           list community {
             key "choice-ident choice-value community-name";
             ordered-by user;
             description "BGP community properties associated with a route";
             leaf choice-ident {
               type enumeration {
                 enum "equal-literal" {
                 }
                 enum "set" {
                 }
                 enum "plus-literal" {
                 }
                 enum "add" {
                 }
                 enum "minus-literal" {
                 }
                 enum "delete" {
                 }
                 enum "community-name" {
                 }
               }
             }
             leaf choice-value {
               type string;
             }
             leaf community-name {
               description "Name to identify a BGP community";
               type string;
             }
           }
           leaf damping {
             description "Define BGP route flap damping parameters";
             type string;
           }
           leaf aggregate-bandwidth {
             description "Advertise aggregate outbound link bandwidth";
             type empty;
           }
           leaf limit-bandwidth {
             description "Limit advertised aggregate outbound link bandwidth";
             type union {
               type string {
                 pattern "<.*>|$.*";
               }
               type uint32 {
                 range "0 .. 4294967295";
               }
             }
           }
           leaf no-entropy-label-capability {
             description "Don't advertise entropy label capability";
             type empty;
           }
           leaf as-path-prepend {
             description "Prepend AS numbers to an AS path (BGP only)";
             type string;
           }
           container as-path-expand {
             description "Prepend AS numbers prior to adding local-as (BGP only)";
             choice aspath_exp_value {
               case case_1 {
                 container last-as {
                   presence "enable last-as";
                   description "Prepend last AS";
                   leaf count {
                     description "Repeat count";
                     type union {
                       type string {
                         pattern "<.*>|$.*";
                       }
                       type uint32 {
                         range "1 .. 32";
                       }
                     }
                   }
                 }
               }
               case case_2 {
                 leaf aspath {
                   description "AS path string";
                   type string;
                 }
               }
             }
           }
           container next-hop {
             description "Set the address of the next-hop router";
             choice nexthop_value {
               case case_1 {
                 leaf self {
                   description "Use a local address as the next-hop address";
                   type empty;
                 }
               }
               case case_2 {
                 leaf peer-address {
                   description "Use the remote peer address as the next-hop address";
                   type empty;
                 }
               }
               case case_3 {
                 leaf address {
                   description "Next-hop address";
                   type jt:ipaddr;
                 }
               }
               case case_4 {
                 leaf reject {
                   description "Use a reject next hop";
                   type empty;
                 }
               }
               case case_5 {
                 leaf discard {
                   description "Use a discard next hop";
                   type empty;
                 }
               }
               case case_6 {
                 leaf next-table {
                   description "Perform a forwarding lookup in the specified table";
                   type string;
                 }
               }
             }
           }
           container install-nexthop {
             description "Choose the next hop to be used for forwarding";
             leaf strict {
               description "Do not use any other available next hops";
               type empty;
             }
             choice nexthop-value {
               case case_1 {
                 leaf-list lsp {
                   ordered-by user;
                   description "Next-hop LSP name";
                   type string;
                 }
               }
               case case_2 {
                 leaf-list lsp-regex {
                   ordered-by user;
                   description "Next-hop LSP name regular expression";
                   type string;
                 }
               }
               case case_3 {
                 leaf-list static-lsp {
                   ordered-by user;
                   description "Next-hop static LSP name";
                   type string;
                 }
               }
               case case_4 {
                 leaf-list static-lsp-regex {
                   ordered-by user;
                   description "Next-hop static LSP name regular expression";
                   type string;
                 }
               }
             }
             container except {
               description "Do not choose to install matching next hops";
               uses apply-advanced;
               choice nexthop-value {
                 case case_1 {
                   leaf-list lsp {
                     ordered-by user;
                     description "Next-hop LSP name";
                     type string;
                   }
                 }
                 case case_2 {
                   leaf-list lsp-regex {
                     ordered-by user;
                     description "Next-hop LSP name regular expression";
                     type string;
                   }
                 }
                 case case_3 {
                   leaf-list static-lsp {
                     ordered-by user;
                     description "Next-hop static LSP name";
                     type string;
                   }
                 }
                 case case_4 {
                   leaf-list static-lsp-regex {
                     ordered-by user;
                     description "Next-hop static LSP name regular expression";
                     type string;
                   }
                 }
               }
             }
           }
           leaf trace {
             description "Log matches to a trace file";
             type empty;
           }
           container external {
             presence "enable external";
             description "External route";
             uses apply-advanced;
             leaf type {
               description "OSPF external metric type";
               type union {
                 type string {
                   pattern "<.*>|$.*";
                 }
                 type int32 {
                   range "1 .. 2";
                 }
               }
             }
             leaf nssa-only {
               description "Clear P-bit on lsa type 7";
               type empty;
             }
           }
           container load-balance {
             description "Type of load balancing in forwarding table";
             choice load_balance_type {
               case case_1 {
                 leaf per-packet {
                   description "Load balance on a per-packet basis";
                   type empty;
                 }
               }
               case case_2 {
               }
               case case_3 {
               }
               case case_4 {
                 leaf consistent-hash {
                   description "Give a prefix consistent load-balancing";
                   type empty;
                 }
               }
               case case_5 {
               }
               case case_6 {
               }
             }
           }
           leaf analyze {
             description "Send to registered controllers for analysis";
             type empty;
           }
           leaf class {
             description "Set class-of-service parameters";
             type string;
           }
           leaf destination-class {
             description "Set destination class in forwarding table";
             type string;
           }
           leaf source-class {
             description "Set source class in forwarding table";
             type string;
           }
           leaf forwarding-class {
             description "Set source or destination class in forwarding table";
             type string;
           }
           container map-to-interface {
             description "Set output logical interface";
             choice map_to_interface_value {
               case case_1 {
                 leaf self {
                   description "Map the interface to itself";
                   type empty;
                 }
               }
               case case_2 {
                 leaf interface {
                   description "Output logical interface";
                   type union {
                     type jt:interface-name;
                     type string {
                       pattern "<.*>|$.*";
                     }
                   }
                 }
               }
             }
           }
           leaf-list ssm-source {
             ordered-by user;
             description "List of Sources for SSM mapping";
             type jt:ipaddr;
           }
           container p2mp-lsp-root {
             description "P2mp lsp root address";
             uses apply-advanced;
             leaf address {
               description "Ipv4 root address";
               type jt:ipv4addr;
             }
           }
           leaf cos-next-hop-map {
             description "Set CoS-based next-hop map in forwarding table";
             type string;
           }
           leaf dynamic-tunnel-attributes {
             description "Choose the dynamic tunnel attributes used for forwarding";
             type string;
           }
           leaf selected-mldp-egress {
             description "This node should act as egress node for MLDP inband signalling";
             type empty;
           }
           leaf mhop-bfd-port {
             description "Use port number 4784 for MPLS-BFD as per RFC5884";
             type empty;
           }
           leaf no-backup {
             description "This prefix should not have backup";
             type empty;
           }
           leaf default-action {
             description "Set default policy action";
             type enumeration {
               enum "accept" {
                 description "Accept a route";
               }
               enum "reject" {
                 description "Reject a route";
               }
             }
           }
           leaf next {
             description "Skip to next policy or term";
             type enumeration {
               enum "policy" {
                 description "Skip to next policy filter";
               }
               enum "term" {
                 description "Skip to next term in a policy filter";
               }
             }
           }
           choice accept_reject {
             case case_1 {
               leaf accept {
                 description "Accept a route";
                 type empty;
               }
             }
             case case_2 {
               leaf reject {
                 description "Reject a route";
                 type empty;
               }
             }
           }
           container bgp-output-queue-priority {
             description "Set the BGP Update output queue priority.";
             choice class {
               case case_1 {
                 leaf priority {
                   description "Output queue priority; higher is better";
                   type union {
                     type string {
                       pattern "<.*>|$.*";
                     }
                     type uint32 {
                       range "1 .. 16";
                     }
                   }
                 }
               }
               case case_2 {
                 leaf expedited {
                   description "Expedited queue; highest priority";
                   type empty;
                 }
               }
             }
           }
           leaf multipath-resolve {
             description "Use all paths for resolution over this prefix";
             type empty;
           }
           leaf label-allocation-fallback-reject {
             description "Suppress prefix export when label allocation fails";
             type empty;
           }
         }
       }
       container from {
         description "Conditions to match the source of a route";
         uses apply-advanced;
         leaf instance {
           description "Routing protocol instance";
           type string;
         }
         leaf instance-any {
           description "Any routing protocol instance";
           type empty;
         }
         leaf-list instance-list {
           description "A list of routing protocol instances";
           type string;
         }
         leaf family {
           type enumeration {
             enum "inet" {
               description "IPv4 family";
             }
             enum "inet-vpn" {
               description "IPv4-VPN family";
             }
             enum "inet6" {
               description "IPv6 family";
             }
             enum "inet6-vpn" {
               description "IPv6-VPN family";
             }
             enum "iso-vpn" {
               description "ISO-VPN family";
             }
             enum "iso" {
               description "ISO family";
             }
             enum "evpn" {
               description "EVPN family";
             }
             enum "inet-mvpn" {
               description "IPv4 Multicast VPN family";
             }
             enum "inet6-mvpn" {
               description "IPv6 Multicast VPN family";
             }
             enum "inet-mdt" {
               description "IPv4 MDT Signaling family";
             }
             enum "route-target" {
               description "Local route target VPN family";
             }
             enum "traffic-engineering" {
               description "Traffic Engineering family";
             }
           }
         }
         leaf-list protocol {
           ordered-by user;
           description "Protocol from which route was learned";
           type enumeration {
             enum "aggregate" {
               description "Aggregate routes";
             }
             enum "bgp" {
               description "BGP";
             }
             enum "direct" {
               description "Directly connected routes";
             }
             enum "dvmrp" {
               description "Distance Vector Multicast Routing Protocol";
             }
             enum "isis" {
               description "Intermediate System-to-Intermediate System";
             }
             enum "esis" {
               description "End System-to-Intermediate System";
             }
             enum "l-isis" {
               description "Labelled ISIS";
             }
             enum "l2circuit" {
               description "Layer 2 circuits";
             }
             enum "l2vpn" {
               description "Layer 2 MPLS virtual private networks";
             }
             enum "local" {
               description "Local system addresses";
             }
             enum "ospf" {
               description "Open Shortest Path First";
             }
             enum "ospf2" {
               description "Open Shortest Path First Version 2";
             }
             enum "ospf3" {
               description "Open Shortest Path First Version 3";
             }
             enum "l-ospf" {
               description "Labelled OSPF";
             }
             enum "pim" {
               description "Protocol Independent Multicast";
             }
             enum "rip" {
               description "Routing Information Protocol";
             }
             enum "ripng" {
               description "Routing Information Protocol next generation";
             }
             enum "static" {
               description "Statically defined addresses";
             }
             enum "arp" {
               description "Addresses learned from ARP";
             }
             enum "frr" {
               description "Addresses created by Host Fast Re-route";
             }
             enum "mpls" {
               description "Multiprotocol Label Switching";
             }
             enum "ldp" {
               description "Label Distribution Protocol";
             }
             enum "rsvp" {
               description "Resource Reservation Protocol";
             }
             enum "msdp" {
               description "Multicast Source Discovery Protocol";
             }
             enum "route-target" {
               description "Local route target VPN membership";
             }
             enum "access" {
               description "Access server routes";
             }
             enum "access-internal" {
               description "Internal routes to directly connected clients";
             }
             enum "anchor" {
               description "Anchor routes connected to UEs";
             }
             enum "bgp-static" {
               description "BGP static routes";
             }
             enum "vpls" {
               description "Virtual Private LAN Service";
             }
             enum "evpn" {
               description "Ethernet VPN Service";
             }
             enum "spring-te" {
               description "SPRING Traffic-Engineered";
             }
             enum "bgp-ls-epe" {
               description "Addresses created by BGP-LS egress TE";
             }
             enum "rift" {
               description "RIFT routes";
             }
           }
         }
         leaf rib {
           description "Routing table";
           type string;
         }
         leaf-list neighbor {
           ordered-by user;
           description "Neighboring router";
           type jt:ipaddr;
         }
         leaf-list next-hop {
           ordered-by user;
           description "Next-hop router";
           type jt:ipaddr;
         }
         leaf-list interface {
           ordered-by user;
           description "Interface name or address";
           type union {
             type jt:ipaddr-or-interface;
             type string {
               pattern "<.*>|$.*";
             }
           }
         }
         leaf area {
           description "OSPF area identifier";
           type jt:areaid;
         }
         leaf-list as-path {
           ordered-by user;
           description "Name of AS path regular expression (BGP only)";
           type string;
         }
         leaf-list as-path-group {
           ordered-by user;
           description "Name of AS path group (BGP only)";
           type string;
         }
         leaf origin {
           description "BGP origin attribute";
           type enumeration {
             enum "igp" {
               description "Path originated in the local IGP";
             }
             enum "egp" {
               description "Path originated in another AS";
             }
             enum "incomplete" {
               description "Path was learned by some other means";
             }
           }
         }
         leaf-list community {
           ordered-by user;
           description "BGP community";
           type string;
         }
         leaf level {
           description "IS-IS level";
           type union {
             type uint32;
             type string {
               pattern "<.*>|$.*";
             }
           }
         }
         container external {
           presence "enable external";
           description "External route";
           uses apply-advanced;
           leaf type {
             description "OSPF external metric type";
             type union {
               type string {
                 pattern "<.*>|$.*";
               }
               type int32 {
                 range "1 .. 2";
               }
             }
           }
         }
         leaf validation-database {
           description "Name to identify a validation-state";
           type enumeration {
             enum "valid" {
               description "Match for valid database validation-state";
             }
             enum "invalid" {
               description "Match for invalid database validation-state";
             }
             enum "unknown" {
               description "Match for unknown database validation-state";
             }
           }
         }
         leaf metric {
           description "Metric value";
           type union {
             type uint32;
             type string {
               pattern "<.*>|$.*";
             }
           }
         }
         leaf metric2 {
           description "Metric value 2";
           type union {
             type uint32;
             type string {
               pattern "<.*>|$.*";
             }
           }
         }
         leaf metric3 {
           description "Metric value 3";
           type union {
             type uint32;
             type string {
               pattern "<.*>|$.*";
             }
           }
         }
         leaf metric4 {
           description "Metric value 4";
           type union {
             type uint32;
             type string {
               pattern "<.*>|$.*";
             }
           }
         }
         leaf-list tag {
           ordered-by user;
           description "Tag string";
           type union {
             type uint32;
             type string {
               pattern "<.*>|$.*";
             }
           }
         }
         leaf tag2 {
           description "Tag string 2";
           type union {
             type uint32;
             type string {
               pattern "<.*>|$.*";
             }
           }
         }
         leaf preference {
           description "Preference value";
           type union {
             type uint32;
             type string {
               pattern "<.*>|$.*";
             }
           }
         }
         leaf preference2 {
           description "Preference value 2";
           type union {
             type uint32;
             type string {
               pattern "<.*>|$.*";
             }
           }
         }
         leaf color {
           description "Color (preference) value";
           type union {
             type uint32;
             type string {
               pattern "<.*>|$.*";
             }
           }
         }
         leaf color2 {
           description "Color (preference) value 2";
           type union {
             type uint32;
             type string {
               pattern "<.*>|$.*";
             }
           }
         }
         leaf local-preference {
           description "Local preference associated with a route";
           type union {
             type uint32;
             type string {
               pattern "<.*>|$.*";
             }
           }
         }
         leaf-list policy {
           ordered-by user;
           description "Name of policy to evaluate";
           type jt:policy-algebra;
         }
         list route-filter {
           key "address choice-ident choice-value";
           ordered-by user;
           description "List of routes to match";
           uses control_route_filter_type;
         }
         list source-address-filter {
           key "address choice-ident choice-value";
           ordered-by user;
           description "List of source addresses to match";
           uses control_source_address_filter_type;
         }
         list prefix-list {
           key name;
           ordered-by user;
           description "List of prefix-lists of routes to match";
           uses control_prefix_list_type;
         }
         list prefix-list-filter {
           key "list_name choice-ident choice-value";
           ordered-by user;
           description "List of prefix-list-filters to match";
           uses control_prefix_list_filter_type;
         }
         list rtf-prefix-list {
           key name;
           ordered-by user;
           description "List of rtf-prefix-lists of routes to match";
           uses control_rtf_prefix_list_type;
         }
         list route-filter-list {
           key name;
           ordered-by user;
           description "List of route-filter-lists of routes to match";
           uses control_route_filter_list_type;
         }
         list source-address-filter-list {
           key name;
           ordered-by user;
           description "List of source-address-filter-lists of routes to match";
           uses control_source_address_filter_list_type;
         }
         container multicast-scope {
           description "Multicast scope to match";
           choice scope-choice {
             case case_1 {
               leaf node-local {
                 description "Node-local scope";
                 type empty;
               }
             }
             case case_2 {
               leaf link-local {
                 description "Link-local scope";
                 type empty;
               }
             }
             case case_3 {
               leaf site-local {
                 description "Site-local scope";
                 type empty;
               }
             }
             case case_4 {
               leaf organization-local {
                 description "Organization-local scope";
                 type empty;
               }
             }
             case case_5 {
               leaf global {
                 description "Global scope";
                 type empty;
               }
             }
             case case_6 {
               leaf scope_value {
                 description "Scope value";
                 type union {
                   type string {
                     pattern "<.*>|$.*";
                   }
                   type uint32 {
                     range "0 .. 15";
                   }
                 }
               }
             }
           }
           choice scope-operator {
             case case_1 {
               leaf orhigher {
                 description "Match higher values";
                 type empty;
               }
             }
             case case_2 {
               leaf orlower {
                 description "Match lower values";
                 type empty;
               }
             }
           }
         }
         leaf aggregate-contributor {
           description "Match more specifics of an aggregate";
           type empty;
         }
         leaf state {
           description "Route state";
           type enumeration {
             enum "active" {
               description "Active route";
             }
             enum "inactive" {
               description "Inactive route";
             }
           }
         }
         leaf route-type {
           description "Route type";
           type enumeration {
             enum "internal" {
               description "Internal route";
             }
             enum "external" {
               description "External route";
             }
           }
         }
         leaf-list nlri-route-type {
           ordered-by user;
           description "Route type from NLRI";
           type union {
             type string {
               pattern "<.*>|$.*";
             }
             type uint32 {
               range "1 .. 10";
             }
           }
         }
         leaf next-hop-type {
           description "Next-hop type";
           type enumeration {
             enum "merged" {
               description "Merged next hop";
             }
           }
         }
         leaf-list condition {
           ordered-by user;
           description "Condition to match on";
           type string;
         }
         list community-count {
           key name;
           ordered-by user;
           description "Number of BGP communities";
           uses community_count_type;
         }
         list as-path-unique-count {
           key name;
           ordered-by user;
           description "Number of unique BGP ASes excluding confederations";
           uses as-path-unique-count-type;
         }
         list as-path-calc-length {
           key name;
           ordered-by user;
           description "Number of BGP ASes excluding confederations";
           uses as-path-calc-length-type;
         }
         container traffic-engineering {
           presence "enable traffic-engineering";
           description "Traffic-Engineering related parameters";
           uses apply-advanced;
           leaf-list protocol {
             ordered-by user;
             description "Protocol that originated the entry";
             type enumeration {
               enum "direct" {
                 description "Directly originated";
               }
               enum "ospf" {
                 description "OSPF originated";
               }
               enum "isis-level-1" {
                 description "ISIS level-1 originated";
               }
               enum "isis-level-2" {
                 description "ISIS level-2 originated";
               }
               enum "static" {
                 description "Statically originated";
               }
               enum "unknown" {
                 description "Originated by unknown sources";
               }
             }
           }
           container node {
             presence "enable node";
             description "Node-related parameters";
             uses apply-advanced;
             leaf as {
               description "AS number";
               type string {
               }
             }
             leaf node-type {
               description "Real or pseudo-node";
               type enumeration {
                 enum "router" {
                   description "Real node";
                 }
                 enum "pseudo-node" {
                   description "Pseudo-node";
                 }
               }
             }
             leaf router-id {
               description "IP prefix to match the router-id against";
               type jt:ipprefix;
             }
             leaf sys-id {
               description "ISO address of the node";
               type jt:sysid;
             }
           }
           container ipv4-prefix {
             presence "enable ipv4-prefix";
             description "IPV4 prefix-related parameters";
             uses apply-advanced;
             leaf as {
               description "AS number";
               type string {
               }
             }
             leaf router-id {
               description "IP prefix to match the router-id against";
               type jt:ipprefix;
             }
             leaf prefix {
               description "IP prefix to match against";
               type jt:ipprefix;
             }
             leaf sys-id {
               description "ISO address of the node";
               type jt:sysid;
             }
           }
           container link {
             presence "enable link";
             description "Link-related parameters";
             uses apply-advanced;
             container from {
               description "Specify parameter of the 'from' side";
               uses apply-advanced;
               leaf as {
                 description "AS number";
                 type string {
                 }
               }
               leaf router-id {
                 description "IP prefix to match the router-id against";
                 type jt:ipprefix;
               }
               leaf sys-id {
                 description "System-ID of the node";
                 type jt:sysid;
               }
               leaf node-type {
                 description "Type of the node";
                 type enumeration {
                   enum "router" {
                     description "Real node";
                   }
                   enum "pseudo-node" {
                     description "Pseudo-node";
                   }
                 }
               }
               leaf link-address {
                 description "IP prefix to match the link address against";
                 type jt:ipprefix;
               }
             }
             container to {
               description "Specify parameters of the 'to' side";
               uses apply-advanced;
               leaf as {
                 description "AS number";
                 type string {
                 }
               }
               leaf router-id {
                 description "IP prefix to match the router-id against";
                 type jt:ipprefix;
               }
               leaf sys-id {
                 description "System-ID of the node";
                 type jt:sysid;
               }
               leaf node-type {
                 description "Type of the node";
                 type enumeration {
                   enum "router" {
                     description "Real node";
                   }
                   enum "pseudo-node" {
                     description "Pseudo-node";
                   }
                 }
               }
               leaf link-address {
                 description "IP prefix to match the link address against";
                 type jt:ipprefix;
               }
             }
           }
         }
         leaf-list route-distinguisher {
           ordered-by user;
           description "Name of the route-distinguisher";
           type string;
         }
       }
       container to {
         description "Conditions to match the destination of a route";
         uses apply-advanced;
         leaf instance {
           description "Routing protocol instance";
           type string;
         }
         leaf instance-any {
           description "Any routing protocol instance";
           type empty;
         }
         leaf-list instance-list {
           description "A list of routing protocol instances";
           type string;
         }
         leaf family {
           type enumeration {
             enum "inet" {
               description "IPv4 family";
             }
             enum "inet-vpn" {
               description "IPv4-VPN family";
             }
             enum "inet6" {
               description "IPv6 family";
             }
             enum "inet6-vpn" {
               description "IPv6-VPN family";
             }
             enum "iso-vpn" {
               description "ISO-VPN family";
             }
             enum "iso" {
               description "ISO family";
             }
             enum "evpn" {
               description "EVPN family";
             }
             enum "inet-mvpn" {
               description "IPv4 Multicast VPN family";
             }
             enum "inet6-mvpn" {
               description "IPv6 Multicast VPN family";
             }
             enum "inet-mdt" {
               description "IPv4 MDT Signaling family";
             }
             enum "route-target" {
               description "Local route target VPN family";
             }
             enum "traffic-engineering" {
               description "Traffic Engineering family";
             }
           }
         }
         leaf-list protocol {
           ordered-by user;
           description "Protocol from which route was learned";
           type enumeration {
             enum "aggregate" {
               description "Aggregate routes";
             }
             enum "bgp" {
               description "BGP";
             }
             enum "direct" {
               description "Directly connected routes";
             }
             enum "dvmrp" {
               description "Distance Vector Multicast Routing Protocol";
             }
             enum "isis" {
               description "Intermediate System-to-Intermediate System";
             }
             enum "esis" {
               description "End System-to-Intermediate System";
             }
             enum "l-isis" {
               description "Labelled ISIS";
             }
             enum "l2circuit" {
               description "Layer 2 circuits";
             }
             enum "l2vpn" {
               description "Layer 2 MPLS virtual private networks";
             }
             enum "local" {
               description "Local system addresses";
             }
             enum "ospf" {
               description "Open Shortest Path First";
             }
             enum "ospf2" {
               description "Open Shortest Path First Version 2";
             }
             enum "ospf3" {
               description "Open Shortest Path First Version 3";
             }
             enum "l-ospf" {
               description "Labelled OSPF";
             }
             enum "pim" {
               description "Protocol Independent Multicast";
             }
             enum "rip" {
               description "Routing Information Protocol";
             }
             enum "ripng" {
               description "Routing Information Protocol next generation";
             }
             enum "static" {
               description "Statically defined addresses";
             }
             enum "arp" {
               description "Addresses learned from ARP";
             }
             enum "frr" {
               description "Addresses created by Host Fast Re-route";
             }
             enum "mpls" {
               description "Multiprotocol Label Switching";
             }
             enum "ldp" {
               description "Label Distribution Protocol";
             }
             enum "rsvp" {
               description "Resource Reservation Protocol";
             }
             enum "msdp" {
               description "Multicast Source Discovery Protocol";
             }
             enum "route-target" {
               description "Local route target VPN membership";
             }
             enum "access" {
               description "Access server routes";
             }
             enum "access-internal" {
               description "Internal routes to directly connected clients";
             }
             enum "anchor" {
               description "Anchor routes connected to UEs";
             }
             enum "bgp-static" {
               description "BGP static routes";
             }
             enum "vpls" {
               description "Virtual Private LAN Service";
             }
             enum "evpn" {
               description "Ethernet VPN Service";
             }
             enum "spring-te" {
               description "SPRING Traffic-Engineered";
             }
             enum "bgp-ls-epe" {
               description "Addresses created by BGP-LS egress TE";
             }
             enum "rift" {
               description "RIFT routes";
             }
           }
         }
         leaf rib {
           description "Routing table";
           type string;
         }
         leaf-list neighbor {
           ordered-by user;
           description "Neighboring router";
           type jt:ipaddr;
         }
         leaf-list next-hop {
           ordered-by user;
           description "Next-hop router";
           type jt:ipaddr;
         }
         leaf-list interface {
           ordered-by user;
           description "Interface name or address";
           type union {
             type jt:ipaddr-or-interface;
             type string {
               pattern "<.*>|$.*";
             }
           }
         }
         leaf area {
           description "OSPF area identifier";
           type jt:areaid;
         }
         leaf-list as-path {
           ordered-by user;
           description "Name of AS path regular expression (BGP only)";
           type string;
         }
         leaf-list as-path-group {
           ordered-by user;
           description "Name of AS path group (BGP only)";
           type string;
         }
         leaf origin {
           description "BGP origin attribute";
           type enumeration {
             enum "igp" {
               description "Path originated in the local IGP";
             }
             enum "egp" {
               description "Path originated in another AS";
             }
             enum "incomplete" {
               description "Path was learned by some other means";
             }
           }
         }
         leaf-list community {
           ordered-by user;
           description "BGP community";
           type string;
         }
         leaf level {
           description "IS-IS level";
           type union {
             type uint32;
             type string {
               pattern "<.*>|$.*";
             }
           }
         }
         container external {
           presence "enable external";
           description "External route";
           uses apply-advanced;
           leaf type {
             description "OSPF external metric type";
             type union {
               type string {
                 pattern "<.*>|$.*";
               }
               type int32 {
                 range "1 .. 2";
               }
             }
           }
         }
         leaf validation-database {
           description "Name to identify a validation-state";
           type enumeration {
             enum "valid" {
               description "Match for valid database validation-state";
             }
             enum "invalid" {
               description "Match for invalid database validation-state";
             }
             enum "unknown" {
               description "Match for unknown database validation-state";
             }
           }
         }
         leaf metric {
           description "Metric value";
           type union {
             type uint32;
             type string {
               pattern "<.*>|$.*";
             }
           }
         }
         leaf metric2 {
           description "Metric value 2";
           type union {
             type uint32;
             type string {
               pattern "<.*>|$.*";
             }
           }
         }
         leaf metric3 {
           description "Metric value 3";
           type union {
             type uint32;
             type string {
               pattern "<.*>|$.*";
             }
           }
         }
         leaf metric4 {
           description "Metric value 4";
           type union {
             type uint32;
             type string {
               pattern "<.*>|$.*";
             }
           }
         }
         leaf-list tag {
           ordered-by user;
           description "Tag string";
           type union {
             type uint32;
             type string {
               pattern "<.*>|$.*";
             }
           }
         }
         leaf tag2 {
           description "Tag string 2";
           type union {
             type uint32;
             type string {
               pattern "<.*>|$.*";
             }
           }
         }
         leaf preference {
           description "Preference value";
           type union {
             type uint32;
             type string {
               pattern "<.*>|$.*";
             }
           }
         }
         leaf preference2 {
           description "Preference value 2";
           type union {
             type uint32;
             type string {
               pattern "<.*>|$.*";
             }
           }
         }
         leaf color {
           description "Color (preference) value";
           type union {
             type uint32;
             type string {
               pattern "<.*>|$.*";
             }
           }
         }
         leaf color2 {
           description "Color (preference) value 2";
           type union {
             type uint32;
             type string {
               pattern "<.*>|$.*";
             }
           }
         }
         leaf local-preference {
           description "Local preference associated with a route";
           type union {
             type uint32;
             type string {
               pattern "<.*>|$.*";
             }
           }
         }
         leaf-list policy {
           ordered-by user;
           description "Name of policy to evaluate";
           type jt:policy-algebra;
         }
       }
       container then {
         description "Actions to take if 'from' and 'to' conditions match";
         uses apply-advanced;
         container metric {
           description "Metric value";
           uses apply-advanced;
           choice metric_action {
             case case_1 {
               leaf metric {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
             case case_4 {
               container igp {
                 presence "enable igp";
                 description "Track the IGP metric (BGP only)";
                 leaf metric_offset {
                   description "Metric offset for MED";
                   type union {
                     type int32;
                     type string {
                       pattern "<.*>|$.*";
                     }
                   }
                 }
               }
             }
             case case_5 {
               container minimum-igp {
                 presence "enable minimum-igp";
                 description "Track the minimum IGP metric (BGP only)";
                 leaf metric_offset {
                   description "Metric offset for MED";
                   type union {
                     type int32;
                     type string {
                       pattern "<.*>|$.*";
                     }
                   }
                 }
               }
             }
             case case_6 {
               container expression {
                 description "Calculate value based on route metric and metric2";
                 uses metric_expression_type;
               }
             }
             case case_7 {
               leaf aigp {
                 description "Use aigp, if it exists, to set the IGP metric";
                 type empty;
               }
             }
           }
         }
         container metric2 {
           description "Metric value 2";
           uses apply-advanced;
           choice metric_action {
             case case_1 {
               leaf metric2 {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
           }
         }
         container metric3 {
           description "Metric value 3";
           uses apply-advanced;
           choice metric_action {
             case case_1 {
               leaf metric3 {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
           }
         }
         container metric4 {
           description "Metric value 4";
           uses apply-advanced;
           choice metric_action {
             case case_1 {
               leaf metric4 {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
           }
         }
         container tag {
           description "Tag string";
           uses apply-advanced;
           choice metric_action {
             case case_1 {
               leaf tag {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
           }
         }
         container tag2 {
           description "Tag string 2";
           uses apply-advanced;
           choice metric_action {
             case case_1 {
               leaf tag2 {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
           }
         }
         container preference {
           description "Preference value";
           uses apply-advanced;
           choice metric_action {
             case case_1 {
               leaf preference {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
           }
         }
         container preference2 {
           description "Preference value 2";
           uses apply-advanced;
           choice metric_action {
             case case_1 {
               leaf preference2 {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
           }
         }
         container color {
           description "Color (preference) value";
           uses apply-advanced;
           choice metric_action {
             case case_1 {
               leaf color {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
           }
         }
         container color2 {
           description "Color (preference) value 2";
           uses apply-advanced;
           choice metric_action {
             case case_1 {
               leaf color2 {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
           }
         }
         container local-preference {
           description "Local preference associated with a route";
           uses apply-advanced;
           choice metric_action {
             case case_1 {
               leaf local-preference {
                 type union {
                   type uint32;
                   type string {
                     pattern "<.*>|$.*";
                   }
                 }
               }
             }
             case case_2 {
               leaf add {
                 description "Add constant to attribute";
                 type union {
                   type uint32;
                   type string {
                     pattern "<.*>|$.*";
                   }
                 }
               }
             }
             case case_3 {
               leaf subtract {
                 description "Subtract constant from attribute";
                 type union {
                   type uint32;
                   type string {
                     pattern "<.*>|$.*";
                   }
                 }
               }
             }
           }
         }
         leaf priority {
           description "Set priority for route installation";
           type enumeration {
             enum "high" {
               description "Set priority to high";
             }
             enum "medium" {
               description "Set priority to medium";
             }
             enum "low" {
               description "Set priority to low";
             }
           }
         }
         container prefix-segment {
           description "Set prefix segment attributes";
           leaf index {
             description "Set prefix segment index ";
             type union {
               type string {
                 pattern "<.*>|$.*";
               }
               type uint32 {
                 range "0 .. 199999";
               }
             }
           }
           leaf node-segment {
             description "Set node segment flag for this prefix segment";
             type empty;
           }
         }
         leaf label-allocation {
           description "Set label allocation mode";
           type enumeration {
             enum "per-table" {
               description "Set per-table label allocation mode";
             }
             enum "per-nexthop" {
               description "Set per-nexthop label allocation mode";
             }
             enum "per-table-localize" {
               description "Set per-table-localize label allocation mode";
             }
           }
         }
         container add-path {
           description "Set BGP add-path attributes";
           leaf send-count {
             description "Number of add-paths sent";
             type union {
               type string {
                 pattern "<.*>|$.*";
               }
               type uint32 {
                 range "2 .. 64";
               }
             }
           }
         }
         leaf validation-state {
           description "Set validation-state of a route";
           type enumeration {
             enum "valid" {
               description "Set validaton-state to valid";
             }
             enum "invalid" {
               description "Set validation-state to invalid";
             }
             enum "unknown" {
               description "Set validation-state to unknown";
             }
           }
         }
         leaf origin {
           description "BGP path origin";
           type enumeration {
             enum "igp" {
               description "Path originated in the local IGP";
             }
             enum "egp" {
               description "Path originated in another AS";
             }
             enum "incomplete" {
               description "Path was learned by some other means";
             }
           }
         }
         container aigp-originate {
           presence "enable aigp-originate";
           description "Originate a BGP AIGP attribute";
           leaf distance {
             description "AIGP distance";
             type union {
               type uint32;
               type string {
                 pattern "<.*>|$.*";
               }
             }
           }
         }
         container aigp-adjust {
           description "Adjust a BGP AIGP attribute";
           choice math-op {
             case case_1 {
               leaf add {
                 type empty;
               }
             }
             case case_2 {
               leaf subtract {
                 type empty;
               }
             }
             case case_3 {
               leaf multiply {
                 type empty;
               }
             }
             case case_4 {
               leaf divide {
                 type empty;
               }
             }
           }
           choice adjust-value {
             case case_1 {
               leaf user-value {
                 description "Adjustment value";
                 type union {
                   type uint64;
                   type string {
                     pattern "<.*>|$.*";
                   }
                 }
               }
             }
             case case_2 {
               leaf distance-to-protocol-nexthop {
                 description "Metric2";
                 type empty;
               }
             }
           }
         }
         list community {
           key "choice-ident choice-value community-name";
           ordered-by user;
           description "BGP community properties associated with a route";
           leaf choice-ident {
             type enumeration {
               enum "equal-literal" {
               }
               enum "set" {
               }
               enum "plus-literal" {
               }
               enum "add" {
               }
               enum "minus-literal" {
               }
               enum "delete" {
               }
               enum "community-name" {
               }
             }
           }
           leaf choice-value {
             type string;
           }
           leaf community-name {
             description "Name to identify a BGP community";
             type string;
           }
         }
         leaf damping {
           description "Define BGP route flap damping parameters";
           type string;
         }
         leaf aggregate-bandwidth {
           description "Advertise aggregate outbound link bandwidth";
           type empty;
         }
         leaf limit-bandwidth {
           description "Limit advertised aggregate outbound link bandwidth";
           type union {
             type string {
               pattern "<.*>|$.*";
             }
             type uint32 {
               range "0 .. 4294967295";
             }
           }
         }
         leaf no-entropy-label-capability {
           description "Don't advertise entropy label capability";
           type empty;
         }
         leaf as-path-prepend {
           description "Prepend AS numbers to an AS path (BGP only)";
           type string;
         }
         container as-path-expand {
           description "Prepend AS numbers prior to adding local-as (BGP only)";
           choice aspath_exp_value {
             case case_1 {
               container last-as {
                 presence "enable last-as";
                 description "Prepend last AS";
                 leaf count {
                   description "Repeat count";
                   type union {
                     type string {
                       pattern "<.*>|$.*";
                     }
                     type uint32 {
                       range "1 .. 32";
                     }
                   }
                 }
               }
             }
             case case_2 {
               leaf aspath {
                 description "AS path string";
                 type string;
               }
             }
           }
         }
         container next-hop {
           description "Set the address of the next-hop router";
           choice nexthop_value {
             case case_1 {
               leaf self {
                 description "Use a local address as the next-hop address";
                 type empty;
               }
             }
             case case_2 {
               leaf peer-address {
                 description "Use the remote peer address as the next-hop address";
                 type empty;
               }
             }
             case case_3 {
               leaf address {
                 description "Next-hop address";
                 type jt:ipaddr;
               }
             }
             case case_4 {
               leaf reject {
                 description "Use a reject next hop";
                 type empty;
               }
             }
             case case_5 {
               leaf discard {
                 description "Use a discard next hop";
                 type empty;
               }
             }
             case case_6 {
               leaf next-table {
                 description "Perform a forwarding lookup in the specified table";
                 type string;
               }
             }
           }
         }
         container install-nexthop {
           description "Choose the next hop to be used for forwarding";
           leaf strict {
             description "Do not use any other available next hops";
             type empty;
           }
           choice nexthop-value {
             case case_1 {
               leaf-list lsp {
                 ordered-by user;
                 description "Next-hop LSP name";
                 type string;
               }
             }
             case case_2 {
               leaf-list lsp-regex {
                 ordered-by user;
                 description "Next-hop LSP name regular expression";
                 type string;
               }
             }
             case case_3 {
               leaf-list static-lsp {
                 ordered-by user;
                 description "Next-hop static LSP name";
                 type string;
               }
             }
             case case_4 {
               leaf-list static-lsp-regex {
                 ordered-by user;
                 description "Next-hop static LSP name regular expression";
                 type string;
               }
             }
           }
           container except {
             description "Do not choose to install matching next hops";
             uses apply-advanced;
             choice nexthop-value {
               case case_1 {
                 leaf-list lsp {
                   ordered-by user;
                   description "Next-hop LSP name";
                   type string;
                 }
               }
               case case_2 {
                 leaf-list lsp-regex {
                   ordered-by user;
                   description "Next-hop LSP name regular expression";
                   type string;
                 }
               }
               case case_3 {
                 leaf-list static-lsp {
                   ordered-by user;
                   description "Next-hop static LSP name";
                   type string;
                 }
               }
               case case_4 {
                 leaf-list static-lsp-regex {
                   ordered-by user;
                   description "Next-hop static LSP name regular expression";
                   type string;
                 }
               }
             }
           }
         }
         leaf trace {
           description "Log matches to a trace file";
           type empty;
         }
         container external {
           presence "enable external";
           description "External route";
           uses apply-advanced;
           leaf type {
             description "OSPF external metric type";
             type union {
               type string {
                 pattern "<.*>|$.*";
               }
               type int32 {
                 range "1 .. 2";
               }
             }
           }
           leaf nssa-only {
             description "Clear P-bit on lsa type 7";
             type empty;
           }
         }
         container load-balance {
           description "Type of load balancing in forwarding table";
           choice load_balance_type {
             case case_1 {
               leaf per-packet {
                 description "Load balance on a per-packet basis";
                 type empty;
               }
             }
             case case_2 {
             }
             case case_3 {
             }
             case case_4 {
               leaf consistent-hash {
                 description "Give a prefix consistent load-balancing";
                 type empty;
               }
             }
             case case_5 {
             }
             case case_6 {
             }
           }
         }
         leaf analyze {
           description "Send to registered controllers for analysis";
           type empty;
         }
         leaf class {
           description "Set class-of-service parameters";
           type string;
         }
         leaf destination-class {
           description "Set destination class in forwarding table";
           type string;
         }
         leaf source-class {
           description "Set source class in forwarding table";
           type string;
         }
         leaf forwarding-class {
           description "Set source or destination class in forwarding table";
           type string;
         }
         container map-to-interface {
           description "Set output logical interface";
           choice map_to_interface_value {
             case case_1 {
               leaf self {
                 description "Map the interface to itself";
                 type empty;
               }
             }
             case case_2 {
               leaf interface {
                 description "Output logical interface";
                 type union {
                   type jt:interface-name;
                   type string {
                     pattern "<.*>|$.*";
                   }
                 }
               }
             }
           }
         }
         leaf-list ssm-source {
           ordered-by user;
           description "List of Sources for SSM mapping";
           type jt:ipaddr;
         }
         container p2mp-lsp-root {
           description "P2mp lsp root address";
           uses apply-advanced;
           leaf address {
             description "Ipv4 root address";
             type jt:ipv4addr;
           }
         }
         leaf cos-next-hop-map {
           description "Set CoS-based next-hop map in forwarding table";
           type string;
         }
         leaf dynamic-tunnel-attributes {
           description "Choose the dynamic tunnel attributes used for forwarding";
           type string;
         }
         leaf selected-mldp-egress {
           description "This node should act as egress node for MLDP inband signalling";
           type empty;
         }
         leaf mhop-bfd-port {
           description "Use port number 4784 for MPLS-BFD as per RFC5884";
           type empty;
         }
         leaf no-backup {
           description "This prefix should not have backup";
           type empty;
         }
         leaf default-action {
           description "Set default policy action";
           type enumeration {
             enum "accept" {
               description "Accept a route";
             }
             enum "reject" {
               description "Reject a route";
             }
           }
         }
         leaf next {
           description "Skip to next policy or term";
           type enumeration {
             enum "policy" {
               description "Skip to next policy filter";
             }
             enum "term" {
               description "Skip to next term in a policy filter";
             }
           }
         }
         choice accept_reject {
           case case_1 {
             leaf accept {
               description "Accept a route";
               type empty;
             }
           }
           case case_2 {
             leaf reject {
               description "Reject a route";
               type empty;
             }
           }
         }
         container bgp-output-queue-priority {
           description "Set the BGP Update output queue priority.";
           choice class {
             case case_1 {
               leaf priority {
                 description "Output queue priority; higher is better";
                 type union {
                   type string {
                     pattern "<.*>|$.*";
                   }
                   type uint32 {
                     range "1 .. 16";
                   }
                 }
               }
             }
             case case_2 {
               leaf expedited {
                 description "Expedited queue; highest priority";
                 type empty;
               }
             }
           }
         }
         leaf multipath-resolve {
           description "Use all paths for resolution over this prefix";
           type empty;
         }
         leaf label-allocation-fallback-reject {
           description "Suppress prefix export when label allocation fails";
           type empty;
         }
       }
     }
     container defaults {
       description "Policy default behaviour";
       uses apply-advanced;
       container route-filter {
         description "Set route filter behaviour";
         leaf walkup {
           description "Route filter walk up enable";
           type empty;
         }
       }
     }
     list community {
       key name;
       description "BGP community information";
       leaf name {
         description "Name to identify BGP community";
         type string;
       }
       uses apply-advanced;
       leaf invert-match {
         description "Invert the result of the community expression matching";
         type empty;
       }
       leaf-list members {
         ordered-by user;
         description "Community members";
         type string;
       }
     }
     list route-distinguisher {
       key name;
       description "Route-distinguisher information";
       leaf name {
         description "Name to identify route-distinguisher";
         type string;
       }
       uses apply-advanced;
       leaf-list members {
         ordered-by user;
         description "Route distinguisher string in ( *:X ) or ( Y:* ) or (X:Y) format";
         type string;
       }
     }
     list as-path {
       key name;
       ordered-by user;
       description "BGP autonomous system path regular expression";
       leaf name {
         description "Name to identify AS path regular expression";
         type string;
       }
       uses apply-advanced;
       leaf path {
         description "AS path regular expression";
         type string {
         }
       }
     }
     list as-path-group {
       key name;
       ordered-by user;
       description "Group a set of AS paths";
       leaf name {
         description "Name to identify AS path group";
         type string;
       }
       uses apply-advanced;
       list as-path {
         key name;
         ordered-by user;
         description "BGP autonomous system path regular expression";
         leaf name {
           description "Name to identify AS path regular expression";
           type string;
         }
         leaf path {
           description "AS path regular expression";
           type string {
           }
         }
       }
     }
     list damping {
       key name;
       ordered-by user;
       description "BGP route flap damping properties";
       leaf name {
         description "Name to identify route flap damping parameters";
         type string;
       }
       uses apply-advanced;
       choice enable-disable {
         case case_1 {
           leaf disable {
             description "Disable damping";
             type empty;
           }
         }
       }
       leaf half-life {
         description "Decay half-life";
         units "minutes";
         type union {
           type string {
             pattern "<.*>|$.*";
           }
           type uint32 {
             range "1 .. 45";
           }
         }
       }
       leaf reuse {
         description "Reuse threshold (figure-of-merit value)";
         type union {
           type string {
             pattern "<.*>|$.*";
           }
           type uint32 {
             range "1 .. 20000";
           }
         }
       }
       leaf suppress {
         description "Cutoff threshold (figure-of-merit value)";
         type union {
           type string {
             pattern "<.*>|$.*";
           }
           type uint32 {
             range "1 .. 20000";
           }
         }
       }
       leaf max-suppress {
         description "Maximum hold-down time";
         units "minutes";
         type union {
           type string {
             pattern "<.*>|$.*";
           }
           type uint32 {
             range "1 .. 720";
           }
         }
       }
     }
     list condition {
       key name;
       description "Define a route advertisement condition";
       leaf name {
         description "Name to identify Condition";
         type string;
       }
       uses apply-advanced;
       choice condition_type {
         case case_1 {
           leaf route-active-on {
             description "Route is active on a specific node";
             type enumeration {
               enum "node0" {
                 description "Route active on node 0";
               }
               enum "node1" {
                 description "Route active on node 1";
               }
             }
           }
         }
         case case_2 {
           container if-route-exists {
             presence "enable if-route-exists";
             description "Route exists in a specific routing table";
             uses apply-advanced;
             container address-family {
               presence "enable address-family";
               description "Indicates the address family of the route to match on";
               uses apply-advanced;
               choice address-family {
                 case case_1 {
                   container inet {
                     presence "enable inet";
                     description "Route to match corresponds to an inet/inet6 prefix";
                     uses apply-advanced;
                     leaf address {
                       description "Exact address of the route";
                       type jt:ipprefix;
                     }
                     leaf table {
                       description "Routing table in which route should exist";
                       type string;
                     }
                   }
                 }
                 case case_2 {
                   container ccc {
                     presence "enable ccc";
                     description "Route to match corresponds to a ccc prefix";
                     uses apply-advanced;
                     leaf address {
                       description "Logical interface used to establish ccc route";
                       type union {
                         type jt:interface-name;
                         type string {
                           pattern "<.*>|$.*";
                         }
                       }
                     }
                     leaf table {
                       description "Routing table in which route should exist";
                       type string;
                     }
                     leaf standby {
                       description "Indicates if route must be in standby state to be considered a match";
                       type empty;
                     }
                     leaf peer-unit {
                       description "Associated LT ifl's peer-unit. Required for LT-based routes";
                       type union {
                         type string {
                           pattern "<.*>|$.*";
                         }
                         type uint32 {
                           range "0 .. 8192";
                         }
                       }
                     }
                   }
                 }
               }
             }
             leaf address {
               description "Exact address of the route";
               type jt:ipprefix;
             }
             leaf table {
               description "Routing table in which route should exist";
               type string;
             }
           }
         }
       }
     }
     list rtf-prefix-list {
       key name;
       ordered-by user;
       description "Define a named set of family route target prefixes";
       leaf name {
         description "RTF prefix list name";
         type string;
       }
       uses apply-advanced;
       list prefix-list {
         key name;
         uses rtf_prefix_list_items;
       }
     }
     list application-maps {
       key name;
       ordered-by user;
       description "Define application maps";
       uses application_map_object;
     }
     list redundancy-policy {
       key name;
       leaf name {
         description "Redundancy policy name";
         type string {
           length "1 .. 63";
         }
       }
       uses apply-advanced;
       leaf-list redundancy-events {
         description "Events related services redundancy under event-options";
         type string;
       }
       container then {
         description "Action to take when of the event occurs";
         presence "enable then";
         uses srd-ev-action-object;
       }
     }
   }
   grouping application_map_object {
     leaf name {
       description "Name of application map";
       type string {
         length "1 .. 63";
       }
     }
     uses apply-advanced;
     list application {
       key name;
       ordered-by user;
       description "Name of the application";
       leaf name {
         description "Name of the application";
         type string {
           length "1 .. 63";
         }
       }
       leaf-list code-points {
         ordered-by user;
         description "List of code point bit strings";
         type string;
       }
     }
   }
   grouping as-path-calc-length-type {
     description "Calculated BGP AS_PATH length per BGP rules";
     leaf name {
       description "Number of ASes";
       type union {
         type string {
           pattern "<.*>|$.*";
         }
         type uint32 {
           range "0 .. 1024";
         }
       }
     }
     choice count-operator {
       case case_1 {
         leaf equal {
           description "Match equal values";
           type empty;
         }
       }
       case case_2 {
         leaf orhigher {
           description "Match higher or equal values";
           type empty;
         }
       }
       case case_3 {
         leaf orlower {
           description "Match lower or equal values";
           type empty;
         }
       }
     }
   }
   grouping as-path-unique-count-type {
     description "Number of unique BGP ASes excluding confederation ASes";
     leaf name {
       description "Number of ASes";
       type union {
         type string {
           pattern "<.*>|$.*";
         }
         type uint32 {
           range "0 .. 1024";
         }
       }
     }
     choice count-operator {
       case case_1 {
         leaf equal {
           description "Match equal values";
           type empty;
         }
       }
       case case_2 {
         leaf orhigher {
           description "Match higher or equal values";
           type empty;
         }
       }
       case case_3 {
         leaf orlower {
           description "Match lower or equal values";
           type empty;
         }
       }
     }
   }
   grouping community_count_type {
     description "Number of BGP communities";
     leaf name {
       description "Number of communities";
       type union {
         type string {
           pattern "<.*>|$.*";
         }
         type uint32 {
           range "0 .. 1024";
         }
       }
     }
     choice count-operator {
       case case_1 {
         leaf equal {
           description "Match equal values";
           type empty;
         }
       }
       case case_2 {
         leaf orhigher {
           description "Match higher or equal	values";
           type empty;
         }
       }
       case case_3 {
         leaf orlower {
           description "Match lower or equal values";
           type empty;
         }
       }
     }
   }
   grouping control_prefix_list_filter_type {
     leaf list_name {
       description "Name of prefix-list of routes to match";
       type string;
     }
     leaf choice-ident {
       type enumeration {
         enum "exact" {
         }
         enum "longer" {
         }
         enum "orlonger" {
         }
         enum "apply-advanced" {
         }
         enum "metric" {
         }
         enum "metric2" {
         }
         enum "metric3" {
         }
         enum "metric4" {
         }
         enum "tag" {
         }
         enum "tag2" {
         }
         enum "preference" {
         }
         enum "preference2" {
         }
         enum "color" {
         }
         enum "color2" {
         }
         enum "local-preference" {
         }
         enum "priority" {
         }
         enum "prefix-segment" {
         }
         enum "label-allocation" {
         }
         enum "add-path" {
         }
         enum "validation-state" {
         }
         enum "origin" {
         }
         enum "aigp-originate" {
         }
         enum "aigp-adjust" {
         }
         enum "community" {
         }
         enum "damping" {
         }
         enum "aggregate-bandwidth" {
         }
         enum "limit-bandwidth" {
         }
         enum "no-entropy-label-capability" {
         }
         enum "as-path-prepend" {
         }
         enum "as-path-expand" {
         }
         enum "next-hop" {
         }
         enum "install-nexthop" {
         }
         enum "trace" {
         }
         enum "external" {
         }
         enum "load-balance" {
         }
         enum "no-route-localize" {
         }
         enum "install-to-fib" {
         }
         enum "analyze" {
         }
         enum "class" {
         }
         enum "destination-class" {
         }
         enum "source-class" {
         }
         enum "forwarding-class" {
         }
         enum "map-to-interface" {
         }
         enum "ssm-source" {
         }
         enum "p2mp-lsp-root" {
         }
         enum "cos-next-hop-map" {
         }
         enum "dynamic-tunnel-attributes" {
         }
         enum "selected-mldp-egress" {
         }
         enum "mhop-bfd-port" {
         }
         enum "no-backup" {
         }
         enum "default-action" {
         }
         enum "next" {
         }
         enum "accept_reject" {
         }
         enum "bgp-output-queue-priority" {
         }
         enum "multipath-resolve" {
         }
         enum "label-allocation-fallback-reject" {
         }
       }
     }
     leaf choice-value {
       type string;
     }
     uses apply-advanced;
     container metric {
       description "Metric value";
       uses apply-advanced;
       choice metric_action {
         case case_1 {
           leaf metric {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
         case case_4 {
           container igp {
             presence "enable igp";
             description "Track the IGP metric (BGP only)";
             leaf metric_offset {
               description "Metric offset for MED";
               type union {
                 type int32;
                 type string {
                   pattern "<.*>|$.*";
                 }
               }
             }
           }
         }
         case case_5 {
           container minimum-igp {
             presence "enable minimum-igp";
             description "Track the minimum IGP metric (BGP only)";
             leaf metric_offset {
               description "Metric offset for MED";
               type union {
                 type int32;
                 type string {
                   pattern "<.*>|$.*";
                 }
               }
             }
           }
         }
         case case_6 {
           container expression {
             description "Calculate value based on route metric and metric2";
             uses metric_expression_type;
           }
         }
         case case_7 {
           leaf aigp {
             description "Use aigp, if it exists, to set the IGP metric";
             type empty;
           }
         }
       }
     }
     container metric2 {
       description "Metric value 2";
       uses apply-advanced;
       choice metric_action {
         case case_1 {
           leaf metric2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric3 {
       description "Metric value 3";
       uses apply-advanced;
       choice metric_action {
         case case_1 {
           leaf metric3 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric4 {
       description "Metric value 4";
       uses apply-advanced;
       choice metric_action {
         case case_1 {
           leaf metric4 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag {
       description "Tag string";
       uses apply-advanced;
       choice metric_action {
         case case_1 {
           leaf tag {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag2 {
       description "Tag string 2";
       uses apply-advanced;
       choice metric_action {
         case case_1 {
           leaf tag2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference {
       description "Preference value";
       uses apply-advanced;
       choice metric_action {
         case case_1 {
           leaf preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference2 {
       description "Preference value 2";
       uses apply-advanced;
       choice metric_action {
         case case_1 {
           leaf preference2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color {
       description "Color (preference) value";
       uses apply-advanced;
       choice metric_action {
         case case_1 {
           leaf color {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color2 {
       description "Color (preference) value 2";
       uses apply-advanced;
       choice metric_action {
         case case_1 {
           leaf color2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container local-preference {
       description "Local preference associated with a route";
       uses apply-advanced;
       choice metric_action {
         case case_1 {
           leaf local-preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     leaf priority {
       description "Set priority for route installation";
       type enumeration {
         enum "high" {
           description "Set priority to high";
         }
         enum "medium" {
           description "Set priority to medium";
         }
         enum "low" {
           description "Set priority to low";
         }
       }
     }
     container prefix-segment {
       description "Set prefix segment attributes";
       leaf index {
         description "Set prefix segment index ";
         type union {
           type string {
             pattern "<.*>|$.*";
           }
           type uint32 {
             range "0 .. 199999";
           }
         }
       }
       leaf node-segment {
         description "Set node segment flag for this prefix segment";
         type empty;
       }
     }
     leaf label-allocation {
       description "Set label allocation mode";
       type enumeration {
         enum "per-table" {
           description "Set per-table label allocation mode";
         }
         enum "per-nexthop" {
           description "Set per-nexthop label allocation mode";
         }
         enum "per-table-localize" {
           description "Set per-table-localize label allocation mode";
         }
       }
     }
     container add-path {
       description "Set BGP add-path attributes";
       leaf send-count {
         description "Number of add-paths sent";
         type union {
           type string {
             pattern "<.*>|$.*";
           }
           type uint32 {
             range "2 .. 64";
           }
         }
       }
     }
     leaf validation-state {
       description "Set validation-state of a route";
       type enumeration {
         enum "valid" {
           description "Set validaton-state to valid";
         }
         enum "invalid" {
           description "Set validation-state to invalid";
         }
         enum "unknown" {
           description "Set validation-state to unknown";
         }
       }
     }
     leaf origin {
       description "BGP path origin";
       type enumeration {
         enum "igp" {
           description "Path originated in the local IGP";
         }
         enum "egp" {
           description "Path originated in another AS";
         }
         enum "incomplete" {
           description "Path was learned by some other means";
         }
       }
     }
     container aigp-originate {
       presence "enable aigp-originate";
       description "Originate a BGP AIGP attribute";
       leaf distance {
         description "AIGP distance";
         type union {
           type uint32;
           type string {
             pattern "<.*>|$.*";
           }
         }
       }
     }
     container aigp-adjust {
       description "Adjust a BGP AIGP attribute";
       choice math-op {
         case case_1 {
           leaf add {
             type empty;
           }
         }
         case case_2 {
           leaf subtract {
             type empty;
           }
         }
         case case_3 {
           leaf multiply {
             type empty;
           }
         }
         case case_4 {
           leaf divide {
             type empty;
           }
         }
       }
       choice adjust-value {
         case case_1 {
           leaf user-value {
             description "Adjustment value";
             type union {
               type uint64;
               type string {
                 pattern "<.*>|$.*";
               }
             }
           }
         }
         case case_2 {
           leaf distance-to-protocol-nexthop {
             description "Metric2";
             type empty;
           }
         }
       }
     }
     list community {
       key "choice-ident choice-value community-name";
       ordered-by user;
       description "BGP community properties associated with a route";
       leaf choice-ident {
         type enumeration {
           enum "equal-literal" {
           }
           enum "set" {
           }
           enum "plus-literal" {
           }
           enum "add" {
           }
           enum "minus-literal" {
           }
           enum "delete" {
           }
           enum "community-name" {
           }
         }
       }
       leaf choice-value {
         type string;
       }
       leaf community-name {
         description "Name to identify a BGP community";
         type string;
       }
     }
     leaf damping {
       description "Define BGP route flap damping parameters";
       type string;
     }
     leaf aggregate-bandwidth {
       description "Advertise aggregate outbound link bandwidth";
       type empty;
     }
     leaf limit-bandwidth {
       description "Limit advertised aggregate outbound link bandwidth";
       type union {
         type string {
           pattern "<.*>|$.*";
         }
         type uint32 {
           range "0 .. 4294967295";
         }
       }
     }
     leaf no-entropy-label-capability {
       description "Don't advertise entropy label capability";
       type empty;
     }
     leaf as-path-prepend {
       description "Prepend AS numbers to an AS path (BGP only)";
       type string;
     }
     container as-path-expand {
       description "Prepend AS numbers prior to adding local-as (BGP only)";
       choice aspath_exp_value {
         case case_1 {
           container last-as {
             presence "enable last-as";
             description "Prepend last AS";
             leaf count {
               description "Repeat count";
               type union {
                 type string {
                   pattern "<.*>|$.*";
                 }
                 type uint32 {
                   range "1 .. 32";
                 }
               }
             }
           }
         }
         case case_2 {
           leaf aspath {
             description "AS path string";
             type string;
           }
         }
       }
     }
     container next-hop {
       description "Set the address of the next-hop router";
       choice nexthop_value {
         case case_1 {
           leaf self {
             description "Use a local address as the next-hop address";
             type empty;
           }
         }
         case case_2 {
           leaf peer-address {
             description "Use the remote peer address as the next-hop address";
             type empty;
           }
         }
         case case_3 {
           leaf address {
             description "Next-hop address";
             type jt:ipaddr;
           }
         }
         case case_4 {
           leaf reject {
             description "Use a reject next hop";
             type empty;
           }
         }
         case case_5 {
           leaf discard {
             description "Use a discard next hop";
             type empty;
           }
         }
         case case_6 {
           leaf next-table {
             description "Perform a forwarding lookup in the specified table";
             type string;
           }
         }
       }
     }
     container install-nexthop {
       description "Choose the next hop to be used for forwarding";
       leaf strict {
         description "Do not use any other available next hops";
         type empty;
       }
       choice nexthop-value {
         case case_1 {
           leaf-list lsp {
             ordered-by user;
             description "Next-hop LSP name";
             type string;
           }
         }
         case case_2 {
           leaf-list lsp-regex {
             ordered-by user;
             description "Next-hop LSP name regular expression";
             type string;
           }
         }
         case case_3 {
           leaf-list static-lsp {
             ordered-by user;
             description "Next-hop static LSP name";
             type string;
           }
         }
         case case_4 {
           leaf-list static-lsp-regex {
             ordered-by user;
             description "Next-hop static LSP name regular expression";
             type string;
           }
         }
       }
       container except {
         description "Do not choose to install matching next hops";
         uses apply-advanced;
         choice nexthop-value {
           case case_1 {
             leaf-list lsp {
               ordered-by user;
               description "Next-hop LSP name";
               type string;
             }
           }
           case case_2 {
             leaf-list lsp-regex {
               ordered-by user;
               description "Next-hop LSP name regular expression";
               type string;
             }
           }
           case case_3 {
             leaf-list static-lsp {
               ordered-by user;
               description "Next-hop static LSP name";
               type string;
             }
           }
           case case_4 {
             leaf-list static-lsp-regex {
               ordered-by user;
               description "Next-hop static LSP name regular expression";
               type string;
             }
           }
         }
       }
     }
     leaf trace {
       description "Log matches to a trace file";
       type empty;
     }
     container external {
       presence "enable external";
       description "External route";
       uses apply-advanced;
       leaf type {
         description "OSPF external metric type";
         type union {
           type string {
             pattern "<.*>|$.*";
           }
           type int32 {
             range "1 .. 2";
           }
         }
       }
       leaf nssa-only {
         description "Clear P-bit on lsa type 7";
         type empty;
       }
     }
     container load-balance {
       description "Type of load balancing in forwarding table";
       choice load_balance_type {
         case case_1 {
           leaf per-packet {
             description "Load balance on a per-packet basis";
             type empty;
           }
         }
         case case_2 {
         }
         case case_3 {
         }
         case case_4 {
           leaf consistent-hash {
             description "Give a prefix consistent load-balancing";
             type empty;
           }
         }
         case case_5 {
         }
         case case_6 {
         }
       }
     }
     leaf analyze {
       description "Send to registered controllers for analysis";
       type empty;
     }
     leaf class {
       description "Set class-of-service parameters";
       type string;
     }
     leaf destination-class {
       description "Set destination class in forwarding table";
       type string;
     }
     leaf source-class {
       description "Set source class in forwarding table";
       type string;
     }
     leaf forwarding-class {
       description "Set source or destination class in forwarding table";
       type string;
     }
     container map-to-interface {
       description "Set output logical interface";
       choice map_to_interface_value {
         case case_1 {
           leaf self {
             description "Map the interface to itself";
             type empty;
           }
         }
         case case_2 {
           leaf interface {
             description "Output logical interface";
             type union {
               type jt:interface-name;
               type string {
                 pattern "<.*>|$.*";
               }
             }
           }
         }
       }
     }
     leaf-list ssm-source {
       ordered-by user;
       description "List of Sources for SSM mapping";
       type jt:ipaddr;
     }
     container p2mp-lsp-root {
       description "P2mp lsp root address";
       uses apply-advanced;
       leaf address {
         description "Ipv4 root address";
         type jt:ipv4addr;
       }
     }
     leaf cos-next-hop-map {
       description "Set CoS-based next-hop map in forwarding table";
       type string;
     }
     leaf dynamic-tunnel-attributes {
       description "Choose the dynamic tunnel attributes used for forwarding";
       type string;
     }
     leaf selected-mldp-egress {
       description "This node should act as egress node for MLDP inband signalling";
       type empty;
     }
     leaf mhop-bfd-port {
       description "Use port number 4784 for MPLS-BFD as per RFC5884";
       type empty;
     }
     leaf no-backup {
       description "This prefix should not have backup";
       type empty;
     }
     leaf default-action {
       description "Set default policy action";
       type enumeration {
         enum "accept" {
           description "Accept a route";
         }
         enum "reject" {
           description "Reject a route";
         }
       }
     }
     leaf next {
       description "Skip to next policy or term";
       type enumeration {
         enum "policy" {
           description "Skip to next policy filter";
         }
         enum "term" {
           description "Skip to next term in a policy filter";
         }
       }
     }
     choice accept_reject {
       case case_1 {
         leaf accept {
           description "Accept a route";
           type empty;
         }
       }
       case case_2 {
         leaf reject {
           description "Reject a route";
           type empty;
         }
       }
     }
     container bgp-output-queue-priority {
       description "Set the BGP Update output queue priority.";
       choice class {
         case case_1 {
           leaf priority {
             description "Output queue priority; higher is better";
             type union {
               type string {
                 pattern "<.*>|$.*";
               }
               type uint32 {
                 range "1 .. 16";
               }
             }
           }
         }
         case case_2 {
           leaf expedited {
             description "Expedited queue; highest priority";
             type empty;
           }
         }
       }
     }
     leaf multipath-resolve {
       description "Use all paths for resolution over this prefix";
       type empty;
     }
     leaf label-allocation-fallback-reject {
       description "Suppress prefix export when label allocation fails";
       type empty;
     }
   }
   grouping control_prefix_list_type {
     leaf name {
       description "Name of prefix-list of routes to match";
       type string;
     }
     uses apply-advanced;
   }
   grouping control_route_filter_list_type {
     leaf name {
       description "Name of route-filter-list of routes to match";
       type string;
     }
     uses apply-advanced;
   }
   grouping control_route_filter_type {
     leaf address {
       description "IP address or hostname";
       type jt:ipprefix;
     }
     leaf choice-ident {
       type enumeration {
         enum "exact" {
         }
         enum "longer" {
         }
         enum "orlonger" {
         }
         enum "upto" {
         }
         enum "through" {
         }
         enum "prefix-length-range" {
         }
         enum "address-mask" {
         }
         enum "apply-advanced" {
         }
         enum "label" {
         }
         enum "metric" {
         }
         enum "metric2" {
         }
         enum "metric3" {
         }
         enum "metric4" {
         }
         enum "tag" {
         }
         enum "tag2" {
         }
         enum "preference" {
         }
         enum "preference2" {
         }
         enum "color" {
         }
         enum "color2" {
         }
         enum "local-preference" {
         }
         enum "priority" {
         }
         enum "prefix-segment" {
         }
         enum "label-allocation" {
         }
         enum "add-path" {
         }
         enum "validation-state" {
         }
         enum "origin" {
         }
         enum "aigp-originate" {
         }
         enum "aigp-adjust" {
         }
         enum "community" {
         }
         enum "damping" {
         }
         enum "aggregate-bandwidth" {
         }
         enum "limit-bandwidth" {
         }
         enum "no-entropy-label-capability" {
         }
         enum "as-path-prepend" {
         }
         enum "as-path-expand" {
         }
         enum "next-hop" {
         }
         enum "install-nexthop" {
         }
         enum "trace" {
         }
         enum "external" {
         }
         enum "load-balance" {
         }
         enum "no-route-localize" {
         }
         enum "install-to-fib" {
         }
         enum "analyze" {
         }
         enum "class" {
         }
         enum "destination-class" {
         }
         enum "source-class" {
         }
         enum "forwarding-class" {
         }
         enum "map-to-interface" {
         }
         enum "ssm-source" {
         }
         enum "p2mp-lsp-root" {
         }
         enum "cos-next-hop-map" {
         }
         enum "dynamic-tunnel-attributes" {
         }
         enum "selected-mldp-egress" {
         }
         enum "mhop-bfd-port" {
         }
         enum "no-backup" {
         }
         enum "default-action" {
         }
         enum "next" {
         }
         enum "accept_reject" {
         }
         enum "bgp-output-queue-priority" {
         }
         enum "multipath-resolve" {
         }
         enum "label-allocation-fallback-reject" {
         }
       }
     }
     leaf choice-value {
       type string;
     }
     uses apply-advanced;
     container label {
       description "Set label for BGP LU label allocation";
       choice label_value {
         case case_1 {
           container range {
             description "Label range";
             choice range_value {
               case case_1 {
                 leaf range {
                   description "Label range in <start>:<end> format";
                   type string {
                   }
                 }
               }
             }
           }
         }
         case case_2 {
           leaf label {
             description "Label value";
             type union {
               type string {
                 pattern "<.*>|$.*";
               }
               type uint32 {
                 range "0 .. 1048575";
               }
             }
           }
         }
       }
     }
     container metric {
       description "Metric value";
       uses apply-advanced;
       choice metric_action {
         case case_1 {
           leaf metric {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
         case case_4 {
           container igp {
             presence "enable igp";
             description "Track the IGP metric (BGP only)";
             leaf metric_offset {
               description "Metric offset for MED";
               type union {
                 type int32;
                 type string {
                   pattern "<.*>|$.*";
                 }
               }
             }
           }
         }
         case case_5 {
           container minimum-igp {
             presence "enable minimum-igp";
             description "Track the minimum IGP metric (BGP only)";
             leaf metric_offset {
               description "Metric offset for MED";
               type union {
                 type int32;
                 type string {
                   pattern "<.*>|$.*";
                 }
               }
             }
           }
         }
         case case_6 {
           container expression {
             description "Calculate value based on route metric and metric2";
             uses metric_expression_type;
           }
         }
         case case_7 {
           leaf aigp {
             description "Use aigp, if it exists, to set the IGP metric";
             type empty;
           }
         }
       }
     }
     container metric2 {
       description "Metric value 2";
       uses apply-advanced;
       choice metric_action {
         case case_1 {
           leaf metric2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric3 {
       description "Metric value 3";
       uses apply-advanced;
       choice metric_action {
         case case_1 {
           leaf metric3 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric4 {
       description "Metric value 4";
       uses apply-advanced;
       choice metric_action {
         case case_1 {
           leaf metric4 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag {
       description "Tag string";
       uses apply-advanced;
       choice metric_action {
         case case_1 {
           leaf tag {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag2 {
       description "Tag string 2";
       uses apply-advanced;
       choice metric_action {
         case case_1 {
           leaf tag2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference {
       description "Preference value";
       uses apply-advanced;
       choice metric_action {
         case case_1 {
           leaf preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference2 {
       description "Preference value 2";
       uses apply-advanced;
       choice metric_action {
         case case_1 {
           leaf preference2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color {
       description "Color (preference) value";
       uses apply-advanced;
       choice metric_action {
         case case_1 {
           leaf color {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color2 {
       description "Color (preference) value 2";
       uses apply-advanced;
       choice metric_action {
         case case_1 {
           leaf color2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container local-preference {
       description "Local preference associated with a route";
       uses apply-advanced;
       choice metric_action {
         case case_1 {
           leaf local-preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     leaf priority {
       description "Set priority for route installation";
       type enumeration {
         enum "high" {
           description "Set priority to high";
         }
         enum "medium" {
           description "Set priority to medium";
         }
         enum "low" {
           description "Set priority to low";
         }
       }
     }
     container prefix-segment {
       description "Set prefix segment attributes";
       leaf index {
         description "Set prefix segment index ";
         type union {
           type string {
             pattern "<.*>|$.*";
           }
           type uint32 {
             range "0 .. 199999";
           }
         }
       }
       leaf node-segment {
         description "Set node segment flag for this prefix segment";
         type empty;
       }
     }
     leaf label-allocation {
       description "Set label allocation mode";
       type enumeration {
         enum "per-table" {
           description "Set per-table label allocation mode";
         }
         enum "per-nexthop" {
           description "Set per-nexthop label allocation mode";
         }
         enum "per-table-localize" {
           description "Set per-table-localize label allocation mode";
         }
       }
     }
     container add-path {
       description "Set BGP add-path attributes";
       leaf send-count {
         description "Number of add-paths sent";
         type union {
           type string {
             pattern "<.*>|$.*";
           }
           type uint32 {
             range "2 .. 64";
           }
         }
       }
     }
     leaf validation-state {
       description "Set validation-state of a route";
       type enumeration {
         enum "valid" {
           description "Set validaton-state to valid";
         }
         enum "invalid" {
           description "Set validation-state to invalid";
         }
         enum "unknown" {
           description "Set validation-state to unknown";
         }
       }
     }
     leaf origin {
       description "BGP path origin";
       type enumeration {
         enum "igp" {
           description "Path originated in the local IGP";
         }
         enum "egp" {
           description "Path originated in another AS";
         }
         enum "incomplete" {
           description "Path was learned by some other means";
         }
       }
     }
     container aigp-originate {
       presence "enable aigp-originate";
       description "Originate a BGP AIGP attribute";
       leaf distance {
         description "AIGP distance";
         type union {
           type uint32;
           type string {
             pattern "<.*>|$.*";
           }
         }
       }
     }
     container aigp-adjust {
       description "Adjust a BGP AIGP attribute";
       choice math-op {
         case case_1 {
           leaf add {
             type empty;
           }
         }
         case case_2 {
           leaf subtract {
             type empty;
           }
         }
         case case_3 {
           leaf multiply {
             type empty;
           }
         }
         case case_4 {
           leaf divide {
             type empty;
           }
         }
       }
       choice adjust-value {
         case case_1 {
           leaf user-value {
             description "Adjustment value";
             type union {
               type uint64;
               type string {
                 pattern "<.*>|$.*";
               }
             }
           }
         }
         case case_2 {
           leaf distance-to-protocol-nexthop {
             description "Metric2";
             type empty;
           }
         }
       }
     }
     list community {
       key "choice-ident choice-value community-name";
       ordered-by user;
       description "BGP community properties associated with a route";
       leaf choice-ident {
         type enumeration {
           enum "equal-literal" {
           }
           enum "set" {
           }
           enum "plus-literal" {
           }
           enum "add" {
           }
           enum "minus-literal" {
           }
           enum "delete" {
           }
           enum "community-name" {
           }
         }
       }
       leaf choice-value {
         type string;
       }
       leaf community-name {
         description "Name to identify a BGP community";
         type string;
       }
     }
     leaf damping {
       description "Define BGP route flap damping parameters";
       type string;
     }
     leaf aggregate-bandwidth {
       description "Advertise aggregate outbound link bandwidth";
       type empty;
     }
     leaf limit-bandwidth {
       description "Limit advertised aggregate outbound link bandwidth";
       type union {
         type string {
           pattern "<.*>|$.*";
         }
         type uint32 {
           range "0 .. 4294967295";
         }
       }
     }
     leaf no-entropy-label-capability {
       description "Don't advertise entropy label capability";
       type empty;
     }
     leaf as-path-prepend {
       description "Prepend AS numbers to an AS path (BGP only)";
       type string;
     }
     container as-path-expand {
       description "Prepend AS numbers prior to adding local-as (BGP only)";
       choice aspath_exp_value {
         case case_1 {
           container last-as {
             presence "enable last-as";
             description "Prepend last AS";
             leaf count {
               description "Repeat count";
               type union {
                 type string {
                   pattern "<.*>|$.*";
                 }
                 type uint32 {
                   range "1 .. 32";
                 }
               }
             }
           }
         }
         case case_2 {
           leaf aspath {
             description "AS path string";
             type string;
           }
         }
       }
     }
     container next-hop {
       description "Set the address of the next-hop router";
       choice nexthop_value {
         case case_1 {
           leaf self {
             description "Use a local address as the next-hop address";
             type empty;
           }
         }
         case case_2 {
           leaf peer-address {
             description "Use the remote peer address as the next-hop address";
             type empty;
           }
         }
         case case_3 {
           leaf address {
             description "Next-hop address";
             type jt:ipaddr;
           }
         }
         case case_4 {
           leaf reject {
             description "Use a reject next hop";
             type empty;
           }
         }
         case case_5 {
           leaf discard {
             description "Use a discard next hop";
             type empty;
           }
         }
         case case_6 {
           leaf next-table {
             description "Perform a forwarding lookup in the specified table";
             type string;
           }
         }
       }
     }
     container install-nexthop {
       description "Choose the next hop to be used for forwarding";
       leaf strict {
         description "Do not use any other available next hops";
         type empty;
       }
       choice nexthop-value {
         case case_1 {
           leaf-list lsp {
             ordered-by user;
             description "Next-hop LSP name";
             type string;
           }
         }
         case case_2 {
           leaf-list lsp-regex {
             ordered-by user;
             description "Next-hop LSP name regular expression";
             type string;
           }
         }
         case case_3 {
           leaf-list static-lsp {
             ordered-by user;
             description "Next-hop static LSP name";
             type string;
           }
         }
         case case_4 {
           leaf-list static-lsp-regex {
             ordered-by user;
             description "Next-hop static LSP name regular expression";
             type string;
           }
         }
       }
       container except {
         description "Do not choose to install matching next hops";
         uses apply-advanced;
         choice nexthop-value {
           case case_1 {
             leaf-list lsp {
               ordered-by user;
               description "Next-hop LSP name";
               type string;
             }
           }
           case case_2 {
             leaf-list lsp-regex {
               ordered-by user;
               description "Next-hop LSP name regular expression";
               type string;
             }
           }
           case case_3 {
             leaf-list static-lsp {
               ordered-by user;
               description "Next-hop static LSP name";
               type string;
             }
           }
           case case_4 {
             leaf-list static-lsp-regex {
               ordered-by user;
               description "Next-hop static LSP name regular expression";
               type string;
             }
           }
         }
       }
     }
     leaf trace {
       description "Log matches to a trace file";
       type empty;
     }
     container external {
       presence "enable external";
       description "External route";
       uses apply-advanced;
       leaf type {
         description "OSPF external metric type";
         type union {
           type string {
             pattern "<.*>|$.*";
           }
           type int32 {
             range "1 .. 2";
           }
         }
       }
       leaf nssa-only {
         description "Clear P-bit on lsa type 7";
         type empty;
       }
     }
     container load-balance {
       description "Type of load balancing in forwarding table";
       choice load_balance_type {
         case case_1 {
           leaf per-packet {
             description "Load balance on a per-packet basis";
             type empty;
           }
         }
         case case_2 {
         }
         case case_3 {
         }
         case case_4 {
           leaf consistent-hash {
             description "Give a prefix consistent load-balancing";
             type empty;
           }
         }
         case case_5 {
         }
         case case_6 {
         }
       }
     }
     leaf analyze {
       description "Send to registered controllers for analysis";
       type empty;
     }
     leaf class {
       description "Set class-of-service parameters";
       type string;
     }
     leaf destination-class {
       description "Set destination class in forwarding table";
       type string;
     }
     leaf source-class {
       description "Set source class in forwarding table";
       type string;
     }
     leaf forwarding-class {
       description "Set source or destination class in forwarding table";
       type string;
     }
     container map-to-interface {
       description "Set output logical interface";
       choice map_to_interface_value {
         case case_1 {
           leaf self {
             description "Map the interface to itself";
             type empty;
           }
         }
         case case_2 {
           leaf interface {
             description "Output logical interface";
             type union {
               type jt:interface-name;
               type string {
                 pattern "<.*>|$.*";
               }
             }
           }
         }
       }
     }
     leaf-list ssm-source {
       ordered-by user;
       description "List of Sources for SSM mapping";
       type jt:ipaddr;
     }
     container p2mp-lsp-root {
       description "P2mp lsp root address";
       uses apply-advanced;
       leaf address {
         description "Ipv4 root address";
         type jt:ipv4addr;
       }
     }
     leaf cos-next-hop-map {
       description "Set CoS-based next-hop map in forwarding table";
       type string;
     }
     leaf dynamic-tunnel-attributes {
       description "Choose the dynamic tunnel attributes used for forwarding";
       type string;
     }
     leaf selected-mldp-egress {
       description "This node should act as egress node for MLDP inband signalling";
       type empty;
     }
     leaf mhop-bfd-port {
       description "Use port number 4784 for MPLS-BFD as per RFC5884";
       type empty;
     }
     leaf no-backup {
       description "This prefix should not have backup";
       type empty;
     }
     leaf default-action {
       description "Set default policy action";
       type enumeration {
         enum "accept" {
           description "Accept a route";
         }
         enum "reject" {
           description "Reject a route";
         }
       }
     }
     leaf next {
       description "Skip to next policy or term";
       type enumeration {
         enum "policy" {
           description "Skip to next policy filter";
         }
         enum "term" {
           description "Skip to next term in a policy filter";
         }
       }
     }
     choice accept_reject {
       case case_1 {
         leaf accept {
           description "Accept a route";
           type empty;
         }
       }
       case case_2 {
         leaf reject {
           description "Reject a route";
           type empty;
         }
       }
     }
     container bgp-output-queue-priority {
       description "Set the BGP Update output queue priority.";
       choice class {
         case case_1 {
           leaf priority {
             description "Output queue priority; higher is better";
             type union {
               type string {
                 pattern "<.*>|$.*";
               }
               type uint32 {
                 range "1 .. 16";
               }
             }
           }
         }
         case case_2 {
           leaf expedited {
             description "Expedited queue; highest priority";
             type empty;
           }
         }
       }
     }
     leaf multipath-resolve {
       description "Use all paths for resolution over this prefix";
       type empty;
     }
     leaf label-allocation-fallback-reject {
       description "Suppress prefix export when label allocation fails";
       type empty;
     }
   }
   grouping control_rtf_prefix_list_type {
     description "RTF prefix list";
     leaf name {
       description "Name of rtf-prefix-list of routes to match";
       type string;
     }
     uses apply-advanced;
   }
   grouping control_source_address_filter_list_type {
     leaf name {
       description "Name of source-address-filter-list of routes to match";
       type string;
     }
     uses apply-advanced;
   }
   grouping control_source_address_filter_type {
     leaf address {
       description "IP address or hostname";
       type jt:ipprefix;
     }
     leaf choice-ident {
       type enumeration {
         enum "exact" {
         }
         enum "longer" {
         }
         enum "orlonger" {
         }
         enum "upto" {
         }
         enum "through" {
         }
         enum "prefix-length-range" {
         }
         enum "apply-advanced" {
         }
         enum "metric" {
         }
         enum "metric2" {
         }
         enum "metric3" {
         }
         enum "metric4" {
         }
         enum "tag" {
         }
         enum "tag2" {
         }
         enum "preference" {
         }
         enum "preference2" {
         }
         enum "color" {
         }
         enum "color2" {
         }
         enum "local-preference" {
         }
         enum "priority" {
         }
         enum "prefix-segment" {
         }
         enum "label-allocation" {
         }
         enum "add-path" {
         }
         enum "validation-state" {
         }
         enum "origin" {
         }
         enum "aigp-originate" {
         }
         enum "aigp-adjust" {
         }
         enum "community" {
         }
         enum "damping" {
         }
         enum "aggregate-bandwidth" {
         }
         enum "limit-bandwidth" {
         }
         enum "no-entropy-label-capability" {
         }
         enum "as-path-prepend" {
         }
         enum "as-path-expand" {
         }
         enum "next-hop" {
         }
         enum "install-nexthop" {
         }
         enum "trace" {
         }
         enum "external" {
         }
         enum "load-balance" {
         }
         enum "no-route-localize" {
         }
         enum "install-to-fib" {
         }
         enum "analyze" {
         }
         enum "class" {
         }
         enum "destination-class" {
         }
         enum "source-class" {
         }
         enum "forwarding-class" {
         }
         enum "map-to-interface" {
         }
         enum "ssm-source" {
         }
         enum "p2mp-lsp-root" {
         }
         enum "cos-next-hop-map" {
         }
         enum "dynamic-tunnel-attributes" {
         }
         enum "selected-mldp-egress" {
         }
         enum "mhop-bfd-port" {
         }
         enum "no-backup" {
         }
         enum "default-action" {
         }
         enum "next" {
         }
         enum "accept_reject" {
         }
         enum "bgp-output-queue-priority" {
         }
         enum "multipath-resolve" {
         }
         enum "label-allocation-fallback-reject" {
         }
       }
     }
     leaf choice-value {
       type string;
     }
     uses apply-advanced;
     container metric {
       description "Metric value";
       uses apply-advanced;
       choice metric_action {
         case case_1 {
           leaf metric {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
         case case_4 {
           container igp {
             presence "enable igp";
             description "Track the IGP metric (BGP only)";
             leaf metric_offset {
               description "Metric offset for MED";
               type union {
                 type int32;
                 type string {
                   pattern "<.*>|$.*";
                 }
               }
             }
           }
         }
         case case_5 {
           container minimum-igp {
             presence "enable minimum-igp";
             description "Track the minimum IGP metric (BGP only)";
             leaf metric_offset {
               description "Metric offset for MED";
               type union {
                 type int32;
                 type string {
                   pattern "<.*>|$.*";
                 }
               }
             }
           }
         }
         case case_6 {
           container expression {
             description "Calculate value based on route metric and metric2";
             uses metric_expression_type;
           }
         }
         case case_7 {
           leaf aigp {
             description "Use aigp, if it exists, to set the IGP metric";
             type empty;
           }
         }
       }
     }
     container metric2 {
       description "Metric value 2";
       uses apply-advanced;
       choice metric_action {
         case case_1 {
           leaf metric2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric3 {
       description "Metric value 3";
       uses apply-advanced;
       choice metric_action {
         case case_1 {
           leaf metric3 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric4 {
       description "Metric value 4";
       uses apply-advanced;
       choice metric_action {
         case case_1 {
           leaf metric4 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag {
       description "Tag string";
       uses apply-advanced;
       choice metric_action {
         case case_1 {
           leaf tag {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag2 {
       description "Tag string 2";
       uses apply-advanced;
       choice metric_action {
         case case_1 {
           leaf tag2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference {
       description "Preference value";
       uses apply-advanced;
       choice metric_action {
         case case_1 {
           leaf preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference2 {
       description "Preference value 2";
       uses apply-advanced;
       choice metric_action {
         case case_1 {
           leaf preference2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color {
       description "Color (preference) value";
       uses apply-advanced;
       choice metric_action {
         case case_1 {
           leaf color {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color2 {
       description "Color (preference) value 2";
       uses apply-advanced;
       choice metric_action {
         case case_1 {
           leaf color2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container local-preference {
       description "Local preference associated with a route";
       uses apply-advanced;
       choice metric_action {
         case case_1 {
           leaf local-preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     leaf priority {
       description "Set priority for route installation";
       type enumeration {
         enum "high" {
           description "Set priority to high";
         }
         enum "medium" {
           description "Set priority to medium";
         }
         enum "low" {
           description "Set priority to low";
         }
       }
     }
     container prefix-segment {
       description "Set prefix segment attributes";
       leaf index {
         description "Set prefix segment index ";
         type union {
           type string {
             pattern "<.*>|$.*";
           }
           type uint32 {
             range "0 .. 199999";
           }
         }
       }
       leaf node-segment {
         description "Set node segment flag for this prefix segment";
         type empty;
       }
     }
     leaf label-allocation {
       description "Set label allocation mode";
       type enumeration {
         enum "per-table" {
           description "Set per-table label allocation mode";
         }
         enum "per-nexthop" {
           description "Set per-nexthop label allocation mode";
         }
         enum "per-table-localize" {
           description "Set per-table-localize label allocation mode";
         }
       }
     }
     container add-path {
       description "Set BGP add-path attributes";
       leaf send-count {
         description "Number of add-paths sent";
         type union {
           type string {
             pattern "<.*>|$.*";
           }
           type uint32 {
             range "2 .. 64";
           }
         }
       }
     }
     leaf validation-state {
       description "Set validation-state of a route";
       type enumeration {
         enum "valid" {
           description "Set validaton-state to valid";
         }
         enum "invalid" {
           description "Set validation-state to invalid";
         }
         enum "unknown" {
           description "Set validation-state to unknown";
         }
       }
     }
     leaf origin {
       description "BGP path origin";
       type enumeration {
         enum "igp" {
           description "Path originated in the local IGP";
         }
         enum "egp" {
           description "Path originated in another AS";
         }
         enum "incomplete" {
           description "Path was learned by some other means";
         }
       }
     }
     container aigp-originate {
       presence "enable aigp-originate";
       description "Originate a BGP AIGP attribute";
       leaf distance {
         description "AIGP distance";
         type union {
           type uint32;
           type string {
             pattern "<.*>|$.*";
           }
         }
       }
     }
     container aigp-adjust {
       description "Adjust a BGP AIGP attribute";
       choice math-op {
         case case_1 {
           leaf add {
             type empty;
           }
         }
         case case_2 {
           leaf subtract {
             type empty;
           }
         }
         case case_3 {
           leaf multiply {
             type empty;
           }
         }
         case case_4 {
           leaf divide {
             type empty;
           }
         }
       }
       choice adjust-value {
         case case_1 {
           leaf user-value {
             description "Adjustment value";
             type union {
               type uint64;
               type string {
                 pattern "<.*>|$.*";
               }
             }
           }
         }
         case case_2 {
           leaf distance-to-protocol-nexthop {
             description "Metric2";
             type empty;
           }
         }
       }
     }
     list community {
       key "choice-ident choice-value community-name";
       ordered-by user;
       description "BGP community properties associated with a route";
       leaf choice-ident {
         type enumeration {
           enum "equal-literal" {
           }
           enum "set" {
           }
           enum "plus-literal" {
           }
           enum "add" {
           }
           enum "minus-literal" {
           }
           enum "delete" {
           }
           enum "community-name" {
           }
         }
       }
       leaf choice-value {
         type string;
       }
       leaf community-name {
         description "Name to identify a BGP community";
         type string;
       }
     }
     leaf damping {
       description "Define BGP route flap damping parameters";
       type string;
     }
     leaf aggregate-bandwidth {
       description "Advertise aggregate outbound link bandwidth";
       type empty;
     }
     leaf limit-bandwidth {
       description "Limit advertised aggregate outbound link bandwidth";
       type union {
         type string {
           pattern "<.*>|$.*";
         }
         type uint32 {
           range "0 .. 4294967295";
         }
       }
     }
     leaf no-entropy-label-capability {
       description "Don't advertise entropy label capability";
       type empty;
     }
     leaf as-path-prepend {
       description "Prepend AS numbers to an AS path (BGP only)";
       type string;
     }
     container as-path-expand {
       description "Prepend AS numbers prior to adding local-as (BGP only)";
       choice aspath_exp_value {
         case case_1 {
           container last-as {
             presence "enable last-as";
             description "Prepend last AS";
             leaf count {
               description "Repeat count";
               type union {
                 type string {
                   pattern "<.*>|$.*";
                 }
                 type uint32 {
                   range "1 .. 32";
                 }
               }
             }
           }
         }
         case case_2 {
           leaf aspath {
             description "AS path string";
             type string;
           }
         }
       }
     }
     container next-hop {
       description "Set the address of the next-hop router";
       choice nexthop_value {
         case case_1 {
           leaf self {
             description "Use a local address as the next-hop address";
             type empty;
           }
         }
         case case_2 {
           leaf peer-address {
             description "Use the remote peer address as the next-hop address";
             type empty;
           }
         }
         case case_3 {
           leaf address {
             description "Next-hop address";
             type jt:ipaddr;
           }
         }
         case case_4 {
           leaf reject {
             description "Use a reject next hop";
             type empty;
           }
         }
         case case_5 {
           leaf discard {
             description "Use a discard next hop";
             type empty;
           }
         }
         case case_6 {
           leaf next-table {
             description "Perform a forwarding lookup in the specified table";
             type string;
           }
         }
       }
     }
     container install-nexthop {
       description "Choose the next hop to be used for forwarding";
       leaf strict {
         description "Do not use any other available next hops";
         type empty;
       }
       choice nexthop-value {
         case case_1 {
           leaf-list lsp {
             ordered-by user;
             description "Next-hop LSP name";
             type string;
           }
         }
         case case_2 {
           leaf-list lsp-regex {
             ordered-by user;
             description "Next-hop LSP name regular expression";
             type string;
           }
         }
         case case_3 {
           leaf-list static-lsp {
             ordered-by user;
             description "Next-hop static LSP name";
             type string;
           }
         }
         case case_4 {
           leaf-list static-lsp-regex {
             ordered-by user;
             description "Next-hop static LSP name regular expression";
             type string;
           }
         }
       }
       container except {
         description "Do not choose to install matching next hops";
         uses apply-advanced;
         choice nexthop-value {
           case case_1 {
             leaf-list lsp {
               ordered-by user;
               description "Next-hop LSP name";
               type string;
             }
           }
           case case_2 {
             leaf-list lsp-regex {
               ordered-by user;
               description "Next-hop LSP name regular expression";
               type string;
             }
           }
           case case_3 {
             leaf-list static-lsp {
               ordered-by user;
               description "Next-hop static LSP name";
               type string;
             }
           }
           case case_4 {
             leaf-list static-lsp-regex {
               ordered-by user;
               description "Next-hop static LSP name regular expression";
               type string;
             }
           }
         }
       }
     }
     leaf trace {
       description "Log matches to a trace file";
       type empty;
     }
     container external {
       presence "enable external";
       description "External route";
       uses apply-advanced;
       leaf type {
         description "OSPF external metric type";
         type union {
           type string {
             pattern "<.*>|$.*";
           }
           type int32 {
             range "1 .. 2";
           }
         }
       }
       leaf nssa-only {
         description "Clear P-bit on lsa type 7";
         type empty;
       }
     }
     container load-balance {
       description "Type of load balancing in forwarding table";
       choice load_balance_type {
         case case_1 {
           leaf per-packet {
             description "Load balance on a per-packet basis";
             type empty;
           }
         }
         case case_2 {
         }
         case case_3 {
         }
         case case_4 {
           leaf consistent-hash {
             description "Give a prefix consistent load-balancing";
             type empty;
           }
         }
         case case_5 {
         }
         case case_6 {
         }
       }
     }
     leaf analyze {
       description "Send to registered controllers for analysis";
       type empty;
     }
     leaf class {
       description "Set class-of-service parameters";
       type string;
     }
     leaf destination-class {
       description "Set destination class in forwarding table";
       type string;
     }
     leaf source-class {
       description "Set source class in forwarding table";
       type string;
     }
     leaf forwarding-class {
       description "Set source or destination class in forwarding table";
       type string;
     }
     container map-to-interface {
       description "Set output logical interface";
       choice map_to_interface_value {
         case case_1 {
           leaf self {
             description "Map the interface to itself";
             type empty;
           }
         }
         case case_2 {
           leaf interface {
             description "Output logical interface";
             type union {
               type jt:interface-name;
               type string {
                 pattern "<.*>|$.*";
               }
             }
           }
         }
       }
     }
     leaf-list ssm-source {
       ordered-by user;
       description "List of Sources for SSM mapping";
       type jt:ipaddr;
     }
     container p2mp-lsp-root {
       description "P2mp lsp root address";
       uses apply-advanced;
       leaf address {
         description "Ipv4 root address";
         type jt:ipv4addr;
       }
     }
     leaf cos-next-hop-map {
       description "Set CoS-based next-hop map in forwarding table";
       type string;
     }
     leaf dynamic-tunnel-attributes {
       description "Choose the dynamic tunnel attributes used for forwarding";
       type string;
     }
     leaf selected-mldp-egress {
       description "This node should act as egress node for MLDP inband signalling";
       type empty;
     }
     leaf mhop-bfd-port {
       description "Use port number 4784 for MPLS-BFD as per RFC5884";
       type empty;
     }
     leaf no-backup {
       description "This prefix should not have backup";
       type empty;
     }
     leaf default-action {
       description "Set default policy action";
       type enumeration {
         enum "accept" {
           description "Accept a route";
         }
         enum "reject" {
           description "Reject a route";
         }
       }
     }
     leaf next {
       description "Skip to next policy or term";
       type enumeration {
         enum "policy" {
           description "Skip to next policy filter";
         }
         enum "term" {
           description "Skip to next term in a policy filter";
         }
       }
     }
     choice accept_reject {
       case case_1 {
         leaf accept {
           description "Accept a route";
           type empty;
         }
       }
       case case_2 {
         leaf reject {
           description "Reject a route";
           type empty;
         }
       }
     }
     container bgp-output-queue-priority {
       description "Set the BGP Update output queue priority.";
       choice class {
         case case_1 {
           leaf priority {
             description "Output queue priority; higher is better";
             type union {
               type string {
                 pattern "<.*>|$.*";
               }
               type uint32 {
                 range "1 .. 16";
               }
             }
           }
         }
         case case_2 {
           leaf expedited {
             description "Expedited queue; highest priority";
             type empty;
           }
         }
       }
     }
     leaf multipath-resolve {
       description "Use all paths for resolution over this prefix";
       type empty;
     }
     leaf label-allocation-fallback-reject {
       description "Suppress prefix export when label allocation fails";
       type empty;
     }
   }
   grouping juniper-protocols {
     uses apply-advanced;
     container router-advertisement {
       description "IPv6 router advertisement options";
       uses apply-advanced;
       container traceoptions {
         description "Trace options for router advertisement";
         uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
         }
       }
       list interface {
         key name;
         ordered-by user;
         description "Interfaces on which to configure router advertisement";
         leaf name {
           type string;
         }
         uses apply-advanced;
         leaf preference {
           description "Set the Preference for Router Selection";
           type enumeration {
             enum "medium" {
               description "Medium / (Default)";
             }
             enum "high" {
               description "High";
             }
             enum "low" {
               description "Low";
             }
           }
         }
         leaf max-advertisement-interval {
           description "Maximum advertisement interval";
           units "seconds";
           type union {
             type string {
               pattern "<.*>|$.*";
             }
             type uint32 {
               range "4 .. 1800";
             }
           }
         }
         leaf min-advertisement-interval {
           description "Minimum advertisement interval";
           units "seconds";
           type union {
             type string {
               pattern "<.*>|$.*";
             }
             type uint32 {
               range "3 .. 1350";
             }
           }
         }
         choice managed-configuration-choice {
           leaf managed-configuration {
             description "Set managed address configuration";
             type empty;
           }
           leaf no-managed-configuration {
             description "Don't set managed address configuration";
             type empty;
           }
         }
         choice other-stateful-configuration-choice {
           leaf other-stateful-configuration {
             description "Set other stateful configuration";
             type empty;
           }
           leaf no-other-stateful-configuration {
             description "Don't set other stateful configuration";
             type empty;
           }
         }
         choice link-mtu-choice {
           leaf link-mtu {
             description "Link MTU";
             type empty;
           }
           leaf no-link-mtu {
             description "Don't link MTU";
             type empty;
           }
         }
         leaf solicit-router-advertisement-unicast {
           description "Enbale solicited router advertisement as unicast";
           type empty;
         }
         leaf reachable-time {
           description "Reachable time";
           units "milliseconds";
           type union {
             type string {
               pattern "<.*>|$.*";
             }
             type uint32 {
               range "0 .. 3600000";
             }
           }
         }
         leaf retransmit-timer {
           description "Retransmit timer";
           units "milliseconds";
           type union {
             type string {
               pattern "<.*>|$.*";
             }
             type uint32 {
               range "0 .. 4294967295";
             }
           }
         }
         leaf virtual-router-only {
           description "Send advertisemnets only for vrrp-inet6-group";
           type empty;
         }
         leaf current-hop-limit {
           description "Current hop limit";
           type union {
             type string {
               pattern "<.*>|$.*";
             }
             type uint32 {
               range "0 .. 255";
             }
           }
         }
         leaf default-lifetime {
           description "Router lifetime";
           units "seconds";
           type union {
             type string {
               pattern "<.*>|$.*";
             }
             type uint32 {
               range "0 .. 9000";
             }
           }
         }
         list dns-server-address {
           key name;
           ordered-by user;
           description "Recursive DNS address configuration";
           max-elements 3;
           leaf name {
             description "DNS address to be advertised";
             type string;
           }
           uses apply-advanced;
           leaf lifetime {
             description "DNS address lifetime";
             default "1800";
             units "seconds";
             type union {
               type string {
                 pattern "<.*>|$.*";
               }
               type uint32 {
                 range "0 .. 4294967295";
               }
             }
           }
         }
         list prefix {
           key name;
           ordered-by user;
           description "Prefix configuration";
           leaf name {
             description "Prefix to be advertised";
             type jt:ipv6prefix;
           }
           uses apply-advanced;
           leaf valid-lifetime {
             description "Valid lifetime (fixed)";
             units "seconds";
             type union {
               type string {
                 pattern "<.*>|$.*";
               }
               type uint32 {
                 range "0 .. 4294967295";
               }
             }
           }
           choice on-link-choice {
             leaf on-link {
               description "Set on-link flag";
               type empty;
             }
             leaf no-on-link {
               description "Don't set on-link flag";
               type empty;
             }
           }
           leaf preferred-lifetime {
             description "Preferred lifetime (fixed)";
             units "seconds";
             type union {
               type string {
                 pattern "<.*>|$.*";
               }
               type uint32 {
                 range "0 .. 4294967295";
               }
             }
           }
           choice autonomous-choice {
             leaf autonomous {
               description "Set autonomous flag";
               type empty;
             }
             leaf no-autonomous {
               description "Don't set autonomous flag";
               type empty;
             }
           }
         }
       }
       container ra-secure {
         description "Protect box against rogue incoming RA messages";
         uses apply-advanced;
         leaf accept-current-hop-limit-min {
           description "Current hop limit acceptable min for incoming RA";
           units "uint";
           type union {
             type string {
               pattern "<.*>|$.*";
             }
             type uint32 {
               range "1 .. 255";
             }
           }
         }
         leaf accept-current-hop-limit-max {
           description "Current hop acceptable min for incoming RA";
           units "uint";
           type union {
             type string {
               pattern "<.*>|$.*";
             }
             type uint32 {
               range "1 .. 255";
             }
           }
         }
         leaf accept-reachable-time-min {
           description "Reachable Time acceptable min for incoming RA";
           units "milliseconds";
           type union {
             type string {
               pattern "<.*>|$.*";
             }
             type uint32 {
               range "1000 .. 3600000";
             }
           }
         }
         leaf accept-reachable-time-max {
           description "Reachable Time acceptable max for incoming RA";
           units "milliseconds";
           type union {
             type string {
               pattern "<.*>|$.*";
             }
             type uint32 {
               range "1000 .. 3600000";
             }
           }
         }
         leaf accept-retransmit-time-min {
           description "Retransmit Time acceptable min for incoming RA";
           units "milliseconds";
           type union {
             type string {
               pattern "<.*>|$.*";
             }
             type uint32 {
               range "1000 .. 3600000";
             }
           }
         }
         leaf accept-retransmit-time-max {
           description "Retransmit Time acceptable min for incoming RA";
           units "milliseconds";
           type union {
             type string {
               pattern "<.*>|$.*";
             }
             type uint32 {
               range "1000 .. 3600000";
             }
           }
         }
       }
     }
     container neighbor-discovery {
       presence "enable neighbor-discovery";
       description "IPv6 neighbor discovery";
       uses apply-advanced;
       leaf onlink-subnet-only {
         description "Onlink subnet only knob";
         type empty;
       }
       container ndp-proxy {
         description "Configure NDP PROXY behaviour";
         uses apply-advanced;
         leaf no-proxy-on-resolve {
           description "Disable proxy on unresolved address";
           type empty;
         }
       }
       container dad-proxy {
         description "Configure DAD PROXY behaviour";
         uses apply-advanced;
         leaf no-proxy-on-resolve {
           description "Disable proxy on unresolved address";
           type empty;
         }
       }
     }
     container iccp {
       description "ICCP options";
       uses apply-advanced;
       leaf local-ip-addr {
         description "Local IP address to use by default for all peers";
         type jt:ipv4addr;
       }
       leaf session-establishment-hold-time {
         description "Time within which connection must succeed with peers";
         default "300";
         units "seconds";
         type union {
           type string {
             pattern "<.*>|$.*";
           }
           type uint32 {
             range "45 .. 600";
           }
         }
       }
       leaf authentication-key {
         description "MD5 authentication key for all peers";
         type string {
           length "1 .. 126";
         }
       }
       list peer {
         key name;
         description "Redundancy Group Configuration";
         uses peer-group;
       }
       container traceoptions {
         description "Trace options for ICCP";
         uses apply-advanced;
         leaf no-remote-trace {
           description "Disable remote tracing";
           type empty;
         }
         container file {
           description "Trace file information";
           leaf filename {
             description "Name of file in which to write trace information";
             type string {
               length "1 .. 1024";
             }
           }
           leaf size {
             description "Maximum trace file size";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           ordered-by user;
           description "Trace flag information";
           leaf name {
             type enumeration {
               enum "error" {
                 description "Trace all errors";
               }
               enum "event" {
                 description "Trace all events";
               }
               enum "packet" {
                 description "Trace all packets";
               }
               enum "pipe" {
                 description "Trace pipe messages";
               }
               enum "pipe-detail" {
                 description "Trace pipe messages in detail";
               }
               enum "all" {
                 description "Trace everything";
               }
             }
           }
         }
       }
     }
     container ilmi {
       description "Interim Local Management Interface Protocol configuration";
       uses apply-advanced;
       container traceoptions {
         description "ILMI trace options";
         uses apply-advanced;
         leaf no-remote-trace {
           description "Disable remote tracing";
           type empty;
         }
         container file {
           description "Trace file information";
           leaf filename {
             description "Name of file in which to write trace information";
             type string {
               length "1 .. 1024";
             }
           }
           leaf size {
             description "Maximum trace file size";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           ordered-by user;
           description "Tracing parameters";
           leaf name {
             type enumeration {
               enum "database" {
                 description "Trace database events";
               }
               enum "routing-socket" {
                 description "Trace Routing socket events";
               }
               enum "state" {
                 description "Trace state change events";
               }
               enum "debug" {
                 description "Trace debug messages";
               }
               enum "event" {
                 description "Trace event handler events";
               }
               enum "packet" {
                 description "Trace packet events";
               }
               enum "all" {
                 description "Trace all areas of code";
               }
             }
           }
         }
       }
     }
     container lacp {
       description "Link Aggregation Control Protocol configuration";
       uses apply-advanced;
       container traceoptions {
         description "LACP trace options";
         uses apply-advanced;
         leaf no-remote-trace {
           description "Disable remote tracing";
           type empty;
         }
         container file {
           description "Trace file information";
           leaf filename {
             description "Name of file in which to write trace information";
             type string {
               length "1 .. 1024";
             }
           }
           leaf size {
             description "Maximum trace file size";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           ordered-by user;
           description "Events and packet types to include in the trace";
           leaf name {
             type enumeration {
               enum "configuration" {
                 description "Configuration events";
               }
               enum "routing-socket" {
                 description "Routing socket events";
               }
               enum "process" {
                 description "Process events";
               }
               enum "startup" {
                 description "Process startup events";
               }
               enum "protocol" {
                 description "Protocol events";
               }
               enum "packet" {
                 description "LACP packets";
               }
               enum "ppm" {
                 description "LACP PPM messages";
               }
               enum "bfd" {
                 description "LACP BFD events";
               }
               enum "mc-ae" {
                 description "Multi-chassis AE messages";
               }
               enum "all" {
                 description "All events and packets";
               }
             }
           }
         }
       }
       leaf ppm {
         description "Force PPM processing";
         type enumeration {
           enum "centralized" {
             description "Centralized PPM processing";
           }
         }
       }
     }
     container oam {
       description "Operation, Administration, and Management configuration";
       uses apply-advanced;
       container ethernet {
         description "OAM configuration for Ethernet";
         uses apply-advanced;
         container link-fault-management {
           description "802.3ah Ethernet OAM configuration";
           uses apply-advanced;
           container traceoptions {
             description "Trace options for link-fault management";
             uses apply-advanced;
             leaf no-remote-trace {
               description "Disable remote tracing";
               type empty;
             }
             container file {
               description "Trace file information";
               leaf filename {
                 description "Name of file in which to write trace information";
                 type string {
                   length "1 .. 1024";
                 }
               }
               leaf size {
                 description "Maximum trace file size";
                 type string;
               }
               leaf files {
                 description "Maximum number of trace files";
                 default "3";
                 type union {
                   type string {
                     pattern "<.*>|$.*";
                   }
                   type uint32 {
                     range "2 .. 1000";
                   }
                 }
               }
               choice world-readable-choice {
                 leaf world-readable {
                   description "Allow any user to read the log file";
                   type empty;
                 }
                 leaf no-world-readable {
                   description "Don't allow any user to read the log file";
                   type empty;
                 }
               }
               leaf match {
                 description "Regular expression for lines to be logged";
                 type jt:regular-expression;
               }
             }
             list flag {
               key name;
               ordered-by user;
               description "Tracing parameters";
               leaf name {
                 type enumeration {
                   enum "configuration" {
                     description "Trace configuration events";
                   }
                   enum "routing-socket" {
                     description "Trace routing socket events";
                   }
                   enum "protocol" {
                     description "Trace protocol processing events";
                   }
                   enum "action-profile" {
                     description "Trace action profile invocation events";
                   }
                   enum "all" {
                     description "Trace everything";
                   }
                 }
               }
             }
           }
           list action-profile {
             key name;
             ordered-by user;
             description "Define an action profile";
             leaf name {
               description "Name of action profile";
               type string {
                 length "1 .. 32";
               }
             }
             uses apply-advanced;
             container event {
               description "Events this action profile will check";
               uses apply-advanced;
               leaf link-adjacency-loss {
                 description "Loss of adjacency with OAM peer";
                 type empty;
               }
               leaf protocol-down {
                 description "Upper layer indication on protocol down";
                 type empty;
               }
               container link-event-rate {
                 uses apply-advanced;
                 leaf symbol-period {
                   description "Rate of receiving symbol period events";
                   units "error(s) per 100 symbol";
                   type union {
                     type string {
                       pattern "<.*>|$.*";
                     }
                     type int32 {
                       range "1 .. 100";
                     }
                   }
                 }
                 leaf frame-error {
                   description "Rate of receiving frame error events";
                   units "error(s) per 100 milli-second";
                   type union {
                     type string {
                       pattern "<.*>|$.*";
                     }
                     type int32 {
                       range "1 .. 1000";
                     }
                   }
                 }
                 leaf frame-period {
                   description "Rate of receiving frame period events";
                   units "error(s) per 100 frames";
                   type union {
                     type string {
                       pattern "<.*>|$.*";
                     }
                     type int32 {
                       range "1 .. 100";
                     }
                   }
                 }
                 leaf frame-period-summary {
                   description "Rate of receiving frame period summary events";
                   units "error(s) per second";
                   type union {
                     type string {
                       pattern "<.*>|$.*";
                     }
                     type int32 {
                       range "1 .. 1000";
                     }
                   }
                 }
               }
             }
             container action {
               description "Action to take on specified events";
               uses apply-advanced;
               leaf syslog {
                 description "Generate syslog message";
                 type empty;
               }
               leaf link-down {
                 description "Mark the interface down for transit traffic";
                 type empty;
               }
               leaf send-critical-event {
                 description "Start sending OAM PDUs with critical event bit set";
                 type empty;
               }
             }
           }
           list interface {
             key name;
             ordered-by user;
             description "Interface on which to set Ethernet OAM parameters";
             leaf name {
               description "Interface name";
               type union {
                 type jt:interface-device;
                 type string {
                   pattern "<.*>|$.*";
                 }
               }
             }
             uses apply-advanced;
             leaf-list apply-action-profile {
               ordered-by user;
               description "Apply the specified action profile on the interface";
               type string;
             }
             leaf pdu-interval {
               description "Periodic OAM protocol data unit interval";
               default "1000";
               units "milliseconds";
               type union {
                 type string {
                   pattern "<.*>|$.*";
                 }
                 type int32 {
                   range "100 .. 1000";
                 }
               }
             }
             leaf loopback-tracking {
               description "Enable link down on loopback detection";
               type empty;
             }
             leaf detect-loc {
               description "Detects initial lack of adjacency formation";
               type empty;
             }
             leaf link-discovery {
               description "Mode of discovery";
               default "active";
               type enumeration {
                 enum "active" {
                 }
                 enum "passive" {
                 }
               }
             }
             leaf pdu-threshold {
               description "Number of PDUs missed before declaring peer lost";
               default "3";
               type union {
                 type string {
                   pattern "<.*>|$.*";
                 }
                 type int32 {
                   range "3 .. 10";
                 }
               }
             }
             leaf remote-loopback {
               description "Put remote DTE into remote-loopback mode";
               type empty;
             }
             container negotiation-options {
               description "802.3ah features supported on the interface";
               uses apply-advanced;
               leaf no-allow-link-events {
                 description "Do not emit periodic PDUs detailing framing and symbol errors";
                 type empty;
               }
               leaf allow-remote-loopback {
                 description "Allow local port to be put into loopback mode";
                 type empty;
               }
             }
             container event-thresholds {
               description "Thresholds for sending 802.3ah events";
               uses apply-advanced;
               leaf symbol-period {
                 description "Threshold for sending symbol period events";
                 default "1";
                 type union {
                   type string {
                     pattern "<.*>|$.*";
                   }
                   type int32 {
                     range "0 .. 100";
                   }
                 }
               }
               leaf frame-error {
                 description "Threshold for sending frame error events";
                 default "1";
                 type union {
                   type string {
                     pattern "<.*>|$.*";
                   }
                   type int32 {
                     range "0 .. 100";
                   }
                 }
               }
               leaf frame-period {
                 description "Threshold for sending frame period error events";
                 default "1";
                 type union {
                   type string {
                     pattern "<.*>|$.*";
                   }
                   type int32 {
                     range "0 .. 100";
                   }
                 }
               }
               leaf frame-period-summary {
                 description "Threshold for sending frame period summary error events";
                 default "1";
                 type union {
                   type string {
                     pattern "<.*>|$.*";
                   }
                   type int32 {
                     range "0 .. 100";
                   }
                 }
               }
             }
           }
         }
         container connectivity-fault-management {
           description "Configurations related to 802.1ag ethernet oam";
           uses apply-advanced;
           leaf no-aggregate-delegate-processing {
             description "Do not distribute aggregate session to pfe";
             type empty;
           }
           leaf enhanced-cfm-mode {
             description "Enables Enhanced CFM Mode";
             type empty;
           }
           container traceoptions {
             description "Trace options for connectivity fault management";
             presence "enable traceoptions";
             uses cfm-traceoptions;
           }
           list action-profile {
             key name;
             ordered-by user;
             description "Action profiles to use when one or more remote maintenance association endpoints are down";
             leaf name {
               description "Name of action profile";
               type string;
             }
             uses apply-advanced;
             container event {
               description "Events that need to be monitored";
               uses apply-advanced;
               leaf-list interface-status-tlv {
                 ordered-by user;
                 description "Values that need to be monitored in interface status TLV";
                 type enumeration {
                   enum "down" {
                     description "Interface is administratively down";
                   }
                   enum "lower-layer-down" {
                     description "Interface is physically down";
                   }
                 }
               }
               leaf-list port-status-tlv {
                 ordered-by user;
                 description "Values that need to be monitored in port status TLV";
                 type enumeration {
                   enum "blocked" {
                     description "Port is blocked";
                   }
                 }
               }
               leaf adjacency-loss {
                 description "Connectivity is lost";
                 type empty;
               }
               leaf rdi {
                 description "RDI received from some MEP";
                 type empty;
               }
               leaf connection-protection-tlv {
                 description "Values that need to be monitored in connection protection TLV";
                 type enumeration {
                   enum "using-working-path" {
                     description "Service traffic is using working path";
                   }
                   enum "using-protection-path" {
                     description "Service traffic is using protection path";
                   }
                 }
               }
             }
             container action {
               uses apply-advanced;
               leaf interface-down {
                 description "Mark the interface as down";
                 type empty;
               }
               leaf revertive-interface-down {
                 description "Wait for CC loss-threshold to bring back the interface up";
                 type empty;
               }
               leaf non-revertive-interface-down {
                 description "Interface will not be brought up when CC is received";
                 type empty;
               }
               leaf propagate-remote-mac-flush {
                 description "Remote mac-flush";
                 type empty;
               }
               leaf interface-group-down {
                 description "Mark the interface group as down";
                 type empty;
               }
               container log-and-generate-ais {
                 uses apply-advanced;
                 leaf-list level {
                   description "Server maintenance domain levels range";
                   type union {
                     type string {
                       pattern "<.*>|$.*";
                     }
                     type uint32 {
                       range "1 .. 7";
                     }
                   }
                 }
                 leaf interval {
                   description "Interval between AIS messages";
                   default "1s";
                   type enumeration {
                     enum "1s" {
                     }
                     enum "1m" {
                     }
                   }
                 }
                 leaf priority {
                   description "802.1p priority of AIS packet";
                   default "0";
                   type union {
                     type string {
                       pattern "<.*>|$.*";
                     }
                     type uint32 {
                       range "0 .. 7";
                     }
                   }
                 }
               }
             }
             container clear-action {
               uses apply-advanced;
               container interface-down {
                 description "Mark the interface as down";
                 leaf peer-interface {
                   description "Mark the interface as down";
                   type empty;
                 }
               }
               leaf propagate-remote-mac-flush {
                 description "Remote  mac flush";
                 type empty;
               }
             }
             container default-actions {
               description "Action that needs to be taken";
               uses apply-advanced;
               leaf interface-down {
                 description "Bring the interface down";
                 type empty;
               }
             }
           }
           container policer {
             description "Rate limit Ethernet OAM packets for all sessions";
             uses apply-advanced;
             leaf continuity-check {
               description "Policer to rate limit Continuity Check Ethernet OAM messages";
               type string;
             }
             leaf other {
               description "Policer to rate limit non Continuity Check Ethernet OAM messages";
               type string;
             }
             leaf all {
               description "Policer to rate limit all Ethernet OAM messages";
               type string;
             }
           }
           container linktrace {
             presence "enable linktrace";
             description "Linktrace protocol global options";
             uses apply-advanced;
             leaf path-database-size {
               description "Number of linktrace reply entries to be stored per linktrace request";
               default "100";
               type union {
                 type string {
                   pattern "<.*>|$.*";
                 }
                 type uint32 {
                   range "1 .. 255";
                 }
               }
             }
             leaf age {
               description "Time after which a stale request-response entry is deleted";
               default "10m";
               type enumeration {
                 enum "10s" {
                 }
                 enum "30s" {
                 }
                 enum "1m" {
                 }
                 enum "10m" {
                 }
                 enum "30m" {
                 }
               }
             }
           }
           list maintenance-domain {
             key name;
             ordered-by user;
             description "Maintenance domain configuration";
             leaf name {
               type string;
             }
             uses apply-advanced;
             list bridge-domain {
               key name;
               ordered-by user;
               description "Bridge-domain information for the default maintenance domain";
               leaf name {
                 description "Bridge domain name";
                 type string;
               }
               leaf-list vlan-id {
                 ordered-by user;
                 description "VLAN id";
                 type string;
               }
             }
             list vlan {
               key name;
               ordered-by user;
               description "VLAN information for the default maintenance domain";
               leaf name {
                 description "VLAN name";
                 type string;
               }
             }
             list virtual-switch {
               key name;
               ordered-by user;
               description "Virtual switch Bridge-domain information for the default maintenance domain";
               leaf name {
                 description "Routing instance of type virtual switch";
                 type string;
               }
               uses apply-advanced;
               list bridge-domain {
                 key name;
                 ordered-by user;
                 leaf name {
                   description "Bridge domain name";
                   type string;
                 }
                 leaf-list vlan-id {
                   ordered-by user;
                   description "VLAN id";
                   type string;
                 }
               }
             }
             list instance {
               key name;
               ordered-by user;
               description "VPLS instance name for the default maintenance domain";
               leaf name {
                 description "VPLS routing instance name";
                 type string;
               }
             }
             list interface {
               key name;
               ordered-by user;
               description "Name of interface for the default maintenance domain";
               leaf name {
                 description "Interface name";
                 type union {
                   type jt:interface-unit;
                   type string {
                     pattern "<.*>|$.*";
                   }
                 }
               }
             }
             leaf level {
               description "Level value for maintenance domain";
               type union {
                 type string {
                   pattern "<.*>|$.*";
                 }
                 type uint8 {
                   range "0 .. 7";
                 }
               }
             }
             leaf name-format {
               description "Format of maintenance domain name";
               type enumeration {
                 enum "none" {
                   description "No format specified";
                 }
                 enum "dns" {
                   description "Character string similar to Domain Name System name";
                 }
                 enum "mac+2oct" {
                   description "MAC address with 2 octet integer (xx:xx:xx:xx:xx:xx.Y format)";
                 }
                 enum "character-string" {
                   description "Character string";
                 }
               }
             }
             leaf mip-half-function {
               description "Half function to be implemented by MIP";
               default "none";
               type enumeration {
                 enum "none" {
                   description "No MHFs should be created";
                 }
                 enum "default" {
                   description "Create MHF as per IEEE 802.1ag specifications for defMHFDefault";
                 }
                 enum "explicit" {
                   description "Create MHF as per IEEE 802.1ag specifications for defMHFExplicit";
                 }
               }
             }
             list maintenance-association {
               key name;
               ordered-by user;
               description "Maintenance association configuration";
               leaf name {
                 description "Name of maintenance association in IEEE compliant format";
                 type string {
                   length "1 .. 45";
                 }
               }
               uses apply-advanced;
               leaf debug-session {
                 description "Debug the CFM session";
                 type empty;
               }
               leaf short-name-format {
                 description "Format of Maintenance Association Name";
                 type enumeration {
                   enum "2octet" {
                     description "An integer in the range 0..65535";
                   }
                   enum "rfc-2685-vpn-id" {
                     description "VPN identifier that complies with RFC 2685";
                   }
                   enum "vlan" {
                     description "Primary VLAN identifier";
                   }
                   enum "character-string" {
                     description "Character string";
                   }
                   enum "icc" {
                     description "ITU Carrier Code";
                   }
                 }
               }
               leaf primary-vid {
                 description "VLAN id";
                 type string;
               }
               container continuity-check {
                 presence "enable continuity-check";
                 description "Continuity check configuration";
                 uses apply-advanced;
                 leaf interval {
                   description "Interval between continuity-check messages";
                   default "1m";
                   type enumeration {
                     enum "10ms" {
                     }
                     enum "100ms" {
                     }
                     enum "1s" {
                     }
                     enum "10s" {
                     }
                     enum "1m" {
                     }
                     enum "10m" {
                     }
                     enum "3.3ms" {
                     }
                   }
                 }
                 leaf loss-threshold {
                   description "Number of continuity-check messages lost before marking endpoint as down";
                   default "3";
                   type union {
                     type string {
                       pattern "<.*>|$.*";
                     }
                     type uint32 {
                       range "3 .. 256";
                     }
                   }
                 }
                 leaf hold-interval {
                   description "Time before flushing MEP database if no updates occur";
                   default "10";
                   units "minutes";
                   type union {
                     type string {
                       pattern "<.*>|$.*";
                     }
                     type uint32 {
                       range "1 .. 30240";
                     }
                   }
                 }
                 leaf port-status-tlv {
                   description "Include port status TLV in CCM";
                   type empty;
                 }
                 leaf interface-status-tlv {
                   description "Include interface status TLV in CCM";
                   type empty;
                 }
                 leaf connection-protection-tlv {
                   description "Include connection protection OUI TLV in CCM";
                   type empty;
                 }
                 leaf convey-loss-threshold {
                   description "Include Loss Threshold OUI TLV in CCM";
                   type empty;
                 }
                 leaf interface-status-send-rdi {
                   description "Send RDI on interface operation status down in CCM";
                   type empty;
                 }
                 container sendid-tlv {
                   description "Include sendid-tlv in CCM/LBM/LTM";
                   uses apply-advanced;
                   leaf send-chassis-tlv {
                     description "Attach Chassis ID & Mgmt Addr to CCM/LBM/LTM";
                     type empty;
                   }
                 }
               }
               leaf mip-half-function {
                 description "Half function to be implemented by MIP";
                 default "defer";
                 type enumeration {
                   enum "none" {
                     description "No MHFs should be created";
                   }
                   enum "default" {
                     description "Create MHF as per IEEE 802.1ag specifications for defMHFDefault";
                   }
                   enum "explicit" {
                     description "Create MHF as per IEEE 802.1ag specifications for defMHFExplicit";
                   }
                   enum "defer" {
                     description "Create MHF as per IEEE 802.1ag specifications for defMHFDefer";
                   }
                 }
               }
               list mep {
                 key name;
                 ordered-by user;
                 description "Maintenance association endpoint configuration";
                 leaf name {
                   description "Identifier for maintenance association endpoint";
                   type union {
                     type string {
                       pattern "<.*>|$.*";
                     }
                     type uint16 {
                       range "1 .. 8191";
                     }
                   }
                 }
                 uses apply-advanced;
                 container interface {
                   presence "enable interface";
                   description "Name of interface";
                   leaf interface-name {
                     type union {
                       type jt:interface-unit;
                       type string {
                         pattern "<.*>|$.*";
                       }
                     }
                   }
                   leaf vlan {
                     description "Trunk port interface VLAN identifier";
                     type union {
                       type string {
                         pattern "<.*>|$.*";
                       }
                       type uint32 {
                         range "1 .. 4094";
                       }
                     }
                   }
                   choice connection-type {
                     case case_1 {
                       leaf working {
                         description "Monitory the primary path";
                         type empty;
                       }
                     }
                     case case_2 {
                       leaf protect {
                         description "Monitory the protect path";
                         type empty;
                       }
                     }
                   }
                 }
                 leaf direction {
                   description "Direction of maintenance endpoint";
                   default "down";
                   type enumeration {
                     enum "up" {
                     }
                     enum "down" {
                     }
                   }
                 }
                 leaf priority {
                   description "802.1p priority of continuity-check and link-trace packet";
                   default "0";
                   type union {
                     type string {
                       pattern "<.*>|$.*";
                     }
                     type uint32 {
                       range "0 .. 7";
                     }
                   }
                 }
                 leaf auto-discovery {
                   description "Accept continuity-check messages from all remote MEPs";
                   type empty;
                 }
                 leaf action-profile {
                   description "Name of the action profile";
                   type string;
                 }
                 list remote-mep {
                   key name;
                   ordered-by user;
                   description "Remote maintenance association endpoint configuration";
                   leaf name {
                     description "Identifier for remote maintenance association endpoint";
                     type union {
                       type string {
                         pattern "<.*>|$.*";
                       }
                       type uint16 {
                         range "1 .. 8191";
                       }
                     }
                   }
                   uses apply-advanced;
                   leaf action-profile {
                     description "Name of the action profile";
                     type string;
                   }
                   container interface-group {
                     presence "enable interface-group";
                     description "Mark this interface group down Profile configured with action interface-group-down";
                     uses apply-advanced;
                     leaf interface-device-name {
                       description "Interface device name";
                       type union {
                         type jt:interface-device;
                         type string {
                           pattern "<.*>|$.*";
                         }
                       }
                     }
                     leaf-list unit-list {
                       description "One or more logical interface unit numbers";
                       type jt:range;
                     }
                   }
                   list sla-iterator-profile {
                     key name;
                     ordered-by user;
                     description "Name of the iterator profile";
                     leaf name {
                       type string;
                     }
                     uses apply-advanced;
                     leaf iteration-count {
                       description "Iterations to partake for acquiring SLA measurements";
                       units "frames";
                       type union {
                         type string {
                           pattern "<.*>|$.*";
                         }
                         type uint32 {
                           range "1 .. 65535";
                         }
                       }
                     }
                     leaf priority {
                       description "The vlan pcp value to be sent in the Y.1731 frame";
                       type union {
                         type string {
                           pattern "<.*>|$.*";
                         }
                         type uint32 {
                           range "0 .. 7";
                         }
                       }
                     }
                     leaf data-tlv-size {
                       description "Size of the data-tlv portion of Y.1731 frame";
                       units "bytes";
                       type union {
                         type string {
                           pattern "<.*>|$.*";
                         }
                         type uint32 {
                           range "1 .. 1400";
                         }
                       }
                     }
                   }
                   leaf detect-loc {
                     description "Detects initial loss of connectivity with remote mep";
                     type empty;
                   }
                 }
                 leaf lowest-priority-defect {
                   description "Lowest priority defect that is allowed to generate a fault alarm";
                   type enumeration {
                     enum "all-defects" {
                       description "Allows all defects";
                     }
                     enum "mac-rem-err-xcon" {
                       description "Allows only MAC, not receiving CCM, erroneous CCM and cross connect defects";
                     }
                     enum "rem-err-xcon" {
                       description "Allows only not receiving CCM, erroneous CCM and cross connect CCM defects";
                     }
                     enum "err-xcon" {
                       description "Allows only erroneous CCM and cross connect CCM defects";
                     }
                     enum "xcon" {
                       description "Allows only cross connect CCM defect";
                     }
                     enum "no-defect" {
                       description "Allows no defect";
                     }
                   }
                 }
               }
               container policer {
                 description "Rate limit Ethernet OAM packets for this session";
                 uses apply-advanced;
                 leaf continuity-check {
                   description "Policer to rate limit Continuity Check Ethernet OAM messages";
                   type string;
                 }
                 leaf other {
                   description "Policer to rate limit non Continuity Check Ethernet OAM messages";
                   type string;
                 }
                 leaf all {
                   description "Policer to rate limit all Ethernet OAM messages";
                   type string;
                 }
               }
             }
           }
           container sendid-tlv {
             description "Include sendid-tlv in CCM/LBM/LTM";
             uses apply-advanced;
             leaf send-chassis-tlv {
               description "Attach Chassis ID & Mgmt Addr to CCM/LBM/LTM";
               type empty;
             }
           }
         }
         list evcs {
           key name;
           description "Ethernet virtual circuits configuration";
           leaf name {
             description "EVC id";
             type string {
               length "1 .. 100";
             }
           }
           uses apply-advanced;
           container evc-protocol {
             description "Signaling protocol to monitor EVC status";
             choice protocol {
               case case_1 {
                 container cfm {
                   presence "enable cfm";
                   description "Connectivity fault management";
                   leaf maintenance-domain {
                     description "Maintenance domain name";
                     type string;
                   }
                   leaf maintenance-association {
                     description "Maintenance association name";
                     type string;
                   }
                   leaf mep {
                     description "Identifier for maintenance association endpoint";
                     type union {
                       type string {
                         pattern "<.*>|$.*";
                       }
                       type uint16 {
                         range "1 .. 8191";
                       }
                     }
                   }
                 }
               }
               case case_2 {
                 container vpls {
                   presence "enable vpls";
                   description "Virtual private LAN service (BGP/LDP)";
                   leaf routing-instance {
                     description "Routing instance name";
                     type string;
                   }
                 }
               }
               case case_3 {
               }
               case case_4 {
               }
             }
           }
           leaf remote-uni-count {
             description "Number of remote UNIs in the EVC";
             default "1";
             type union {
               type string {
                 pattern "<.*>|$.*";
               }
               type uint8 {
                 range "1 .. 255";
               }
             }
           }
           leaf multipoint-to-multipoint {
             description "Multipoint to Multipoint EVC";
             type empty;
           }
         }
         container lmi {
           presence "enable lmi";
           description "Ethernet local management interface configuration";
           uses apply-advanced;
           container traceoptions {
             description "Trace options for ethernet local management interface";
             uses apply-advanced;
             leaf no-remote-trace {
               description "Disable remote tracing";
               type empty;
             }
             container file {
               description "Trace file information";
               leaf filename {
                 description "Name of file in which to write trace information";
                 type string {
                   length "1 .. 1024";
                 }
               }
               leaf size {
                 description "Maximum trace file size";
                 type string;
               }
               leaf files {
                 description "Maximum number of trace files";
                 default "3";
                 type union {
                   type string {
                     pattern "<.*>|$.*";
                   }
                   type uint32 {
                     range "2 .. 1000";
                   }
                 }
               }
               choice world-readable-choice {
                 leaf world-readable {
                   description "Allow any user to read the log file";
                   type empty;
                 }
                 leaf no-world-readable {
                   description "Don't allow any user to read the log file";
                   type empty;
                 }
               }
               leaf match {
                 description "Regular expression for lines to be logged";
                 type jt:regular-expression;
               }
             }
             list flag {
               key name;
               ordered-by user;
               description "Tracing parameters";
               leaf name {
                 type enumeration {
                   enum "configuration" {
                     description "Trace configuration events";
                   }
                   enum "routing-socket" {
                     description "Trace routing socket events";
                   }
                   enum "protocol" {
                     description "Trace protocol processing events";
                   }
                   enum "init" {
                     description "Trace events related to protocol daemon start-up";
                   }
                   enum "error" {
                     description "Trace events related to catestrophic errors in daemon";
                   }
                   enum "packet" {
                     description "Trace events related to packet flow";
                   }
                   enum "all" {
                     description "Trace everything";
                   }
                 }
               }
             }
           }
           leaf status-counter {
             description "E-LMI status counter (N393)";
             default "4";
             type union {
               type string {
                 pattern "<.*>|$.*";
               }
               type uint8 {
                 range "2 .. 10";
               }
             }
           }
           leaf polling-verification-timer {
             description "Polling verification timer (T392)";
             default "15";
             units "seconds";
             type union {
               type string {
                 pattern "<.*>|$.*";
               }
               type uint8 {
                 range "5 .. 30";
               }
             }
           }
           list interface {
             key name;
             description "Interface options";
             leaf name {
               type union {
                 type jt:interface-device;
                 type string {
                   pattern "<.*>|$.*";
                 }
               }
             }
             uses apply-advanced;
             leaf uni-id {
               description "UNI identifier";
               type string {
                 length "1 .. 64";
               }
             }
             leaf status-counter {
               description "E-LMI status counter (N393)";
               default "4";
               type union {
                 type string {
                   pattern "<.*>|$.*";
                 }
                 type uint8 {
                   range "2 .. 10";
                 }
               }
             }
             leaf polling-verification-timer {
               description "Polling verification timer (T392)";
               default "15";
               units "seconds";
               type union {
                 type string {
                   pattern "<.*>|$.*";
                 }
                 type uint8 {
                   range "5 .. 30";
                 }
               }
             }
             leaf evc-map-type {
               description "CE-VLAN ID/EVC map type";
               default "bundling";
               type enumeration {
                 enum "all-to-one-bundling" {
                   description "All to one bundling";
                 }
                 enum "service-multiplexing" {
                   description "Service multiplexing with no bundling";
                 }
                 enum "bundling" {
                   description "Bundling with service multiplexing";
                 }
               }
             }
             list evc {
               key name;
               description "EVC configuration";
               leaf name {
                 description "EVC identifier";
                 type string {
                   length "1 .. 100";
                 }
               }
               uses apply-advanced;
               leaf default-evc {
                 description "Default EVC";
                 type empty;
               }
               leaf-list vlan-list {
                 description "Vlans mapped to this EVC";
                 type jt:vlan-range;
               }
             }
           }
         }
         container fnp {
           presence "enable fnp";
           description "Failure notification protocol configuration";
           uses apply-advanced;
           container traceoptions {
             description "Tracing options for FNP";
             uses apply-advanced;
             container file {
               description "Trace file options";
               leaf filename {
                 description "Name of file in which to write trace information";
                 type string {
                   length "1 .. 1024";
                 }
               }
               leaf replace {
                 description "Replace trace file rather than appending to it";
                 status deprecated;
                 type empty;
               }
               leaf size {
                 description "Maximum trace file size";
                 type string;
               }
               leaf files {
                 description "Maximum number of trace files";
                 default "10";
                 type union {
                   type string {
                     pattern "<.*>|$.*";
                   }
                   type uint32 {
                     range "2 .. 1000";
                   }
                 }
               }
               leaf no-stamp {
                 description "Do not timestamp trace file";
                 status deprecated;
                 type empty;
               }
               choice world-readable-choice {
                 leaf world-readable {
                   description "Allow any user to read the log file";
                   type empty;
                 }
                 leaf no-world-readable {
                   description "Don't allow any user to read the log file";
                   type empty;
                 }
               }
             }
             list flag {
               key name;
               ordered-by user;
               description "Tracing parameters";
               leaf name {
                 type enumeration {
                   enum "events" {
                     description "Trace protocol events";
                   }
                   enum "pdu" {
                     description "Trace PDU reception and transmission";
                   }
                   enum "timers" {
                     description "Trace protocol timers";
                   }
                   enum "error" {
                     description "Trace all failure conditions";
                   }
                   enum "all" {
                     description "Trace all";
                   }
                 }
               }
             }
           }
           leaf interval {
             description "Interval between FNP messages";
             default "1s";
             type enumeration {
               enum "100ms" {
               }
               enum "1s" {
               }
               enum "10s" {
               }
               enum "1m" {
               }
               enum "10m" {
               }
             }
           }
           leaf loss-threshold {
             description "Number of FNP messages lost before clearing FNP state";
             default "4";
             type union {
               type string {
                 pattern "<.*>|$.*";
               }
               type uint8 {
                 range "3 .. 255";
               }
             }
           }
           list interface {
             key name;
             ordered-by user;
             description "Interface configuration";
             leaf name {
               type union {
                 type jt:interface-name;
                 type string {
                   pattern "<.*>|$.*";
                 }
               }
             }
             uses apply-advanced;
             leaf domain-id {
               description "Ethernet domain identifier";
               default "0";
               type union {
                 type uint32;
                 type string {
                   pattern "<.*>|$.*";
                 }
               }
             }
           }
         }
       }
       container gre-tunnel {
         presence "enable gre-tunnel";
         uses apply-advanced;
         container traceoptions {
           description "Trace options for GRE keepalives";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "configuration" {
                   description "Trace configuration events";
                 }
                 enum "routing-socket" {
                   description "Trace routing socket events";
                 }
                 enum "protocol" {
                   description "Trace protocol processing events";
                 }
                 enum "snmp" {
                   description "Trace snmp processing events";
                 }
                 enum "all" {
                   description "Trace everything";
                 }
               }
             }
           }
         }
         list interface {
           key name;
           ordered-by user;
           leaf name {
             description "Interface name";
             type union {
               type jt:interface-unit;
               type string {
                 pattern "<.*>|$.*";
               }
             }
           }
           uses apply-advanced;
           leaf keepalive-time {
             description "Keepalive time";
             default "1";
             units "seconds";
             type union {
               type string {
                 pattern "<.*>|$.*";
               }
               type int32 {
                 range "1 .. 50";
               }
             }
           }
           leaf hold-time {
             description "Hold time";
             default "5";
             units "seconds";
             type union {
               type string {
                 pattern "<.*>|$.*";
               }
               type int32 {
                 range "5 .. 250";
               }
             }
           }
         }
       }
     }
     container dot1x {
       description "802.1X options";
       uses juniper-protocols-dot1x;
     }
     container ospf {
       description "OSPF configuration";
       uses juniper-protocols-ospf;
     }
     container msdp {
       description "MSDP configuration";
       uses juniper-protocols-msdp;
     }
     container ldp {
       description "LDP options";
       uses juniper-protocols-ldp;
     }
     container bgp {
       description "BGP options";
       uses juniper-protocols-bgp;
     }
     container isis {
       description "IS-IS options";
       uses juniper-protocols-isis;
     }
     container esis {
       description "End system-intermediate system options";
       uses juniper-protocols-esis;
     }
     container ospf3 {
       description "OSPFv3 configuration";
       list realm {
         key name;
         ordered-by user;
         description "OSPFv3 realm configuration";
         leaf name {
           description "OSPFv3 realm name";
           type enumeration {
             enum "ipv6-unicast" {
               description "IPv6 unicast realm";
             }
             enum "ipv6-multicast" {
               description "IPv6 multicast realm";
             }
             enum "ipv4-unicast" {
               description "IPv4 unicast realm";
             }
             enum "ipv4-multicast" {
               description "IPv4 multicast realm";
             }
           }
         }
         uses apply-advanced;
         choice enable-disable {
           case case_1 {
             leaf disable {
               description "Disable OSPF";
               type empty;
             }
           }
         }
         container traceoptions {
           description "Trace options for OSPF";
           uses apply-advanced;
           container file {
             description "Trace file options";
             leaf filename {
               description "Name of file in which to write trace information";
               type string {
                 length "1 .. 1024";
               }
             }
             leaf replace {
               description "Replace trace file rather than appending to it";
               status deprecated;
               type empty;
             }
             leaf size {
               description "Maximum trace file size";
               type string;
             }
             leaf files {
               description "Maximum number of trace files";
               default "10";
               type union {
                 type string {
                   pattern "<.*>|$.*";
                 }
                 type uint32 {
                   range "2 .. 1000";
                 }
               }
             }
             leaf no-stamp {
               description "Do not timestamp trace file";
               status deprecated;
               type empty;
             }
             choice world-readable-choice {
               leaf world-readable {
                 description "Allow any user to read the log file";
                 type empty;
               }
               leaf no-world-readable {
                 description "Don't allow any user to read the log file";
                 type empty;
               }
             }
           }
           list flag {
             key name;
             ordered-by user;
             description "Tracing parameters";
             leaf name {
               type enumeration {
                 enum "spf" {
                   description "Trace SPF calculations";
                 }
                 enum "error" {
                   description "Trace errored packets";
                 }
                 enum "event" {
                   description "Trace OSPF state machine events";
                 }
                 enum "packet-dump" {
                   description "Dump the contents of selected packet types";
                 }
                 enum "flooding" {
                   description "Trace LSA flooding";
                 }
                 enum "lsa-analysis" {
                   description "Trace LSA analysis";
                 }
                 enum "packets" {
                   description "Trace all OSPF packets";
                 }
                 enum "hello" {
                   description "Trace hello packets";
                 }
                 enum "database-description" {
                   description "Trace database description packets";
                 }
                 enum "lsa-request" {
                   description "Trace LSA request packets";
                 }
                 enum "lsa-update" {
                   description "Trace LSA update packets";
                 }
                 enum "lsa-ack" {
                   description "Trace LSA acknowledgment packets";
                 }
                 enum "ldp-synchronization" {
                   description "Trace synchronization between OSPF and LDP";
                 }
                 enum "on-demand" {
                   description "Trace demand circuit extensions";
                 }
                 enum "nsr-synchronization" {
                   description "Trace NSR synchronization events";
                 }
                 enum "graceful-restart" {
                   description "Trace graceful restart";
                 }
                 enum "restart-signaling" {
                   description "Trace restart signaling";
                 }
                 enum "backup-spf" {
                   description "Trace backup SPF (LFA) specific events";
                 }
                 enum "source-packet-routing" {
                   description "Trace source packet routing (SPRING) events";
                 }
                 enum "post-convergence-lfa" {
                   description "Trace post-convergence-lfa related events";
                 }
                 enum "route" {
                   description "Trace routing information";
                 }
                 enum "normal" {
                   description "Trace normal events";
                 }
                 enum "general" {
                   description "Trace general events";
                 }
                 enum "state" {
                   description "Trace state transitions";
                 }
                 enum "policy" {
                   description "Trace policy processing";
                 }
                 enum "task" {
                   description "Trace routing protocol task processing";
                 }
                 enum "timer" {
                   description "Trace routing protocol timer processing";
                 }
                 enum "all" {
                   description "Trace everything";
                 }
               }
             }
             leaf send {
               description "Trace transmitted packets";
               type empty;
             }
             leaf receive {
               description "Trace received packets";
               type empty;
             }
             leaf detail {
               description "Trace detailed information";
               type empty;
             }
             leaf disable {
               description "Disable this trace flag";
               type empty;
             }
           }
         }
         list topology {
           key name;
           ordered-by user;
           description "Topology parameters";
           leaf name {
             description "Topology name";
             type string;
           }
           uses apply-advanced;
           leaf disable {
             description "Disable this topology";
             type empty;
           }
           leaf topology-id {
             description "Topology identifier";
             type union {
               type string {
                 pattern "<.*>|$.*";
               }
               type uint8 {
                 range "32 .. 127";
               }
             }
           }
           leaf overload {
             description "Set the overload mode (repel transit traffic)";
             type empty;
           }
           leaf rib-group {
             description "Routing table group for importing routes";
             type string;
           }
           container spf-options {
             description "Configure options for SPF";
             uses apply-advanced;
             leaf delay {
               description "Time to wait before running an SPF";
               units "milliseconds";
               type union {
                 type string {
                   pattern "<.*>|$.*";
                 }
                 type uint32 {
                   range "50 .. 8000";
                 }
               }
             }
             leaf holddown {
               description "Time to hold down before running an SPF";
               units "milliseconds";
               type union {
                 type string {
                   pattern "<.*>|$.*";
                 }
                 type uint32 {
                   range "2000 .. 20000";
                 }
               }
             }
             leaf rapid-runs {
               description "Number of maximum rapid SPF runs before holddown";
               type union {
                 type string {
                   pattern "<.*>|$.*";
                 }
                 type uint32 {
                   range "1 .. 10";
                 }
               }
             }
             leaf no-ignore-our-externals {
               description "Do not ignore self-generated external and NSSA LSAs";
               type empty;
             }
           }
           container backup-spf-options {
             description "Configure options for backup SPF";
             uses apply-advanced;
             leaf disable {
               description "Do not run backup SPF";
               type empty;
             }
             leaf no-install {
               description "Do not install backup nexthops into the RIB";
               type empty;
             }
             leaf downstream-paths-only {
               description "Use only downstream backup paths";
               type empty;
             }
             container remote-backup-calculation {
               presence "enable remote-backup-calculation";
               description "Calculate Remote LFA backup nexthops";
               uses apply-advanced;
               container pq-nodes-nearest-to-source {
                 description "PQ nodes selection based upon nearest to source";
                 uses apply-advanced;
                 leaf percent {
                   description "Selection percentage for nearest to source";
                   type union {
                     type string {
                       pattern "<.*>|$.*";
                     }
                     type uint32 {
                       range "10 .. 100";
                     }
                   }
                 }
               }
             }
             container use-post-convergence-lfa {
               presence "enable use-post-convergence-lfa";
               description "Calculate post-convergence backup paths";
               uses apply-advanced;
               leaf maximum-labels {
                 description "Maximum number of labels installed for post-convergence paths";
                 type union {
                   type string {
                     pattern "<.*>|$.*";
                   }
                   type uint32 {
                     range "2 .. 5";
                   }
                 }
               }
               leaf maximum-backup-paths {
                 description "Maximum number of equal-cost post-convergence paths installed";
                 type union {
                   type string {
                     pattern "<.*>|$.*";
                   }
                   type uint32 {
                     range "1 .. 8";
                   }
                 }
               }
             }
             container per-prefix-calculation {
               description "Calculate backup nexthops for non-best prefix originators";
               uses apply-advanced;
               leaf stubs {
                 description "Per prefix calculation for stubs only";
                 type empty;
               }
               leaf summary {
                 description "Per prefix calculation for summary originators only";
                 type empty;
               }
               leaf externals {
                 description "Per prefix calculation for externals";
                 type empty;
               }
               leaf all {
                 description "Per prefix calculation for all";
                 type empty;
               }
             }
             leaf node-link-degradation {
               description "Degrade to link protection when nodelink protection not available";
               type empty;
             }
             leaf use-source-packet-routing {
               description "Use spring backup paths for inet.0 routes";
               type empty;
             }
           }
           leaf prefix-export-limit {
             description "Maximum number of prefixes that can be exported";
             type union {
               type string {
                 pattern "<.*>|$.*";
               }
               type uint32 {
                 range "0 .. 4294967295";
               }
             }
           }
         }
         container spf-options {
           description "Configure options for SPF";
           uses apply-advanced;
           leaf delay {
             description "Time to wait before running an SPF";
             units "milliseconds";
             type union {
               type string {
                 pattern "<.*>|$.*";
               }
               type uint32 {
                 range "50 .. 8000";
               }
             }
           }
           leaf holddown {
             description "Time to hold down before running an SPF";
             units "milliseconds";
             type union {
               type string {
                 pattern "<.*>|$.*";
               }
               type uint32 {
                 range "2000 .. 20000";
               }
             }
           }
           leaf rapid-runs {
             description "Number of maximum rapid SPF runs before holddown";
             type union {
               type string {
                 pattern "<.*>|$.*";
               }
               type uint32 {
                 range "1 .. 10";
               }
             }
           }
           leaf no-ignore-our-externals {
             description "Do not ignore self-generated external and NSSA LSAs";
             type empty;
           }
         }
         container backup-spf-options {
           description "Configure options for backup SPF";
           uses apply-advanced;
           leaf disable {
             description "Do not run backup SPF";
             type empty;
           }
           leaf no-install {
             description "Do not install backup nexthops into the RIB";
             type empty;
           }
           leaf downstream-paths-only {
             description "Use only downstream backup paths";
             type empty;
           }
           container remote-backup-calculation {
             presence "enable remote-backup-calculation";
             description "Calculate Remote LFA backup nexthops";
             uses apply-advanced;
             container pq-nodes-nearest-to-source {
               description "PQ nodes selection based upon nearest to source";
               uses apply-advanced;
               leaf percent {
                 description "Selection percentage for nearest to source";
                 type union {
                   type string {
                     pattern "<.*>|$.*";
                   }
                   type uint32 {
                     range "10 .. 100";
                   }
                 }
               }
             }
           }
           container use-post-convergence-lfa {
             presence "enable use-post-convergence-lfa";
             description "Calculate post-convergence backup paths";
             uses apply-advanced;
             leaf maximum-labels {
               description "Maximum number of labels installed for post-convergence paths";
               type union {
                 type string {
                   pattern "<.*>|$.*";
                 }
                 type uint32 {
                   range "2 .. 5";
                 }
               }
             }
             leaf maximum-backup-paths {
               description "Maximum number of equal-cost post-convergence paths installed";
               type union {
                 type string {
                   pattern "<.*>|$.*";
                 }
                 type uint32 {
                   range "1 .. 8";
                 }
               }
             }
           }
           container per-prefix-calculation {
             description "Calculate backup nexthops for non-best prefix originators";
             uses apply-advanced;
             leaf stubs {
               description "Per prefix calculation for stubs only";
               type empty;
             }
             leaf summary {
               description "Per prefix calculation for summary originators only";
               type empty;
             }
             leaf externals {
               description "Per prefix calculation for externals";
               type empty;
             }
             leaf all {
               description "Per prefix calculation for all";
               type empty;
             }
           }
           leaf node-link-degradation {
             description "Degrade to link protection when nodelink protection not available";
             type empty;
           }
           leaf use-source-packet-routing {
             description "Use spring backup paths for inet.0 routes";
             type empty;
           }
         }
         leaf prefix-export-limit {
           description "Maximum number of prefixes that can be exported";
           type union {
             type string {
               pattern "<.*>|$.*";
             }
             type uint32 {
               range "0 .. 4294967295";
             }
           }
         }
         container rib-groups {
           description "Routing table groups for importing OSPF routes";
           uses apply-advanced;
           leaf inet {
             description "Name of the IPv4/v6 routing table group";
             type string;
           }
           leaf inet3 {
             description "Name of the IPv4/v6 inet.3 routing table group";
             type string;
           }
         }
         leaf job-stats {
           description "Collect job statistics";
           type empty;
         }
         container overload {
           presence "enable overload";
           description "Set the overload mode (repel transit traffic)";
           uses apply-advanced;
           leaf timeout {
             description "Time after which overload mode is reset";
             units "seconds";
             type union {
               type string {
                 pattern "<.*>|$.*";
               }
               type uint32 {
                 range "60 .. 1800";
               }
             }
           }
           leaf allow-route-leaking {
             description "Allow routes to be leaked when overload is configured";
             type empty;
           }
           leaf stub-network {
             description "Advertise Stub Network with maximum metric";
             type empty;
           }
           leaf intra-area-prefix {
             description "Advertise Intra Area Prefix with maximum metric";
             type empty;
           }
           leaf as-external {
             description "Advertise As External with maximum usable metric";
             type empty;
           }
         }
         container database-protection {
           presence "enable database-protection";
           description "Configure database protection attributes";
           uses apply-advanced;
           leaf maximum-lsa {
             description "Maximum allowed non self-generated LSAs";
             type union {
               type string {
                 pattern "<.*>|$.*";
               }
               type uint32 {
                 range "1 .. 1000000";
               }
             }
           }
           leaf warning-only {
             description "Emit only a warning when LSA maximum limit is exceeded";
             type empty;
           }
           leaf warning-threshold {
             description "Percentage of LSA maximum above which to trigger warning";
             units "percent";
             type union {
               type string {
                 pattern "<.*>|$.*";
               }
               type uint8 {
                 range "30 .. 100";
               }
             }
           }
           leaf ignore-count {
             description "Maximum number of times to go into ignore state";
             type union {
               type string {
                 pattern "<.*>|$.*";
               }
               type uint8 {
                 range "1 .. 32";
               }
             }
           }
           leaf ignore-time {
             description "Time to stay in ignore state and ignore all neighbors";
             units "seconds";
             type union {
               type string {
                 pattern "<.*>|$.*";
               }
               type uint16 {
                 range "30 .. 3600";
               }
             }
           }
           leaf reset-time {
             description "Time after which the ignore count gets reset to zero";
             units "seconds";
             type union {
               type string {
                 pattern "<.*>|$.*";
               }
               type uint32 {
                 range "60 .. 86400";
               }
             }
           }
         }
         container graceful-restart {
           description "Configure graceful restart attributes";
           uses apply-advanced;
           choice enable-disable {
             case case_1 {
               leaf disable {
                 description "Disable OSPF graceful restart capability";
                 type empty;
               }
             }
           }
           leaf restart-duration {
             description "Time for all neighbors to become full";
             units "seconds";
             type union {
               type string {
                 pattern "<.*>|$.*";
               }
               type uint32 {
                 range "1 .. 3600";
               }
             }
           }
           leaf notify-duration {
             description "Time to send all max-aged grace LSAs";
             units "seconds";
             type union {
               type string {
                 pattern "<.*>|$.*";
               }
               type uint32 {
                 range "1 .. 3600";
               }
             }
           }
           container helper-disable {
             presence "enable helper-disable";
             description "Disable graceful restart helper capability";
             uses apply-advanced;
             choice disable-choices {
               case case_1 {
                 leaf standard {
                   description "Disable helper-mode for rfc3623 based GR";
                   type empty;
                 }
               }
               case case_2 {
                 leaf restart-signaling {
                   description "Disable helper mode for restart-signaling ";
                   type empty;
                 }
               }
               case case_3 {
                 leaf both {
                   description "Disable helper mode for both the types of GR";
                   type empty;
                 }
               }
             }
           }
           leaf no-strict-lsa-checking {
             description "Do not abort graceful helper mode upon LSA changes";
             type empty;
           }
         }
         container traffic-engineering {
           presence "enable traffic-engineering";
           description "Configure traffic engineering attributes";
           uses apply-advanced;
           leaf no-topology {
             description "Disable dissemination of TE link-state topology information";
             type empty;
           }
           leaf multicast-rpf-routes {
             description "Install routes for multicast RPF checks into inet.2";
             type empty;
           }
           leaf igp-topology {
             description "Download IGP topology into TED";
             type empty;
           }
           leaf ignore-lsp-metrics {
             description "Ignore label-switched path metrics when doing shortcuts";
             type empty;
           }
           container shortcuts {
             presence "enable shortcuts";
             description "Use label-switched paths as next hops, if possible";
             uses apply-advanced;
             leaf ignore-lsp-metrics {
               description "Ignore label-switched path metrics when doing shortcuts";
               status deprecated;
               type empty;
             }
             leaf lsp-metric-into-summary {
               description "Advertise LSP metric into summary LSAs";
               type empty;
             }
             list family {
               key name;
               ordered-by user;
               description "Address family specific traffic-engineering attributes";
               leaf name {
                 type enumeration {
                   enum "inet" {
                     description "IPv4 family";
                   }
                   enum "inet-mpls" {
                     description "IPv4-MPLS family";
                   }
                 }
               }
               uses apply-advanced;
             }
           }
           leaf advertise-unnumbered-interfaces {
             description "Advertise unnumbered interfaces";
             type empty;
           }
           leaf credibility-protocol-preference {
             description "TED protocol credibility follows protocol preference";
             type empty;
           }
         }
         leaf route-type-community {
           description "Specify BGP extended community value to encode OSPF route type";
           type enumeration {
             enum "iana" {
               description "BGP extended community value used is 0x0306";
             }
             enum "vendor" {
               description "Vendor BGP extended community value used is 0x8000";
             }
           }
         }
         container domain-id {
           description "Configure domain ID";
           choice domain_id_or_disable {
             case case_1 {
               leaf domain-id {
                 description "Domain ID";
                 type string;
               }
             }
             case case_2 {
               leaf disable {
                 description "Disable domain ID";
                 type empty;
               }
             }
           }
         }
         choice domain_vpn_tag_or_disable {
           case case_1 {
             leaf domain-vpn-tag {
               description "Domain VPN tag for external LSA";
               type union {
                 type string {
                   pattern "<.*>|$.*";
                 }
                 type uint32 {
                   range "0 .. 4294967295";
                 }
               }
             }
           }
           case case_2 {
             leaf no-domain-vpn-tag {
               description "Disable domain VPN tag";
               type empty;
             }
           }
         }
         leaf preference {
           description "Preference of internal routes";
           type union {
             type uint32;
             type string {
               pattern "<.*>|$.*";
             }
           }
         }
         leaf external-preference {
           description "Preference of external routes";
           type union {
             type uint32;
             type string {
               pattern "<.*>|$.*";
             }
           }
         }
         leaf labeled-preference {
           description "Preference of labeled routes";
           type union {
             type uint32;
             type string {
               pattern "<.*>|$.*";
             }
           }
         }
         leaf-list export {
           ordered-by user;
           description "Export policy";
           type jt:policy-algebra;
         }
         leaf-list import {
           ordered-by user;
           description "Import policy (for external routes or setting priority)";
           type jt:policy-algebra;
         }
         leaf reference-bandwidth {
           description "Bandwidth for calculating metric defaults";
           type string;
         }
         leaf lsa-refresh-interval {
           description "LSA refresh interval (minutes)";
           default "50";
           type union {
             type string {
               pattern "<.*>|$.*";
             }
             type uint32 {
               range "25 .. 50";
             }
           }
         }
         leaf spf-delay {
           description "Time to wait before running an SPF";
           status deprecated;
           units "milliseconds";
           type union {
             type string {
               pattern "<.*>|$.*";
             }
             type uint32 {
               range "50 .. 8000";
             }
           }
         }
         leaf no-rfc-1583 {
           description "Disable RFC1583 compatibility";
           type empty;
         }
         container source-packet-routing {
           presence "enable source-packet-routing";
           description "Enable source packet routing (SPRING)";
           uses apply-advanced;
           container adjacency-segment {
             description "Attributes for adjacency segments in spring";
             uses apply-advanced;
             leaf hold-time {
               description "Retain time of Adjacency segment after isolating from an interface";
               type union {
                 type string {
                   pattern "<.*>|$.*";
                 }
                 type uint32 {
                   range "180000 .. 900000";
                 }
               }
             }
           }
           leaf-list prefix-segment {
             ordered-by user;
             description "Prefix Segment policy";
             type jt:policy-algebra;
           }
           leaf explicit-null {
             description "Set E and P bits in all Prefix SID advertisements";
             type empty;
           }
           container node-segment {
             presence "enable node-segment";
             description "Enable support for Node segments in SPRING";
             uses apply-advanced;
             leaf ipv4-index {
               description "Set ipv4 node segment index";
               type union {
                 type string {
                   pattern "<.*>|$.*";
                 }
                 type uint32 {
                   range "0 .. 16383";
                 }
               }
             }
             leaf index-range {
               description "Set range of node segment indices allowed";
               type union {
                 type string {
                   pattern "<.*>|$.*";
                 }
                 type uint32 {
                   range "32 .. 16384";
                 }
               }
             }
           }
           leaf mapping-server {
             description "Mapping server name";
             type string;
           }
           leaf install-prefix-sid-for-best-route {
             description "For best route install a exact prefix sid route";
             type empty;
           }
         }
         leaf forwarding-address-to-broadcast {
           description "Set forwarding address in Type 5 LSA in broadcast network";
           type empty;
         }
         choice nssa-abr-option {
           case case_1 {
             leaf no-nssa-abr {
               description "Disable full NSSA functionality at ABR";
               type empty;
             }
           }
         }
         container sham-link {
           presence "enable sham-link";
           description "Configure parameters for sham links";
           uses apply-advanced;
           leaf local {
             description "Local sham link endpoint address";
             type jt:ipaddr;
           }
           leaf no-advertise-local {
             description "Don't advertise local sham link endpoint as stub in router LSA";
             status deprecated;
             type empty;
           }
         }
         list area {
           key name;
           ordered-by user;
           description "Configure an OSPF area";
           leaf name {
             description "Area ID";
             type jt:areaid;
           }
           uses apply-advanced;
           choice stub-option {
             case case_1 {
               container stub {
                 presence "enable stub";
                 description "Configure a stub area";
                 leaf default-metric {
                   description "Metric for the default route in this stub area";
                   type union {
                     type string {
                       pattern "<.*>|$.*";
                     }
                     type uint32 {
                       range "1 .. 16777215";
                     }
                   }
                 }
                 choice summaries-choice {
                   leaf summaries {
                     description "Flood summary LSAs into this stub area";
                     type empty;
                   }
                   leaf no-summaries {
                     description "Don't flood summary LSAs into this stub area";
                     type empty;
                   }
                 }
               }
             }
             case case_2 {
               container nssa {
                 presence "enable nssa";
                 description "Configure a not-so-stubby area";
                 uses apply-advanced;
                 container default-lsa {
                   presence "enable default-lsa";
                   description "Configure a default LSA";
                   uses apply-advanced;
                   leaf default-metric {
                     description "Metric for the default route in this area";
                     type union {
                       type string {
                         pattern "<.*>|$.*";
                       }
                       type uint32 {
                         range "1 .. 16777215";
                       }
                     }
                   }
                   leaf metric-type {
                     description "External metric type for the default type 7 LSA";
                     type union {
                       type string {
                         pattern "<.*>|$.*";
                       }
                       type uint32 {
                         range "1 .. 2";
                       }
                     }
                   }
                   leaf type-7 {
                     description "Flood type 7 default LSA if no-summaries is configured";
                     type empty;
                   }
                 }
                 leaf default-metric {
                   description "Metric for the default route in this area";
                   status deprecated;
                   type union {
                     type string {
                       pattern "<.*>|$.*";
                     }
                     type uint32 {
                       range "1 .. 16777215";
                     }
                   }
                 }
                 leaf metric-type {
                   description "External metric type for the default type 7 LSA";
                   status deprecated;
                   type union {
                     type string {
                       pattern "<.*>|$.*";
                     }
                     type uint32 {
                       range "1 .. 2";
                     }
                   }
                 }
                 choice summaries-choice {
                   leaf summaries {
                     description "Flood summary LSAs into this NSSA area";
                     type empty;
                   }
                   leaf no-summaries {
                     description "Don't flood summary LSAs into this NSSA area";
                     type empty;
                   }
                 }
                 list area-range {
                   key name;
                   ordered-by user;
                   description "Configure NSSA area ranges";
                   leaf name {
                     description "Range to summarize NSSA routes in this area";
                     type jt:ipprefix;
                   }
                   uses apply-advanced;
                   leaf restrict {
                     description "Restrict advertisement of this area range";
                     type empty;
                   }
                   leaf exact {
                     description "Enforce exact match for advertisement of this area range";
                     type empty;
                   }
                   container override-metric {
                     presence "enable override-metric";
                     description "Override the dynamic metric for this area-range";
                     uses apply-advanced;
                     leaf metric {
                       description "Metric value";
                       type union {
                         type string {
                           pattern "<.*>|$.*";
                         }
                         type uint32 {
                           range "1 .. 16777215";
                         }
                       }
                     }
                     leaf metric-type {
                       description "Set the metric type for the override metric";
                       default "1";
                       type union {
                         type string {
                           pattern "<.*>|$.*";
                         }
                         type uint32 {
                           range "1 .. 2";
                         }
                       }
                     }
                   }
                 }
               }
             }
           }
           list area-range {
             key name;
             ordered-by user;
             description "Configure area ranges";
             leaf name {
               description "Range to summarize routes in this area";
               type jt:ipprefix;
             }
             uses apply-advanced;
             leaf restrict {
               description "Restrict advertisement of this area range";
               type empty;
             }
             leaf exact {
               description "Enforce exact match for advertisement of this area range";
               type empty;
             }
             leaf override-metric {
               description "Override the dynamic metric for this area-range";
               type union {
                 type string {
                   pattern "<.*>|$.*";
                 }
                 type uint32 {
                   range "1 .. 16777215";
                 }
               }
             }
           }
           leaf-list network-summary-export {
             ordered-by user;
             description "Export policy for Type 3 Summary LSAs";
             type jt:policy-algebra;
           }
           leaf-list network-summary-import {
             ordered-by user;
             description "Import policy for Type 3 Summary LSAs";
             type jt:policy-algebra;
           }
           leaf-list inter-area-prefix-export {
             ordered-by user;
             description "Export policy for Inter Area Prefix LSAs";
             type jt:policy-algebra;
           }
           leaf-list inter-area-prefix-import {
             ordered-by user;
             description "Import policy for Inter Area Prefix LSAs";
             type jt:policy-algebra;
           }
           leaf authentication-type {
             description "Authentication type";
             status deprecated;
             type enumeration {
               enum "none" {
                 description "No authentication";
                 status deprecated;
               }
               enum "simple" {
                 description "Simple password authentication";
                 status deprecated;
               }
               enum "md5" {
                 description "MD5 authentication";
                 status deprecated;
               }
             }
           }
           list virtual-link {
             key "neighbor-id transit-area";
             ordered-by user;
             description "Configure virtual links";
             leaf neighbor-id {
               description "Router ID of a virtual neighbor";
               type jt:ipv4addr;
             }
             leaf transit-area {
               description "Transit area in common with virtual neighbor";
               type jt:areaid;
             }
             uses apply-advanced;
             choice enable-disable {
               case case_1 {
                 leaf disable {
                   description "Disable this virtual link";
                   type empty;
                 }
               }
             }
             leaf retransmit-interval {
               description "Retransmission interval (seconds)";
               type union {
                 type string {
                   pattern "<.*>|$.*";
                 }
                 type uint32 {
                   range "1 .. 65535";
                 }
               }
             }
             leaf transit-delay {
               description "Transit delay (seconds)";
               type union {
                 type string {
                   pattern "<.*>|$.*";
                 }
                 type uint32 {
                   range "1 .. 65535";
                 }
               }
             }
             leaf hello-interval {
               description "Hello interval (seconds)";
               type union {
                 type string {
                   pattern "<.*>|$.*";
                 }
                 type uint32 {
                   range "1 .. 255";
                 }
               }
             }
             leaf dead-interval {
               description "Dead interval (seconds)";
               type union {
                 type string {
                   pattern "<.*>|$.*";
                 }
                 type uint32 {
                   range "1 .. 65535";
                 }
               }
             }
             leaf mtu {
               description "Maximum OSPF packet size";
               type union {
                 type string {
                   pattern "<.*>|$.*";
                 }
                 type uint32 {
                   range "128 .. 65535";
                 }
               }
             }
             choice auth {
               case case_1 {
                 container authentication {
                   uses juniper-ospf-authentication;
                 }
               }
               case case_2 {
                 container authentication-key {
                   description "Authentication key";
                   status deprecated;
                   leaf keyname {
                     description "Authentication key value";
                     type jt:unreadable;
                   }
                   leaf key-id {
                     description "Key ID for MD5 authentication";
                     type union {
                       type string {
                         pattern "<.*>|$.*";
                       }
                       type uint32 {
                         range "0 .. 255";
                       }
                     }
                   }
                 }
               }
             }
             leaf demand-circuit {
               description "Interface functions as a demand circuit";
               type empty;
             }
             leaf flood-reduction {
               description "Enable flood reduction";
               type empty;
             }
             leaf no-neighbor-down-notification {
               description "Don't inform other protocols about neighbor down events";
               type empty;
             }
             leaf ipsec-sa {
               description "IPSec security association name";
               type string {
                 length "1 .. 32";
               }
             }
             list topology {
               key name;
               ordered-by user;
               description "Topology specific attributes";
               leaf name {
                 description "Topology name";
                 type string;
               }
               uses apply-advanced;
               leaf disable {
                 description "Disable this topology";
                 type empty;
               }
               leaf metric {
                 description "Topology metric";
                 type union {
                   type string {
                     pattern "<.*>|$.*";
                   }
                   type uint16 {
                     range "1 .. 65535";
                   }
                 }
               }
               container bandwidth-based-metrics {
                 description "Configure bandwidth based metrics";
                 uses apply-advanced;
                 list bandwidth {
                   key name;
                   description "Bandwidth threshold";
                   leaf name {
                     type string;
                   }
                   leaf metric {
                     description "Metric associated with specified bandwidth";
                     type union {
                       type string {
                         pattern "<.*>|$.*";
                       }
                       type uint16 {
                         range "1 .. 65535";
                       }
                     }
                   }
                 }
               }
             }
           }
           list sham-link-remote {
             key name;
             ordered-by user;
             description "Configure parameters for remote sham link endpoint";
             leaf name {
               description "Remote sham link endpoint address";
               type jt:ipaddr;
             }
             uses apply-advanced;
             leaf metric {
               description "Sham link metric";
               type union {
                 type string {
                   pattern "<.*>|$.*";
                 }
                 type uint16 {
                   range "1 .. 65535";
                 }
               }
             }
             leaf ipsec-sa {
               description "IPSec security association name";
               type string {
                 length "1 .. 32";
               }
             }
             leaf demand-circuit {
               description "Interface functions as a demand circuit";
               type empty;
             }
             leaf flood-reduction {
               description "Enable flood reduction";
               type empty;
             }
             list topology {
               key name;
               ordered-by user;
               description "Topology specific attributes";
               leaf name {
                 description "Topology name";
                 type string;
               }
               uses apply-advanced;
               leaf disable {
                 description "Disable this topology";
                 type empty;
               }
               leaf metric {
                 description "Topology metric";
                 type union {
                   type string {
                     pattern "<.*>|$.*";
                   }
                   type uint16 {
                     range "1 .. 65535";
                   }
                 }
               }
               container bandwidth-based-metrics {
                 description "Configure bandwidth based metrics";
                 uses apply-advanced;
                 list bandwidth {
                   key name;
                   description "Bandwidth threshold";
                   leaf name {
                     type string;
                   }
                   leaf metric {
                     description "Metric associated with specified bandwidth";
                     type union {
                       type string {
                         pattern "<.*>|$.*";
                       }
                       type uint16 {
                         range "1 .. 65535";
                       }
                     }
                   }
                 }
               }
             }
           }
           list interface {
             key name;
             ordered-by user;
             description "Include an interface in this area";
             leaf name {
               description "Interface name";
               type union {
                 type jt:ipv4addr-or-interface;
                 type string {
                   pattern "<.*>|$.*";
                 }
               }
             }
             uses apply-advanced;
             choice enable-disable {
               case case_1 {
                 leaf disable {
                   description "Disable OSPF on this interface";
                   type empty;
                 }
               }
             }
             leaf interface-type {
               description "Type of interface";
               type enumeration {
                 enum "nbma" {
                   description "Nonbroadcast multiaccess";
                 }
                 enum "p2mp" {
                   description "Point-to-multipoint NBMA";
                 }
                 enum "p2p" {
                   description "Point-to-point";
                 }
                 enum "p2mp-over-lan" {
                   description "Point-to-multipoint over LAN mode";
                 }
               }
             }
             container post-convergence-lfa {
               presence "enable post-convergence-lfa";
               description "Protect interface using post-convergence backup path";
               uses apply-advanced;
               container node-protection {
                 presence "enable node-protection";
                 description "Compute backup path assuming node failure";
                 uses apply-advanced;
                 leaf cost {
                   description "Cost for node protection";
                   type union {
                     type string {
                       pattern "<.*>|$.*";
                     }
                     type uint16 {
                       range "1 .. 65535";
                     }
                   }
                 }
               }
             }
             choice protection-type {
               case case_1 {
                 leaf link-protection {
                   description "Protect interface from link faults only";
                   type empty;
                 }
               }
               case case_2 {
                 leaf node-link-protection {
                   description "Protect interface from both link and node faults";
                   type empty;
                 }
               }
             }
             leaf no-eligible-backup {
               description "Not eligible to backup traffic from protected interfaces";
               type empty;
             }
             leaf no-eligible-remote-backup {
               description "Not eligible for Remote-LFA backup traffic from protected interfaces";
               type empty;
             }
             container passive {
               presence "enable passive";
               description "Do not run OSPF, but advertise it";
               uses apply-advanced;
               container traffic-engineering {
                 description "Advertise TE link information";
                 uses apply-advanced;
                 leaf remote-node-id {
                   description "Remote address of the link";
                   type jt:ipaddr;
                 }
                 leaf remote-node-router-id {
                   description "TE Router-ID of the remote node";
                   type jt:ipv4addr;
                 }
               }
             }
             leaf secondary {
               description "Treat interface as secondary";
               type empty;
             }
             leaf own-router-lsa {
               description "Generate a separate router LSA for this interface";
               type empty;
             }
             container bandwidth-based-metrics {
               description "Configure bandwidth based metrics";
               uses apply-advanced;
               list bandwidth {
                 key name;
                 description "Bandwidth threshold";
                 leaf name {
                   type string;
                 }
                 leaf metric {
                   description "Metric associated with specified bandwidth";
                   type union {
                     type string {
                       pattern "<.*>|$.*";
                     }
                     type uint16 {
                       range "1 .. 65535";
                     }
                   }
                 }
               }
             }
             leaf metric {
               description "Interface metric";
               type union {
                 type string {
                   pattern "<.*>|$.*";
                 }
                 type uint16 {
                   range "1 .. 65535";
                 }
               }
             }
             leaf te-metric {
               description "Traffic engineering metric";
               type union {
                 type string {
                   pattern "<.*>|$.*";
                 }
                 type uint32 {
                   range "1 .. 4294967295";
                 }
               }
             }
             leaf priority {
               description "Designated router priority";
               type union {
                 type string {
                   pattern "<.*>|$.*";
                 }
                 type uint32 {
                   range "0 .. 255";
                 }
               }
             }
             container ldp-synchronization {
               description "Advertise maximum metric until LDP is operational";
               presence "enable ldp-synchronization";
               uses ldp-sync-obj;
             }
             leaf retransmit-interval {
               description "Retransmission interval (seconds)";
               type union {
                 type string {
                   pattern "<.*>|$.*";
                 }
                 type uint32 {
                   range "1 .. 65535";
                 }
               }
             }
             leaf transit-delay {
               description "Transit delay (seconds)";
               type union {
                 type string {
                   pattern "<.*>|$.*";
                 }
                 type uint32 {
                   range "1 .. 65535";
                 }
               }
             }
             leaf hello-interval {
               description "Hello interval (seconds)";
               type union {
                 type string {
                   pattern "<.*>|$.*";
                 }
                 type uint32 {
                   range "1 .. 255";
                 }
               }
             }
             leaf dead-interval {
               description "Dead interval (seconds)";
               type union {
                 type string {
                   pattern "<.*>|$.*";
                 }
                 type uint32 {
                   range "1 .. 65535";
                 }
               }
             }
             leaf mtu {
               description "Maximum OSPF packet size";
               type union {
                 type string {
                   pattern "<.*>|$.*";
                 }
                 type uint32 {
                   range "128 .. 65535";
                 }
               }
             }
             choice auth {
               case case_1 {
                 container authentication {
                   uses juniper-ospf-authentication;
                 }
               }
               case case_2 {
                 container authentication-key {
                   description "Authentication key";
                   status deprecated;
                   leaf keyname {
                     description "Authentication key value";
                     type jt:unreadable;
                   }
                   leaf key-id {
                     description "Key ID for MD5 authentication";
                     type union {
                       type string {
                         pattern "<.*>|$.*";
                       }
                       type uint32 {
                         range "0 .. 255";
                       }
                     }
                   }
                 }
               }
             }
             leaf demand-circuit {
               description "Interface functions as a demand circuit";
               type empty;
             }
             leaf flood-reduction {
               description "Enable flood reduction";
               type empty;
             }
             leaf no-neighbor-down-notification {
               description "Don't inform other protocols about neighbor down events";
               type empty;
             }
             leaf ipsec-sa {
               description "IPSec security association name";
               type string {
                 length "1 .. 32";
               }
             }
             list topology {
               key name;
               ordered-by user;
               description "Topology specific attributes";
               leaf name {
                 description "Topology name";
                 type string;
               }
               uses apply-advanced;
               leaf disable {
                 description "Disable this topology";
                 type empty;
               }
               leaf metric {
                 description "Topology metric";
                 type union {
                   type string {
                     pattern "<.*>|$.*";
                   }
                   type uint16 {
                     range "1 .. 65535";
                   }
                 }
               }
               container bandwidth-based-metrics {
                 description "Configure bandwidth based metrics";
                 uses apply-advanced;
                 list bandwidth {
                   key name;
                   description "Bandwidth threshold";
                   leaf name {
                     type string;
                   }
                   leaf metric {
                     description "Metric associated with specified bandwidth";
                     type union {
                       type string {
                         pattern "<.*>|$.*";
                       }
                       type uint16 {
                         range "1 .. 65535";
                       }
                     }
                   }
                 }
               }
             }
             leaf transmit-interval {
               description "OSPF packet transmit interval (milliseconds)";
               status deprecated;
               type union {
                 type string {
                   pattern "<.*>|$.*";
                 }
                 type uint32 {
                   range "1 .. 4294967295";
                 }
               }
             }
             container bfd-liveness-detection {
               description "Bidirectional Forwarding Detection options";
               uses apply-advanced;
               leaf version {
                 description "BFD protocol version number";
                 default "automatic";
                 type enumeration {
                   enum "0" {
                     description "BFD version 0 (deprecated)";
                   }
                   enum "1" {
                     description "BFD version 1";
                   }
                   enum "automatic" {
                     description "Choose BFD version automatically";
                   }
                 }
               }
               leaf minimum-interval {
                 description "Minimum transmit and receive interval";
                 units "milliseconds";
                 type union {
                   type string {
                     pattern "<.*>|$.*";
                   }
                   type uint32 {
                     range "1 .. 255000";
                   }
                 }
               }
               leaf minimum-transmit-interval {
                 description "Minimum transmit interval";
                 status deprecated;
                 units "milliseconds";
                 type union {
                   type string {
                     pattern "<.*>|$.*";
                   }
                   type uint32 {
                     range "1 .. 255000";
                   }
                 }
               }
               leaf minimum-receive-interval {
                 description "Minimum receive interval";
                 units "milliseconds";
                 type union {
                   type string {
                     pattern "<.*>|$.*";
                   }
                   type uint32 {
                     range "1 .. 255000";
                   }
                 }
               }
               leaf multiplier {
                 description "Detection time multiplier";
                 default "3";
                 type union {
                   type string {
                     pattern "<.*>|$.*";
                   }
                   type uint32 {
                     range "1 .. 255";
                   }
                 }
               }
               choice adaptation-choice {
                 case case_1 {
                   leaf no-adaptation {
                     description "Disable adaptation";
                     type empty;
                   }
                 }
               }
               container transmit-interval {
                 description "Transmit-interval options";
                 uses apply-advanced;
                 leaf minimum-interval {
                   description "Minimum transmit interval";
                   units "milliseconds";
                   type union {
                     type string {
                       pattern "<.*>|$.*";
                     }
                     type uint32 {
                       range "1 .. 255000";
                     }
                   }
                 }
                 leaf threshold {
                   description "High transmit interval triggering a trap";
                   units "milliseconds";
                   type union {
                     type uint32;
                     type string {
                       pattern "<.*>|$.*";
                     }
                   }
                 }
               }
               container detection-time {
                 description "Detection-time options";
                 uses apply-advanced;
                 leaf threshold {
                   description "High detection-time triggering a trap";
                   units "milliseconds";
                   type union {
                     type uint32;
                     type string {
                       pattern "<.*>|$.*";
                     }
                   }
                 }
               }
               container authentication {
                 description "Authentication options";
                 uses apply-advanced;
                 leaf key-chain {
                   description "Key chain name";
                   type string;
                 }
                 leaf algorithm {
                   description "Algorithm name";
                   type enumeration {
                     enum "simple-password" {
                       description "Simple password";
                     }
                     enum "keyed-md5" {
                       description "Keyed message Digest 5";
                     }
                     enum "meticulous-keyed-md5" {
                       description "Meticulous keyed message Digest 5";
                     }
                     enum "keyed-sha-1" {
                       description "Keyed secure hash algorithm (SHA1) ";
                     }
                     enum "meticulous-keyed-sha-1" {
                       description "Meticulous keyed secure hash algorithm (SHA1) ";
                     }
                   }
                 }
                 leaf loose-check {
                   description "Verify authentication only if authentication is negotiated";
                   type empty;
                 }
               }
               leaf full-neighbors-only {
                 description "Setup BFD sessions only to Full neighbors";
                 type empty;
               }
             }
             leaf dynamic-neighbors {
               description "Learn neighbors dynamically on a p2mp interface";
               type empty;
             }
             leaf no-advertise-adjacency-segment {
               description "Do not advertise an adjacency segment for this interface";
               type empty;
             }
             list neighbor {
               key name;
               ordered-by user;
               description "NBMA neighbor";
               leaf name {
                 description "Address of neighbor";
                 type jt:ipaddr;
               }
               leaf eligible {
                 description "Eligible to be DR on an NBMA network";
                 type empty;
               }
             }
             leaf poll-interval {
               description "Poll interval for NBMA interfaces";
               type union {
                 type string {
                   pattern "<.*>|$.*";
                 }
                 type uint32 {
                   range "1 .. 65535";
                 }
               }
             }
             leaf no-interface-state-traps {
               description "Do not send interface state change traps";
               type empty;
             }
           }
           leaf no-source-packet-routing {
             description "Disable SPRING in this area";
             type empty;
           }
           leaf no-context-identifier-advertisement {
             description "Disable context identifier advertisments in this area";
             type empty;
           }
           list context-identifier {
             key name;
             ordered-by user;
             description "Configure context identifier in support of edge protection";
             leaf name {
               description "Context identifier";
               type jt:ipv4addr;
             }
             uses apply-advanced;
           }
           list label-switched-path {
             key name;
             ordered-by user;
             description "Configuration for advertisement of a label-switched path";
             leaf name {
               description "Name of label-switched path to be advertised";
               type string {
                 length "1 .. 64";
               }
             }
             uses apply-advanced;
             choice enable-disable {
               case case_1 {
                 leaf disable {
                   description "Disable OSPF on this label-switched path";
                   type empty;
                 }
               }
             }
             leaf metric {
               description "Interface metric";
               type union {
                 type string {
                   pattern "<.*>|$.*";
                 }
                 type uint16 {
                   range "1 .. 65535";
                 }
               }
             }
             list topology {
               key name;
               ordered-by user;
               description "Topology specific attributes";
               leaf name {
                 description "Topology name";
                 type string;
               }
               uses apply-advanced;
               leaf disable {
                 description "Disable this topology";
                 type empty;
               }
               leaf metric {
                 description "Topology metric";
                 type union {
                   type string {
                     pattern "<.*>|$.*";
                   }
                   type uint16 {
                     range "1 .. 65535";
                   }
                 }
               }
               container bandwidth-based-metrics {
                 description "Configure bandwidth based metrics";
                 uses apply-advanced;
                 list bandwidth {
                   key name;
                   description "Bandwidth threshold";
                   leaf name {
                     type string;
                   }
                   leaf metric {
                     description "Metric associated with specified bandwidth";
                     type union {
                       type string {
                         pattern "<.*>|$.*";
                       }
                       type uint16 {
                         range "1 .. 65535";
                       }
                     }
                   }
                 }
               }
             }
           }
           list peer-interface {
             key name;
             ordered-by user;
             description "Configuration for peer interface";
             leaf name {
               description "Name of peer interface";
               type string;
             }
             uses apply-advanced;
             choice enable-disable {
               case case_1 {
                 leaf disable {
                   description "Disable OSPF on this control peer";
                   type empty;
                 }
               }
             }
             leaf retransmit-interval {
               description "Retransmission interval (seconds)";
               type union {
                 type string {
                   pattern "<.*>|$.*";
                 }
                 type uint32 {
                   range "1 .. 65535";
                 }
               }
             }
             leaf transit-delay {
               description "Transit delay (seconds)";
               type union {
                 type string {
                   pattern "<.*>|$.*";
                 }
                 type uint32 {
                   range "1 .. 65535";
                 }
               }
             }
             leaf hello-interval {
               description "Hello interval (seconds)";
               type union {
                 type string {
                   pattern "<.*>|$.*";
                 }
                 type uint32 {
                   range "1 .. 255";
                 }
               }
             }
             leaf dead-interval {
               description "Dead interval (seconds)";
               type union {
                 type string {
                   pattern "<.*>|$.*";
                 }
                 type uint32 {
                   range "1 .. 65535";
                 }
               }
             }
             leaf mtu {
               description "Maximum OSPF packet size";
               type union {
                 type string {
                   pattern "<.*>|$.*";
                 }
                 type uint32 {
                   range "128 .. 65535";
                 }
               }
             }
             choice auth {
               case case_1 {
                 container authentication {
                   uses juniper-ospf-authentication;
                 }
               }
               case case_2 {
                 container authentication-key {
                   description "Authentication key";
                   status deprecated;
                   leaf keyname {
                     description "Authentication key value";
                     type jt:unreadable;
                   }
                   leaf key-id {
                     description "Key ID for MD5 authentication";
                     type union {
                       type string {
                         pattern "<.*>|$.*";
                       }
                       type uint32 {
                         range "0 .. 255";
                       }
                     }
                   }
                 }
               }
             }
             leaf demand-circuit {
               description "Interface functions as a demand circuit";
               type empty;
             }
             leaf flood-reduction {
               description "Enable flood reduction";
               type empty;
             }
             leaf no-neighbor-down-notification {
               description "Don't inform other protocols about neighbor down events";
               type empty;
             }
           }
         }
       }
       uses apply-advanced;
       choice enable-disable {
         case case_1 {
           leaf disable {
             description "Disable OSPF";
             type empty;
           }
         }
       }
       container traceoptions {
         description "Trace options for OSPF";
         uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "spf" {
                 description "Trace SPF calculations";
               }
               enum "error" {
                 description "Trace errored packets";
               }
               enum "event" {
                 description "Trace OSPF state machine events";
               }
               enum "packet-dump" {
                 description "Dump the contents of selected packet types";
               }
               enum "flooding" {
                 description "Trace LSA flooding";
               }
               enum "lsa-analysis" {
                 description "Trace LSA analysis";
               }
               enum "packets" {
                 description "Trace all OSPF packets";
               }
               enum "hello" {
                 description "Trace hello packets";
               }
               enum "database-description" {
                 description "Trace database description packets";
               }
               enum "lsa-request" {
                 description "Trace LSA request packets";
               }
               enum "lsa-update" {
                 description "Trace LSA update packets";
               }
               enum "lsa-ack" {
                 description "Trace LSA acknowledgment packets";
               }
               enum "ldp-synchronization" {
                 description "Trace synchronization between OSPF and LDP";
               }
               enum "on-demand" {
                 description "Trace demand circuit extensions";
               }
               enum "nsr-synchronization" {
                 description "Trace NSR synchronization events";
               }
               enum "graceful-restart" {
                 description "Trace graceful restart";
               }
               enum "restart-signaling" {
                 description "Trace restart signaling";
               }
               enum "backup-spf" {
                 description "Trace backup SPF (LFA) specific events";
               }
               enum "source-packet-routing" {
                 description "Trace source packet routing (SPRING) events";
               }
               enum "post-convergence-lfa" {
                 description "Trace post-convergence-lfa related events";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       list topology {
         key name;
         ordered-by user;
         description "Topology parameters";
         leaf name {
           description "Topology name";
           type string;
         }
         uses apply-advanced;
         leaf disable {
           description "Disable this topology";
           type empty;
         }
         leaf topology-id {
           description "Topology identifier";
           type union {
             type string {
               pattern "<.*>|$.*";
             }
             type uint8 {
               range "32 .. 127";
             }
           }
         }
         leaf overload {
           description "Set the overload mode (repel transit traffic)";
           type empty;
         }
         leaf rib-group {
           description "Routing table group for importing routes";
           type string;
         }
         container spf-options {
           description "Configure options for SPF";
           uses apply-advanced;
           leaf delay {
             description "Time to wait before running an SPF";
             units "milliseconds";
             type union {
               type string {
                 pattern "<.*>|$.*";
               }
               type uint32 {
                 range "50 .. 8000";
               }
             }
           }
           leaf holddown {
             description "Time to hold down before running an SPF";
             units "milliseconds";
             type union {
               type string {
                 pattern "<.*>|$.*";
               }
               type uint32 {
                 range "2000 .. 20000";
               }
             }
           }
           leaf rapid-runs {
             description "Number of maximum rapid SPF runs before holddown";
             type union {
               type string {
                 pattern "<.*>|$.*";
               }
               type uint32 {
                 range "1 .. 10";
               }
             }
           }
           leaf no-ignore-our-externals {
             description "Do not ignore self-generated external and NSSA LSAs";
             type empty;
           }
         }
         container backup-spf-options {
           description "Configure options for backup SPF";
           uses apply-advanced;
           leaf disable {
             description "Do not run backup SPF";
             type empty;
           }
           leaf no-install {
             description "Do not install backup nexthops into the RIB";
             type empty;
           }
           leaf downstream-paths-only {
             description "Use only downstream backup paths";
             type empty;
           }
           container remote-backup-calculation {
             presence "enable remote-backup-calculation";
             description "Calculate Remote LFA backup nexthops";
             uses apply-advanced;
             container pq-nodes-nearest-to-source {
               description "PQ nodes selection based upon nearest to source";
               uses apply-advanced;
               leaf percent {
                 description "Selection percentage for nearest to source";
                 type union {
                   type string {
                     pattern "<.*>|$.*";
                   }
                   type uint32 {
                     range "10 .. 100";
                   }
                 }
               }
             }
           }
           container use-post-convergence-lfa {
             presence "enable use-post-convergence-lfa";
             description "Calculate post-convergence backup paths";
             uses apply-advanced;
             leaf maximum-labels {
               description "Maximum number of labels installed for post-convergence paths";
               type union {
                 type string {
                   pattern "<.*>|$.*";
                 }
                 type uint32 {
                   range "2 .. 5";
                 }
               }
             }
             leaf maximum-backup-paths {
               description "Maximum number of equal-cost post-convergence paths installed";
               type union {
                 type string {
                   pattern "<.*>|$.*";
                 }
                 type uint32 {
                   range "1 .. 8";
                 }
               }
             }
           }
           container per-prefix-calculation {
             description "Calculate backup nexthops for non-best prefix originators";
             uses apply-advanced;
             leaf stubs {
               description "Per prefix calculation for stubs only";
               type empty;
             }
             leaf summary {
               description "Per prefix calculation for summary originators only";
               type empty;
             }
             leaf externals {
               description "Per prefix calculation for externals";
               type empty;
             }
             leaf all {
               description "Per prefix calculation for all";
               type empty;
             }
           }
           leaf node-link-degradation {
             description "Degrade to link protection when nodelink protection not available";
             type empty;
           }
           leaf use-source-packet-routing {
             description "Use spring backup paths for inet.0 routes";
             type empty;
           }
         }
         leaf prefix-export-limit {
           description "Maximum number of prefixes that can be exported";
           type union {
             type string {
               pattern "<.*>|$.*";
             }
             type uint32 {
               range "0 .. 4294967295";
             }
           }
         }
       }
       container spf-options {
         description "Configure options for SPF";
         uses apply-advanced;
         leaf delay {
           description "Time to wait before running an SPF";
           units "milliseconds";
           type union {
             type string {
               pattern "<.*>|$.*";
             }
             type uint32 {
               range "50 .. 8000";
             }
           }
         }
         leaf holddown {
           description "Time to hold down before running an SPF";
           units "milliseconds";
           type union {
             type string {
               pattern "<.*>|$.*";
             }
             type uint32 {
               range "2000 .. 20000";
             }
           }
         }
         leaf rapid-runs {
           description "Number of maximum rapid SPF runs before holddown";
           type union {
             type string {
               pattern "<.*>|$.*";
             }
             type uint32 {
               range "1 .. 10";
             }
           }
         }
         leaf no-ignore-our-externals {
           description "Do not ignore self-generated external and NSSA LSAs";
           type empty;
         }
       }
       container backup-spf-options {
         description "Configure options for backup SPF";
         uses apply-advanced;
         leaf disable {
           description "Do not run backup SPF";
           type empty;
         }
         leaf no-install {
           description "Do not install backup nexthops into the RIB";
           type empty;
         }
         leaf downstream-paths-only {
           description "Use only downstream backup paths";
           type empty;
         }
         container remote-backup-calculation {
           presence "enable remote-backup-calculation";
           description "Calculate Remote LFA backup nexthops";
           uses apply-advanced;
           container pq-nodes-nearest-to-source {
             description "PQ nodes selection based upon nearest to source";
             uses apply-advanced;
             leaf percent {
               description "Selection percentage for nearest to source";
               type union {
                 type string {
                   pattern "<.*>|$.*";
                 }
                 type uint32 {
                   range "10 .. 100";
                 }
               }
             }
           }
         }
         container use-post-convergence-lfa {
           presence "enable use-post-convergence-lfa";
           description "Calculate post-convergence backup paths";
           uses apply-advanced;
           leaf maximum-labels {
             description "Maximum number of labels installed for post-convergence paths";
             type union {
               type string {
                 pattern "<.*>|$.*";
               }
               type uint32 {
                 range "2 .. 5";
               }
             }
           }
           leaf maximum-backup-paths {
             description "Maximum number of equal-cost post-convergence paths installed";
             type union {
               type string {
                 pattern "<.*>|$.*";
               }
               type uint32 {
                 range "1 .. 8";
               }
             }
           }
         }
         container per-prefix-calculation {
           description "Calculate backup nexthops for non-best prefix originators";
           uses apply-advanced;
           leaf stubs {
             description "Per prefix calculation for stubs only";
             type empty;
           }
           leaf summary {
             description "Per prefix calculation for summary originators only";
             type empty;
           }
           leaf externals {
             description "Per prefix calculation for externals";
             type empty;
           }
           leaf all {
             description "Per prefix calculation for all";
             type empty;
           }
         }
         leaf node-link-degradation {
           description "Degrade to link protection when nodelink protection not available";
           type empty;
         }
         leaf use-source-packet-routing {
           description "Use spring backup paths for inet.0 routes";
           type empty;
         }
       }
       leaf prefix-export-limit {
         description "Maximum number of prefixes that can be exported";
         type union {
           type string {
             pattern "<.*>|$.*";
           }
           type uint32 {
             range "0 .. 4294967295";
           }
         }
       }
       container rib-groups {
         description "Routing table groups for importing OSPF routes";
         uses apply-advanced;
         leaf inet {
           description "Name of the IPv4/v6 routing table group";
           type string;
         }
         leaf inet3 {
           description "Name of the IPv4/v6 inet.3 routing table group";
           type string;
         }
       }
       leaf job-stats {
         description "Collect job statistics";
         type empty;
       }
       container overload {
         presence "enable overload";
         description "Set the overload mode (repel transit traffic)";
         uses apply-advanced;
         leaf timeout {
           description "Time after which overload mode is reset";
           units "seconds";
           type union {
             type string {
               pattern "<.*>|$.*";
             }
             type uint32 {
               range "60 .. 1800";
             }
           }
         }
         leaf allow-route-leaking {
           description "Allow routes to be leaked when overload is configured";
           type empty;
         }
         leaf stub-network {
           description "Advertise Stub Network with maximum metric";
           type empty;
         }
         leaf intra-area-prefix {
           description "Advertise Intra Area Prefix with maximum metric";
           type empty;
         }
         leaf as-external {
           description "Advertise As External with maximum usable metric";
           type empty;
         }
       }
       container database-protection {
         presence "enable database-protection";
         description "Configure database protection attributes";
         uses apply-advanced;
         leaf maximum-lsa {
           description "Maximum allowed non self-generated LSAs";
           type union {
             type string {
               pattern "<.*>|$.*";
             }
             type uint32 {
               range "1 .. 1000000";
             }
           }
         }
         leaf warning-only {
           description "Emit only a warning when LSA maximum limit is exceeded";
           type empty;
         }
         leaf warning-threshold {
           description "Percentage of LSA maximum above which to trigger warning";
           units "percent";
           type union {
             type string {
               pattern "<.*>|$.*";
             }
             type uint8 {
               range "30 .. 100";
             }
           }
         }
         leaf ignore-count {
           description "Maximum number of times to go into ignore state";
           type union {
             type string {
               pattern "<.*>|$.*";
             }
             type uint8 {
               range "1 .. 32";
             }
           }
         }
         leaf ignore-time {
           description "Time to stay in ignore state and ignore all neighbors";
           units "seconds";
           type union {
             type string {
               pattern "<.*>|$.*";
             }
             type uint16 {
               range "30 .. 3600";
             }
           }
         }
         leaf reset-time {
           description "Time after which the ignore count gets reset to zero";
           units "seconds";
           type union {
             type string {
               pattern "<.*>|$.*";
             }
             type uint32 {
               range "60 .. 86400";
             }
           }
         }
       }
       container graceful-restart {
         description "Configure graceful restart attributes";
         uses apply-advanced;
         choice enable-disable {
           case case_1 {
             leaf disable {
               description "Disable OSPF graceful restart capability";
               type empty;
             }
           }
         }
         leaf restart-duration {
           description "Time for all neighbors to become full";
           units "seconds";
           type union {
             type string {
               pattern "<.*>|$.*";
             }
             type uint32 {
               range "1 .. 3600";
             }
           }
         }
         leaf notify-duration {
           description "Time to send all max-aged grace LSAs";
           units "seconds";
           type union {
             type string {
               pattern "<.*>|$.*";
             }
             type uint32 {
               range "1 .. 3600";
             }
           }
         }
         container helper-disable {
           presence "enable helper-disable";
           description "Disable graceful restart helper capability";
           uses apply-advanced;
           choice disable-choices {
             case case_1 {
               leaf standard {
                 description "Disable helper-mode for rfc3623 based GR";
                 type empty;
               }
             }
             case case_2 {
               leaf restart-signaling {
                 description "Disable helper mode for restart-signaling ";
                 type empty;
               }
             }
             case case_3 {
               leaf both {
                 description "Disable helper mode for both the types of GR";
                 type empty;
               }
             }
           }
         }
         leaf no-strict-lsa-checking {
           description "Do not abort graceful helper mode upon LSA changes";
           type empty;
         }
       }
       container traffic-engineering {
         presence "enable traffic-engineering";
         description "Configure traffic engineering attributes";
         uses apply-advanced;
         leaf no-topology {
           description "Disable dissemination of TE link-state topology information";
           type empty;
         }
         leaf multicast-rpf-routes {
           description "Install routes for multicast RPF checks into inet.2";
           type empty;
         }
         leaf igp-topology {
           description "Download IGP topology into TED";
           type empty;
         }
         leaf ignore-lsp-metrics {
           description "Ignore label-switched path metrics when doing shortcuts";
           type empty;
         }
         container shortcuts {
           presence "enable shortcuts";
           description "Use label-switched paths as next hops, if possible";
           uses apply-advanced;
           leaf ignore-lsp-metrics {
             description "Ignore label-switched path metrics when doing shortcuts";
             status deprecated;
             type empty;
           }
           leaf lsp-metric-into-summary {
             description "Advertise LSP metric into summary LSAs";
             type empty;
           }
           list family {
             key name;
             ordered-by user;
             description "Address family specific traffic-engineering attributes";
             leaf name {
               type enumeration {
                 enum "inet" {
                   description "IPv4 family";
                 }
                 enum "inet-mpls" {
                   description "IPv4-MPLS family";
                 }
               }
             }
             uses apply-advanced;
           }
         }
         leaf advertise-unnumbered-interfaces {
           description "Advertise unnumbered interfaces";
           type empty;
         }
         leaf credibility-protocol-preference {
           description "TED protocol credibility follows protocol preference";
           type empty;
         }
       }
       leaf route-type-community {
         description "Specify BGP extended community value to encode OSPF route type";
         type enumeration {
           enum "iana" {
             description "BGP extended community value used is 0x0306";
           }
           enum "vendor" {
             description "Vendor BGP extended community value used is 0x8000";
           }
         }
       }
       container domain-id {
         description "Configure domain ID";
         choice domain_id_or_disable {
           case case_1 {
             leaf domain-id {
               description "Domain ID";
               type string;
             }
           }
           case case_2 {
             leaf disable {
               description "Disable domain ID";
               type empty;
             }
           }
         }
       }
       choice domain_vpn_tag_or_disable {
         case case_1 {
           leaf domain-vpn-tag {
             description "Domain VPN tag for external LSA";
             type union {
               type string {
                 pattern "<.*>|$.*";
               }
               type uint32 {
                 range "0 .. 4294967295";
               }
             }
           }
         }
         case case_2 {
           leaf no-domain-vpn-tag {
             description "Disable domain VPN tag";
             type empty;
           }
         }
       }
       leaf preference {
         description "Preference of internal routes";
         type union {
           type uint32;
           type string {
             pattern "<.*>|$.*";
           }
         }
       }
       leaf external-preference {
         description "Preference of external routes";
         type union {
           type uint32;
           type string {
             pattern "<.*>|$.*";
           }
         }
       }
       leaf labeled-preference {
         description "Preference of labeled routes";
         type union {
           type uint32;
           type string {
             pattern "<.*>|$.*";
           }
         }
       }
       leaf-list export {
         ordered-by user;
         description "Export policy";
         type jt:policy-algebra;
       }
       leaf-list import {
         ordered-by user;
         description "Import policy (for external routes or setting priority)";
         type jt:policy-algebra;
       }
       leaf reference-bandwidth {
         description "Bandwidth for calculating metric defaults";
         type string;
       }
       leaf lsa-refresh-interval {
         description "LSA refresh interval (minutes)";
         default "50";
         type union {
           type string {
             pattern "<.*>|$.*";
           }
           type uint32 {
             range "25 .. 50";
           }
         }
       }
       leaf spf-delay {
         description "Time to wait before running an SPF";
         status deprecated;
         units "milliseconds";
         type union {
           type string {
             pattern "<.*>|$.*";
           }
           type uint32 {
             range "50 .. 8000";
           }
         }
       }
       leaf no-rfc-1583 {
         description "Disable RFC1583 compatibility";
         type empty;
       }
       container source-packet-routing {
         presence "enable source-packet-routing";
         description "Enable source packet routing (SPRING)";
         uses apply-advanced;
         container adjacency-segment {
           description "Attributes for adjacency segments in spring";
           uses apply-advanced;
           leaf hold-time {
             description "Retain time of Adjacency segment after isolating from an interface";
             type union {
               type string {
                 pattern "<.*>|$.*";
               }
               type uint32 {
                 range "180000 .. 900000";
               }
             }
           }
         }
         leaf-list prefix-segment {
           ordered-by user;
           description "Prefix Segment policy";
           type jt:policy-algebra;
         }
         leaf explicit-null {
           description "Set E and P bits in all Prefix SID advertisements";
           type empty;
         }
         container node-segment {
           presence "enable node-segment";
           description "Enable support for Node segments in SPRING";
           uses apply-advanced;
           leaf ipv4-index {
             description "Set ipv4 node segment index";
             type union {
               type string {
                 pattern "<.*>|$.*";
               }
               type uint32 {
                 range "0 .. 16383";
               }
             }
           }
           leaf index-range {
             description "Set range of node segment indices allowed";
             type union {
               type string {
                 pattern "<.*>|$.*";
               }
               type uint32 {
                 range "32 .. 16384";
               }
             }
           }
         }
         leaf mapping-server {
           description "Mapping server name";
           type string;
         }
         leaf install-prefix-sid-for-best-route {
           description "For best route install a exact prefix sid route";
           type empty;
         }
       }
       leaf forwarding-address-to-broadcast {
         description "Set forwarding address in Type 5 LSA in broadcast network";
         type empty;
       }
       choice nssa-abr-option {
         case case_1 {
           leaf no-nssa-abr {
             description "Disable full NSSA functionality at ABR";
             type empty;
           }
         }
       }
       container sham-link {
         presence "enable sham-link";
         description "Configure parameters for sham links";
         uses apply-advanced;
         leaf local {
           description "Local sham link endpoint address";
           type jt:ipaddr;
         }
         leaf no-advertise-local {
           description "Don't advertise local sham link endpoint as stub in router LSA";
           status deprecated;
           type empty;
         }
       }
       list area {
         key name;
         ordered-by user;
         description "Configure an OSPF area";
         leaf name {
           description "Area ID";
           type jt:areaid;
         }
         uses apply-advanced;
         choice stub-option {
           case case_1 {
             container stub {
               presence "enable stub";
               description "Configure a stub area";
               leaf default-metric {
                 description "Metric for the default route in this stub area";
                 type union {
                   type string {
                     pattern "<.*>|$.*";
                   }
                   type uint32 {
                     range "1 .. 16777215";
                   }
                 }
               }
               choice summaries-choice {
                 leaf summaries {
                   description "Flood summary LSAs into this stub area";
                   type empty;
                 }
                 leaf no-summaries {
                   description "Don't flood summary LSAs into this stub area";
                   type empty;
                 }
               }
             }
           }
           case case_2 {
             container nssa {
               presence "enable nssa";
               description "Configure a not-so-stubby area";
               uses apply-advanced;
               container default-lsa {
                 presence "enable default-lsa";
                 description "Configure a default LSA";
                 uses apply-advanced;
                 leaf default-metric {
                   description "Metric for the default route in this area";
                   type union {
                     type string {
                       pattern "<.*>|$.*";
                     }
                     type uint32 {
                       range "1 .. 16777215";
                     }
                   }
                 }
                 leaf metric-type {
                   description "External metric type for the default type 7 LSA";
                   type union {
                     type string {
                       pattern "<.*>|$.*";
                     }
                     type uint32 {
                       range "1 .. 2";
                     }
                   }
                 }
                 leaf type-7 {
                   description "Flood type 7 default LSA if no-summaries is configured";
                   type empty;
                 }
               }
               leaf default-metric {
                 description "Metric for the default route in this area";
                 status deprecated;
                 type union {
                   type string {
                     pattern "<.*>|$.*";
                   }
                   type uint32 {
                     range "1 .. 16777215";
                   }
                 }
               }
               leaf metric-type {
                 description "External metric type for the default type 7 LSA";
                 status deprecated;
                 type union {
                   type string {
                     pattern "<.*>|$.*";
                   }
                   type uint32 {
                     range "1 .. 2";
                   }
                 }
               }
               choice summaries-choice {
                 leaf summaries {
                   description "Flood summary LSAs into this NSSA area";
                   type empty;
                 }
                 leaf no-summaries {
                   description "Don't flood summary LSAs into this NSSA area";
                   type empty;
                 }
               }
               list area-range {
                 key name;
                 ordered-by user;
                 description "Configure NSSA area ranges";
                 leaf name {
                   description "Range to summarize NSSA routes in this area";
                   type jt:ipprefix;
                 }
                 uses apply-advanced;
                 leaf restrict {
                   description "Restrict advertisement of this area range";
                   type empty;
                 }
                 leaf exact {
                   description "Enforce exact match for advertisement of this area range";
                   type empty;
                 }
                 container override-metric {
                   presence "enable override-metric";
                   description "Override the dynamic metric for this area-range";
                   uses apply-advanced;
                   leaf metric {
                     description "Metric value";
                     type union {
                       type string {
                         pattern "<.*>|$.*";
                       }
                       type uint32 {
                         range "1 .. 16777215";
                       }
                     }
                   }
                   leaf metric-type {
                     description "Set the metric type for the override metric";
                     default "1";
                     type union {
                       type string {
                         pattern "<.*>|$.*";
                       }
                       type uint32 {
                         range "1 .. 2";
                       }
                     }
                   }
                 }
               }
             }
           }
         }
         list area-range {
           key name;
           ordered-by user;
           description "Configure area ranges";
           leaf name {
             description "Range to summarize routes in this area";
             type jt:ipprefix;
           }
           uses apply-advanced;
           leaf restrict {
             description "Restrict advertisement of this area range";
             type empty;
           }
           leaf exact {
             description "Enforce exact match for advertisement of this area range";
             type empty;
           }
           leaf override-metric {
             description "Override the dynamic metric for this area-range";
             type union {
               type string {
                 pattern "<.*>|$.*";
               }
               type uint32 {
                 range "1 .. 16777215";
               }
             }
           }
         }
         leaf-list network-summary-export {
           ordered-by user;
           description "Export policy for Type 3 Summary LSAs";
           type jt:policy-algebra;
         }
         leaf-list network-summary-import {
           ordered-by user;
           description "Import policy for Type 3 Summary LSAs";
           type jt:policy-algebra;
         }
         leaf-list inter-area-prefix-export {
           ordered-by user;
           description "Export policy for Inter Area Prefix LSAs";
           type jt:policy-algebra;
         }
         leaf-list inter-area-prefix-import {
           ordered-by user;
           description "Import policy for Inter Area Prefix LSAs";
           type jt:policy-algebra;
         }
         leaf authentication-type {
           description "Authentication type";
           status deprecated;
           type enumeration {
             enum "none" {
               description "No authentication";
               status deprecated;
             }
             enum "simple" {
               description "Simple password authentication";
               status deprecated;
             }
             enum "md5" {
               description "MD5 authentication";
               status deprecated;
             }
           }
         }
         list virtual-link {
           key "neighbor-id transit-area";
           ordered-by user;
           description "Configure virtual links";
           leaf neighbor-id {
             description "Router ID of a virtual neighbor";
             type jt:ipv4addr;
           }
           leaf transit-area {
             description "Transit area in common with virtual neighbor";
             type jt:areaid;
           }
           uses apply-advanced;
           choice enable-disable {
             case case_1 {
               leaf disable {
                 description "Disable this virtual link";
                 type empty;
               }
             }
           }
           leaf retransmit-interval {
             description "Retransmission interval (seconds)";
             type union {
               type string {
                 pattern "<.*>|$.*";
               }
               type uint32 {
                 range "1 .. 65535";
               }
             }
           }
           leaf transit-delay {
             description "Transit delay (seconds)";
             type union {
               type string {
                 pattern "<.*>|$.*";
               }
               type uint32 {
                 range "1 .. 65535";
               }
             }
           }
           leaf hello-interval {
             description "Hello interval (seconds)";
             type union {
               type string {
                 pattern "<.*>|$.*";
               }
               type uint32 {
                 range "1 .. 255";
               }
             }
           }
           leaf dead-interval {
             description "Dead interval (seconds)";
             type union {
               type string {
                 pattern "<.*>|$.*";
               }
               type uint32 {
                 range "1 .. 65535";
               }
             }
           }
           leaf mtu {
             description "Maximum OSPF packet size";
             type union {
               type string {
                 pattern "<.*>|$.*";
               }
               type uint32 {
                 range "128 .. 65535";
               }
             }
           }
           choice auth {
             case case_1 {
               container authentication {
                 uses juniper-ospf-authentication;
               }
             }
             case case_2 {
               container authentication-key {
                 description "Authentication key";
                 status deprecated;
                 leaf keyname {
                   description "Authentication key value";
                   type jt:unreadable;
                 }
                 leaf key-id {
                   description "Key ID for MD5 authentication";
                   type union {
                     type string {
                       pattern "<.*>|$.*";
                     }
                     type uint32 {
                       range "0 .. 255";
                     }
                   }
                 }
               }
             }
           }
           leaf demand-circuit {
             description "Interface functions as a demand circuit";
             type empty;
           }
           leaf flood-reduction {
             description "Enable flood reduction";
             type empty;
           }
           leaf no-neighbor-down-notification {
             description "Don't inform other protocols about neighbor down events";
             type empty;
           }
           leaf ipsec-sa {
             description "IPSec security association name";
             type string {
               length "1 .. 32";
             }
           }
           list topology {
             key name;
             ordered-by user;
             description "Topology specific attributes";
             leaf name {
               description "Topology name";
               type string;
             }
             uses apply-advanced;
             leaf disable {
               description "Disable this topology";
               type empty;
             }
             leaf metric {
               description "Topology metric";
               type union {
                 type string {
                   pattern "<.*>|$.*";
                 }
                 type uint16 {
                   range "1 .. 65535";
                 }
               }
             }
             container bandwidth-based-metrics {
               description "Configure bandwidth based metrics";
               uses apply-advanced;
               list bandwidth {
                 key name;
                 description "Bandwidth threshold";
                 leaf name {
                   type string;
                 }
                 leaf metric {
                   description "Metric associated with specified bandwidth";
                   type union {
                     type string {
                       pattern "<.*>|$.*";
                     }
                     type uint16 {
                       range "1 .. 65535";
                     }
                   }
                 }
               }
             }
           }
         }
         list sham-link-remote {
           key name;
           ordered-by user;
           description "Configure parameters for remote sham link endpoint";
           leaf name {
             description "Remote sham link endpoint address";
             type jt:ipaddr;
           }
           uses apply-advanced;
           leaf metric {
             description "Sham link metric";
             type union {
               type string {
                 pattern "<.*>|$.*";
               }
               type uint16 {
                 range "1 .. 65535";
               }
             }
           }
           leaf ipsec-sa {
             description "IPSec security association name";
             type string {
               length "1 .. 32";
             }
           }
           leaf demand-circuit {
             description "Interface functions as a demand circuit";
             type empty;
           }
           leaf flood-reduction {
             description "Enable flood reduction";
             type empty;
           }
           list topology {
             key name;
             ordered-by user;
             description "Topology specific attributes";
             leaf name {
               description "Topology name";
               type string;
             }
             uses apply-advanced;
             leaf disable {
               description "Disable this topology";
               type empty;
             }
             leaf metric {
               description "Topology metric";
               type union {
                 type string {
                   pattern "<.*>|$.*";
                 }
                 type uint16 {
                   range "1 .. 65535";
                 }
               }
             }
             container bandwidth-based-metrics {
               description "Configure bandwidth based metrics";
               uses apply-advanced;
               list bandwidth {
                 key name;
                 description "Bandwidth threshold";
                 leaf name {
                   type string;
                 }
                 leaf metric {
                   description "Metric associated with specified bandwidth";
                   type union {
                     type string {
                       pattern "<.*>|$.*";
                     }
                     type uint16 {
                       range "1 .. 65535";
                     }
                   }
                 }
               }
             }
           }
         }
         list interface {
           key name;
           ordered-by user;
           description "Include an interface in this area";
           leaf name {
             description "Interface name";
             type union {
               type jt:ipv4addr-or-interface;
               type string {
                 pattern "<.*>|$.*";
               }
             }
           }
           uses apply-advanced;
           choice enable-disable {
             case case_1 {
               leaf disable {
                 description "Disable OSPF on this interface";
                 type empty;
               }
             }
           }
           leaf interface-type {
             description "Type of interface";
             type enumeration {
               enum "nbma" {
                 description "Nonbroadcast multiaccess";
               }
               enum "p2mp" {
                 description "Point-to-multipoint NBMA";
               }
               enum "p2p" {
                 description "Point-to-point";
               }
               enum "p2mp-over-lan" {
                 description "Point-to-multipoint over LAN mode";
               }
             }
           }
           container post-convergence-lfa {
             presence "enable post-convergence-lfa";
             description "Protect interface using post-convergence backup path";
             uses apply-advanced;
             container node-protection {
               presence "enable node-protection";
               description "Compute backup path assuming node failure";
               uses apply-advanced;
               leaf cost {
                 description "Cost for node protection";
                 type union {
                   type string {
                     pattern "<.*>|$.*";
                   }
                   type uint16 {
                     range "1 .. 65535";
                   }
                 }
               }
             }
           }
           choice protection-type {
             case case_1 {
               leaf link-protection {
                 description "Protect interface from link faults only";
                 type empty;
               }
             }
             case case_2 {
               leaf node-link-protection {
                 description "Protect interface from both link and node faults";
                 type empty;
               }
             }
           }
           leaf no-eligible-backup {
             description "Not eligible to backup traffic from protected interfaces";
             type empty;
           }
           leaf no-eligible-remote-backup {
             description "Not eligible for Remote-LFA backup traffic from protected interfaces";
             type empty;
           }
           container passive {
             presence "enable passive";
             description "Do not run OSPF, but advertise it";
             uses apply-advanced;
             container traffic-engineering {
               description "Advertise TE link information";
               uses apply-advanced;
               leaf remote-node-id {
                 description "Remote address of the link";
                 type jt:ipaddr;
               }
               leaf remote-node-router-id {
                 description "TE Router-ID of the remote node";
                 type jt:ipv4addr;
               }
             }
           }
           leaf secondary {
             description "Treat interface as secondary";
             type empty;
           }
           leaf own-router-lsa {
             description "Generate a separate router LSA for this interface";
             type empty;
           }
           container bandwidth-based-metrics {
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint16 {
                     range "1 .. 65535";
                   }
                 }
               }
             }
           }
           leaf metric {
             description "Interface metric";
             type union {
               type string {
                 pattern "<.*>|$.*";
               }
               type uint16 {
                 range "1 .. 65535";
               }
             }
           }
           leaf te-metric {
             description "Traffic engineering metric";
             type union {
               type string {
                 pattern "<.*>|$.*";
               }
               type uint32 {
                 range "1 .. 4294967295";
               }
             }
           }
           leaf priority {
             description "Designated router priority";
             type union {
               type string {
                 pattern "<.*>|$.*";
               }
               type uint32 {
                 range "0 .. 255";
               }
             }
           }
           container ldp-synchronization {
             description "Advertise maximum metric until LDP is operational";
             presence "enable ldp-synchronization";
             uses ldp-sync-obj;
           }
           leaf retransmit-interval {
             description "Retransmission interval (seconds)";
             type union {
               type string {
                 pattern "<.*>|$.*";
               }
               type uint32 {
                 range "1 .. 65535";
               }
             }
           }
           leaf transit-delay {
             description "Transit delay (seconds)";
             type union {
               type string {
                 pattern "<.*>|$.*";
               }
               type uint32 {
                 range "1 .. 65535";
               }
             }
           }
           leaf hello-interval {
             description "Hello interval (seconds)";
             type union {
               type string {
                 pattern "<.*>|$.*";
               }
               type uint32 {
                 range "1 .. 255";
               }
             }
           }
           leaf dead-interval {
             description "Dead interval (seconds)";
             type union {
               type string {
                 pattern "<.*>|$.*";
               }
               type uint32 {
                 range "1 .. 65535";
               }
             }
           }
           leaf mtu {
             description "Maximum OSPF packet size";
             type union {
               type string {
                 pattern "<.*>|$.*";
               }
               type uint32 {
                 range "128 .. 65535";
               }
             }
           }
           choice auth {
             case case_1 {
               container authentication {
                 uses juniper-ospf-authentication;
               }
             }
             case case_2 {
               container authentication-key {
                 description "Authentication key";
                 status deprecated;
                 leaf keyname {
                   description "Authentication key value";
                   type jt:unreadable;
                 }
                 leaf key-id {
                   description "Key ID for MD5 authentication";
                   type union {
                     type string {
                       pattern "<.*>|$.*";
                     }
                     type uint32 {
                       range "0 .. 255";
                     }
                   }
                 }
               }
             }
           }
           leaf demand-circuit {
             description "Interface functions as a demand circuit";
             type empty;
           }
           leaf flood-reduction {
             description "Enable flood reduction";
             type empty;
           }
           leaf no-neighbor-down-notification {
             description "Don't inform other protocols about neighbor down events";
             type empty;
           }
           leaf ipsec-sa {
             description "IPSec security association name";
             type string {
               length "1 .. 32";
             }
           }
           list topology {
             key name;
             ordered-by user;
             description "Topology specific attributes";
             leaf name {
               description "Topology name";
               type string;
             }
             uses apply-advanced;
             leaf disable {
               description "Disable this topology";
               type empty;
             }
             leaf metric {
               description "Topology metric";
               type union {
                 type string {
                   pattern "<.*>|$.*";
                 }
                 type uint16 {
                   range "1 .. 65535";
                 }
               }
             }
             container bandwidth-based-metrics {
               description "Configure bandwidth based metrics";
               uses apply-advanced;
               list bandwidth {
                 key name;
                 description "Bandwidth threshold";
                 leaf name {
                   type string;
                 }
                 leaf metric {
                   description "Metric associated with specified bandwidth";
                   type union {
                     type string {
                       pattern "<.*>|$.*";
                     }
                     type uint16 {
                       range "1 .. 65535";
                     }
                   }
                 }
               }
             }
           }
           leaf transmit-interval {
             description "OSPF packet transmit interval (milliseconds)";
             status deprecated;
             type union {
               type string {
                 pattern "<.*>|$.*";
               }
               type uint32 {
                 range "1 .. 4294967295";
               }
             }
           }
           container bfd-liveness-detection {
             description "Bidirectional Forwarding Detection options";
             uses apply-advanced;
             leaf version {
               description "BFD protocol version number";
               default "automatic";
               type enumeration {
                 enum "0" {
                   description "BFD version 0 (deprecated)";
                 }
                 enum "1" {
                   description "BFD version 1";
                 }
                 enum "automatic" {
                   description "Choose BFD version automatically";
                 }
               }
             }
             leaf minimum-interval {
               description "Minimum transmit and receive interval";
               units "milliseconds";
               type union {
                 type string {
                   pattern "<.*>|$.*";
                 }
                 type uint32 {
                   range "1 .. 255000";
                 }
               }
             }
             leaf minimum-transmit-interval {
               description "Minimum transmit interval";
               status deprecated;
               units "milliseconds";
               type union {
                 type string {
                   pattern "<.*>|$.*";
                 }
                 type uint32 {
                   range "1 .. 255000";
                 }
               }
             }
             leaf minimum-receive-interval {
               description "Minimum receive interval";
               units "milliseconds";
               type union {
                 type string {
                   pattern "<.*>|$.*";
                 }
                 type uint32 {
                   range "1 .. 255000";
                 }
               }
             }
             leaf multiplier {
               description "Detection time multiplier";
               default "3";
               type union {
                 type string {
                   pattern "<.*>|$.*";
                 }
                 type uint32 {
                   range "1 .. 255";
                 }
               }
             }
             choice adaptation-choice {
               case case_1 {
                 leaf no-adaptation {
                   description "Disable adaptation";
                   type empty;
                 }
               }
             }
             container transmit-interval {
               description "Transmit-interval options";
               uses apply-advanced;
               leaf minimum-interval {
                 description "Minimum transmit interval";
                 units "milliseconds";
                 type union {
                   type string {
                     pattern "<.*>|$.*";
                   }
                   type uint32 {
                     range "1 .. 255000";
                   }
                 }
               }
               leaf threshold {
                 description "High transmit interval triggering a trap";
                 units "milliseconds";
                 type union {
                   type uint32;
                   type string {
                     pattern "<.*>|$.*";
                   }
                 }
               }
             }
             container detection-time {
               description "Detection-time options";
               uses apply-advanced;
               leaf threshold {
                 description "High detection-time triggering a trap";
                 units "milliseconds";
                 type union {
                   type uint32;
                   type string {
                     pattern "<.*>|$.*";
                   }
                 }
               }
             }
             container authentication {
               description "Authentication options";
               uses apply-advanced;
               leaf key-chain {
                 description "Key chain name";
                 type string;
               }
               leaf algorithm {
                 description "Algorithm name";
                 type enumeration {
                   enum "simple-password" {
                     description "Simple password";
                   }
                   enum "keyed-md5" {
                     description "Keyed message Digest 5";
                   }
                   enum "meticulous-keyed-md5" {
                     description "Meticulous keyed message Digest 5";
                   }
                   enum "keyed-sha-1" {
                     description "Keyed secure hash algorithm (SHA1) ";
                   }
                   enum "meticulous-keyed-sha-1" {
                     description "Meticulous keyed secure hash algorithm (SHA1) ";
                   }
                 }
               }
               leaf loose-check {
                 description "Verify authentication only if authentication is negotiated";
                 type empty;
               }
             }
             leaf full-neighbors-only {
               description "Setup BFD sessions only to Full neighbors";
               type empty;
             }
           }
           leaf dynamic-neighbors {
             description "Learn neighbors dynamically on a p2mp interface";
             type empty;
           }
           leaf no-advertise-adjacency-segment {
             description "Do not advertise an adjacency segment for this interface";
             type empty;
           }
           list neighbor {
             key name;
             ordered-by user;
             description "NBMA neighbor";
             leaf name {
               description "Address of neighbor";
               type jt:ipaddr;
             }
             leaf eligible {
               description "Eligible to be DR on an NBMA network";
               type empty;
             }
           }
           leaf poll-interval {
             description "Poll interval for NBMA interfaces";
             type union {
               type string {
                 pattern "<.*>|$.*";
               }
               type uint32 {
                 range "1 .. 65535";
               }
             }
           }
           leaf no-interface-state-traps {
             description "Do not send interface state change traps";
             type empty;
           }
         }
         leaf no-source-packet-routing {
           description "Disable SPRING in this area";
           type empty;
         }
         leaf no-context-identifier-advertisement {
           description "Disable context identifier advertisments in this area";
           type empty;
         }
         list context-identifier {
           key name;
           ordered-by user;
           description "Configure context identifier in support of edge protection";
           leaf name {
             description "Context identifier";
             type jt:ipv4addr;
           }
           uses apply-advanced;
         }
         list label-switched-path {
           key name;
           ordered-by user;
           description "Configuration for advertisement of a label-switched path";
           leaf name {
             description "Name of label-switched path to be advertised";
             type string {
               length "1 .. 64";
             }
           }
           uses apply-advanced;
           choice enable-disable {
             case case_1 {
               leaf disable {
                 description "Disable OSPF on this label-switched path";
                 type empty;
               }
             }
           }
           leaf metric {
             description "Interface metric";
             type union {
               type string {
                 pattern "<.*>|$.*";
               }
               type uint16 {
                 range "1 .. 65535";
               }
             }
           }
           list topology {
             key name;
             ordered-by user;
             description "Topology specific attributes";
             leaf name {
               description "Topology name";
               type string;
             }
             uses apply-advanced;
             leaf disable {
               description "Disable this topology";
               type empty;
             }
             leaf metric {
               description "Topology metric";
               type union {
                 type string {
                   pattern "<.*>|$.*";
                 }
                 type uint16 {
                   range "1 .. 65535";
                 }
               }
             }
             container bandwidth-based-metrics {
               description "Configure bandwidth based metrics";
               uses apply-advanced;
               list bandwidth {
                 key name;
                 description "Bandwidth threshold";
                 leaf name {
                   type string;
                 }
                 leaf metric {
                   description "Metric associated with specified bandwidth";
                   type union {
                     type string {
                       pattern "<.*>|$.*";
                     }
                     type uint16 {
                       range "1 .. 65535";
                     }
                   }
                 }
               }
             }
           }
         }
         list peer-interface {
           key name;
           ordered-by user;
           description "Configuration for peer interface";
           leaf name {
             description "Name of peer interface";
             type string;
           }
           uses apply-advanced;
           choice enable-disable {
             case case_1 {
               leaf disable {
                 description "Disable OSPF on this control peer";
                 type empty;
               }
             }
           }
           leaf retransmit-interval {
             description "Retransmission interval (seconds)";
             type union {
               type string {
                 pattern "<.*>|$.*";
               }
               type uint32 {
                 range "1 .. 65535";
               }
             }
           }
           leaf transit-delay {
             description "Transit delay (seconds)";
             type union {
               type string {
                 pattern "<.*>|$.*";
               }
               type uint32 {
                 range "1 .. 65535";
               }
             }
           }
           leaf hello-interval {
             description "Hello interval (seconds)";
             type union {
               type string {
                 pattern "<.*>|$.*";
               }
               type uint32 {
                 range "1 .. 255";
               }
             }
           }
           leaf dead-interval {
             description "Dead interval (seconds)";
             type union {
               type string {
                 pattern "<.*>|$.*";
               }
               type uint32 {
                 range "1 .. 65535";
               }
             }
           }
           leaf mtu {
             description "Maximum OSPF packet size";
             type union {
               type string {
                 pattern "<.*>|$.*";
               }
               type uint32 {
                 range "128 .. 65535";
               }
             }
           }
           choice auth {
             case case_1 {
               container authentication {
                 uses juniper-ospf-authentication;
               }
             }
             case case_2 {
               container authentication-key {
                 description "Authentication key";
                 status deprecated;
                 leaf keyname {
                   description "Authentication key value";
                   type jt:unreadable;
                 }
                 leaf key-id {
                   description "Key ID for MD5 authentication";
                   type union {
                     type string {
                       pattern "<.*>|$.*";
                     }
                     type uint32 {
                       range "0 .. 255";
                     }
                   }
                 }
               }
             }
           }
           leaf demand-circuit {
             description "Interface functions as a demand circuit";
             type empty;
           }
           leaf flood-reduction {
             description "Enable flood reduction";
             type empty;
           }
           leaf no-neighbor-down-notification {
             description "Don't inform other protocols about neighbor down events";
             type empty;
           }
         }
       }
     }
     container overlay {
       description "Overlay protocol";
       uses juniper-protocols-overlayd;
     }
     container l2iw {
       presence "enable l2iw";
       description "Configuration for Layer 2 interworking";
       uses apply-advanced;
       container traceoptions {
         description "Trace options for Layer 2 circuits";
         uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "error" {
                 description "Trace errors";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
     }
     container igmp {
       presence "enable igmp";
       description "IGMP options";
       uses apply-advanced;
       container traceoptions {
         description "Trace options for IGMP";
         uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "packets" {
                 description "Trace all IGMP packets";
               }
               enum "query" {
                 description "Trace IGMP membership query messages";
               }
               enum "report" {
                 description "Trace membership report messages";
               }
               enum "leave" {
                 description "Trace leave group messages (IGMPv2 only)";
               }
               enum "mtrace" {
                 description "Trace mtrace packets";
               }
               enum "group" {
                 description "Trace group operations";
               }
               enum "client-notification" {
                 description "Trace notifications";
               }
               enum "host-notification" {
                 description "Trace host notifications";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       leaf query-interval {
         description "When to send host query messages";
         units "seconds";
         type union {
           type string {
             pattern "<.*>|$.*";
           }
           type uint32 {
             range "1 .. 1024";
           }
         }
       }
       leaf query-response-interval {
         description "How long to wait for a host query response";
         units "seconds";
         type string {
         }
       }
       leaf query-last-member-interval {
         description "When to send group query messages";
         units "seconds";
         type string {
         }
       }
       leaf robust-count {
         description "Expected packet loss on a subnet";
         type union {
           type string {
             pattern "<.*>|$.*";
           }
           type uint32 {
             range "2 .. 10";
           }
         }
       }
       leaf maximum-transmit-rate {
         description "Maximum transmission rate (packets per second)";
         type union {
           type string {
             pattern "<.*>|$.*";
           }
           type uint32 {
             range "1 .. 10000";
           }
         }
       }
       leaf accounting {
         description "Enable join and leave event notification";
         type empty;
       }
       list interface {
         key name;
         ordered-by user;
         description "Interface options for IGMP";
         leaf name {
           type string;
         }
         uses apply-advanced;
         choice enable-disable {
           case case_1 {
             leaf disable {
               description "Disable IGMP on this interface";
               type empty;
             }
           }
         }
         leaf version {
           description "Set IGMP version number on this interface";
           type union {
             type string {
               pattern "<.*>|$.*";
             }
             type uint8 {
               range "1 .. 3";
             }
           }
         }
         container static {
           description "Static group or source membership";
           uses apply-advanced;
           list group {
             key name;
             ordered-by user;
             description "IP multicast group address";
             leaf name {
               description "IP multicast group address";
               type jt:ipv4addr;
             }
             uses apply-advanced;
             leaf group-increment {
               description "Mask for the incrementing group IP address";
               type jt:ipv4addr;
             }
             leaf group-count {
               description "Number of groups";
               type union {
                 type string {
                   pattern "<.*>|$.*";
                 }
                 type uint32 {
                   range "1 .. 512";
                 }
               }
             }
             leaf exclude {
               description "Exclude sources";
               type empty;
             }
             list source {
               key name;
               ordered-by user;
               description "IP multicast source address";
               leaf name {
                 description "Source address of IP multicast data";
                 type jt:ipv4addr;
               }
               uses apply-advanced;
               leaf source-increment {
                 description "Mask for the incrementing source IP address";
                 type jt:ipv4addr;
               }
               leaf source-count {
                 description "Number of sources";
                 type union {
                   type string {
                     pattern "<.*>|$.*";
                   }
                   type uint32 {
                     range "1 .. 1024";
                   }
                 }
               }
             }
           }
         }
         leaf ssm-map {
           description "Map for SSM translation of IGMPv1 or IGMPv2 messages";
           type string;
         }
         leaf-list ssm-map-policy {
           ordered-by user;
           description "SSM map policy name";
           type jt:policy-algebra;
         }
         leaf immediate-leave {
           description "Group removed immediately, last membership query not sent";
           type empty;
         }
         leaf promiscuous-mode {
           description "Accept igmp messages coming from different subnet";
           type empty;
         }
         choice accounting-choice {
           leaf accounting {
             description "Enable join and leave event notification";
             type empty;
           }
           leaf no-accounting {
             description "Don't enable join and leave event notification";
             type empty;
           }
         }
         leaf-list group-policy {
           ordered-by user;
           description "Group filter applied to incoming IGMP report messages";
           type jt:policy-algebra;
         }
         leaf group-limit {
           description "Maximum number of (source,group) per interface";
           type union {
             type string {
               pattern "<.*>|$.*";
             }
             type uint16 {
               range "1 .. 32767";
             }
           }
         }
         leaf group-threshold {
           description "Percentage of limit at which to generate warnings";
           type union {
             type string {
               pattern "<.*>|$.*";
             }
             type uint32 {
               range "1 .. 100";
             }
           }
         }
         leaf log-interval {
           description "Time between consecutive log messages";
           type union {
             type string {
               pattern "<.*>|$.*";
             }
             type uint32 {
               range "6 .. 32767";
             }
           }
         }
         container passive {
           presence "enable passive";
           description "Suppress sending and receiving IGMP messages";
           leaf allow-receive {
             description "Allow receiving IGMP messages";
             type empty;
           }
           leaf send-general-query {
             description "Send IGMP general query messages";
             type empty;
           }
           leaf send-group-query {
             description "Send IGMP group query messages";
             type empty;
           }
         }
         leaf-list oif-map {
           ordered-by user;
           description "Output interface map";
           type jt:policy-algebra;
         }
         leaf distributed {
           description "Distributed IGMP interface";
           type empty;
         }
       }
       container amt {
         description "Automatic Multicast Tunnel options for IGMP";
         uses apply-advanced;
         container relay {
           description "AMT relay options for IGMP";
           uses apply-advanced;
           container defaults {
             presence "enable defaults";
             description "Default AMT relay options for IGMP";
             uses apply-advanced;
             leaf version {
               description "Set IGMP version number on AMT interfaces";
               type union {
                 type string {
                   pattern "<.*>|$.*";
                 }
                 type uint8 {
                   range "1 .. 3";
                 }
               }
             }
             leaf ssm-map {
               description "Map for SSM translation of IGMPv1 or IGMPv2 messages";
               type string;
             }
             leaf-list ssm-map-policy {
               ordered-by user;
               description "SSM map policy name";
               type jt:policy-algebra;
             }
             choice accounting-choice {
               leaf accounting {
                 description "Enable join and leave event notification";
                 type empty;
               }
               leaf no-accounting {
                 description "Don't enable join and leave event notification";
                 type empty;
               }
             }
             leaf-list group-policy {
               ordered-by user;
               description "Group filter applied to incoming IGMP report messages";
               type jt:policy-algebra;
             }
             leaf group-limit {
               description "Maximum number of (source,group) per interface";
               type union {
                 type string {
                   pattern "<.*>|$.*";
                 }
                 type uint16 {
                   range "1 .. 32767";
                 }
               }
             }
             leaf group-threshold {
               description "Percentage of limit at which to generate warnings";
               type union {
                 type string {
                   pattern "<.*>|$.*";
                 }
                 type uint32 {
                   range "1 .. 100";
                 }
               }
             }
             leaf log-interval {
               description "Time between consecutive log messages";
               type union {
                 type string {
                   pattern "<.*>|$.*";
                 }
                 type uint32 {
                   range "6 .. 32767";
                 }
               }
             }
             leaf robust-count {
               description "Expected packet loss on a subnet";
               type union {
                 type string {
                   pattern "<.*>|$.*";
                 }
                 type uint32 {
                   range "2 .. 10";
                 }
               }
             }
             leaf query-interval {
               description "When to send host query messages";
               units "seconds";
               type union {
                 type string {
                   pattern "<.*>|$.*";
                 }
                 type uint32 {
                   range "1 .. 1024";
                 }
               }
             }
             leaf query-response-interval {
               description "How long to wait for a host query response";
               units "seconds";
               type string {
               }
             }
           }
         }
       }
     }
     container mld {
       presence "enable mld";
       description "MLD options";
       uses apply-advanced;
       container traceoptions {
         description "Trace options for MLD";
         uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "packets" {
                 description "Trace all MLD packets";
               }
               enum "query" {
                 description "Trace MLD membership query messages";
               }
               enum "report" {
                 description "Trace membership report messages";
               }
               enum "leave" {
                 description "Trace leave group messages (MLDv2 only)";
               }
               enum "mtrace" {
                 description "Trace mtrace packets";
               }
               enum "group" {
                 description "Trace group operations";
               }
               enum "client-notification" {
                 description "Trace notifications";
               }
               enum "host-notification" {
                 description "Trace host notifications";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       leaf query-interval {
         description "When to send host query messages";
         units "seconds";
         type union {
           type string {
             pattern "<.*>|$.*";
           }
           type uint32 {
             range "1 .. 1024";
           }
         }
       }
       leaf query-response-interval {
         description "How long to wait for a host query response";
         units "seconds";
         type string {
         }
       }
       leaf query-last-member-interval {
         description "When to send group query messages";
         units "seconds";
         type string {
         }
       }
       leaf robust-count {
         description "Expected packet loss on a subnet";
         type union {
           type string {
             pattern "<.*>|$.*";
           }
           type uint32 {
             range "2 .. 10";
           }
         }
       }
       leaf maximum-transmit-rate {
         description "Maximum transmission rate (packets per second)";
         type union {
           type string {
             pattern "<.*>|$.*";
           }
           type uint32 {
             range "1 .. 10000";
           }
         }
       }
       leaf accounting {
         description "Enable join and leave event notification";
         type empty;
       }
       list interface {
         key name;
         ordered-by user;
         description "Interface options for MLD";
         leaf name {
           type string;
         }
         uses apply-advanced;
         choice enable-disable {
           case case_1 {
             leaf disable {
               description "Disable MLD on this interface";
               type empty;
             }
           }
         }
         leaf version {
           description "Set mld version number on this interface";
           type union {
             type string {
               pattern "<.*>|$.*";
             }
             type uint8 {
               range "1 .. 2";
             }
           }
         }
         container static {
           description "Static group or source membership";
           uses apply-advanced;
           list group {
             key name;
             ordered-by user;
             description "IP multicast group address";
             leaf name {
               description "IP multicast group address";
               type jt:ipv6addr;
             }
             uses apply-advanced;
             leaf group-increment {
               description "Mask for the incrementing group IP address";
               type jt:ipv6addr;
             }
             leaf group-count {
               description "Number of groups";
               type union {
                 type string {
                   pattern "<.*>|$.*";
                 }
                 type uint32 {
                   range "1 .. 512";
                 }
               }
             }
             leaf exclude {
               description "Exclude sources";
               type empty;
             }
             list source {
               key name;
               ordered-by user;
               description "IP multicast source address";
               leaf name {
                 description "Source address of IP multicast data";
                 type jt:ipv6addr;
               }
               uses apply-advanced;
               leaf source-increment {
                 description "Mask for the incrementing source IP address";
                 type jt:ipv6addr;
               }
               leaf source-count {
                 description "Number of sources";
                 type union {
                   type string {
                     pattern "<.*>|$.*";
                   }
                   type uint32 {
                     range "1 .. 1024";
                   }
                 }
               }
             }
           }
         }
         leaf ssm-map {
           description "Map for ssm translation of mld v1 messages";
           type string;
         }
         leaf-list ssm-map-policy {
           ordered-by user;
           description "SSM map policy name";
           type jt:policy-algebra;
         }
         leaf immediate-leave {
           description "Group removed immediately, last membership query not sent";
           type empty;
         }
         leaf-list group-policy {
           ordered-by user;
           description "Group filter applied to incoming mld report messages";
           type jt:policy-algebra;
         }
         leaf group-limit {
           description "Maximum number of (source,group) per interface";
           type union {
             type string {
               pattern "<.*>|$.*";
             }
             type uint16 {
               range "1 .. 32767";
             }
           }
         }
         leaf group-threshold {
           description "Percentage of group-limit at which to start generating warnings";
           type union {
             type string {
               pattern "<.*>|$.*";
             }
             type uint16 {
               range "1 .. 100";
             }
           }
         }
         leaf log-interval {
           description "Time between consecutive log messages";
           type union {
             type string {
               pattern "<.*>|$.*";
             }
             type uint32 {
               range "6 .. 32767";
             }
           }
         }
         choice accounting-choice {
           leaf accounting {
             description "Enable join and leave event notification";
             type empty;
           }
           leaf no-accounting {
             description "Don't enable join and leave event notification";
             type empty;
           }
         }
         container passive {
           presence "enable passive";
           description "Suppress sending and receiving mld messages";
           leaf allow-receive {
             description "Allow receiving mld messages";
             type empty;
           }
           leaf send-general-query {
             description "Send mld general query messages";
             type empty;
           }
           leaf send-group-query {
             description "Send mld group query messages";
             type empty;
           }
         }
         leaf-list oif-map {
           ordered-by user;
           description "Output interface map";
           type jt:policy-algebra;
         }
         leaf distributed {
           description "Distributed MLD interface";
           type empty;
         }
       }
     }
     container amt {
       description "AMT configuration";
       uses juniper-protocols-amt;
     }
     container router-discovery {
       description "ICMP router discovery options";
       uses juniper-protocols-router-discovery;
     }
     container sap {
       presence "enable sap";
       description "Session Advertisement Protocol options";
       uses apply-advanced;
       choice enable-disable {
         case case_1 {
           leaf disable {
             description "Disable SAP";
             type empty;
           }
         }
       }
       list listen {
         key name;
         ordered-by user;
         description "Address for SAP and SDP to listen on";
         leaf name {
           description "IP address";
           type jt:ipv4addr;
         }
         leaf port {
           description "Port to listen for session advertisements";
           type union {
             type uint16;
             type string {
               pattern "<.*>|$.*";
             }
           }
         }
       }
     }
     container rsvp {
       description "RSVP options";
       uses juniper-protocols-rsvp;
     }
     container mpls {
       description "Multiprotocol Label Switching options";
       uses juniper-protocols-mpls;
     }
     container dvmrp {
       presence "enable dvmrp";
       description "DVMRP options";
       status deprecated;
       uses apply-advanced;
       choice enable-disable {
         case case_1 {
           leaf disable {
             description "Disable DVMRP";
             type empty;
           }
         }
       }
       container traceoptions {
         description "Trace options for DVMRP";
         uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "route" {
                 description "Trace routing information";
               }
               enum "poison" {
                 description "Trace poison-route-reverse packets";
               }
               enum "packets" {
                 description "Trace all DVMRP packets";
               }
               enum "probe" {
                 description "Trace probe packets";
               }
               enum "report" {
                 description "Trace DVMRP route report packets";
               }
               enum "neighbor" {
                 description "Trace neighbor probe packets";
               }
               enum "prune" {
                 description "Trace prune messages";
               }
               enum "graft" {
                 description "Trace graft messages";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       container rib-group {
         description "Routing table group";
         uses rib_group_inet_type;
       }
       leaf-list import {
         ordered-by user;
         description "Import policy";
         type jt:policy-algebra;
       }
       leaf-list export {
         ordered-by user;
         description "Export policy";
         type jt:policy-algebra;
       }
       list interface {
         key name;
         ordered-by user;
         description "DVMRP interface options";
         leaf name {
           description "Interface name";
           type union {
             type jt:interface-name;
             type string {
               pattern "<.*>|$.*";
             }
           }
         }
         uses apply-advanced;
         choice enable-disable {
           case case_1 {
             leaf disable {
               description "Disable DVMRP on this interface";
               type empty;
             }
           }
         }
         leaf mode {
           description "Mode of interface";
           type enumeration {
             enum "forwarding" {
               description "Use DVMRP for multicast forwarding";
             }
             enum "unicast-routing" {
               description "Use DVMRP for unicast routing only";
             }
           }
         }
         leaf metric {
           description "DVMRP metric value";
           type union {
             type string {
               pattern "<.*>|$.*";
             }
             type uint32 {
               range "1 .. 32";
             }
           }
         }
         leaf hold-time {
           description "When neighbors think the interface is down";
           units "seconds";
           type union {
             type string {
               pattern "<.*>|$.*";
             }
             type uint32 {
               range "1 .. 255";
             }
           }
         }
       }
     }
     container pim {
       description "PIM configuration";
       uses juniper-protocols-pim;
     }
     container rip {
       description "RIP options";
       uses juniper-protocols-rip;
     }
     container ripng {
       description "RIPng options";
       uses juniper-protocols-ripng;
     }
     container connections {
       description "Circuit cross-connect configuration";
       uses apply-advanced;
       list interface-switch {
         key name;
         ordered-by user;
         description "Bidirectional switch between interfaces";
         leaf name {
           description "Name of interface switch";
           type string {
           }
         }
         uses apply-advanced;
         list interface {
           key name;
           ordered-by user;
           description "Interface to be switched";
           leaf name {
             description "Interface name";
             type union {
               type jt:interface-name;
               type string {
                 pattern "<.*>|$.*";
               }
             }
           }
           uses apply-advanced;
         }
       }
       list remote-interface-switch {
         key name;
         ordered-by user;
         description "Bidirectional switch between a local and a remote interface";
         leaf name {
           description "Name of remote interface switch";
           type string {
           }
         }
         uses apply-advanced;
         leaf interface {
           description "Local interface name";
           type union {
             type jt:interface-name;
             type string {
               pattern "<.*>|$.*";
             }
           }
         }
         leaf transmit-lsp {
           description "Name of outgoing label-switched path";
           type string;
         }
         leaf receive-lsp {
           description "Name of incoming label-switched path";
           type string;
         }
       }
       list lsp-switch {
         key name;
         ordered-by user;
         description "Unidirectional switch between two label-switched paths";
         leaf name {
           description "Name of label-switched path switch";
           type string {
           }
         }
         uses apply-advanced;
         leaf transmit-lsp {
           description "Name of outgoing label-switched path";
           type string;
         }
         leaf receive-lsp {
           description "Name of incoming label-switched path";
           type string;
         }
       }
       list p2mp-transmit-switch {
         key name;
         ordered-by user;
         description "Local interface to point-to-multipoint LSP switch";
         leaf name {
           description "Point-to-multipoint switch name on which to transmit";
           type string {
           }
         }
         uses apply-advanced;
         leaf input-interface {
           description "Input interface name";
           type union {
             type jt:interface-name;
             type string {
               pattern "<.*>|$.*";
             }
           }
         }
         leaf transmit-p2mp-lsp {
           description "Point-to-multipoint LSP name on which to transmit";
           type string;
         }
         leaf-list output-interface {
           ordered-by user;
           description "Outgoing interface name";
           type union {
             type jt:interface-name;
             type string {
               pattern "<.*>|$.*";
             }
           }
           max-elements 16;
         }
       }
       list p2mp-receive-switch {
         key name;
         ordered-by user;
         description "Point-to-multipoint LSP to local interfaces switch";
         leaf name {
           description "Point-to-multipoint switch name on which to receive";
           type string {
           }
         }
         uses apply-advanced;
         leaf receive-p2mp-lsp {
           description "Point-to-multipoint LSP name on which to receive";
           type string;
         }
         leaf-list output-interface {
           ordered-by user;
           description "Next outgoing interface name";
           type union {
             type jt:interface-name;
             type string {
               pattern "<.*>|$.*";
             }
           }
         }
       }
     }
     container vrrp {
       description "VRRP options";
       uses apply-advanced;
       container traceoptions {
         description "Trace options for VRRP";
         uses apply-advanced;
         leaf no-remote-trace {
           description "Disable remote tracing";
           type empty;
         }
         container file {
           description "Trace file information";
           leaf filename {
             description "Name of file in which to write trace information";
             type string {
               length "1 .. 1024";
             }
           }
           leaf size {
             description "Maximum trace file size";
             type string;
           }
           leaf files {
             description "Maximum number of trace files";
             default "3";
             type union {
               type string {
                 pattern "<.*>|$.*";
               }
               type uint32 {
                 range "0 .. 4294967295";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
           leaf microsecond-stamp {
             description "Timestamp with microsecond granularity";
             type empty;
           }
         }
         list flag {
           key name;
           ordered-by user;
           description "Tracing parameters";
           leaf name {
             type enumeration {
               enum "database" {
                 description "Trace database";
               }
               enum "general" {
                 description "Trace general events";
               }
               enum "interfaces" {
                 description "Trace interface messages";
               }
               enum "normal" {
                 description "Trace normal events";
               }
               enum "packets" {
                 description "Trace packets";
               }
               enum "state" {
                 description "Trace state transitions";
               }
               enum "timer" {
                 description "Trace timer events";
               }
               enum "ppm" {
                 description "VRRP PPM related messages";
               }
               enum "all" {
                 description "Trace all events";
               }
             }
           }
         }
       }
       leaf failover-delay {
         description "Additional failover delay timer";
         units "milliseconds";
         type union {
           type string {
             pattern "<.*>|$.*";
           }
           type uint32 {
             range "50 .. 100000";
           }
         }
       }
       leaf startup-silent-period {
         description "Period for ignoring master down timer at device startup";
         units "seconds";
         type union {
           type string {
             pattern "<.*>|$.*";
           }
           type uint32 {
             range "1 .. 2000";
           }
         }
       }
       leaf asymmetric-hold-time {
         description "Priority hold time asymmetric behaviour";
         type empty;
       }
       leaf skew-timer-disable {
         description "Disable the skew timer";
         type empty;
       }
       leaf global-advertisements-threshold {
         description "Number of vrrp advertisements missed before declaring master down";
         default "3";
         type union {
           type string {
             pattern "<.*>|$.*";
           }
           type uint32 {
             range "1 .. 15";
           }
         }
       }
       leaf inherit-advertisement-interval {
         description "Advertisement interval for inherit sessions";
         default "120";
         type union {
           type string {
             pattern "<.*>|$.*";
           }
           type uint32 {
             range "5 .. 120";
           }
         }
       }
       leaf version-3 {
         description "VRRPv3 conformance";
         type empty;
       }
     }
     container l2circuit {
       description "Configuration for Layer 2 circuits over MPLS";
       uses apply-advanced;
       container traceoptions {
         description "Trace options for Layer 2 circuits";
         uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "error" {
                 description "Trace errors";
               }
               enum "topology" {
                 description "Trace Layer 2 circuit topology changes";
               }
               enum "fec" {
                 description "Trace Layer 2 circuit VC FEC advertisements";
               }
               enum "connections" {
                 description "Trace Layer 2 circuit connections";
               }
               enum "oam" {
                 description "Trace Layer 2 circuit OAM messages";
               }
               enum "egress-protection" {
                 description "Trace Layer 2 circuit egress protection messages";
               }
               enum "auto-sensing" {
                 description "Trace Layer 2 circuit PW auto-sensing";
               }
               enum "sdb" {
                 description "Trace SDB";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       list neighbor {
         key name;
         ordered-by user;
         description "List of Layer 2 circuits to this neighbor";
         leaf name {
           description "Neighbor ID";
           type jt:ipv4addr;
         }
         uses apply-advanced;
         list interface {
           key name;
           ordered-by user;
           description "Interface forming the Layer 2 circuit";
           leaf name {
             description "Interface name";
             type union {
               type jt:interface-name;
               type string {
                 pattern "<.*>|$.*";
               }
             }
           }
           uses apply-advanced;
           container static {
             presence "enable static";
             description "Configuration of static Pseudowire";
             uses apply-advanced;
             leaf incoming-label {
               description "Layer 2 circuit incoming static label";
               type union {
                 type string {
                   pattern "<.*>|$.*";
                 }
                 type uint32 {
                   range "16 .. 1048575";
                 }
               }
             }
             leaf outgoing-label {
               description "Layer 2 circuit outgoing static label";
               type union {
                 type string {
                   pattern "<.*>|$.*";
                 }
                 type uint32 {
                   range "16 .. 1048575";
                 }
               }
             }
             leaf send-oam {
               description "Turn on sending of l2ckt ping";
               type empty;
             }
           }
           leaf psn-tunnel-endpoint {
             description "Endpoint of the transport tunnel on the remote PE";
             type jt:ipv4addr;
           }
           leaf protect-interface {
             description "Name of protect interface";
             type union {
               type jt:interface-name;
               type string {
                 pattern "<.*>|$.*";
               }
             }
           }
           leaf virtual-circuit-id {
             description "Identifier for this Layer 2 circuit";
             type union {
               type string {
                 pattern "<.*>|$.*";
               }
               type uint32 {
                 range "1 .. 4294967295";
               }
             }
           }
           leaf description {
             description "Text description of Layer 2 circuit";
             type string;
           }
           choice control-word-choice {
             leaf control-word {
               description "Add control word to the Layer 2 encapsulation";
               type empty;
             }
             leaf no-control-word {
               description "Don't add control word to the Layer 2 encapsulation";
               type empty;
             }
           }
           leaf flow-label-transmit {
             description "Advertise capability to push Flow Label in transmit direction to remote PE";
             type empty;
           }
           leaf flow-label-transmit-static {
             description "Push Flow Label on PW packets sent to remote PE";
             type empty;
           }
           leaf flow-label-receive {
             description "Advertise capability to pop Flow Label in receive direction to remote PE";
             type empty;
           }
           leaf flow-label-receive-static {
             description "Pop Flow Label from PW packets received from remote PE";
             type empty;
           }
           leaf community {
             description "Community associated with this Layer 2 circuit";
             type string;
           }
           leaf mtu {
             description "MTU to be advertised for this Layer 2 circuit";
             type union {
               type string {
                 pattern "<.*>|$.*";
               }
               type uint32 {
                 range "512 .. 65535";
               }
             }
           }
           leaf encapsulation-type {
             description "Encapsulation type for VPN";
             type enumeration {
               enum "atm-aal5" {
                 description "ATM AAL/5 encapsulation";
               }
               enum "atm-cell" {
                 description "ATM port promiscuous mode cell encapsulation";
               }
               enum "atm-cell-port-mode" {
                 description "ATM port promiscuous mode cell encapsulation";
               }
               enum "atm-cell-vp-mode" {
                 description "ATM VP promiscuous mode cell encapsulation";
               }
               enum "atm-cell-vc-mode" {
                 description "ATM non-promiscuous cell encapsulation";
               }
               enum "frame-relay" {
                 description "Frame Relay encapsulation";
               }
               enum "ppp" {
                 description "PPP encapsulation";
               }
               enum "cisco-hdlc" {
                 description "Cisco-compatible HDLC encapsulation";
               }
               enum "ethernet-vlan" {
                 description "Ethernet VLAN encapsulation";
               }
               enum "ethernet" {
                 description "Ethernet encapsulation";
               }
               enum "interworking" {
                 description "Layer 2.5 interworking VPN";
               }
               enum "frame-relay-port-mode" {
                 description "Frame Relay port mode encapsulation";
               }
               enum "satop-t1" {
                 description "SATOP-T1 based Layer 2 VPN";
               }
               enum "satop-e1" {
                 description "SATOP-E1 based Layer 2 VPN";
               }
               enum "satop-t3" {
                 description "SATOP-T3 based Layer 2 VPN";
               }
               enum "satop-e3" {
                 description "SATOP-E3 based Layer 2 VPN";
               }
               enum "cesop" {
                 description "CESOP based Layer 2 VPN";
               }
             }
           }
           leaf ignore-encapsulation-mismatch {
             description "Allow different encapsulation types on local and remote end";
             type empty;
           }
           leaf ignore-mtu-mismatch {
             description "Allow different MTUs on interfaces";
             type empty;
           }
           leaf no-revert {
             description "Don't revert to primary-interface";
             type empty;
           }
           container bandwidth {
             description "Bandwidth to reserve (bps)";
             uses bandwidth-type;
           }
           container pseudowire-status-tlv {
             presence "enable pseudowire-status-tlv";
             description "Send pseudowire status TLV";
             uses apply-advanced;
             leaf hot-standby-vc-on {
               description "Activate pseudowire upon arrival of 'hot-standby' status TLV message";
               type empty;
             }
           }
           leaf switchover-delay {
             description "Layer 2 circuit switchover delay";
             default "10000";
             units "milliseconds";
             type union {
               type string {
                 pattern "<.*>|$.*";
               }
               type uint32 {
                 range "0 .. 180000";
               }
             }
           }
           container revert-time {
             presence "enable revert-time";
             description "Enable pseudowire redundancy reversion";
             leaf delay {
               description "Reversion timer (seconds)";
               units "seconds";
               type union {
                 type string {
                   pattern "<.*>|$.*";
                 }
                 type uint32 {
                   range "0 .. 600";
                 }
               }
             }
             leaf maximum {
               description "Maximum reversion interval to add over revert-time delay";
               units "seconds";
               type union {
                 type string {
                   pattern "<.*>|$.*";
                 }
                 type uint32 {
                   range "0 .. 1200";
                 }
               }
             }
           }
           leaf connection-protection {
             description "End-2-end protection via OAM failure detection";
             type empty;
           }
           list backup-neighbor {
             key name;
             ordered-by user;
             description "Configuration of redundant l2circuit";
             leaf name {
               description "Neighbor ID";
               type jt:ipv4addr;
             }
             uses apply-advanced;
             container static {
               presence "enable static";
               description "Configuration of static Pseudowire";
               uses apply-advanced;
               leaf incoming-label {
                 description "Layer 2 circuit incoming static label";
                 type union {
                   type string {
                     pattern "<.*>|$.*";
                   }
                   type uint32 {
                     range "16 .. 1048575";
                   }
                 }
               }
               leaf outgoing-label {
                 description "Layer 2 circuit outgoing static label";
                 type union {
                   type string {
                     pattern "<.*>|$.*";
                   }
                   type uint32 {
                     range "16 .. 1048575";
                   }
                 }
               }
             }
             leaf virtual-circuit-id {
               description "Identifier for this Layer 2 circuit";
               type union {
                 type string {
                   pattern "<.*>|$.*";
                 }
                 type uint32 {
                   range "1 .. 4294967295";
                 }
               }
             }
             leaf community {
               description "Community associated with this Layer 2 circuit";
               type string;
             }
             leaf psn-tunnel-endpoint {
               description "Endpoint of the transport tunnel on the remote PE";
               type jt:ipv4addr;
             }
             leaf standby {
               description "Keep backup pseudowire in continuous standby";
               type empty;
             }
             leaf hot-standby {
               description "Keep backup pseudowire in continuous standby mode and ready for traffic forwarding";
               type empty;
             }
           }
           container egress-protection {
             description "Egress protection for Layer 2 circuit";
             uses apply-advanced;
             choice protection-type {
               case case_1 {
                 leaf protector-interface {
                   description "Name of the protector interface for local protection";
                   type union {
                     type jt:interface-name;
                     type string {
                       pattern "<.*>|$.*";
                     }
                   }
                 }
               }
               case case_2 {
                 container protector-pe {
                   description "Address of the protector PE";
                   leaf address {
                     description "Address of the protector PE";
                     type jt:ipv4addr;
                   }
                   leaf context-identifier {
                     description "Identifier of the context used for this protection";
                     type jt:ipv4addr;
                   }
                   leaf lsp {
                     description "Name of the label-switched path used for the protection";
                     type string {
                     }
                   }
                 }
               }
             }
             container protected-l2circuit {
               description "Primary Layer 2 circuit to be protected";
               leaf l2circuit-name {
                 description "Name of the protected Layer 2 circuit";
                 type string {
                 }
               }
               leaf ingress-pe {
                 description "Ingress PE address of the protected Layer 2 circuit";
                 type jt:ipv4addr;
               }
               leaf egress-pe {
                 description "Egress PE address of the protected Layer 2 circuit";
                 type jt:ipv4addr;
               }
               leaf virtual-circuit-id {
                 description "Identifier of the protected Layer 2 circuit";
                 type union {
                   type string {
                     pattern "<.*>|$.*";
                   }
                   type uint32 {
                     range "1 .. 4294967295";
                   }
                 }
               }
             }
           }
         }
       }
       container local-switching {
         description "Configuration of Layer 2 circuits local switching";
         uses apply-advanced;
         list interface {
           key name;
           ordered-by user;
           description "Interface forming the local Layer 2 circuit";
           leaf name {
             description "Interface name";
             type union {
               type jt:interface-name;
               type string {
                 pattern "<.*>|$.*";
               }
             }
           }
           uses apply-advanced;
           leaf no-revert {
             description "Do not revert to primary-interface";
             type empty;
           }
           leaf protect-interface {
             description "Name of protect interface";
             type union {
               type jt:interface-name;
               type string {
                 pattern "<.*>|$.*";
               }
             }
           }
           leaf connection-protection {
             description "End-2-end protection via OAM failure detection";
             type empty;
           }
           list neighbor {
             key name;
             ordered-by user;
             description "Configuration of Layer 2 circuit";
             leaf name {
               description "Neighbor ID";
               type jt:ipv4addr;
             }
             uses apply-advanced;
             leaf virtual-circuit-id {
               description "Identifier for this Layer 2 circuit";
               type union {
                 type string {
                   pattern "<.*>|$.*";
                 }
                 type uint32 {
                   range "1 .. 4294967295";
                 }
               }
             }
             leaf community {
               description "Community associated with this Layer 2 circuit";
               type string;
             }
             leaf psn-tunnel-endpoint {
               description "Endpoint of the transport tunnel on the neighbor PE";
               type jt:ipv4addr;
             }
             leaf mtu {
               description "MTU to be advertised for this Layer 2 circuit";
               type union {
                 type string {
                   pattern "<.*>|$.*";
                 }
                 type uint32 {
                   range "512 .. 65535";
                 }
               }
             }
           }
           list backup-neighbor {
             key name;
             ordered-by user;
             description "Configuration of redundant l2circuit";
             leaf name {
               description "Backup Neighbor ID";
               type jt:ipv4addr;
             }
             uses apply-advanced;
             leaf virtual-circuit-id {
               description "Identifier for this Layer 2 circuit";
               type union {
                 type string {
                   pattern "<.*>|$.*";
                 }
                 type uint32 {
                   range "1 .. 4294967295";
                 }
               }
             }
             leaf psn-tunnel-endpoint {
               description "Endpoint of the transport tunnel on the backup neighbor PE";
               type jt:ipv4addr;
             }
             leaf community {
               description "Community associated with this Layer 2 circuit";
               type string;
             }
             leaf mtu {
               description "MTU to be advertised for this Layer 2 circuit";
               type union {
                 type string {
                   pattern "<.*>|$.*";
                 }
                 type uint32 {
                   range "512 .. 65535";
                 }
               }
             }
           }
           container end-interface {
             description "Interface name of the other end point";
             uses apply-advanced;
             leaf interface {
               description "Interface name";
               type union {
                 type jt:interface-name;
                 type string {
                   pattern "<.*>|$.*";
                 }
               }
             }
             leaf no-revert {
               description "Do not revert to primary-interface";
               type empty;
             }
             leaf protect-interface {
               description "Name of protect interface";
               type union {
                 type jt:interface-name;
                 type string {
                   pattern "<.*>|$.*";
                 }
               }
             }
             leaf backup-interface {
               description "Name of backup interface";
               type union {
                 type jt:interface-name;
                 type string {
                   pattern "<.*>|$.*";
                 }
               }
             }
           }
           leaf description {
             description "Text description of Layer 2 circuit";
             type string;
           }
           leaf encapsulation-type {
             description "Encapsulation type for VPN";
             type enumeration {
               enum "atm-aal5" {
                 description "ATM AAL/5 encapsulation";
               }
               enum "atm-cell" {
                 description "ATM port promiscuous mode cell encapsulation";
               }
               enum "atm-cell-port-mode" {
                 description "ATM port promiscuous mode cell encapsulation";
               }
               enum "atm-cell-vp-mode" {
                 description "ATM VP promiscuous mode cell encapsulation";
               }
               enum "atm-cell-vc-mode" {
                 description "ATM non-promiscuous cell encapsulation";
               }
               enum "frame-relay" {
                 description "Frame Relay encapsulation";
               }
               enum "ppp" {
                 description "PPP encapsulation";
               }
               enum "cisco-hdlc" {
                 description "Cisco-compatible HDLC encapsulation";
               }
               enum "ethernet-vlan" {
                 description "Ethernet VLAN encapsulation";
               }
               enum "ethernet" {
                 description "Ethernet encapsulation";
               }
               enum "interworking" {
                 description "Layer 2.5 interworking VPN";
               }
               enum "frame-relay-port-mode" {
                 description "Frame Relay port mode encapsulation";
               }
               enum "satop-t1" {
                 description "SATOP-T1 based Layer 2 VPN";
               }
               enum "satop-e1" {
                 description "SATOP-E1 based Layer 2 VPN";
               }
               enum "satop-t3" {
                 description "SATOP-T3 based Layer 2 VPN";
               }
               enum "satop-e3" {
                 description "SATOP-E3 based Layer 2 VPN";
               }
               enum "cesop" {
                 description "CESOP based Layer 2 VPN";
               }
             }
           }
           leaf ignore-encapsulation-mismatch {
             description "Allow different encapsulation types on local and remote end";
             type empty;
           }
           leaf ignore-mtu-mismatch {
             description "Allow different MTUs on interfaces";
             type empty;
           }
         }
       }
       container auto-sensing {
         presence "enable auto-sensing";
         description "Configuration of PW auto-sensing";
         uses apply-advanced;
         leaf password {
           description "Password for authentication with Radius server; 1 to 15 characters long";
           type jt:unreadable;
         }
       }
     }
     container evpn {
       description "Configuration EVPN default routing instance";
       uses apply-advanced;
       container traceoptions {
         description "Trace options for Layer 2 VPNs";
         uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "error" {
                 description "Trace errors";
               }
               enum "topology" {
                 description "Trace Layer 2 VPN, VPLS and EVPN topology changes";
               }
               enum "nlri" {
                 description "Trace Layer 2 VPN, VPLS and EVPN remote site advertisements";
               }
               enum "connections" {
                 description "Trace Layer 2 VPN and VPLS connections";
               }
               enum "automatic-site" {
                 description "Trace VPLS automatic site state";
               }
               enum "oam" {
                 description "Trace OAM messages";
               }
               enum "mac-database" {
                 description "Trace MAC route database in a EVPN instance";
               }
               enum "nsr" {
                 description "Trace NSR in a EVPN instance";
               }
               enum "egress-protection" {
                 description "Trace Edge Protection messages";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       leaf es-import-oldstyle {
         description "Enable noncompliant ES import route-target computation";
         type empty;
       }
       leaf es-label-oldstyle {
         description "Enable noncompliant ESI 24 bit label";
         type empty;
       }
       leaf mac-history {
         description "Number of history entries to be maitained per mac";
         type union {
           type string {
             pattern "<.*>|$.*";
           }
           type uint16 {
             range "0 .. 255";
           }
         }
       }
       list mac-list {
         key name;
         description "Configure MAC lists";
         leaf name {
           description "List name";
           type string {
             length "1 .. 128";
           }
         }
         uses apply-advanced;
         leaf-list mac-address {
           description "MAC address";
           type jt:mac-addr;
         }
       }
       container vni-options {
         description "Vni options";
         uses juniper-protocols-vni-options;
       }
       leaf encapsulation {
         description "Encapsulation type for EVPN";
         default "mpls";
         type enumeration {
           enum "mpls" {
             description "MPLS encapsulation";
           }
           enum "vxlan" {
             description "VXLAN encapsulation";
           }
         }
       }
       leaf multicast-mode {
         description "Multicast mode for EVPN";
         default "ingress-replication";
         type enumeration {
           enum "ingress-replication" {
             description "Ingress Replication";
           }
         }
       }
       container assisted-replication {
         description "Option to enable Assisted Replication";
         uses apply-advanced;
         choice AR {
           case case_1 {
             container leaf {
               presence "enable leaf";
               description "Assisted Replicator Leaf";
               uses apply-advanced;
               leaf replicator-activation-delay {
                 description "Dealy interval in starting replication";
                 default "10";
                 units "seconds";
                 type union {
                   type string {
                     pattern "<.*>|$.*";
                   }
                   type uint32 {
                     range "0 .. 180";
                   }
                 }
               }
             }
           }
           case case_2 {
           }
         }
       }
       leaf designated-forwarder-election-hold-time {
         description "Time to wait before electing a DF(seconds)";
         units "seconds";
         type union {
           type string {
             pattern "<.*>|$.*";
           }
           type uint32 {
             range "1 .. 1800";
           }
         }
       }
       container mac-mobility {
         description "MAC mobility settings";
         uses apply-advanced;
         leaf no-sequence-numbers {
           description "Don't use sequence numbers for MAC mobility";
           type empty;
         }
       }
       container remote-ip-host-routes {
         presence "enable remote-ip-host-routes";
         description "Virtual machine traffic optimization(VMTO) for EVPN";
         uses apply-advanced;
         leaf-list import {
           ordered-by user;
           description "Policy to control the creation of remote IP host routes";
           type jt:policy-algebra;
         }
       }
     }
     container link-management {
       description "LMP options";
       uses juniper-protocols-lmp;
     }
     container pgm {
       description "PGM options";
       presence "enable pgm";
       status deprecated;
       uses juniper-protocols-pgm;
     }
     container bfd {
       description "Bidirectional Forwarding Detection (BFD) options";
       uses apply-advanced;
       container traceoptions {
         description "Trace options for BFD";
         uses apply-advanced;
         leaf no-remote-trace {
           description "Disable remote tracing";
           type empty;
         }
         container file {
           description "Trace file information";
           leaf filename {
             description "Name of file in which to write trace information";
             type string {
               length "1 .. 1024";
             }
           }
           leaf size {
             description "Maximum trace file size";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           ordered-by user;
           description "Trace flag information";
           leaf name {
             type enumeration {
               enum "adjacency" {
                 description "Trace adjacency messages";
               }
               enum "event" {
                 description "Trace all events";
               }
               enum "error" {
                 description "Trace all errors";
               }
               enum "rtsock" {
                 description "Trace all rtscok messages";
               }
               enum "packet" {
                 description "Trace all packets";
               }
               enum "ppm-packet" {
                 description "Trace packet activity by periodic packet management";
               }
               enum "pipe" {
                 description "Trace pipe messages";
               }
               enum "pipe-detail" {
                 description "Trace pipe messages in detail";
               }
               enum "state" {
                 description "Trace state transitions";
               }
               enum "timer" {
                 description "Trace timer processing";
               }
               enum "nsr-synchronization" {
                 description "Trace NSR synchronization events";
               }
               enum "nsr-packet" {
                 description "Trace packet activity of NSR";
               }
               enum "issu" {
                 description "Trace ISSU packet activity";
               }
               enum "slow-start" {
                 description "Trace slow-start activity";
               }
               enum "session" {
                 description "Per session activity";
               }
               enum "all" {
                 description "Trace everything";
               }
             }
           }
         }
       }
       leaf no-issu-timer-negotiation {
         description "Disable ISSU timer negotiation";
         type empty;
       }
       container sbfd {
         description "Seamless BFD parameters";
         uses apply-advanced;
         leaf-list pool {
           description "List of Seamless BFD endpoints";
           type union {
             type uint32;
             type string {
               pattern "<.*>|$.*";
             }
           }
         }
         list local-discriminator {
           key name;
           ordered-by user;
           description "Local discriminator for Seamless BFD responder";
           leaf name {
             description "Local discriminator for Seamless BFD responder";
             type union {
               type string {
                 pattern "<.*>|$.*";
               }
               type uint32 {
                 range "1 .. 4294967295";
               }
             }
           }
           uses apply-advanced;
           leaf minimum-receive-interval {
             description "Minimum receive interval for Seamless BFD responder";
             units "milliseconds";
             type union {
               type string {
                 pattern "<.*>|$.*";
               }
               type uint32 {
                 range "10 .. 255000";
               }
             }
           }
         }
       }
     }
     container mvpn {
       description "BGP-MVPN configuration";
       uses juniper-protocols-mvpn;
     }
     container source-packet-routing {
       presence "enable source-packet-routing";
       description "Enable source packet routing (SPRING)";
       uses apply-advanced;
       container traceoptions {
         description "Trace options for soure-packet-routing";
         uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "controller" {
                 description "Trace controller-related activity";
               }
               enum "state" {
                 description "Trace LSP state-related activity";
               }
               enum "route" {
                 description "Trace route-related activity";
               }
               enum "general" {
                 description "Trace general activity";
               }
               enum "interface" {
                 description "Trace interface-related activity";
               }
               enum "all" {
                 description "Trace everything";
               }
             }
           }
         }
       }
       list lsp-external-controller {
         key name;
         ordered-by user;
         description "External path computing entity";
         leaf name {
           description "Name of the external path computing entity";
           type string {
           }
         }
         uses apply-advanced;
       }
       leaf preference {
         description "Route preference for SPRING-TE routes";
         type union {
           type uint32;
           type string {
             pattern "<.*>|$.*";
           }
         }
       }
       leaf sr-preference-override {
         description "SR-preference override for static SR-policies.Higher value is more preferred";
         type union {
           type string {
             pattern "<.*>|$.*";
           }
           type uint32 {
             range "0 .. 4294967295";
           }
         }
       }
       leaf sr-preference {
         description "SR-preference for static SR-policies.Higher value is more preferred";
         type union {
           type string {
             pattern "<.*>|$.*";
           }
           type uint32 {
             range "0 .. 4294967295";
           }
         }
       }
       leaf maximum-segment-list-depth {
         description "Maximum segment list depth for SR-TE policies";
         type union {
           type string {
             pattern "<.*>|$.*";
           }
           type uint32 {
             range "1 .. 5";
           }
         }
       }
       list segment-list {
         key name;
         ordered-by user;
         description "Explicit path for SR-TE segments";
         leaf name {
           description "Name of SR-TE segment-list";
           type string {
             length "1 .. 64";
           }
         }
         uses apply-advanced;
         list hop-list {
           key name;
           ordered-by user;
           max-elements 5;
           leaf name {
             description "Next hop in SR-TE segment-list";
             type string {
               length "1 .. 64";
             }
           }
           uses apply-advanced;
           leaf label {
             description "Next label in SR-TE segment-list";
             type union {
               type string {
                 pattern "<.*>|$.*";
               }
               type uint32 {
                 range "0 .. 1048575";
               }
             }
           }
           leaf ip-address {
             description "IP address of the hop";
             type jt:ipaddr;
           }
         }
         container bfd-liveness-detection {
           description "Bidirectional forwarding detection options";
           uses apply-advanced;
           container sbfd {
             presence "enable sbfd";
             description "Seamless BFD parameters";
             uses apply-advanced;
             leaf remote-discriminator {
               description "Remote discriminator of reflector";
               type union {
                 type string {
                   pattern "<.*>|$.*";
                 }
                 type uint32 {
                   range "0 .. 4294967295";
                 }
               }
             }
           }
           leaf minimum-interval {
             description "Minimum transmit and receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           leaf no-router-alert-option {
             description "Do not set the Router Alert option in IP header";
             type empty;
           }
         }
         leaf inherit-label-nexthops {
           description "Inherit label nexthops for first hop in this segment list";
           type empty;
         }
       }
       list source-routing-path {
         key name;
         ordered-by user;
         description "Configure a source-routing-path";
         leaf name {
           description "Name of the source routing path";
           type string {
             length "1 .. 64";
           }
         }
         uses apply-advanced;
         leaf ldp-tunneling {
           description "Allow LDP to use this LSP for tunneling";
           type empty;
         }
         leaf to {
           description "Ip-address of the tunnel end-point";
           type jt:ipaddr;
         }
         leaf color {
           description "Color identifier for the tunnel end-point";
           type union {
             type uint32;
             type string {
               pattern "<.*>|$.*";
             }
           }
         }
         leaf no-ingress {
           description "Disable ingress functionality for this tunnel";
           type empty;
         }
         leaf binding-sid {
           description "Specify the binding-label to enable transit functionality for this tunnel";
           type union {
             type string {
               pattern "<.*>|$.*";
             }
             type uint32 {
               range "16 .. 1048575";
             }
           }
         }
         list install {
           key name;
           ordered-by user;
           description "Install prefix";
           leaf name {
             description "Destination prefix";
             type jt:ipaddr;
           }
         }
         leaf preference {
           description "Preference for routes downloaded for this tunnel";
           type union {
             type uint32;
             type string {
               pattern "<.*>|$.*";
             }
           }
         }
         leaf metric {
           description "Metric for routes downloaded for this tunnel";
           type union {
             type string {
               pattern "<.*>|$.*";
             }
             type uint32 {
               range "1 .. 16777215";
             }
           }
         }
         leaf sr-preference {
           description "SR-preference for SPRING-TE routes. Higher value is more preferred";
           type union {
             type string {
               pattern "<.*>|$.*";
             }
             type uint32 {
               range "0 .. 4294967295";
             }
           }
         }
         list primary {
           key name;
           ordered-by user;
           description "Configure a primary segment list for this source-routing-path";
           max-elements 8;
           leaf name {
             description "Name of SR-TE segment-list";
             type string {
               length "1 .. 64";
             }
           }
           uses apply-advanced;
           leaf weight {
             description "Specify the balance factor for this segment list in SR-TE tunnel";
             type union {
               type uint32;
               type string {
                 pattern "<.*>|$.*";
               }
             }
           }
         }
         list secondary {
           key name;
           ordered-by user;
           description "Configure a secondary segment list for this source-routing-path";
           max-elements 1;
           leaf name {
             description "Name of SR-TE segment-list";
             type string {
               length "1 .. 64";
             }
           }
           uses apply-advanced;
         }
       }
       leaf inherit-label-nexthops {
         description "Inherit label nexthops for first hop in segment lists";
         type empty;
       }
       container telemetry {
         description "Enable telemetry on SR-TE policies";
         uses apply-advanced;
         container statistics {
           presence "enable statistics";
           description "Enable traffic-statistics collection on SR-TE policies";
           uses apply-advanced;
           leaf no-transit {
             description "Disable statistics collection on binding sid route";
             type empty;
           }
           leaf no-ingress {
             description "Disable statistics collection on destination route";
             type empty;
           }
         }
       }
     }
     container l2-learning {
       description "Layer 2 forwarding configuration";
       uses juniper-protocols-bridge;
     }
     container dcbx {
       presence "enable dcbx";
     }
     container lldp {
       description "Link Layer Detection Protocol";
       uses apply-advanced;
       choice enable-disable {
         case case_1 {
           leaf disable {
             description "Disable LLDP";
             type empty;
           }
         }
       }
       container traceoptions {
         description "Trace options for LLDP";
         uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           description "Tracing parameters";
           leaf name {
             type enumeration {
               enum "all" {
                 description "Trace configuration events";
               }
               enum "configuration" {
                 description "Log configuration events";
               }
               enum "rtsock" {
                 description "Trace rtsock message events";
               }
               enum "packet" {
                 description "Trace packet information";
               }
               enum "protocol" {
                 description "Trace protocol information";
               }
               enum "interface" {
                 description "Trace interface update events";
               }
               enum "vlan" {
                 description "Trace VLAN update events";
               }
               enum "snmp" {
                 description "Trace SNMP events";
               }
               enum "jvision" {
                 description "Trace Jvision events";
               }
             }
           }
           leaf disable {
             description "Disable this trace flag";
             type empty;
           }
         }
       }
       leaf management-address {
         description "LLDP management address";
         type jt:ipaddr;
       }
       leaf advertisement-interval {
         description "Transmit interval for LLDP messages";
         default "30";
         units "seconds";
         type union {
           type string {
             pattern "<.*>|$.*";
           }
           type uint32 {
             range "5 .. 32768";
           }
         }
       }
       leaf transmit-delay {
         description "Transmit delay time interval for LLDP messages";
         units "seconds";
         type union {
           type string {
             pattern "<.*>|$.*";
           }
           type uint32 {
             range "1 .. 8192";
           }
         }
       }
       leaf hold-multiplier {
         description "Hold timer interval for LLDP messages";
         default "4";
         type union {
           type string {
             pattern "<.*>|$.*";
           }
           type uint32 {
             range "2 .. 10";
           }
         }
       }
       leaf ptopo-configuration-trap-interval {
         description "Interval for physical topology configuration change trap";
         default "0";
         units "seconds";
         type union {
           type string {
             pattern "<.*>|$.*";
           }
           type uint32 {
             range "0 .. 3600";
           }
         }
       }
       leaf ptopo-configuration-maximum-hold-time {
         description "Hold time for physical topology connection entries";
         default "300";
         units "seconds";
         type union {
           type string {
             pattern "<.*>|$.*";
           }
           type uint32 {
             range "1 .. 2147483647";
           }
         }
       }
       leaf lldp-configuration-notification-interval {
         description "Time interval for LLDP notification";
         default "5";
         units "seconds";
         type union {
           type string {
             pattern "<.*>|$.*";
           }
           type uint32 {
             range "5 .. 3600";
           }
         }
       }
       leaf port-id-subtype {
         description "Sub-type to be used for Port ID TLV generation";
         default "locally-assigned";
         type enumeration {
           enum "locally-assigned" {
             description "Locally assigned value (SNMP index of the interface)";
           }
           enum "interface-name" {
             description "Interface name on which LLDPDU is sent";
           }
         }
       }
       leaf port-description-type {
         description "The Interfaces Group MIB object to be used for Port Description TLV generation";
         default "interface-alias";
         type enumeration {
           enum "interface-alias" {
             description "Use object ifAlias value for TLV generation";
           }
           enum "interface-description" {
             description "Use object ifDescr value for TLV generation";
           }
         }
       }
       leaf neighbour-port-info-display {
         description "Show lldp neighbors to display port-id or port-description ";
         type enumeration {
           enum "port-id" {
             description "Display port-id information of neighbor in port info";
           }
           enum "port-description" {
             description "Display port description of neighbor in port info";
           }
         }
       }
       leaf vlan-name-tlv-option {
         description "Vlan tlv options to transmit vlan name or vlan-id";
         default "vlan-id";
         type enumeration {
           enum "vlan-id" {
             description "Use vlan-id for tlv";
           }
           enum "name" {
             description "Use vlan-name for tlv";
           }
         }
       }
       leaf-list tlv-select {
         ordered-by user;
         description "Select TLVs to be sent";
         type enumeration {
           enum "port-description" {
             description "Port Description";
           }
           enum "system-name" {
             description "System Name";
           }
           enum "system-description" {
             description "System Description";
           }
           enum "system-capabilities" {
             description "System Capabilities";
           }
           enum "management-address" {
             description "Management Address";
           }
           enum "mac-phy-config-status" {
             description "OUI IEEE 802.3 mac-phy-config-status";
           }
           enum "power-vi-mdi" {
             description "OUI IEEE 802.3 power-vi-mdi";
           }
           enum "link-aggregation" {
             description "OUI IEEE 802.3 link-aggregation";
           }
           enum "maximum-frame-size" {
             description "OUI IEEE 802.3 maximum-frame-size";
           }
           enum "jnpr-chassis-serial" {
             description "OUI Juniper chassis-serial";
           }
           enum "jnpr-vcp" {
             description "OUI Juniper vcp";
           }
           enum "jnpr-mode-change" {
             description "OUI Juniper mode-change";
           }
           enum "jnpr-mode-change-error" {
             description "OUI Juniper mode-change-error";
           }
           enum "jnpr-mode-change-ip-address" {
             description "OUI Juniper mode-change-ip-address";
           }
           enum "jnpr-mode-change-image-name" {
             description "OUI Juniper mode-change-image-name";
           }
           enum "jnpr-mode-change-ftp-login" {
             description "OUI Juniper mode-change-ftp-login";
           }
           enum "jnpr-mode-change-image-md5" {
             description "OUI Juniper mode-change-image-md5";
           }
           enum "jnpr-mode-change-ftp-server" {
             description "OUI Juniper mode-change-ftp-server";
           }
           enum "port-vid" {
             description "OUI IEEE 802.1 port-vid";
           }
           enum "port-protocol-vid" {
             description "OUI IEEE 802.1 port-procol-vid";
           }
           enum "vlan-name" {
             description "OUI IEEE 802.1 vlan-name";
           }
           enum "protocol-id" {
             description "OUI IEEE 802.1 protocol-id";
           }
           enum "evb" {
             description "OUI IEEE 82.1QBG evb";
           }
         }
       }
       leaf-list tlv-filter {
         ordered-by user;
         description "Filter TLVs to be sent";
         type enumeration {
           enum "all" {
             description "Filter all non mandatory TLVs";
           }
           enum "port-description" {
             description "Port Description";
           }
           enum "system-name" {
             description "System Name";
           }
           enum "system-description" {
             description "System Description";
           }
           enum "system-capabilities" {
             description "System Capabilities";
           }
           enum "management-address" {
             description "Management Address";
           }
           enum "mac-phy-config-status" {
             description "OUI IEEE 802.3 mac-phy-config-status";
           }
           enum "power-vi-mdi" {
             description "OUI IEEE 802.3 power-vi-mdi";
           }
           enum "link-aggregation" {
             description "OUI IEEE 802.3 link-aggregation";
           }
           enum "maximum-frame-size" {
             description "OUI IEEE 802.3 maximum-frame-size";
           }
           enum "jnpr-chassis-serial" {
             description "OUI Juniper chassis-serial";
           }
           enum "jnpr-vcp" {
             description "OUI Juniper vcp";
           }
           enum "jnpr-mode-change" {
             description "OUI Juniper mode-change";
           }
           enum "jnpr-mode-change-error" {
             description "OUI Juniper mode-change-error";
           }
           enum "jnpr-mode-change-ip-address" {
             description "OUI Juniper mode-change-ip-address";
           }
           enum "jnpr-mode-change-image-name" {
             description "OUI Juniper mode-change-image-name";
           }
           enum "jnpr-mode-change-ftp-login" {
             description "OUI Juniper mode-change-ftp-login";
           }
           enum "jnpr-mode-change-image-md5" {
             description "OUI Juniper mode-change-image-md5";
           }
           enum "jnpr-mode-change-ftp-server" {
             description "OUI Juniper mode-change-ftp-server";
           }
           enum "port-vid" {
             description "OUI IEEE 802.1 port-vid";
           }
           enum "port-protocol-vid" {
             description "OUI IEEE 802.1 port-procol-vid";
           }
           enum "vlan-name" {
             description "OUI IEEE 802.1 vlan-name";
           }
           enum "protocol-id" {
             description "OUI IEEE 802.1 protocol-id";
           }
           enum "evb" {
             description "OUI IEEE 802.1QBG evb";
           }
         }
       }
       list interface {
         key name;
         ordered-by user;
         description "Interface configuration";
         leaf name {
           type string;
         }
         uses apply-advanced;
         choice enable-disable {
           case case_1 {
             leaf disable {
               description "Disable LLDP";
               type empty;
             }
           }
         }
         leaf-list tlv-select {
           ordered-by user;
           description "Select TLV(s) to be sent";
           type enumeration {
             enum "port-description" {
               description "Port Description";
             }
             enum "system-name" {
               description "System Name";
             }
             enum "system-description" {
               description "System Description";
             }
             enum "system-capabilities" {
               description "System Capabilities";
             }
             enum "management-address" {
               description "Management Address";
             }
             enum "mac-phy-config-status" {
               description "OUI IEEE 802.3 mac-phy-config-status";
             }
             enum "power-vi-mdi" {
               description "OUI IEEE 802.3 power-vi-mdi";
             }
             enum "link-aggregation" {
               description "OUI IEEE 802.3 link-aggregation";
             }
             enum "maximum-frame-size" {
               description "OUI IEEE 802.3 maximum-frame-size";
             }
             enum "jnpr-chassis-serial" {
               description "OUI Juniper chassis-serial";
             }
             enum "jnpr-vcp" {
               description "OUI Juniper vcp";
             }
             enum "jnpr-mode-change" {
               description "OUI Juniper mode-change";
             }
             enum "jnpr-mode-change-error" {
               description "OUI Juniper mode-change-error";
             }
             enum "jnpr-mode-change-ip-address" {
               description "OUI Juniper mode-change-ip-address";
             }
             enum "jnpr-mode-change-image-name" {
               description "OUI Juniper mode-change-image-name";
             }
             enum "jnpr-mode-change-ftp-login" {
               description "OUI Juniper mode-change-ftp-login";
             }
             enum "jnpr-mode-change-image-md5" {
               description "OUI Juniper mode-change-image-md5";
             }
             enum "jnpr-mode-change-ftp-server" {
               description "OUI Juniper mode-change-ftp-server";
             }
             enum "port-vid" {
               description "OUI IEEE 802.1 port-vid";
             }
             enum "port-protocol-vid" {
               description "OUI IEEE 802.1 port-procol-vid";
             }
             enum "vlan-name" {
               description "OUI IEEE 802.1 vlan-name";
             }
             enum "protocol-id" {
               description "OUI IEEE 802.1 protocol-id";
             }
             enum "evb" {
               description "OUI IEEE 82.1QBG evb";
             }
           }
         }
         leaf-list tlv-filter {
           ordered-by user;
           description "Filter TLV(s) to be sent";
           type enumeration {
             enum "all" {
               description "Filter all non mandatory TLVs";
             }
             enum "port-description" {
               description "Port Description";
             }
             enum "system-name" {
               description "System Name";
             }
             enum "system-description" {
               description "System Description";
             }
             enum "system-capabilities" {
               description "System Capabilities";
             }
             enum "management-address" {
               description "Management Address";
             }
             enum "mac-phy-config-status" {
               description "OUI IEEE 802.3 mac-phy-config-status";
             }
             enum "power-vi-mdi" {
               description "OUI IEEE 802.3 power-vi-mdi";
             }
             enum "link-aggregation" {
               description "OUI IEEE 802.3 link-aggregation";
             }
             enum "maximum-frame-size" {
               description "OUI IEEE 802.3 maximum-frame-size";
             }
             enum "jnpr-chassis-serial" {
               description "OUI Juniper chassis-serial";
             }
             enum "jnpr-vcp" {
               description "OUI Juniper vcp";
             }
             enum "jnpr-mode-change" {
               description "OUI Juniper mode-change";
             }
             enum "jnpr-mode-change-error" {
               description "OUI Juniper mode-change-error";
             }
             enum "jnpr-mode-change-ip-address" {
               description "OUI Juniper mode-change-ip-address";
             }
             enum "jnpr-mode-change-image-name" {
               description "OUI Juniper mode-change-image-name";
             }
             enum "jnpr-mode-change-ftp-login" {
               description "OUI Juniper mode-change-ftp-login";
             }
             enum "jnpr-mode-change-image-md5" {
               description "OUI Juniper mode-change-image-md5";
             }
             enum "jnpr-mode-change-ftp-server" {
               description "OUI Juniper mode-change-ftp-server";
             }
             enum "port-vid" {
               description "OUI IEEE 802.1 port-vid";
             }
             enum "port-protocol-vid" {
               description "OUI IEEE 802.1 port-procol-vid";
             }
             enum "vlan-name" {
               description "OUI IEEE 802.1 vlan-name";
             }
             enum "protocol-id" {
               description "OUI IEEE 802.1 protocol-id";
             }
             enum "evb" {
               description "OUI IEEE 802.1QBG evb";
             }
           }
         }
       }
     }
     container lldp-med {
       presence "enable lldp-med";
       description "LLDP Media Endpoint Discovery";
       uses apply-advanced;
       leaf fast-start {
         description "Discovery count for MED";
         type union {
           type string {
             pattern "<.*>|$.*";
           }
           type uint32 {
             range "1 .. 10";
           }
         }
       }
       list interface {
         key name;
         ordered-by user;
         description "Interface configuration";
         leaf name {
           type string;
         }
         uses apply-advanced;
         choice enable-disable {
           case case_1 {
             leaf disable {
               description "Disable LLDP";
               type empty;
             }
           }
         }
         container location {
           presence "enable location";
           uses apply-advanced;
           choice location-type {
             case case_1 {
               container civic-based {
                 description "Postal address";
                 presence "enable civic-based";
                 uses civic-address-elements;
               }
             }
             case case_2 {
               leaf elin {
                 description "Emergency line identification (ELIN) string";
                 type string;
               }
             }
             case case_3 {
               container co-ordinate {
                 description "Address based on longitude and latitude coordinates";
                 presence "enable co-ordinate";
                 uses co-ordinate-elements;
               }
             }
           }
         }
         leaf-list tlv-select {
           ordered-by user;
           description "Select TLV(s) to be sent";
           type enumeration {
             enum "med-capabilities" {
               description "OUI TIA med-capabilities";
             }
             enum "network-policy" {
               description "OUI TIA network-policy";
             }
             enum "location-id" {
               description "OUI TIA location-id";
             }
             enum "ext-power-via-mdi" {
               description "OUI TIA ext-power-via-mdi";
             }
           }
         }
         leaf-list tlv-filter {
           ordered-by user;
           description "Filter TLV(s) to be sent";
           type enumeration {
             enum "all" {
               description "Filter all non mandatory TLVs";
             }
             enum "med-capabilities" {
               description "OUI TIA med-capabilities";
             }
             enum "network-policy" {
               description "OUI TIA network-policy";
             }
             enum "location-id" {
               description "OUI TIA location-id";
             }
             enum "ext-power-via-mdi" {
               description "OUI TIA ext-power-via-mdi";
             }
           }
         }
       }
       leaf-list tlv-select {
         ordered-by user;
         description "Select MED TLVs to be sent";
         type enumeration {
           enum "med-capabilities" {
             description "OUI TIA med-capabilities";
           }
           enum "network-policy" {
             description "OUI TIA network-policy";
           }
           enum "location-id" {
             description "OUI TIA location-id";
           }
           enum "ext-power-via-mdi" {
             description "OUI TIA ext-power-via-mdi";
           }
         }
       }
       leaf-list tlv-filter {
         ordered-by user;
         description "Filter MED TLVs to be sent";
         type enumeration {
           enum "all" {
             description "Filter all non mandatory TLVs";
           }
           enum "med-capabilities" {
             description "OUI TIA med-capabilities";
           }
           enum "network-policy" {
             description "OUI TIA network-policy";
           }
           enum "location-id" {
             description "OUI TIA location-id";
           }
           enum "ext-power-via-mdi" {
             description "OUI TIA ext-power-via-mdi";
           }
         }
       }
     }
     container igmp-snooping {
       description "IGMP snooping configuration";
       uses juniper-default-ri-protocols-igmp-snooping;
     }
     container mld-snooping {
       description "MLD snooping configuration";
       presence "enable mld-snooping";
       uses juniper-default-ri-protocols-mld-snooping;
     }
     container pcep {
       description "Path computation client configuration";
       uses apply-advanced;
       leaf message-rate-limit {
         description "Messages per minute rate that path computation client will handle at maximum. 0 - disabled";
         type union {
           type string {
             pattern "<.*>|$.*";
           }
           type uint16 {
             range "0 .. 16384";
           }
         }
       }
       leaf update-rate-limit {
         description "Updates per minute rate that path computation client will handle at maximum. 0 - disabled";
         type union {
           type string {
             pattern "<.*>|$.*";
           }
           type uint16 {
             range "0 .. 16384";
           }
         }
       }
       leaf max-provisioned-lsps {
         description "Defines max count of externally provisioned LSPs over all conected PCEs (default: 16000)";
         default "16000";
         type union {
           type string {
             pattern "<.*>|$.*";
           }
           type uint32 {
             range "1 .. 32000";
           }
         }
       }
       list pce-group {
         key name;
         ordered-by user;
         description "PCE group definition";
         leaf name {
           description "PCE group identifier";
           type string {
             length "1 .. 63";
           }
         }
         uses apply-advanced;
         container pce-type {
           description "Type of the PCE (e.g. stateful or stateless)";
           leaf active {
             description "The PCE can modify delegated LSPs";
             type empty;
           }
           choice statefullness {
             case case_1 {
               leaf stateful {
                 description "The PCE is stateful";
                 type empty;
               }
             }
           }
         }
         leaf lsp-provisioning {
           description "The PCE is capable of provisioning LSPs";
           type empty;
         }
         leaf p2mp-lsp-report-capability {
           description "The PCE is capable of reporting P2MP  LSPs";
           type empty;
         }
         leaf p2mp-lsp-update-capability {
           description "The PCE is capable of update P2MP  LSPs";
           type empty;
         }
         leaf p2mp-lsp-init-capability {
           description "The PCE is capable of provisioning P2MP  LSPs";
           type empty;
         }
         leaf lsp-cleanup-timer {
           description "LSP cleanup time (default: 60)";
           units "seconds";
           type union {
             type string {
               pattern "<.*>|$.*";
             }
             type uint32 {
               range "0 .. 2147483647";
             }
           }
         }
         leaf spring-capability {
           description "PCE is capable of supporting SPRING based provisioning";
           type empty;
         }
         leaf max-sid-depth {
           description "Max SID Depth (default: 5)";
           default "5";
           type union {
             type string {
               pattern "<.*>|$.*";
             }
             type uint32 {
               range "1 .. 16";
             }
           }
         }
         leaf lsp-retry-delegation {
           description "Retry LSP delegation process is enabled";
           type empty;
         }
         leaf lsp-retry-delegation-timer {
           description "LSP retry delegation timer in case delegation failure or re-delegate (default: 3600)";
           units "seconds";
           type union {
             type string {
               pattern "<.*>|$.*";
             }
             type uint32 {
               range "0 .. 2147483647";
             }
           }
         }
         leaf request-timer {
           description "The amount of time path computation client waits for a reply before resending its requests";
           units "seconds";
           type union {
             type string {
               pattern "<.*>|$.*";
             }
             type uint16 {
               range "0 .. 65535";
             }
           }
         }
         leaf max-unknown-requests {
           description "Max unknown requests per minute after which the connection will be closed. 0 - disabled";
           default "5";
           units "requests-per-minute";
           type union {
             type string {
               pattern "<.*>|$.*";
             }
             type uint32 {
               range "0 .. 16384";
             }
           }
         }
         leaf max-unknown-messages {
           description "Max unknown messages per minute after which the connection will be closed. 0 - disabled";
           default "5";
           units "messages-per-minute";
           type union {
             type string {
               pattern "<.*>|$.*";
             }
             type uint32 {
               range "0 .. 16384";
             }
           }
         }
         container traceoptions {
           description "Path Computation Element Protocol trace options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Area of Path Computation Client Daemon to enable debugging output";
             leaf name {
               type enumeration {
                 enum "pcep" {
                   description "Trace Path Computation Element protocol";
                 }
                 enum "all" {
                   description "Trace all areas of Path Computation Client Daemon  code";
                 }
               }
             }
           }
         }
         leaf delegation-cleanup-timeout {
           description "Return control of LSPs or Re-delegation time after PCEP session disconnect (default: 30)";
           units "seconds";
           type union {
             type string {
               pattern "<.*>|$.*";
             }
             type uint32 {
               range "0 .. 2147483647";
             }
           }
         }
       }
       list pce {
         key name;
         ordered-by user;
         description "Per PCE configuration";
         leaf name {
           description "PCE unique identifier";
           type string {
             length "1 .. 63";
           }
         }
         uses apply-advanced;
         leaf local-address {
           description "Address of local end of PCEP session";
           type jt:ipv4addr;
         }
         leaf destination-ipv4-address {
           description "IPV4 Address of PCE";
           type jt:ipv4addr;
         }
         leaf destination-port {
           description "Destination TCP port PCE is listening on";
           default "4189";
           type union {
             type string {
               pattern "<.*>|$.*";
             }
             type uint16 {
               range "1 .. 65535";
             }
           }
         }
         leaf delegation-priority {
           description "This PCE's priority among configured stateful PCEs in one pce-group";
           type union {
             type string {
               pattern "<.*>|$.*";
             }
             type uint16 {
               range "1 .. 65535";
             }
           }
         }
         leaf request-priority {
           description "This PCE's priority among configured stateless PCEs in one pce-group";
           type union {
             type string {
               pattern "<.*>|$.*";
             }
             type uint16 {
               range "1 .. 65535";
             }
           }
         }
         leaf pce-group {
           description "Assign this PCE to defined pce group. PCE will inherit default values from the pce-group";
           type string;
         }
         leaf authentication-key {
           description "MD5 authentication key";
           type string {
             length "1 .. 128";
           }
         }
         leaf authentication-algorithm {
           description "Authentication algorithm name";
           type enumeration {
             enum "md5" {
               description "Message Digest 5";
             }
           }
         }
         leaf authentication-key-chain {
           description "Key chain name";
           type string {
             length "1 .. 128";
           }
         }
         container pce-type {
           description "Type of the PCE (e.g. stateful or stateless)";
           leaf active {
             description "The PCE can modify delegated LSPs";
             type empty;
           }
           choice statefullness {
             case case_1 {
               leaf stateful {
                 description "The PCE is stateful";
                 type empty;
               }
             }
           }
         }
         leaf lsp-provisioning {
           description "The PCE is capable of provisioning LSPs";
           type empty;
         }
         leaf p2mp-lsp-report-capability {
           description "The PCE is capable of reporting P2MP  LSPs";
           type empty;
         }
         leaf p2mp-lsp-update-capability {
           description "The PCE is capable of update P2MP  LSPs";
           type empty;
         }
         leaf p2mp-lsp-init-capability {
           description "The PCE is capable of provisioning P2MP  LSPs";
           type empty;
         }
         leaf lsp-cleanup-timer {
           description "LSP cleanup time (default: 60)";
           units "seconds";
           type union {
             type string {
               pattern "<.*>|$.*";
             }
             type uint32 {
               range "0 .. 2147483647";
             }
           }
         }
         leaf spring-capability {
           description "PCE is capable of supporting SPRING based provisioning";
           type empty;
         }
         leaf max-sid-depth {
           description "Max SID Depth (default: 5)";
           default "5";
           type union {
             type string {
               pattern "<.*>|$.*";
             }
             type uint32 {
               range "1 .. 16";
             }
           }
         }
         leaf lsp-retry-delegation {
           description "Retry LSP delegation process is enabled";
           type empty;
         }
         leaf lsp-retry-delegation-timer {
           description "LSP retry delegation timer in case delegation failure or re-delegate (default: 3600)";
           units "seconds";
           type union {
             type string {
               pattern "<.*>|$.*";
             }
             type uint32 {
               range "0 .. 2147483647";
             }
           }
         }
         leaf request-timer {
           description "The amount of time path computation client waits for a reply before resending its requests";
           units "seconds";
           type union {
             type string {
               pattern "<.*>|$.*";
             }
             type uint16 {
               range "0 .. 65535";
             }
           }
         }
         leaf max-unknown-requests {
           description "Max unknown requests per minute after which the connection will be closed. 0 - disabled";
           default "5";
           units "requests-per-minute";
           type union {
             type string {
               pattern "<.*>|$.*";
             }
             type uint32 {
               range "0 .. 16384";
             }
           }
         }
         leaf max-unknown-messages {
           description "Max unknown messages per minute after which the connection will be closed. 0 - disabled";
           default "5";
           units "messages-per-minute";
           type union {
             type string {
               pattern "<.*>|$.*";
             }
             type uint32 {
               range "0 .. 16384";
             }
           }
         }
         container traceoptions {
           description "Path Computation Element Protocol trace options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Area of Path Computation Client Daemon to enable debugging output";
             leaf name {
               type enumeration {
                 enum "pcep" {
                   description "Trace Path Computation Element protocol";
                 }
                 enum "all" {
                   description "Trace all areas of Path Computation Client Daemon  code";
                 }
               }
             }
           }
         }
         leaf delegation-cleanup-timeout {
           description "Return control of LSPs or Re-delegation time after PCEP session disconnect (default: 30)";
           units "seconds";
           type union {
             type string {
               pattern "<.*>|$.*";
             }
             type uint32 {
               range "0 .. 2147483647";
             }
           }
         }
       }
       container traceoptions {
         description "Path Computation Client Daemon trace options";
         uses pccd-traceoptions-type;
       }
     }
     container ppp {
       description "Configure PPP process";
       uses apply-advanced;
       container traceoptions {
         description "PPP trace options";
         uses ppp-traceoptions-type;
       }
       list monitor-session {
         key session-name;
         description "Monitor packet exchange for PPP session";
         leaf session-name {
           description "PPP session name";
           type string;
         }
         uses apply-advanced;
       }
     }
     container pppoe {
       description "Configure PPPoE process";
       uses apply-advanced;
       container traceoptions {
         description "PPPoE trace options";
         uses pppoe-traceoptions-type;
       }
       leaf pado-advertise {
         description "Enable PADO advertising of PPPoE Service-Names";
         type empty;
       }
     }
     container r2cp {
       description "Radio-to-Router Control Protocol configuration";
       uses apply-advanced;
       choice enable-disable {
         case case_1 {
           leaf disable {
             description "Disable R2CP";
             type empty;
           }
         }
       }
       container traceoptions {
         description "R2CP trace options";
         uses r2cp-traceoptions-type;
       }
       leaf server-port {
         description "R2CP server port number";
         type union {
           type string {
             pattern "<.*>|$.*";
           }
           type uint16 {
             range "1 .. 65535";
           }
         }
       }
       container client-port {
         description "R2CP client port number";
         choice client-port-value {
           case case_1 {
             leaf port-number {
               description "UDP port number for R2CP clients";
               type union {
                 type string {
                   pattern "<.*>|$.*";
                 }
                 type uint16 {
                   range "1 .. 65535";
                 }
               }
             }
           }
           case case_2 {
             choice port-any {
               case case_1 {
                 leaf any {
                   description "Accept R2CP messages sent on any port";
                   type empty;
                 }
               }
             }
           }
         }
       }
       leaf node-terminate-count {
         description "Node Term retransmit count";
         type union {
           type string {
             pattern "<.*>|$.*";
           }
           type uint16 {
             range "1 .. 5";
           }
         }
       }
       leaf node-terminate-interval {
         description "Node Terminate interval";
         units "milliseconds";
         type union {
           type string {
             pattern "<.*>|$.*";
           }
           type uint16 {
             range "100 .. 5000";
           }
         }
       }
       leaf session-terminate-count {
         description "Session Term retransmit count";
         type union {
           type string {
             pattern "<.*>|$.*";
           }
           type uint16 {
             range "1 .. 5";
           }
         }
       }
       leaf session-terminate-interval {
         description "Session Term interval";
         units "milliseconds";
         type union {
           type string {
             pattern "<.*>|$.*";
           }
           type uint16 {
             range "100 .. 5000";
           }
         }
       }
       list radio {
         key name;
         ordered-by user;
         leaf name {
           description "Radio name";
           type string {
           }
         }
         uses apply-advanced;
         leaf interface {
           description "Interface listening for R2CP messages";
           type union {
             type jt:interface-unit;
             type string {
               pattern "<.*>|$.*";
             }
           }
         }
         leaf down-count {
           description "Number of missed keepalives before radio is assumed 'down'";
           status deprecated;
           type union {
             type uint16;
             type string {
               pattern "<.*>|$.*";
             }
           }
         }
         leaf virtual-channel-group {
           description "Virtual channel group name";
           type string {
           }
         }
         list radio-interface {
           key name;
           ordered-by user;
           leaf name {
             description "Data channel interface";
             type union {
               type jt:interface-unit;
               type string {
                 pattern "<.*>|$.*";
               }
             }
           }
           uses apply-advanced;
         }
       }
     }
     container protection-group {
       description "Protection group";
       presence "enable protection-group";
       uses juniper-protocols-protection-group;
     }
     container mvrp {
       description "MVRP configuration";
       uses juniper-protocols-mvrp;
     }
     container layer2-control {
       description "Global options for layer 2 protocols";
       uses juniper-protocols-l2control;
     }
     container rstp {
       description "Rapid Spanning Tree Protocol options";
       uses juniper-protocols-stp;
     }
     container mstp {
       description "Multiple Spanning Tree Protocol options";
       uses juniper-protocols-mstp;
     }
     container vstp {
       description "VLAN Spanning Tree Protocol options";
       uses juniper-protocols-vstp;
     }
     container loop-detect {
       presence "enable loop-detect";
       description "Layer2 Loop Detect on interface with non-IP L2 Multicast mac as destination mac";
       uses apply-advanced;
       list interface {
         key name;
         ordered-by user;
         description "Interface name to block Loop Detect PDUs on";
         leaf name {
           type string;
         }
         uses apply-advanced;
         leaf disable {
           description "Disable loop detect feature on a port";
           type empty;
         }
       }
       leaf destination-mac {
         description "Destination non-IP L2 multicast mac to be used for transmitting Loop Detect PDUs";
         type jt:mac-multicast;
       }
       leaf transmit-interval {
         description "Loop Detect PDU TX interval in sec --default 30s";
         units "seconds";
         type union {
           type string {
             pattern "<.*>|$.*";
           }
           type uint16 {
             range "5 .. 3600";
           }
         }
       }
     }
   }
   grouping bandwidth-type {
     uses apply-advanced;
     leaf per-traffic-class-bandwidth {
       description "Bandwidth to reserve";
       units "bps";
       type string;
     }
     leaf ct0 {
       description "Bandwidth from traffic class 0";
       units "bps";
       type string;
     }
     leaf ct1 {
       description "Bandwidth from traffic class 1";
       units "bps";
       type string;
     }
     leaf ct2 {
       description "Bandwidth from traffic class 2";
       units "bps";
       type string;
     }
     leaf ct3 {
       description "Bandwidth from traffic class 3";
       units "bps";
       type string;
     }
   }
   grouping cfm-traceoptions {
     description "Trace options for connectivity fault management";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Tracing parameters";
       leaf name {
         type enumeration {
           enum "configuration" {
             description "Trace configuration events";
           }
           enum "routing-socket" {
             description "Trace routing socket events";
           }
           enum "protocol" {
             description "Trace protocol processing events";
           }
           enum "init" {
             description "Trace events related to protocol daemon start-up";
           }
           enum "error" {
             description "Trace events related to catestrophic errors in daemon";
           }
           enum "issu" {
             description "Trace ISSU related events";
           }
           enum "all" {
             description "Trace everything";
           }
         }
       }
     }
   }
   grouping civic-address-elements {
     uses apply-advanced;
     leaf what {
       description "Type of address";
       default "1";
       type union {
         type string {
           pattern "<.*>|$.*";
         }
         type uint16 {
           range "0 .. 2";
         }
       }
     }
     leaf country-code {
       description "Two-letter country code";
       type string {
         length 2;
       }
     }
     list ca-type {
       key name;
       ordered-by user;
       leaf name {
         description "Address element type";
         type union {
           type string {
             pattern "<.*>|$.*";
           }
           type uint16 {
             range "0 .. 255";
           }
         }
       }
       uses apply-advanced;
       leaf ca-value {
         description "Address element value";
         type string;
       }
     }
   }
   grouping co-ordinate-elements {
     description "Geographical co-ordinates";
     uses apply-advanced;
     leaf longitude {
       description "Longitude vlaue";
       type union {
         type string {
           pattern "<.*>|$.*";
         }
         type uint16 {
           range "0 .. 360";
         }
       }
     }
     leaf lattitude {
       description "Lattitude vlaue";
       type union {
         type string {
           pattern "<.*>|$.*";
         }
         type uint16 {
           range "0 .. 360";
         }
       }
     }
   }
   grouping juniper-default-ri-protocols-igmp-snooping {
     description "IGMP snooping options";
     uses apply-advanced;
     list vlan {
       key name;
       ordered-by user;
       description "VLAN options";
       leaf name {
         description "VLAN name";
         type string;
       }
       uses apply-advanced;
       container traceoptions {
         description "Trace options for IGMP Snooping";
         uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "packets" {
                 description "Trace all IGMP packets";
               }
               enum "query" {
                 description "Trace IGMP membership query messages";
               }
               enum "report" {
                 description "Trace membership report messages";
               }
               enum "leave" {
                 description "Trace leave group messages (IGMPv2 only)";
               }
               enum "group" {
                 description "Trace group operations";
               }
               enum "client-notification" {
                 description "Trace notifications";
               }
               enum "route" {
                 description "Trace routing information";
               }
               enum "normal" {
                 description "Trace normal events";
               }
               enum "general" {
                 description "Trace general events";
               }
               enum "state" {
                 description "Trace state transitions";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       leaf query-interval {
         description "When to send host query messages";
         default "125";
         units "seconds";
         type union {
           type string {
             pattern "<.*>|$.*";
           }
           type uint32 {
             range "1 .. 1024";
           }
         }
       }
       container l2-querier {
         description "Enable L2 querier mode";
         uses apply-advanced;
         leaf source-address {
           description "Source IP address to use for L2 querier";
           type jt:ipv4addr;
         }
       }
       leaf query-response-interval {
         description "How long to wait for a host query response";
         default "10";
         units "seconds";
         type string {
         }
       }
       leaf query-last-member-interval {
         description "When to send group query messages";
         default "1";
         units "seconds";
         type string {
         }
       }
       leaf robust-count {
         description "Expected packet loss on a subnet";
         default "2";
         type union {
           type string {
             pattern "<.*>|$.*";
           }
           type uint32 {
             range "2 .. 10";
           }
         }
       }
       leaf immediate-leave {
         description "Enable immediate group leave on interfaces";
         type empty;
       }
       container proxy {
         presence "enable proxy";
         description "Enable proxy mode";
         uses apply-advanced;
         leaf source-address {
           description "Source IP address to use for proxy";
           type jt:ipv4addr;
         }
       }
       list interface {
         key name;
         ordered-by user;
         description "Interface options for IGMP";
         leaf name {
           description "Interface name";
           type union {
             type jt:interface-name;
             type string {
               pattern "<.*>|$.*";
             }
           }
         }
         uses apply-advanced;
         leaf multicast-router-interface {
           description "Enabling multicast-router-interface on the interface";
           type empty;
         }
         leaf immediate-leave {
           description "Enable immediate group leave on interface";
           type empty;
         }
         leaf host-only-interface {
           description "Enable interface to be treated as host-side interface";
           type empty;
         }
         leaf group-limit {
           description "Maximum number of groups an interface can join";
           type union {
             type uint16;
             type string {
               pattern "<.*>|$.*";
             }
           }
         }
         container static {
           description "Static group or source membership";
           uses apply-advanced;
           list group {
             key name;
             ordered-by user;
             description "IP multicast group address";
             leaf name {
               description "IP multicast group address";
               type jt:ipv4addr;
             }
             uses apply-advanced;
             list source {
               key name;
               ordered-by user;
               description "IP multicast source address";
               leaf name {
                 description "Source address of IP multicast data";
                 type jt:ipv4addr;
               }
               uses apply-advanced;
             }
           }
         }
       }
       list qualified-vlan {
         key name;
         ordered-by user;
         description "VLAN options for qualified-learning";
         leaf name {
           description "VLAN ID of the learning-domain";
           type union {
             type string {
               pattern "<.*>|$.*";
             }
             type uint32 {
               range "0 .. 1023";
             }
           }
         }
         uses apply-advanced;
         leaf query-interval {
           description "When to send host query messages";
           units "seconds";
           type union {
             type string {
               pattern "<.*>|$.*";
             }
             type uint32 {
               range "1 .. 1024";
             }
           }
         }
         container l2-querier {
           description "Enable L2 querier mode";
           uses apply-advanced;
           leaf source-address {
             description "Source IP address to use for L2 querier";
             type jt:ipv4addr;
           }
         }
         leaf query-response-interval {
           description "How long to wait for a host query response";
           units "seconds";
           type string {
           }
         }
         leaf query-last-member-interval {
           description "When to send group query messages";
           units "seconds";
           type string {
           }
         }
         leaf robust-count {
           description "Expected packet loss on a subnet";
           type union {
             type string {
               pattern "<.*>|$.*";
             }
             type uint32 {
               range "2 .. 10";
             }
           }
         }
         leaf immediate-leave {
           description "Enable immediate group leave on interfaces";
           type empty;
         }
         container proxy {
           presence "enable proxy";
           description "Enable proxy mode";
           uses apply-advanced;
           leaf source-address {
             description "Source IP address to use for proxy";
             type jt:ipv4addr;
           }
         }
         list interface {
           key name;
           ordered-by user;
           description "Interface options for IGMP";
           leaf name {
             description "Interface name";
             type union {
               type jt:interface-name;
               type string {
                 pattern "<.*>|$.*";
               }
             }
           }
           uses apply-advanced;
           leaf multicast-router-interface {
             description "Enabling multicast-router-interface on the interface";
             type empty;
           }
           leaf immediate-leave {
             description "Enable immediate group leave on interface";
             type empty;
           }
           leaf host-only-interface {
             description "Enable interface to be treated as host-side interface";
             type empty;
           }
           leaf group-limit {
             description "Maximum number of groups an interface can join";
             type union {
               type uint16;
               type string {
                 pattern "<.*>|$.*";
               }
             }
           }
           container static {
             description "Static group or source membership";
             uses apply-advanced;
             list group {
               key name;
               ordered-by user;
               description "IP multicast group address";
               leaf name {
                 description "IP multicast group address";
                 type jt:ipv4addr;
               }
               uses apply-advanced;
               list source {
                 key name;
                 ordered-by user;
                 description "IP multicast source address";
                 leaf name {
                   description "Source address of IP multicast data";
                   type jt:ipv4addr;
                 }
                 uses apply-advanced;
               }
             }
           }
         }
       }
     }
     container traceoptions {
       description "Trace options for IGMP Snooping";
       uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "packets" {
               description "Trace all IGMP packets";
             }
             enum "query" {
               description "Trace IGMP membership query messages";
             }
             enum "report" {
               description "Trace membership report messages";
             }
             enum "leave" {
               description "Trace leave group messages (IGMPv2 only)";
             }
             enum "group" {
               description "Trace group operations";
             }
             enum "client-notification" {
               description "Trace notifications";
             }
             enum "host-notification" {
               description "Trace host notifications";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     leaf query-interval {
       description "When to send host query messages";
       default "125";
       units "seconds";
       type union {
         type string {
           pattern "<.*>|$.*";
         }
         type uint32 {
           range "1 .. 1024";
         }
       }
     }
     leaf query-response-interval {
       description "How long to wait for a host query response";
       default "10";
       units "seconds";
       type string {
       }
     }
     leaf query-last-member-interval {
       description "When to send group query messages";
       default "1";
       units "seconds";
       type string {
       }
     }
     leaf robust-count {
       description "Expected packet loss on a subnet";
       default "2";
       type union {
         type string {
           pattern "<.*>|$.*";
         }
         type uint32 {
           range "2 .. 10";
         }
       }
     }
     leaf immediate-leave {
       description "Enable immediate group leave on interfaces";
       type empty;
     }
     container proxy {
       presence "enable proxy";
       description "Enable proxy mode";
       uses apply-advanced;
       leaf source-address {
         description "Source IP address to use for proxy";
         type jt:ipv4addr;
       }
       leaf irb {
         description "Proxy IGMP reports to IRB";
         type empty;
       }
     }
     list interface {
       key name;
       ordered-by user;
       description "Interface options for IGMP";
       leaf name {
         description "Interface name";
         type union {
           type jt:interface-name;
           type string {
             pattern "<.*>|$.*";
           }
         }
       }
       uses apply-advanced;
       leaf multicast-router-interface {
         description "Enabling multicast-router-interface on the interface";
         type empty;
       }
       leaf immediate-leave {
         description "Enable immediate group leave on interfaces";
         type empty;
       }
       leaf host-only-interface {
         description "Enable interfaces to be treated as host-side interfaces";
         type empty;
       }
       leaf group-limit {
         description "Maximum number of (source,group) per interface";
         type union {
           type string {
             pattern "<.*>|$.*";
           }
           type uint16 {
             range "1 .. 65535";
           }
         }
       }
       container static {
         description "Static group or source membership";
         uses apply-advanced;
         list group {
           key name;
           ordered-by user;
           description "IP multicast group address";
           leaf name {
             description "IP multicast group address";
             type jt:ipv4addr;
           }
           uses apply-advanced;
           list source {
             key name;
             ordered-by user;
             description "IP multicast source address";
             leaf name {
               description "Source address of IP multicast data";
               type jt:ipv4addr;
             }
             uses apply-advanced;
           }
         }
       }
     }
   }
   grouping juniper-default-ri-protocols-mld-snooping {
     description "MLD snooping options";
     uses apply-advanced;
     list vlan {
       key name;
       ordered-by user;
       description "VLAN options";
       leaf name {
         description "VLAN name";
         type string;
       }
       uses apply-advanced;
       container traceoptions {
         description "Trace options for MLD Snooping";
         uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "packets" {
                 description "Trace all MLD packets";
               }
               enum "query" {
                 description "Trace MLD membership query messages";
               }
               enum "report" {
                 description "Trace membership report messages";
               }
               enum "leave" {
                 description "Trace leave group messages (MLDv1 only)";
               }
               enum "group" {
                 description "Trace group operations";
               }
               enum "client-notification" {
                 description "Trace notifications";
               }
               enum "host-notification" {
                 description "Trace host notifications";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       leaf query-interval {
         description "When to send host query messages";
         default "125";
         units "seconds";
         type union {
           type string {
             pattern "<.*>|$.*";
           }
           type uint32 {
             range "1 .. 1024";
           }
         }
       }
       container l2-querier {
         description "Enable L2 querier mode";
         uses apply-advanced;
         leaf source-address {
           description "Source IP address to use for L2 querier";
           type jt:ipv6addr;
         }
       }
       leaf query-response-interval {
         description "How long to wait for a host query response";
         default "10";
         units "seconds";
         type string {
         }
       }
       leaf query-last-member-interval {
         description "When to send group query messages";
         default "1";
         units "seconds";
         type string {
         }
       }
       leaf robust-count {
         description "Expected packet loss on a subnet";
         default "2";
         type union {
           type string {
             pattern "<.*>|$.*";
           }
           type uint32 {
             range "2 .. 10";
           }
         }
       }
       leaf immediate-leave {
         description "Enable immediate group leave on interfaces";
         type empty;
       }
       list interface {
         key name;
         ordered-by user;
         description "Interface options for MLD";
         leaf name {
           description "Interface name";
           type union {
             type jt:interface-name;
             type string {
               pattern "<.*>|$.*";
             }
           }
         }
         uses apply-advanced;
         leaf multicast-router-interface {
           description "Enabling multicast-router-interface on the interface";
           type empty;
         }
         leaf immediate-leave {
           description "Enable immediate group leave on interfaces";
           type empty;
         }
         leaf host-only-interface {
           description "Enable interfaces to be treated as host-side interfaces";
           type empty;
         }
         leaf group-limit {
           description "Maximum number of groups an interface can join";
           type union {
             type uint16;
             type string {
               pattern "<.*>|$.*";
             }
           }
         }
         container static {
           description "Static group or source membership";
           uses apply-advanced;
           list group {
             key name;
             ordered-by user;
             description "IP multicast group address";
             leaf name {
               description "IP multicast group address";
               type jt:ipv6addr;
             }
             uses apply-advanced;
             list source {
               key name;
               ordered-by user;
               description "IP multicast source address";
               leaf name {
                 description "Source address of IP multicast data";
                 type jt:ipv6addr;
               }
               uses apply-advanced;
             }
           }
         }
       }
       list qualified-vlan {
         key name;
         ordered-by user;
         description "VLAN options for qualified-learning";
         leaf name {
           description "VLAN ID of the learning-domain";
           type union {
             type string {
               pattern "<.*>|$.*";
             }
             type uint32 {
               range "0 .. 1023";
             }
           }
         }
         uses apply-advanced;
         leaf query-interval {
           description "When to send host query messages";
           units "seconds";
           type union {
             type string {
               pattern "<.*>|$.*";
             }
             type uint32 {
               range "1 .. 1024";
             }
           }
         }
         container l2-querier {
           uses apply-advanced;
           leaf source-address {
             description "Source IP address to use for L2 querier";
             type jt:ipv6addr;
           }
         }
         leaf query-response-interval {
           description "How long to wait for a host query response";
           units "seconds";
           type string {
           }
         }
         leaf query-last-member-interval {
           description "When to send group query messages";
           units "seconds";
           type string {
           }
         }
         leaf robust-count {
           description "Expected packet loss on a subnet";
           type union {
             type string {
               pattern "<.*>|$.*";
             }
             type uint32 {
               range "2 .. 10";
             }
           }
         }
         leaf immediate-leave {
           description "Enable immediate group leave on interfaces";
           type empty;
         }
         list interface {
           key name;
           ordered-by user;
           description "Interface options for MLD";
           leaf name {
             description "Interface name";
             type union {
               type jt:interface-name;
               type string {
                 pattern "<.*>|$.*";
               }
             }
           }
           uses apply-advanced;
           leaf multicast-router-interface {
             description "Enabling multicast-router-interface on the interface";
             type empty;
           }
           leaf immediate-leave {
             description "Enable immediate group leave on interfaces";
             type empty;
           }
           leaf host-only-interface {
             description "Enable interfaces to be treated as host-side interfaces";
             type empty;
           }
           leaf group-limit {
             description "Maximum number of groups an interface can join";
             type union {
               type uint16;
               type string {
                 pattern "<.*>|$.*";
               }
             }
           }
           container static {
             description "Static group or source membership";
             uses apply-advanced;
             list group {
               key name;
               ordered-by user;
               description "IP multicast group address";
               leaf name {
                 description "IP multicast group address";
                 type jt:ipv6addr;
               }
               uses apply-advanced;
               list source {
                 key name;
                 ordered-by user;
                 description "IP multicast source address";
                 leaf name {
                   description "Source address of IP multicast data";
                   type jt:ipv6addr;
                 }
                 uses apply-advanced;
               }
             }
           }
         }
       }
     }
     container traceoptions {
       description "Trace options for MLD Snooping";
       uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "packets" {
               description "Trace all MLD packets";
             }
             enum "query" {
               description "Trace MLD membership query messages";
             }
             enum "report" {
               description "Trace membership report messages";
             }
             enum "leave" {
               description "Trace leave group messages (MLDv2 only)";
             }
             enum "group" {
               description "Trace group operations";
             }
             enum "client-notification" {
               description "Trace notifications";
             }
             enum "host-notification" {
               description "Trace host notifications";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     leaf query-interval {
       description "When to send host query messages";
       default "125";
       units "seconds";
       type union {
         type string {
           pattern "<.*>|$.*";
         }
         type uint32 {
           range "1 .. 1024";
         }
       }
     }
     leaf query-response-interval {
       description "How long to wait for a host query response";
       default "10";
       units "seconds";
       type string {
       }
     }
     leaf query-last-member-interval {
       description "When to send group query messages";
       default "1";
       units "seconds";
       type string {
       }
     }
     leaf robust-count {
       description "Expected packet loss on a subnet";
       default "2";
       type union {
         type string {
           pattern "<.*>|$.*";
         }
         type uint32 {
           range "2 .. 10";
         }
       }
     }
     leaf immediate-leave {
       description "Enable immediate group leave on interfaces";
       type empty;
     }
     container proxy {
       presence "enable proxy";
       description "Enable proxy mode";
       uses apply-advanced;
       leaf source-address {
         description "Source IP address to use for proxy";
         type jt:ipv6addr;
       }
       leaf irb {
         description "Proxy IGMP reports to IRB";
         type empty;
       }
     }
     leaf evpn-ssm-reports-only {
       description "Accept and process only <s,g> reports of SSM groups";
       type empty;
     }
     list interface {
       key name;
       ordered-by user;
       description "Interface options for MLD";
       leaf name {
         description "Interface name";
         type union {
           type jt:interface-name;
           type string {
             pattern "<.*>|$.*";
           }
         }
       }
       uses apply-advanced;
       leaf multicast-router-interface {
         description "Enabling multicast-router-interface on the interface";
         type empty;
       }
       leaf immediate-leave {
         description "Enable immediate group leave on interfaces";
         type empty;
       }
       leaf host-only-interface {
         description "Enable interfaces to be treated as host-side interfaces";
         type empty;
       }
       leaf group-limit {
         description "Maximum number of (source,group) per interface";
         type union {
           type string {
             pattern "<.*>|$.*";
           }
           type uint16 {
             range "1 .. 65535";
           }
         }
       }
       container static {
         description "Static group or source membership";
         uses apply-advanced;
         list group {
           key name;
           ordered-by user;
           description "IP multicast group address";
           leaf name {
             description "IP multicast group address";
             type jt:ipv6addr;
           }
           uses apply-advanced;
           list source {
             key name;
             ordered-by user;
             description "IP multicast source address";
             leaf name {
               description "Source address of IP multicast data";
               type jt:ipv6addr;
             }
             uses apply-advanced;
           }
         }
       }
     }
   }
   grouping juniper-ospf-authentication {
     description "Authentication information";
     uses apply-advanced;
     choice authentication-type {
       case case_1 {
         leaf simple-password {
           description "Authentication key";
           type jt:unreadable;
         }
       }
       case case_2 {
         list md5 {
           key name;
           ordered-by user;
           description "MD5 authentication key";
           leaf name {
             description "Key ID for MD5 authentication";
             type union {
               type string {
                 pattern "<.*>|$.*";
               }
               type uint32 {
                 range "0 .. 255";
               }
             }
           }
           leaf key {
             description "MD5 authentication key value";
             type jt:unreadable;
           }
           leaf start-time {
             description "Start time for key transmission (YYYY-MM-DD.HH:MM)";
             type jt:time;
           }
         }
       }
     }
   }
   grouping juniper-protocols-amt {
     uses apply-advanced;
     container traceoptions {
       description "Trace options for AMT";
       uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "packets" {
               description "Trace all AMT packets";
             }
             enum "errors" {
               description "Trace all error messages";
             }
             enum "tunnels" {
               description "Trace all AMT tunnel messages";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     container relay {
       description "AMT relay";
       presence "enable relay";
       uses juniper-protocols-amt-relay;
     }
   }
   grouping juniper-protocols-amt-relay {
     uses apply-advanced;
     container family {
       presence "enable family";
       description "Protocol family";
       uses apply-advanced;
       container inet {
         presence "enable inet";
         uses apply-advanced;
         leaf anycast-prefix {
           description "IPv4 anycast prefix";
           type jt:ipv4prefix;
         }
         leaf local-address {
           description "IPv4 local address";
           type jt:ipv4addr;
         }
       }
     }
     leaf secret-key-timeout {
       description "Time interval for the secret key to expire";
       units "minutes";
       type union {
         type string {
           pattern "<.*>|$.*";
         }
         type uint32 {
           range "5 .. 1440";
         }
       }
     }
     leaf tunnel-limit {
       description "Number of AMT tunnels";
       type union {
         type uint32;
         type string {
           pattern "<.*>|$.*";
         }
       }
     }
     leaf unicast-stream-limit {
       description "Maximum number of AMT unicast streams(s,g,intf)";
       type union {
         type uint32;
         type string {
           pattern "<.*>|$.*";
         }
       }
     }
     leaf accounting {
       description "Enable AMT accounting";
       type empty;
     }
     leaf-list tunnel-devices {
       ordered-by user;
       description "Tunnel devices to be used for creating ud interfaces";
       type union {
         type jt:interface-device;
         type string {
           pattern "<.*>|$.*";
         }
       }
     }
   }
   grouping juniper-protocols-bd {
     description "Bridging configuration";
     uses apply-advanced;
     container mac-table-size {
       description "Size of MAC address forwarding table";
       uses apply-advanced;
       leaf limit {
         description "Maximum number of MAC addresses";
         type union {
           type string {
             pattern "<.*>|$.*";
           }
           type uint32;
         }
       }
       leaf packet-action {
         description "Action when MAC limit is reached";
         type enumeration {
           enum "none" {
             description "Forward the packet";
           }
           enum "drop" {
             description "Drop packets and do not learn. Default is forward";
           }
         }
       }
     }
     container mac-ip-table-size {
       description "Size of MAC+IP bindings table";
       uses apply-advanced;
       leaf limit {
         description "Maximum number of MAC+IP bindings";
         type union {
           type string {
             pattern "<.*>|$.*";
           }
           type uint32;
         }
       }
     }
     container interface-mac-limit {
       description "Maximum MAC address learned per interface";
       uses apply-advanced;
       leaf limit {
         description "Maximum number of MAC addresses per interface";
         type union {
           type string {
             pattern "<.*>|$.*";
           }
           type uint32;
         }
       }
       leaf packet-action {
         description "Action when MAC limit is reached";
         type enumeration {
           enum "none" {
             description "Forward the packet";
           }
           enum "drop" {
             description "Drop packets and do not learn. Default is forward";
           }
           enum "log" {
             description "Do not drop the packet but generate an alarm, an SNMP trap or a system log entry";
           }
           enum "shutdown" {
             description "Disable the interface and generate an alarm, an SNMP trap or a system log entry";
           }
           enum "drop-and-log" {
             description "Drop the packet and generate an alarm, an SNMP trap or a system log entry";
           }
         }
       }
     }
     container interface-mac-ip-limit {
       description "Maximum MAC+IP bindings learned per interface";
       uses apply-advanced;
       leaf limit {
         description "Maximum number of MAC+IP bindings per interface";
         type union {
           type string {
             pattern "<.*>|$.*";
           }
           type uint32;
         }
       }
     }
     container mac-notification {
       presence "enable mac-notification";
       description "MAC notification options";
       uses apply-advanced;
       leaf notification-interval {
         description "Interval for sending MAC notifications";
         default "30";
         units "seconds";
         type union {
           type string {
             pattern "<.*>|$.*";
           }
           type uint32 {
             range "1 .. 60";
           }
         }
       }
     }
     leaf mac-table-aging-time {
       description "Delay for discarding MAC address if no updates are received";
       units "seconds";
       type union {
         type string {
           pattern "<.*>|$.*";
         }
         type uint32;
       }
     }
     leaf no-mac-learning {
       description "Disable dynamic MAC address learning";
       type empty;
     }
     leaf no-normalization {
       description "Disable vlan id normalization for interfaces";
       type empty;
     }
     leaf mac-statistics {
       description "Enable MAC address statistics";
       type empty;
     }
     container mib {
       presence "enable mib";
       description "Snmp mib options";
       uses apply-advanced;
       container dot1q-mib {
         presence "enable dot1q-mib";
         description "Dot1q MIB configuration options";
         uses apply-advanced;
         leaf port-list {
           description "Port list for staticegressports and staticuntaggedports MIB";
           type enumeration {
             enum "bit-map" {
               description "Port list is represented in bit-map format";
             }
             enum "string" {
               description "Port list is represented in string format";
             }
           }
         }
       }
     }
     container static-rvtep-mac {
       description "Configure Static MAC and remote VxLAN tunnel endpoint entries";
       uses apply-advanced;
       list mac {
         key "mac_addr remote-vtep";
         description "Unicast MAC address";
         leaf mac_addr {
           type jt:mac-unicast;
         }
         leaf remote-vtep {
           description "Configure static remote VXLAN tunnel endpoints";
           type jt:ipaddr;
         }
       }
     }
     list interface {
       key name;
       ordered-by user;
       description "Interface that connect this site to the VPN";
       leaf name {
         description "Interface name";
         type union {
           type jt:interface-name;
           type string {
             pattern "<.*>|$.*";
           }
         }
       }
       uses apply-advanced;
       container interface-mac-limit {
         description "Maximum number of MAC addresses learned on the interface";
         uses apply-advanced;
         leaf limit {
           description "Maximum number of MAC addresses per interface";
           type union {
             type string {
               pattern "<.*>|$.*";
             }
             type uint32;
           }
         }
         leaf disable {
           description "Disable interface for interface-mac-limit";
           type empty;
         }
         leaf packet-action {
           description "Action when MAC limit is reached";
           type enumeration {
             enum "none" {
               description "Forward the packet";
             }
             enum "drop" {
               description "Drop packets and do not learn. Default is forward";
             }
             enum "log" {
               description "Do not drop the packet but generate an alarm, an SNMP trap or a system log entry";
             }
             enum "shutdown" {
               description "Disable the interface and generate an alarm, an SNMP trap or a system log entry";
             }
             enum "drop-and-log" {
               description "Drop the packet and generate an alarm, an SNMP trap or a system log entry";
             }
           }
         }
       }
       container vpws-service-id {
         presence "enable vpws-service-id";
         description "Service-id for EVPN VPWS routing instance";
         uses apply-advanced;
         leaf local {
           description "Local EVPN VPWS service id";
           type union {
             type string {
               pattern "<.*>|$.*";
             }
             type uint32 {
               range "1 .. 16777215";
             }
           }
         }
         leaf remote {
           description "Remote EVPN VPWS service id";
           type union {
             type string {
               pattern "<.*>|$.*";
             }
             type uint32 {
               range "1 .. 16777215";
             }
           }
         }
       }
       leaf protect-interface {
         description "Name of protect interface";
         type union {
           type jt:interface-name;
           type string {
             pattern "<.*>|$.*";
           }
         }
       }
       leaf action-priority {
         description "Blocking priority of this interface on mac move detection";
         type union {
           type string {
             pattern "<.*>|$.*";
           }
           type uint32 {
             range "0 .. 8";
           }
         }
       }
       leaf remote-site-id {
         description "Site identifier associated with this interface";
         type union {
           type string {
             pattern "<.*>|$.*";
           }
           type uint32 {
             range "1 .. 65534";
           }
         }
       }
       leaf target-attachment-identifier {
         description "FEC 129 VPWS target attachment identifier";
         type string {
         }
       }
       leaf flow-label-transmit {
         description "Advertise capability to push Flow Label in transmit direction to remote PE";
         type empty;
       }
       leaf flow-label-receive {
         description "Advertise capability to push Flow Label in receive direction to remote PE";
         type empty;
       }
       leaf encapsulation-type {
         description "Encapsulation type for VPN";
         type enumeration {
           enum "atm-aal5" {
             description "ATM AAL/5 encapsulation";
           }
           enum "atm-cell" {
             description "ATM port promiscuous mode cell encapsulation";
           }
           enum "atm-cell-port-mode" {
             description "ATM port promiscuous mode cell encapsulation";
           }
           enum "atm-cell-vp-mode" {
             description "ATM VP promiscuous mode cell encapsulation";
           }
           enum "atm-cell-vc-mode" {
             description "ATM non-promiscuous cell encapsulation";
           }
           enum "frame-relay" {
             description "Frame Relay encapsulation";
           }
           enum "ppp" {
             description "PPP encapsulation";
           }
           enum "cisco-hdlc" {
             description "Cisco-compatible HDLC encapsulation";
           }
           enum "ethernet-vlan" {
             description "Ethernet VLAN encapsulation";
           }
           enum "ethernet" {
             description "Ethernet encapsulation";
           }
           enum "interworking" {
             description "Layer 2.5 interworking VPN";
           }
           enum "frame-relay-port-mode" {
             description "Frame Relay port mode encapsulation";
           }
           enum "satop-t1" {
             description "SATOP-T1 based Layer 2 VPN";
           }
           enum "satop-e1" {
             description "SATOP-E1 based Layer 2 VPN";
           }
           enum "satop-t3" {
             description "SATOP-T3 based Layer 2 VPN";
           }
           enum "satop-e3" {
             description "SATOP-E3 based Layer 2 VPN";
           }
           enum "cesop" {
             description "CESOP based Layer 2 VPN";
           }
         }
       }
       leaf ignore-encapsulation-mismatch {
         description "Allow different encapsulation types on local and remote end";
         type empty;
       }
       leaf mtu {
         description "MTU to be advertised to the remote end";
         type union {
           type string {
             pattern "<.*>|$.*";
           }
           type uint16 {
             range "512 .. 65535";
           }
         }
       }
       leaf ignore-mtu-mismatch {
         description "Allow different MTU values on local and remote end";
         type empty;
       }
       choice cword {
         case case_1 {
           leaf control-word {
             description "Adds control-word to the Layer 2 encapsulation";
             type empty;
           }
         }
         case case_2 {
           leaf no-control-word {
             description "Disables control-word to the Layer 2 encapsulation";
             type empty;
           }
         }
       }
       leaf pseudowire-status-tlv {
         description "Send pseudowire status TLV";
         type empty;
       }
       container oam {
         description "OAM Configuration for VPN";
         uses apply-advanced;
         leaf ping-interval {
           description "Time interval between ping messages";
           default "60";
           units "seconds";
           type union {
             type string {
               pattern "<.*>|$.*";
             }
             type uint16 {
               range "30 .. 3600";
             }
           }
         }
         leaf ping-multiplier {
           description "Number of ping reply missed before declaring BFD down";
           type union {
             type string {
               pattern "<.*>|$.*";
             }
             type uint8 {
               range "1 .. 5";
             }
           }
         }
         container bfd-liveness-detection {
           description "Bidirectional Forwarding Detection (BFD) options";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
         }
       }
       leaf community {
         description "Community associated with this interface";
         type string;
       }
       list static-mac {
         key name;
         ordered-by user;
         description "Static MAC addresses assigned to this interface";
         leaf name {
           description "MAC address";
           type jt:mac-addr;
         }
         uses apply-advanced;
         list vlan-id {
           key name;
           ordered-by user;
           description "VLAN ID of learning VLAN";
           leaf name {
             description "Learning VLAN";
             type union {
               type string {
                 pattern "<.*>|$.*";
               }
               type uint32 {
                 range "0 .. 4094";
               }
             }
           }
           uses apply-advanced;
         }
       }
       container interface-mac-ip-limit {
         description "Maximum number of MAC+IP bindings learned on the interface";
         uses apply-advanced;
         leaf limit {
           description "Maximum number of MAC+IP bindings per interface";
           type union {
             type string {
               pattern "<.*>|$.*";
             }
             type uint32;
           }
         }
       }
       leaf no-mac-learning {
         description "Disable dynamic MAC address learning";
         type empty;
       }
       leaf mac-pinning {
         description "Enable MAC pinning";
         type empty;
       }
       leaf description {
         description "Text description";
         type string;
       }
       leaf persistent-learning {
         description "Enable persistent MAC learning on this interface";
         type empty;
       }
     }
     container traceoptions {
       description "Trace options for this bridge domain";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       leaf level {
         description "Level of debugging output";
         default "error";
         type enumeration {
           enum "error" {
             description "Match error conditions";
           }
           enum "warning" {
             description "Match warning messages";
           }
           enum "notice" {
             description "Match conditions that should be handled specially";
           }
           enum "info" {
             description "Match informational messages";
           }
           enum "verbose" {
             description "Match verbose messages";
           }
           enum "all" {
             description "Match all levels";
           }
         }
       }
       list flag {
         key name;
         ordered-by user;
         description "Type of operation or event to include in trace";
         leaf name {
           type enumeration {
             enum "configuration" {
               description "Configuration operations";
             }
             enum "routing-socket" {
               description "Routing socket operations";
             }
             enum "interface-device" {
               description "Interface device operations";
             }
             enum "interface-logical" {
               description "Logical interface operations";
             }
             enum "interface-family" {
               description "Interface family operations";
             }
             enum "learning-domain" {
               description "Learning domain operations";
             }
             enum "ipc" {
               description "Inter-process communications operations";
             }
             enum "mac-learning" {
               description "MAC address learning operations";
             }
             enum "initialization" {
               description "Initialization operations";
             }
             enum "flood-next-hop" {
               description "Flood next hop operations";
             }
             enum "storm-control" {
               description "Storm-control";
             }
             enum "unknown-unicast-forwarding" {
               description "Trace unknown unicast forwarding events";
             }
             enum "all" {
               description "All operations";
             }
           }
         }
       }
     }
   }
   grouping juniper-protocols-bgp {
     uses apply-advanced;
     choice enable-disable {
       case case_1 {
         leaf disable {
           description "Disable BGP";
           type empty;
         }
       }
     }
     choice precision-timers-choice {
       leaf precision-timers {
         description "Use precision timers for scheduling keepalives";
         type empty;
       }
       leaf no-precision-timers {
         description "Don't use precision timers for scheduling keepalives";
         type empty;
       }
     }
     container path-selection {
       description "Configure path selection strategy";
       uses apply-advanced;
       leaf cisco-non-deterministic {
         description "Use Cisco IOS nondeterministic path selection algorithm";
         type empty;
       }
       leaf always-compare-med {
         description "Always compare MED values, regardless of neighbor AS";
         type empty;
       }
       container med-plus-igp {
         presence "enable med-plus-igp";
         description "Add IGP cost to next-hop to MED before comparing MED values";
         uses apply-advanced;
         leaf med-multiplier {
           description "Multiplier for MED";
           default "1";
           type union {
             type string {
               pattern "<.*>|$.*";
             }
             type uint16 {
               range "1 .. 1000";
             }
           }
         }
         leaf igp-multiplier {
           description "Multiplier for IGP cost to next-hop";
           default "1";
           type union {
             type string {
               pattern "<.*>|$.*";
             }
             type uint16 {
               range "1 .. 1000";
             }
           }
         }
       }
       leaf external-router-id {
         description "Compare router ID on BGP externals";
         type empty;
       }
       leaf as-path-ignore {
         description "Ignore AS path comparison during path selection";
         type empty;
       }
       leaf l2vpn-use-bgp-rules {
         description "Use standard BGP rules during L2VPN path selection";
         type empty;
       }
     }
     container snmp-options {
       description "Customize SNMP behaviors specifically for BGP MIBs";
       uses apply-advanced;
       leaf backward-traps-only-from-established {
         description "Limit traps for backward transitions to only those moving from Established state.";
         type empty;
       }
       leaf emit-inet-address-length-in-oid {
         description "Emit Length in OID for InetAddress MIB type.";
         type empty;
       }
     }
     leaf advertise-from-main-vpn-tables {
       description "Advertise VPN routes from bgp.Xvpn.0 tables in master instance";
       type empty;
     }
     leaf stale-labels-holddown-period {
       description "Duration (sec) MPLS labels allocated by BGP are kept after they go stale";
       type union {
         type string {
           pattern "<.*>|$.*";
         }
         type int32 {
           range "1 .. 600";
         }
       }
     }
     leaf holddown-all-stale-labels {
       description "Hold all BGP stale-labels, facilating make-before-break for new label advertisements";
       type empty;
     }
     container egress-te-backup-paths {
       description "Backup-path for Egress-TE peer interface failure";
       uses apply-advanced;
       list template {
         key name;
         description "Backup-path template";
         leaf name {
           description "Name of Egress-TE backup path";
           type string {
           }
         }
         uses apply-advanced;
         list peer {
           key name;
           ordered-by user;
           description "Egress peer TE backup exit path";
           leaf name {
             description "Address of BGP peer to use as backup next-hop";
             type jt:ipaddr;
           }
           uses apply-advanced;
         }
         container remote-nexthop {
           description "Resolve and use tunnel to this next-hop as backup path";
           uses apply-advanced;
           leaf remote-nh-addr {
             description "Address of remote-nexthop to use as backup path";
             type jt:ipaddr;
           }
         }
         container ip-forward {
           presence "enable ip-forward";
           description "Use IP-forward backup path for Egress TE";
           uses apply-advanced;
           leaf rti-name {
             description "Routing-instance to use as IP forward backup-path";
             type string {
             }
           }
         }
       }
     }
     leaf sr-preference-override {
       description "Replace received segment routing traffic engineering preference value with override value";
       type union {
         type uint32;
         type string {
           pattern "<.*>|$.*";
         }
       }
     }
     container traceoptions {
       description "Trace options for BGP";
       uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "damping" {
               description "Trace BGP damping information";
             }
             enum "packets" {
               description "Trace all BGP protocol packets";
             }
             enum "open" {
               description "Trace BGP open packets";
             }
             enum "update" {
               description "Trace BGP update packets";
             }
             enum "keepalive" {
               description "Trace BGP keepalive packets";
             }
             enum "refresh" {
               description "Trace BGP refresh packets";
             }
             enum "nsr-synchronization" {
               description "Trace NSR synchronization events";
             }
             enum "bfd" {
               description "Trace BFD events";
             }
             enum "4byte-as" {
               description "Trace 4 byte AS events";
             }
             enum "add-path" {
               description "Trace add-path events";
             }
             enum "graceful-restart" {
               description "Trace Graceful Restart events";
             }
             enum "egress-te" {
               description "Egress Peering Traffic-Engineering events";
             }
             enum "thread-io" {
               description "Trace threaded I/O processing";
             }
             enum "thread-update-io" {
               description "Trace threaded update I/O processing";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
         container filter {
           description "Filter to apply to this flag";
           presence "enable filter";
           uses bgp_filter_obj;
         }
       }
     }
     leaf description {
       description "Text description";
       type string {
         length "1 .. 255";
       }
     }
     container metric-out {
       description "Route metric sent in MED";
       choice metric_param {
         case case_1 {
           leaf metric-value {
             description "Metric value";
             type union {
               type string {
                 pattern "<.*>|$.*";
               }
               type uint32 {
                 range "0 .. 4294967295";
               }
             }
           }
         }
         case case_2 {
           container minimum-igp {
             presence "enable minimum-igp";
             description "Track the minimum IGP metric";
             leaf metric-offset {
               description "Metric offset for MED";
               type union {
                 type int32;
                 type string {
                   pattern "<.*>|$.*";
                 }
               }
             }
           }
         }
         case case_3 {
           container igp {
             presence "enable igp";
             description "Track the IGP metric";
             leaf metric-offset {
               description "Metric offset for MED";
               type union {
                 type int32;
                 type string {
                   pattern "<.*>|$.*";
                 }
               }
             }
             leaf delay-med-update {
               description "Delay updating MED when IGP metric increases";
               type empty;
             }
           }
         }
       }
     }
     container multihop {
       presence "enable multihop";
       description "Configure an EBGP multihop session";
       uses apply-advanced;
       leaf ttl {
         description "TTL value for the session";
         type union {
           type string {
             pattern "<.*>|$.*";
           }
           type uint8 {
             range "1 .. 255";
           }
         }
       }
       leaf no-nexthop-change {
         description "Do not change next hop to self in advertisements";
         type empty;
       }
     }
     leaf route-server-client {
       description "Enable route server client behavior";
       type empty;
     }
     leaf accept-remote-nexthop {
       description "Allow import policy to specify a non-directly connected next-hop";
       type empty;
     }
     leaf preference {
       description "Preference value";
       type union {
         type uint32;
         type string {
           pattern "<.*>|$.*";
         }
       }
     }
     leaf local-preference {
       description "Value of LOCAL_PREF path attribute";
       type union {
         type uint32;
         type string {
           pattern "<.*>|$.*";
         }
       }
     }
     leaf local-address {
       description "Address of local end of BGP session";
       type jt:ipaddr;
     }
     leaf local-interface {
       description "Local interface for IPv6 link local EBGP peering";
       type union {
         type jt:interface-name;
         type string {
           pattern "<.*>|$.*";
         }
       }
     }
     leaf forwarding-context {
       description "Routing-instance used for data-forwarding and transport-session";
       type string {
       }
     }
     leaf hold-time {
       description "Hold time used when negotiating with a peer";
       type union {
         type string {
           pattern "<.*>|$.*";
         }
         type uint32 {
           range "0 .. 65535";
         }
       }
     }
     leaf passive {
       description "Do not send open messages to a peer";
       type empty;
     }
     leaf advertise-inactive {
       description "Advertise inactive routes";
       type empty;
     }
     choice advertise-peer-as-choice {
       leaf advertise-peer-as {
         description "Advertise routes received from the same autonomous system";
         type empty;
       }
       leaf no-advertise-peer-as {
         description "Don't advertise routes received from the same autonomous system";
         type empty;
       }
     }
     container advertise-external {
       presence "enable advertise-external";
       description "Advertise best external routes";
       leaf conditional {
         description "Route matches active route upto med-comparison rule";
         type empty;
       }
     }
     leaf keep {
       description "How to retain routes in the routing table";
       type enumeration {
         enum "all" {
           description "Retain all routes";
         }
         enum "none" {
           description "Retain no routes";
         }
       }
     }
     leaf rfc6514-compliant-safi129 {
       description "Compliant with RFC6514 SAFI129 format";
       type empty;
     }
     leaf no-aggregator-id {
       description "Set router ID in aggregator path attribute to 0";
       type empty;
     }
     leaf mtu-discovery {
       description "Enable TCP path MTU discovery";
       type empty;
     }
     leaf enforce-first-as {
       description "Enforce first AS in AS-path is the neighbor's AS";
       type empty;
     }
     leaf out-delay {
       description "How long before exporting routes from routing table";
       type union {
         type string {
           pattern "<.*>|$.*";
         }
         type uint32 {
           range "0 .. 65535";
         }
       }
     }
     leaf ttl {
       description "TTL value for the single-hop peer";
       type enumeration {
         enum "1" {
         }
         enum "255" {
         }
       }
     }
     leaf log-updown {
       description "Log a message for peer state transitions";
       type empty;
     }
     leaf damping {
       description "Enable route flap damping";
       type empty;
     }
     leaf-list import {
       ordered-by user;
       description "Import policy";
       type jt:policy-algebra;
     }
     leaf-list nlri {
       ordered-by user;
       description "NLRI type to include in updates";
       status deprecated;
       type enumeration {
         enum "unicast" {
           description "Include unicast NLRI";
           status deprecated;
         }
         enum "multicast" {
           description "Include multicast NLRI";
           status deprecated;
         }
         enum "any" {
           description "Include any kind of NLRI";
           status deprecated;
         }
       }
     }
     container bgp-error-tolerance {
       presence "enable bgp-error-tolerance";
       description "Handle BGP malformed updates softly";
       uses apply-advanced;
       leaf malformed-update-log-interval {
         description "Time used when logging malformed update";
         default "300";
         units "seconds";
         type union {
           type string {
             pattern "<.*>|$.*";
           }
           type uint32 {
             range "10 .. 65535";
           }
         }
       }
       choice malformed-routes-limit-choice {
         case case_1 {
           leaf malformed-route-limit {
             description "Maximum number of malformed routes from a peer";
             default "1000";
             type union {
               type string {
                 pattern "<.*>|$.*";
               }
               type uint32 {
                 range "0 .. 4294967295";
               }
             }
           }
         }
         case case_2 {
           leaf no-malformed-route-limit {
             description "No malformed route limit";
             type empty;
           }
         }
       }
     }
     container family {
       description "Protocol family for NLRIs in updates";
       container inet {
         description "IPv4 NLRI parameters";
         uses apply-advanced;
         container unicast {
           description "Include unicast NLRI";
           presence "enable unicast";
           uses bgp-afi-topo;
         }
         container multicast {
           description "Include multicast NLRI";
           presence "enable multicast";
           uses bgp-afi-default;
         }
         container flow {
           description "Include flow NLRI";
           presence "enable flow";
           uses bgp-afi-flow-with-redirect-ip-action;
         }
         container any {
           description "Include unicast or multicast NLRI";
           presence "enable any";
           uses bgp-afi-default;
         }
         container labeled-unicast {
           description "Include labeled unicast NLRI";
           presence "enable labeled-unicast";
           uses bgp-afi-labeled;
         }
         container segment-routing-te {
           description "Include segment-routing TE policy";
           presence "enable segment-routing-te";
           uses bgp-afi-srte;
         }
       }
       container inet-vpn {
         description "IPv4 Layer 3 VPN NLRI parameters";
         uses apply-advanced;
         container unicast {
           description "Include unicast NLRI";
           presence "enable unicast";
           uses bgp-afi-vpn-protection;
         }
         container multicast {
           description "Include multicast NLRI";
           presence "enable multicast";
           uses bgp-afi-vpn;
         }
         container flow {
           description "Include flow VPN NLRI";
           presence "enable flow";
           uses bgp-afi-flow-with-redirect-ip-action;
         }
         container any {
           description "Include unicast or multicast NLRI";
           presence "enable any";
           uses bgp-afi-vpn;
         }
       }
       container inet6 {
         description "IPv6 NLRI parameters";
         uses apply-advanced;
         container unicast {
           description "Include unicast NLRI";
           presence "enable unicast";
           uses bgp-afi-topo;
         }
         container multicast {
           description "Include multicast NLRI";
           presence "enable multicast";
           uses bgp-afi-default;
         }
         container flow {
           description "Include flow NLRI";
           presence "enable flow";
           uses bgp-afi-flow;
         }
         container any {
           description "Include unicast or multicast NLRI";
           presence "enable any";
           uses bgp-afi-default;
         }
         container labeled-unicast {
           description "Include labeled unicast NLRI";
           presence "enable labeled-unicast";
           uses bgp-afi-inet6-labeled;
         }
         container segment-routing-te {
           description "Include segment-routing TE policy";
           presence "enable segment-routing-te";
           uses bgp-afi-srte;
         }
       }
       container inet6-vpn {
         description "IPv6 Layer 3 VPN NLRI parameters";
         uses apply-advanced;
         container unicast {
           description "Include unicast NLRI";
           presence "enable unicast";
           uses bgp-afi-vpn-protection;
         }
         container multicast {
           description "Include multicast NLRI";
           presence "enable multicast";
           uses bgp-afi-vpn;
         }
         container flow {
           description "Include flow VPN NLRI";
           presence "enable flow";
           uses bgp-afi-flow;
         }
         container any {
           description "Include unicast or multicast NLRI";
           presence "enable any";
           uses bgp-afi-vpn;
         }
       }
       container iso-vpn {
         description "ISO Layer 3 VPN NLRI parameters";
         uses apply-advanced;
         container unicast {
           description "Include unicast NLRI";
           presence "enable unicast";
           uses bgp-afi-vpn-protection;
         }
       }
       container l2vpn {
         description "MPLS-based Layer 2 VPN and VPLS NLRI parameters";
         uses apply-advanced;
         container auto-discovery-only {
           description "Include auto-discovery NLRI for LDP Layer 2 VPN and VPLS";
           presence "enable auto-discovery-only";
           uses bgp-afi-default;
         }
         container auto-discovery-mspw {
           description "Include auto-discovery NLRI for LDP Signalled MultiSegment PW";
           presence "enable auto-discovery-mspw";
           uses bgp-afi-default;
         }
         container signaling {
           description "Include Layer 2 VPN and VPLS signaling NLRI";
           presence "enable signaling";
           uses bgp-afi-l2vpn;
         }
       }
       container evpn {
         description "EVPN NLRI parameters";
         uses apply-advanced;
         container signaling {
           description "Include EVPN signaling NLRI";
           presence "enable signaling";
           uses bgp-afi-default;
         }
       }
       container inet-mvpn {
         description "IPv4 MVPN NLRI parameters";
         uses apply-advanced;
         container signaling {
           description "Include IPv4 multicast VPN signaling NLRI";
           presence "enable signaling";
           uses bgp-afi-default;
         }
       }
       container inet6-mvpn {
         description "IPv6 MVPN NLRI parameters";
         uses apply-advanced;
         container signaling {
           description "Include IPv6 multicast VPN signaling NLRI";
           presence "enable signaling";
           uses bgp-afi-default;
         }
       }
       container inet-mdt {
         description "IPv4 Multicast Distribution Tree (MDT) NLRI parameters";
         uses apply-advanced;
         container signaling {
           description "Include IPv4 multicast VPN auto-discovery NLRI";
           presence "enable signaling";
           uses bgp-afi-default;
         }
       }
       container traffic-engineering {
         description "Traffic Engineering (BGP-TE) NLRI parameters";
         uses apply-advanced;
         container unicast {
           description "Include BGP-TE NLRI";
           presence "enable unicast";
           uses bgp-afi-default;
         }
       }
       container route-target {
         presence "enable route-target";
         description "Route target NLRI used for VPN route filtering";
         uses apply-advanced;
         container prefix-limit {
           description "Limit maximum number of prefixes from a peer";
           uses bgpaf-prefix-limit;
         }
         container accepted-prefix-limit {
           description "Limit maximum number of prefixes accepted from a peer";
           uses bgpaf-accepted-prefix-limit;
         }
         container proxy-generate {
           presence "enable proxy-generate";
           description "Generate route target NLRI for peers that don't support it";
           uses apply-advanced;
           leaf-list route-target-policy {
             ordered-by user;
             description "Limit VPN routes that are used to generate proxy route-target filters";
             type jt:policy-algebra;
           }
         }
         leaf external-paths {
           description "Number of external paths accepted for route filtering";
           type union {
             type string {
               pattern "<.*>|$.*";
             }
             type uint32 {
               range "1 .. 256";
             }
           }
         }
         leaf advertise-default {
           description "Advertise default and suppress more specific routes";
           type empty;
         }
         leaf damping {
           description "Enable route flap damping";
           type empty;
         }
         container graceful-restart {
           description "BGP graceful restart options";
           uses bgp-af-gr;
         }
         leaf local-ipv4-address {
           description "Local IPv4 address";
           type jt:ipv4addr;
         }
         container output-queue-priority {
           description "Default output-queue to assign updates to";
           uses bgp-output-queue-priority-class;
         }
         container route-refresh-priority {
           description "Default output-queue to assign route refreshes to";
           uses bgp-output-queue-priority-class;
         }
         container withdraw-priority {
           description "Default output-queue to assign withdrawn routes to";
           uses bgp-output-queue-priority-class;
         }
       }
     }
     leaf authentication-key {
       description "MD5 authentication key";
       type string {
         length "1 .. 126";
       }
     }
     leaf authentication-algorithm {
       description "Authentication algorithm name";
       default "hmac-sha-1-96";
       type enumeration {
         enum "md5" {
           description "Message Digest 5";
         }
         enum "hmac-sha-1-96" {
           description "Hash-based Message Authentication Code (SHA1) (96 bits)";
         }
         enum "aes-128-cmac-96" {
           description "Cipher-based Message Authentication Code (AES128) (96 bits)";
         }
       }
     }
     leaf authentication-key-chain {
       description "Key chain name";
       type string {
         length "1 .. 128";
       }
     }
     leaf-list export {
       ordered-by user;
       description "Export policy";
       type jt:policy-algebra;
     }
     leaf vpn-apply-export {
       description "Apply BGP export policy when exporting VPN routes";
       type empty;
     }
     container egress-te {
       presence "enable egress-te";
       description "Use Egress Peering traffic engineering";
       uses apply-advanced;
       leaf backup-path {
         description "The 'egress-te-backup-paths template' to use for this peer";
         type string {
         }
       }
     }
     container remove-private {
       presence "enable remove-private";
       description "Remove well-known private AS numbers";
       uses apply-advanced;
       container all {
         presence "enable all";
         description "Remove all private AS numbers and do not stop at the first public AS number";
         container replace {
           presence "enable replace";
           description "Replace private AS numbers with the BGP Group's local AS number";
           leaf nearest {
             description "Use closest public AS number to replace a private AS number";
             type empty;
           }
         }
       }
       leaf no-peer-loop-check {
         description "Remove peer loop-check";
         type empty;
       }
     }
     leaf cluster {
       description "Cluster identifier";
       type jt:areaid;
     }
     leaf no-client-reflect {
       description "Disable intracluster route redistribution";
       type empty;
     }
     leaf peer-as {
       description " Autonomous system number in plain number or 'higher 16bits'.'Lower 16 bits' (asdot notation) format";
       type string {
       }
     }
     container local-as {
       description "Local autonomous system number";
       leaf as-number {
         description " Autonomous system number in plain number or 'higher 16bits'.'Lower 16 bits' (asdot notation) format";
         type string {
         }
       }
       leaf loops {
         description "Maximum number of times this AS can be in an AS path";
         type union {
           type string {
             pattern "<.*>|$.*";
           }
           type int32 {
             range "1 .. 10";
           }
         }
       }
       leaf private {
         description "Hide this local AS in paths learned from this peering";
         type empty;
       }
       leaf alias {
         description "Treat this AS as an alias to the system AS";
         type empty;
       }
       leaf no-prepend-global-as {
         description "Do not prepend global autonomous-system number in advertised paths";
         type empty;
       }
     }
     leaf ipsec-sa {
       description "IPSec SA name";
       type string {
         length "1 .. 32";
       }
     }
     leaf unconfigured-peer-graceful-restart {
       description "BGP unconfigured peer graceful restart options";
       type empty;
     }
     container graceful-restart {
       presence "enable graceful-restart";
       description "BGP graceful restart options";
       uses apply-advanced;
       choice enable-disable {
         case case_1 {
           leaf disable {
             description "Disable graceful restart";
             type empty;
           }
         }
       }
       leaf restart-time {
         description "Restart time used when negotiating with a peer";
         type union {
           type string {
             pattern "<.*>|$.*";
           }
           type uint32 {
             range "1 .. 1800";
           }
         }
       }
       leaf stale-routes-time {
         description "Maximum time for which stale routes are kept";
         type union {
           type string {
             pattern "<.*>|$.*";
           }
           type uint32 {
             range "1 .. 1800";
           }
         }
       }
       container long-lived {
         description "Long-lived graceful restart options";
         uses apply-advanced;
         container receiver {
           description "Long-lived graceful restart receiver (helper) options";
           uses apply-advanced;
           choice enable-disable {
             case case_1 {
               leaf disable {
                 description "Disable receiver (helper) functionality";
                 type empty;
               }
             }
           }
         }
         container advertise-to-non-llgr-neighbor {
           presence "enable advertise-to-non-llgr-neighbor";
           description "Advertise stale routes to non-LLGR neighbors";
           uses apply-advanced;
           leaf omit-no-export {
             description "Do not attach no-export community to stale routes";
             type empty;
           }
         }
       }
       leaf forwarding-state-bit {
         description "Control forwarding-state flag negotiation";
         type enumeration {
           enum "as-rr-client" {
             description "As for a route reflector client";
           }
           enum "from-fib" {
             description "Always use state of associated FIB(s)";
           }
         }
       }
       leaf dont-help-shared-fate-bfd-down {
         description "Honor BFD-Down(C=0) if GR-restart not in progress";
         type empty;
       }
     }
     leaf include-mp-next-hop {
       description "Include NEXT-HOP attribute in multiprotocol updates";
       type empty;
     }
     container idle-after-switch-over {
       description "Stop peer session from coming up after nonstop-routing switch-over";
       choice idle-interval {
         case case_1 {
           leaf forever {
             description "Idle the peer until the user intervenes";
             type empty;
           }
         }
         case case_2 {
           leaf timeout {
             description "Timeout value, in seconds, for starting peer after switch over";
             type union {
               type string {
                 pattern "<.*>|$.*";
               }
               type uint32 {
                 range "1 .. 4294967295";
               }
             }
           }
         }
       }
     }
     container outbound-route-filter {
       description "Dynamically negotiated cooperative route filtering";
       uses apply-advanced;
       leaf bgp-orf-cisco-mode {
         description "Using BGP ORF capability code 130 and Prefix ORF type 128";
         type empty;
       }
       container extended-community {
         description "Extended community filtering";
         status deprecated;
         uses apply-advanced;
         choice accept-choice {
           leaf accept {
             description "Honor remote requests for extended community ORF";
             type empty;
           }
           leaf no-accept {
             description "Don't honor remote requests for extended community ORF";
             type empty;
           }
         }
         leaf vrf-filter {
           description "Request remote filtering using locally configured VRF import targets";
           type empty;
         }
       }
       container prefix-based {
         presence "enable prefix-based";
         description "Prefix-based outbound route filtering";
         uses apply-advanced;
         container accept {
           presence "enable accept";
           description "Honor Prefix-based ORFs from remote peers";
           uses apply-advanced;
           leaf inet {
             description "Honor IPv4 prefix filters";
             type empty;
           }
           leaf inet6 {
             description "Honor IPv6 prefix filters";
             type empty;
           }
         }
       }
     }
     container multipath {
       presence "enable multipath";
       description "Allow load sharing among multiple BGP paths";
       uses apply-advanced;
       leaf disable {
         description "Disable Multipath";
         type empty;
       }
       leaf multiple-as {
         description "Use paths received from different ASs";
         type empty;
       }
     }
     leaf tcp-mss {
       description "Maximum TCP segment size";
       type union {
         type string {
           pattern "<.*>|$.*";
         }
         type uint32 {
           range "1 .. 4096";
         }
       }
     }
     leaf tcp-aggressive-transmission {
       description "Enable aggressive transmission of pure TCP ACKs and retransmissions";
       type empty;
     }
     container bmp {
       description "Specific settings to override the routing-options settings";
       uses apply-advanced;
       leaf monitor {
         description "Enable/Disable monitoring";
         type enumeration {
           enum "enable" {
             description "Enable monitoring of BGP peer(s)";
           }
           enum "disable" {
             description "Disable monitoring of BGP peer(s)";
           }
         }
       }
       container route-monitoring {
         description "Control route monitoring settings";
         uses apply-advanced;
         leaf none {
           description "Do not send route montoring messages";
           type empty;
         }
         container pre-policy {
           presence "enable pre-policy";
           description "Send pre policy route montoring messages";
           leaf exclude-non-feasible {
             description "Exclude looped routes, etc";
             type empty;
           }
         }
         container post-policy {
           presence "enable post-policy";
           description "Send post policy route montoring messages";
           leaf exclude-non-eligible {
             description "Exclude unresolved routes, etc.";
             type empty;
           }
         }
       }
     }
     container advertise-bgp-static {
       presence "enable advertise-bgp-static";
       description "Advertise bgp-static routes";
       uses apply-advanced;
       leaf-list policy {
         ordered-by user;
         description "Static route advertisement policy";
         type jt:policy-algebra;
       }
     }
     leaf add-path-display-ipv4-address {
       description "Display add-path path-id in IPv4 address format";
       type empty;
     }
     container bfd-liveness-detection {
       description "Bidirectional Forwarding Detection (BFD) options";
       uses apply-advanced;
       leaf version {
         description "BFD protocol version number";
         default "automatic";
         type enumeration {
           enum "0" {
             description "BFD version 0 (deprecated)";
           }
           enum "1" {
             description "BFD version 1";
           }
           enum "automatic" {
             description "Choose BFD version automatically";
           }
         }
       }
       leaf minimum-interval {
         description "Minimum transmit and receive interval";
         units "milliseconds";
         type union {
           type string {
             pattern "<.*>|$.*";
           }
           type uint32 {
             range "1 .. 255000";
           }
         }
       }
       leaf minimum-transmit-interval {
         description "Minimum transmit interval";
         status deprecated;
         units "milliseconds";
         type union {
           type string {
             pattern "<.*>|$.*";
           }
           type uint32 {
             range "1 .. 255000";
           }
         }
       }
       leaf minimum-receive-interval {
         description "Minimum receive interval";
         units "milliseconds";
         type union {
           type string {
             pattern "<.*>|$.*";
           }
           type uint32 {
             range "1 .. 255000";
           }
         }
       }
       leaf multiplier {
         description "Detection time multiplier";
         default "3";
         type union {
           type string {
             pattern "<.*>|$.*";
           }
           type uint32 {
             range "1 .. 255";
           }
         }
       }
       choice adaptation-choice {
         case case_1 {
           leaf no-adaptation {
             description "Disable adaptation";
             type empty;
           }
         }
       }
       container transmit-interval {
         description "Transmit-interval options";
         uses apply-advanced;
         leaf minimum-interval {
           description "Minimum transmit interval";
           units "milliseconds";
           type union {
             type string {
               pattern "<.*>|$.*";
             }
             type uint32 {
               range "1 .. 255000";
             }
           }
         }
         leaf threshold {
           description "High transmit interval triggering a trap";
           units "milliseconds";
           type union {
             type uint32;
             type string {
               pattern "<.*>|$.*";
             }
           }
         }
       }
       container detection-time {
         description "Detection-time options";
         uses apply-advanced;
         leaf threshold {
           description "High detection-time triggering a trap";
           units "milliseconds";
           type union {
             type uint32;
             type string {
               pattern "<.*>|$.*";
             }
           }
         }
       }
       container authentication {
         description "Authentication options";
         uses apply-advanced;
         leaf key-chain {
           description "Key chain name";
           type string;
         }
         leaf algorithm {
           description "Algorithm name";
           type enumeration {
             enum "simple-password" {
               description "Simple password";
             }
             enum "keyed-md5" {
               description "Keyed message Digest 5";
             }
             enum "meticulous-keyed-md5" {
               description "Meticulous keyed message Digest 5";
             }
             enum "keyed-sha-1" {
               description "Keyed secure hash algorithm (SHA1) ";
             }
             enum "meticulous-keyed-sha-1" {
               description "Meticulous keyed secure hash algorithm (SHA1) ";
             }
           }
         }
         leaf loose-check {
           description "Verify authentication only if authentication is negotiated";
           type empty;
         }
       }
       leaf session-mode {
         description "BFD single-hop or multihop session-mode";
         default "automatic";
         type enumeration {
           enum "automatic" {
             description "Choose session-mode automatically";
           }
           enum "single-hop" {
             description "Use single-hop";
           }
           enum "multihop" {
             description "Use multihop";
           }
         }
       }
       leaf holddown-interval {
         description "Time to hold the session-UP notification to the client";
         units "milliseconds";
         type union {
           type string {
             pattern "<.*>|$.*";
           }
           type uint32 {
             range "0 .. 255000";
           }
         }
       }
     }
     leaf egress-te-sid-stats {
       description "Create BGP-Peer-SID sensor";
       type empty;
     }
     list egress-te-set-segment {
       key name;
       ordered-by user;
       description "Configure BGP-Peer-Set segment";
       leaf name {
         description "The BGP-Peer-Set segment name";
         type string {
         }
       }
       uses apply-advanced;
       container label {
         description "BGP-Peer-Set SID label from static label pool";
         uses apply-advanced;
         leaf label-value {
           description "BGP-Peer-Set SID label value from static label pool";
           type union {
             type string {
               pattern "<.*>|$.*";
             }
             type uint32 {
               range "16 .. 1048575";
             }
           }
         }
       }
       container egress-te-backup-segment {
         description "Backup segment for FRR";
         uses apply-advanced;
         container label {
           description "Backup segment label from static label pool";
           uses apply-advanced;
           leaf label-value {
             description "Backup segment label value from static label pool";
             type union {
               type string {
                 pattern "<.*>|$.*";
               }
               type uint32 {
                 range "16 .. 1048575";
               }
             }
           }
         }
       }
     }
     container output-queue-priority {
       description "BGP output queue priority scheduler for updates";
       uses apply-advanced;
       container expedited {
         presence "enable expedited";
         description "Expedited queue; highest priority";
         leaf update-tokens {
           description "Number of tokens";
           type union {
             type string {
               pattern "<.*>|$.*";
             }
             type uint32 {
               range "1 .. 100";
             }
           }
         }
       }
       list priority {
         key name;
         description "Output queue priority 1..16; higher is better";
         leaf name {
           description "Output queue priority; higher is better";
           type union {
             type string {
               pattern "<.*>|$.*";
             }
             type uint32 {
               range "1 .. 16";
             }
           }
         }
         leaf update-tokens {
           description "Number of tokens";
           type union {
             type string {
               pattern "<.*>|$.*";
             }
             type uint32 {
               range "1 .. 100";
             }
           }
         }
       }
       container defaults {
         description "Map policy's priority class and BGP output-queue";
         uses apply-advanced;
         container low {
           description "Assign the 'low' priority class to this output-queue";
           uses bgp-output-queue-priority-class;
         }
         container medium {
           description "Assign the 'medium' priority class to this output-queue";
           uses bgp-output-queue-priority-class;
         }
         container high {
           description "Assign the 'high' priority class to this output-queue";
           uses bgp-output-queue-priority-class;
         }
       }
     }
     list group {
       key name;
       ordered-by user;
       description "Define a peer group";
       leaf name {
         description "Group name";
         type string;
       }
       uses apply-advanced;
       leaf type {
         description "Type of peer group";
         type enumeration {
           enum "internal" {
             description "IBGP group";
           }
           enum "external" {
             description "EBGP group";
           }
         }
       }
       leaf protocol {
         description "IGP to use to resolve the next hop";
         status deprecated;
         type enumeration {
           enum "rip" {
             description "Use RIP to resolve the BGP next hop";
             status deprecated;
           }
           enum "ospf" {
             description "Use OSPF to resolve the BGP next hop";
             status deprecated;
           }
           enum "isis" {
             description "Use IS-IS to resolve the BGP next hop";
             status deprecated;
           }
         }
       }
       container traceoptions {
         description "Trace options for BGP";
         uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "damping" {
                 description "Trace BGP damping information";
               }
               enum "packets" {
                 description "Trace all BGP protocol packets";
               }
               enum "open" {
                 description "Trace BGP open packets";
               }
               enum "update" {
                 description "Trace BGP update packets";
               }
               enum "keepalive" {
                 description "Trace BGP keepalive packets";
               }
               enum "refresh" {
                 description "Trace BGP refresh packets";
               }
               enum "nsr-synchronization" {
                 description "Trace NSR synchronization events";
               }
               enum "bfd" {
                 description "Trace BFD events";
               }
               enum "4byte-as" {
                 description "Trace 4 byte AS events";
               }
               enum "add-path" {
                 description "Trace add-path events";
               }
               enum "graceful-restart" {
                 description "Trace Graceful Restart events";
               }
               enum "egress-te" {
                 description "Egress Peering Traffic-Engineering events";
               }
               enum "thread-io" {
                 description "Trace threaded I/O processing";
               }
               enum "thread-update-io" {
                 description "Trace threaded update I/O processing";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
           container filter {
             description "Filter to apply to this flag";
             presence "enable filter";
             uses bgp_filter_obj;
           }
         }
       }
       leaf description {
         description "Text description";
         type string {
           length "1 .. 255";
         }
       }
       container metric-out {
         description "Route metric sent in MED";
         choice metric_param {
           case case_1 {
             leaf metric-value {
               description "Metric value";
               type union {
                 type string {
                   pattern "<.*>|$.*";
                 }
                 type uint32 {
                   range "0 .. 4294967295";
                 }
               }
             }
           }
           case case_2 {
             container minimum-igp {
               presence "enable minimum-igp";
               description "Track the minimum IGP metric";
               leaf metric-offset {
                 description "Metric offset for MED";
                 type union {
                   type int32;
                   type string {
                     pattern "<.*>|$.*";
                   }
                 }
               }
             }
           }
           case case_3 {
             container igp {
               presence "enable igp";
               description "Track the IGP metric";
               leaf metric-offset {
                 description "Metric offset for MED";
                 type union {
                   type int32;
                   type string {
                     pattern "<.*>|$.*";
                   }
                 }
               }
               leaf delay-med-update {
                 description "Delay updating MED when IGP metric increases";
                 type empty;
               }
             }
           }
         }
       }
       container multihop {
         presence "enable multihop";
         description "Configure an EBGP multihop session";
         uses apply-advanced;
         leaf ttl {
           description "TTL value for the session";
           type union {
             type string {
               pattern "<.*>|$.*";
             }
             type uint8 {
               range "1 .. 255";
             }
           }
         }
         leaf no-nexthop-change {
           description "Do not change next hop to self in advertisements";
           type empty;
         }
       }
       leaf route-server-client {
         description "Enable route server client behavior";
         type empty;
       }
       leaf accept-remote-nexthop {
         description "Allow import policy to specify a non-directly connected next-hop";
         type empty;
       }
       leaf preference {
         description "Preference value";
         type union {
           type uint32;
           type string {
             pattern "<.*>|$.*";
           }
         }
       }
       leaf local-preference {
         description "Value of LOCAL_PREF path attribute";
         type union {
           type uint32;
           type string {
             pattern "<.*>|$.*";
           }
         }
       }
       leaf local-address {
         description "Address of local end of BGP session";
         type jt:ipaddr;
       }
       leaf local-interface {
         description "Local interface for IPv6 link local EBGP peering";
         type union {
           type jt:interface-name;
           type string {
             pattern "<.*>|$.*";
           }
         }
       }
       leaf forwarding-context {
         description "Routing-instance used for data-forwarding and transport-session";
         type string {
         }
       }
       leaf hold-time {
         description "Hold time used when negotiating with a peer";
         type union {
           type string {
             pattern "<.*>|$.*";
           }
           type uint32 {
             range "0 .. 65535";
           }
         }
       }
       leaf passive {
         description "Do not send open messages to a peer";
         type empty;
       }
       leaf advertise-inactive {
         description "Advertise inactive routes";
         type empty;
       }
       choice advertise-peer-as-choice {
         leaf advertise-peer-as {
           description "Advertise routes received from the same autonomous system";
           type empty;
         }
         leaf no-advertise-peer-as {
           description "Don't advertise routes received from the same autonomous system";
           type empty;
         }
       }
       container advertise-external {
         presence "enable advertise-external";
         description "Advertise best external routes";
         leaf conditional {
           description "Route matches active route upto med-comparison rule";
           type empty;
         }
       }
       leaf keep {
         description "How to retain routes in the routing table";
         type enumeration {
           enum "all" {
             description "Retain all routes";
           }
           enum "none" {
             description "Retain no routes";
           }
         }
       }
       leaf rfc6514-compliant-safi129 {
         description "Compliant with RFC6514 SAFI129 format";
         type empty;
       }
       leaf no-aggregator-id {
         description "Set router ID in aggregator path attribute to 0";
         type empty;
       }
       leaf mtu-discovery {
         description "Enable TCP path MTU discovery";
         type empty;
       }
       leaf enforce-first-as {
         description "Enforce first AS in AS-path is the neighbor's AS";
         type empty;
       }
       leaf out-delay {
         description "How long before exporting routes from routing table";
         type union {
           type string {
             pattern "<.*>|$.*";
           }
           type uint32 {
             range "0 .. 65535";
           }
         }
       }
       leaf ttl {
         description "TTL value for the single-hop peer";
         type enumeration {
           enum "1" {
           }
           enum "255" {
           }
         }
       }
       leaf log-updown {
         description "Log a message for peer state transitions";
         type empty;
       }
       leaf damping {
         description "Enable route flap damping";
         type empty;
       }
       leaf-list import {
         ordered-by user;
         description "Import policy";
         type jt:policy-algebra;
       }
       leaf-list nlri {
         ordered-by user;
         description "NLRI type to include in updates";
         status deprecated;
         type enumeration {
           enum "unicast" {
             description "Include unicast NLRI";
             status deprecated;
           }
           enum "multicast" {
             description "Include multicast NLRI";
             status deprecated;
           }
           enum "any" {
             description "Include any kind of NLRI";
             status deprecated;
           }
         }
       }
       container bgp-error-tolerance {
         presence "enable bgp-error-tolerance";
         description "Handle BGP malformed updates softly";
         uses apply-advanced;
         leaf malformed-update-log-interval {
           description "Time used when logging malformed update";
           default "300";
           units "seconds";
           type union {
             type string {
               pattern "<.*>|$.*";
             }
             type uint32 {
               range "10 .. 65535";
             }
           }
         }
         choice malformed-routes-limit-choice {
           case case_1 {
             leaf malformed-route-limit {
               description "Maximum number of malformed routes from a peer";
               default "1000";
               type union {
                 type string {
                   pattern "<.*>|$.*";
                 }
                 type uint32 {
                   range "0 .. 4294967295";
                 }
               }
             }
           }
           case case_2 {
             leaf no-malformed-route-limit {
               description "No malformed route limit";
               type empty;
             }
           }
         }
       }
       container family {
         description "Protocol family for NLRIs in updates";
         container inet {
           description "IPv4 NLRI parameters";
           uses apply-advanced;
           container unicast {
             description "Include unicast NLRI";
             presence "enable unicast";
             uses bgp-afi-topo;
           }
           container multicast {
             description "Include multicast NLRI";
             presence "enable multicast";
             uses bgp-afi-default;
           }
           container flow {
             description "Include flow NLRI";
             presence "enable flow";
             uses bgp-afi-flow-with-redirect-ip-action;
           }
           container any {
             description "Include unicast or multicast NLRI";
             presence "enable any";
             uses bgp-afi-default;
           }
           container labeled-unicast {
             description "Include labeled unicast NLRI";
             presence "enable labeled-unicast";
             uses bgp-afi-labeled;
           }
           container segment-routing-te {
             description "Include segment-routing TE policy";
             presence "enable segment-routing-te";
             uses bgp-afi-srte;
           }
         }
         container inet-vpn {
           description "IPv4 Layer 3 VPN NLRI parameters";
           uses apply-advanced;
           container unicast {
             description "Include unicast NLRI";
             presence "enable unicast";
             uses bgp-afi-vpn-protection;
           }
           container multicast {
             description "Include multicast NLRI";
             presence "enable multicast";
             uses bgp-afi-vpn;
           }
           container flow {
             description "Include flow VPN NLRI";
             presence "enable flow";
             uses bgp-afi-flow-with-redirect-ip-action;
           }
           container any {
             description "Include unicast or multicast NLRI";
             presence "enable any";
             uses bgp-afi-vpn;
           }
         }
         container inet6 {
           description "IPv6 NLRI parameters";
           uses apply-advanced;
           container unicast {
             description "Include unicast NLRI";
             presence "enable unicast";
             uses bgp-afi-topo;
           }
           container multicast {
             description "Include multicast NLRI";
             presence "enable multicast";
             uses bgp-afi-default;
           }
           container flow {
             description "Include flow NLRI";
             presence "enable flow";
             uses bgp-afi-flow;
           }
           container any {
             description "Include unicast or multicast NLRI";
             presence "enable any";
             uses bgp-afi-default;
           }
           container labeled-unicast {
             description "Include labeled unicast NLRI";
             presence "enable labeled-unicast";
             uses bgp-afi-inet6-labeled;
           }
           container segment-routing-te {
             description "Include segment-routing TE policy";
             presence "enable segment-routing-te";
             uses bgp-afi-srte;
           }
         }
         container inet6-vpn {
           description "IPv6 Layer 3 VPN NLRI parameters";
           uses apply-advanced;
           container unicast {
             description "Include unicast NLRI";
             presence "enable unicast";
             uses bgp-afi-vpn-protection;
           }
           container multicast {
             description "Include multicast NLRI";
             presence "enable multicast";
             uses bgp-afi-vpn;
           }
           container flow {
             description "Include flow VPN NLRI";
             presence "enable flow";
             uses bgp-afi-flow;
           }
           container any {
             description "Include unicast or multicast NLRI";
             presence "enable any";
             uses bgp-afi-vpn;
           }
         }
         container iso-vpn {
           description "ISO Layer 3 VPN NLRI parameters";
           uses apply-advanced;
           container unicast {
             description "Include unicast NLRI";
             presence "enable unicast";
             uses bgp-afi-vpn-protection;
           }
         }
         container l2vpn {
           description "MPLS-based Layer 2 VPN and VPLS NLRI parameters";
           uses apply-advanced;
           container auto-discovery-only {
             description "Include auto-discovery NLRI for LDP Layer 2 VPN and VPLS";
             presence "enable auto-discovery-only";
             uses bgp-afi-default;
           }
           container auto-discovery-mspw {
             description "Include auto-discovery NLRI for LDP Signalled MultiSegment PW";
             presence "enable auto-discovery-mspw";
             uses bgp-afi-default;
           }
           container signaling {
             description "Include Layer 2 VPN and VPLS signaling NLRI";
             presence "enable signaling";
             uses bgp-afi-l2vpn;
           }
         }
         container evpn {
           description "EVPN NLRI parameters";
           uses apply-advanced;
           container signaling {
             description "Include EVPN signaling NLRI";
             presence "enable signaling";
             uses bgp-afi-default;
           }
         }
         container inet-mvpn {
           description "IPv4 MVPN NLRI parameters";
           uses apply-advanced;
           container signaling {
             description "Include IPv4 multicast VPN signaling NLRI";
             presence "enable signaling";
             uses bgp-afi-default;
           }
         }
         container inet6-mvpn {
           description "IPv6 MVPN NLRI parameters";
           uses apply-advanced;
           container signaling {
             description "Include IPv6 multicast VPN signaling NLRI";
             presence "enable signaling";
             uses bgp-afi-default;
           }
         }
         container inet-mdt {
           description "IPv4 Multicast Distribution Tree (MDT) NLRI parameters";
           uses apply-advanced;
           container signaling {
             description "Include IPv4 multicast VPN auto-discovery NLRI";
             presence "enable signaling";
             uses bgp-afi-default;
           }
         }
         container traffic-engineering {
           description "Traffic Engineering (BGP-TE) NLRI parameters";
           uses apply-advanced;
           container unicast {
             description "Include BGP-TE NLRI";
             presence "enable unicast";
             uses bgp-afi-default;
           }
         }
         container route-target {
           presence "enable route-target";
           description "Route target NLRI used for VPN route filtering";
           uses apply-advanced;
           container prefix-limit {
             description "Limit maximum number of prefixes from a peer";
             uses bgpaf-prefix-limit;
           }
           container accepted-prefix-limit {
             description "Limit maximum number of prefixes accepted from a peer";
             uses bgpaf-accepted-prefix-limit;
           }
           container proxy-generate {
             presence "enable proxy-generate";
             description "Generate route target NLRI for peers that don't support it";
             uses apply-advanced;
             leaf-list route-target-policy {
               ordered-by user;
               description "Limit VPN routes that are used to generate proxy route-target filters";
               type jt:policy-algebra;
             }
           }
           leaf external-paths {
             description "Number of external paths accepted for route filtering";
             type union {
               type string {
                 pattern "<.*>|$.*";
               }
               type uint32 {
                 range "1 .. 256";
               }
             }
           }
           leaf advertise-default {
             description "Advertise default and suppress more specific routes";
             type empty;
           }
           leaf damping {
             description "Enable route flap damping";
             type empty;
           }
           container graceful-restart {
             description "BGP graceful restart options";
             uses bgp-af-gr;
           }
           leaf local-ipv4-address {
             description "Local IPv4 address";
             type jt:ipv4addr;
           }
           container output-queue-priority {
             description "Default output-queue to assign updates to";
             uses bgp-output-queue-priority-class;
           }
           container route-refresh-priority {
             description "Default output-queue to assign route refreshes to";
             uses bgp-output-queue-priority-class;
           }
           container withdraw-priority {
             description "Default output-queue to assign withdrawn routes to";
             uses bgp-output-queue-priority-class;
           }
         }
       }
       leaf authentication-key {
         description "MD5 authentication key";
         type string {
           length "1 .. 126";
         }
       }
       leaf authentication-algorithm {
         description "Authentication algorithm name";
         type enumeration {
           enum "md5" {
             description "Message Digest 5";
           }
           enum "hmac-sha-1-96" {
             description "Hash-based Message Authentication Code (SHA1) (96 bits)";
           }
           enum "aes-128-cmac-96" {
             description "Cipher-based Message Authentication Code (AES128) (96 bits)";
           }
         }
       }
       leaf authentication-key-chain {
         description "Key chain name";
         type string {
           length "1 .. 128";
         }
       }
       leaf-list export {
         ordered-by user;
         description "Export policy";
         type jt:policy-algebra;
       }
       leaf vpn-apply-export {
         description "Apply BGP export policy when exporting VPN routes";
         type empty;
       }
       container egress-te {
         presence "enable egress-te";
         description "Use Egress Peering traffic engineering";
         uses apply-advanced;
         leaf backup-path {
           description "The 'egress-te-backup-paths template' to use for this peer";
           type string {
           }
         }
       }
       container remove-private {
         presence "enable remove-private";
         description "Remove well-known private AS numbers";
         uses apply-advanced;
         container all {
           presence "enable all";
           description "Remove all private AS numbers and do not stop at the first public AS number";
           container replace {
             presence "enable replace";
             description "Replace private AS numbers with the BGP Group's local AS number";
             leaf nearest {
               description "Use closest public AS number to replace a private AS number";
               type empty;
             }
           }
         }
         leaf no-peer-loop-check {
           description "Remove peer loop-check";
           type empty;
         }
       }
       leaf cluster {
         description "Cluster identifier";
         type jt:areaid;
       }
       leaf no-client-reflect {
         description "Disable intracluster route redistribution";
         type empty;
       }
       leaf peer-as {
         description " Autonomous system number in plain number or 'higher 16bits'.'Lower 16 bits' (asdot notation) format";
         type string {
         }
       }
       container local-as {
         description "Local autonomous system number";
         leaf as-number {
           description " Autonomous system number in plain number or 'higher 16bits'.'Lower 16 bits' (asdot notation) format";
           type string {
           }
         }
         leaf loops {
           description "Maximum number of times this AS can be in an AS path";
           type union {
             type string {
               pattern "<.*>|$.*";
             }
             type int32 {
               range "1 .. 10";
             }
           }
         }
         leaf private {
           description "Hide this local AS in paths learned from this peering";
           type empty;
         }
         leaf alias {
           description "Treat this AS as an alias to the system AS";
           type empty;
         }
         leaf no-prepend-global-as {
           description "Do not prepend global autonomous-system number in advertised paths";
           type empty;
         }
       }
       leaf ipsec-sa {
         description "IPSec SA name";
         type string {
           length "1 .. 32";
         }
       }
       leaf unconfigured-peer-graceful-restart {
         description "BGP unconfigured peer graceful restart options";
         type empty;
       }
       container graceful-restart {
         presence "enable graceful-restart";
         description "BGP graceful restart options";
         uses apply-advanced;
         choice enable-disable {
           case case_1 {
             leaf disable {
               description "Disable graceful restart";
               type empty;
             }
           }
         }
         leaf restart-time {
           description "Restart time used when negotiating with a peer";
           type union {
             type string {
               pattern "<.*>|$.*";
             }
             type uint32 {
               range "1 .. 1800";
             }
           }
         }
         leaf stale-routes-time {
           description "Maximum time for which stale routes are kept";
           type union {
             type string {
               pattern "<.*>|$.*";
             }
             type uint32 {
               range "1 .. 1800";
             }
           }
         }
         container long-lived {
           description "Long-lived graceful restart options";
           uses apply-advanced;
           container receiver {
             description "Long-lived graceful restart receiver (helper) options";
             uses apply-advanced;
             choice enable-disable {
               case case_1 {
                 leaf disable {
                   description "Disable receiver (helper) functionality";
                   type empty;
                 }
               }
             }
           }
           container advertise-to-non-llgr-neighbor {
             presence "enable advertise-to-non-llgr-neighbor";
             description "Advertise stale routes to non-LLGR neighbors";
             uses apply-advanced;
             leaf omit-no-export {
               description "Do not attach no-export community to stale routes";
               type empty;
             }
           }
         }
         leaf forwarding-state-bit {
           description "Control forwarding-state flag negotiation";
           type enumeration {
             enum "as-rr-client" {
               description "As for a route reflector client";
             }
             enum "from-fib" {
               description "Always use state of associated FIB(s)";
             }
           }
         }
         leaf dont-help-shared-fate-bfd-down {
           description "Honor BFD-Down(C=0) if GR-restart not in progress";
           type empty;
         }
       }
       leaf include-mp-next-hop {
         description "Include NEXT-HOP attribute in multiprotocol updates";
         type empty;
       }
       container idle-after-switch-over {
         description "Stop peer session from coming up after nonstop-routing switch-over";
         choice idle-interval {
           case case_1 {
             leaf forever {
               description "Idle the peer until the user intervenes";
               type empty;
             }
           }
           case case_2 {
             leaf timeout {
               description "Timeout value, in seconds, for starting peer after switch over";
               type union {
                 type string {
                   pattern "<.*>|$.*";
                 }
                 type uint32 {
                   range "1 .. 4294967295";
                 }
               }
             }
           }
         }
       }
       container outbound-route-filter {
         description "Dynamically negotiated cooperative route filtering";
         uses apply-advanced;
         leaf bgp-orf-cisco-mode {
           description "Using BGP ORF capability code 130 and Prefix ORF type 128";
           type empty;
         }
         container extended-community {
           description "Extended community filtering";
           status deprecated;
           uses apply-advanced;
           choice accept-choice {
             leaf accept {
               description "Honor remote requests for extended community ORF";
               type empty;
             }
             leaf no-accept {
               description "Don't honor remote requests for extended community ORF";
               type empty;
             }
           }
           leaf vrf-filter {
             description "Request remote filtering using locally configured VRF import targets";
             type empty;
           }
         }
         container prefix-based {
           presence "enable prefix-based";
           description "Prefix-based outbound route filtering";
           uses apply-advanced;
           container accept {
             presence "enable accept";
             description "Honor Prefix-based ORFs from remote peers";
             uses apply-advanced;
             leaf inet {
               description "Honor IPv4 prefix filters";
               type empty;
             }
             leaf inet6 {
               description "Honor IPv6 prefix filters";
               type empty;
             }
           }
         }
       }
       container multipath {
         presence "enable multipath";
         description "Allow load sharing among multiple BGP paths";
         uses apply-advanced;
         leaf disable {
           description "Disable Multipath";
           type empty;
         }
         leaf multiple-as {
           description "Use paths received from different ASs";
           type empty;
         }
       }
       leaf tcp-mss {
         description "Maximum TCP segment size";
         type union {
           type string {
             pattern "<.*>|$.*";
           }
           type uint32 {
             range "1 .. 4096";
           }
         }
       }
       leaf tcp-aggressive-transmission {
         description "Enable aggressive transmission of pure TCP ACKs and retransmissions";
         type empty;
       }
       container bmp {
         description "Specific settings to override the routing-options settings";
         uses apply-advanced;
         leaf monitor {
           description "Enable/Disable monitoring";
           type enumeration {
             enum "enable" {
               description "Enable monitoring of BGP peer(s)";
             }
             enum "disable" {
               description "Disable monitoring of BGP peer(s)";
             }
           }
         }
         container route-monitoring {
           description "Control route monitoring settings";
           uses apply-advanced;
           leaf none {
             description "Do not send route montoring messages";
             type empty;
           }
           container pre-policy {
             presence "enable pre-policy";
             description "Send pre policy route montoring messages";
             leaf exclude-non-feasible {
               description "Exclude looped routes, etc";
               type empty;
             }
           }
           container post-policy {
             presence "enable post-policy";
             description "Send post policy route montoring messages";
             leaf exclude-non-eligible {
               description "Exclude unresolved routes, etc.";
               type empty;
             }
           }
         }
       }
       container advertise-bgp-static {
         presence "enable advertise-bgp-static";
         description "Advertise bgp-static routes";
         uses apply-advanced;
         leaf-list policy {
           ordered-by user;
           description "Static route advertisement policy";
           type jt:policy-algebra;
         }
       }
       leaf add-path-display-ipv4-address {
         description "Display add-path path-id in IPv4 address format";
         type empty;
       }
       container bfd-liveness-detection {
         description "Bidirectional Forwarding Detection (BFD) options";
         uses apply-advanced;
         leaf version {
           description "BFD protocol version number";
           default "automatic";
           type enumeration {
             enum "0" {
               description "BFD version 0 (deprecated)";
             }
             enum "1" {
               description "BFD version 1";
             }
             enum "automatic" {
               description "Choose BFD version automatically";
             }
           }
         }
         leaf minimum-interval {
           description "Minimum transmit and receive interval";
           units "milliseconds";
           type union {
             type string {
               pattern "<.*>|$.*";
             }
             type uint32 {
               range "1 .. 255000";
             }
           }
         }
         leaf minimum-transmit-interval {
           description "Minimum transmit interval";
           status deprecated;
           units "milliseconds";
           type union {
             type string {
               pattern "<.*>|$.*";
             }
             type uint32 {
               range "1 .. 255000";
             }
           }
         }
         leaf minimum-receive-interval {
           description "Minimum receive interval";
           units "milliseconds";
           type union {
             type string {
               pattern "<.*>|$.*";
             }
             type uint32 {
               range "1 .. 255000";
             }
           }
         }
         leaf multiplier {
           description "Detection time multiplier";
           default "3";
           type union {
             type string {
               pattern "<.*>|$.*";
             }
             type uint32 {
               range "1 .. 255";
             }
           }
         }
         choice adaptation-choice {
           case case_1 {
             leaf no-adaptation {
               description "Disable adaptation";
               type empty;
             }
           }
         }
         container transmit-interval {
           description "Transmit-interval options";
           uses apply-advanced;
           leaf minimum-interval {
             description "Minimum transmit interval";
             units "milliseconds";
             type union {
               type string {
                 pattern "<.*>|$.*";
               }
               type uint32 {
                 range "1 .. 255000";
               }
             }
           }
           leaf threshold {
             description "High transmit interval triggering a trap";
             units "milliseconds";
             type union {
               type uint32;
               type string {
                 pattern "<.*>|$.*";
               }
             }
           }
         }
         container detection-time {
           description "Detection-time options";
           uses apply-advanced;
           leaf threshold {
             description "High detection-time triggering a trap";
             units "milliseconds";
             type union {
               type uint32;
               type string {
                 pattern "<.*>|$.*";
               }
             }
           }
         }
         container authentication {
           description "Authentication options";
           uses apply-advanced;
           leaf key-chain {
             description "Key chain name";
             type string;
           }
           leaf algorithm {
             description "Algorithm name";
             type enumeration {
               enum "simple-password" {
                 description "Simple password";
               }
               enum "keyed-md5" {
                 description "Keyed message Digest 5";
               }
               enum "meticulous-keyed-md5" {
                 description "Meticulous keyed message Digest 5";
               }
               enum "keyed-sha-1" {
                 description "Keyed secure hash algorithm (SHA1) ";
               }
               enum "meticulous-keyed-sha-1" {
                 description "Meticulous keyed secure hash algorithm (SHA1) ";
               }
             }
           }
           leaf loose-check {
             description "Verify authentication only if authentication is negotiated";
             type empty;
           }
         }
         leaf session-mode {
           description "BFD single-hop or multihop session-mode";
           default "automatic";
           type enumeration {
             enum "automatic" {
               description "Choose session-mode automatically";
             }
             enum "single-hop" {
               description "Use single-hop";
             }
             enum "multihop" {
               description "Use multihop";
             }
           }
         }
         leaf holddown-interval {
           description "Time to hold the session-UP notification to the client";
           units "milliseconds";
           type union {
             type string {
               pattern "<.*>|$.*";
             }
             type uint32 {
               range "0 .. 255000";
             }
           }
         }
       }
       leaf as-override {
         description "Replace neighbor AS number with our AS number";
         type empty;
       }
       leaf-list allow {
         ordered-by user;
         description "Configure peer connections for specific networks";
         type jt:ipprefix;
       }
       container optimal-route-reflection {
         description "Enable optimal route reflection for this client group";
         uses apply-advanced;
         leaf igp-primary {
           description "Primary node identifier for this client group";
           type jt:ipv4addr;
         }
         leaf igp-backup {
           description "Backup node identifier for this client group";
           type jt:ipv4addr;
         }
       }
       leaf mvpn-iana-rt-import {
         description "Use IANA assigned rt-import type value for MVPN";
         status deprecated;
         type empty;
       }
       list neighbor {
         key name;
         ordered-by user;
         description "Configure a neighbor";
         leaf name {
           type jt:ipaddr;
         }
         uses apply-advanced;
         container egress-te-node-segment {
           description "Configure BGP-Peer-Node segment";
           uses apply-advanced;
           container label {
             description "BGP-Peer-Node SID label from static label pool";
             uses apply-advanced;
             leaf label-value {
               description "BGP-Peer-Node SID label value from static label pool";
               type union {
                 type string {
                   pattern "<.*>|$.*";
                 }
                 type uint32 {
                   range "16 .. 1048575";
                 }
               }
             }
           }
           container egress-te-set {
             description "Configure as a member of a SET segment";
             uses apply-advanced;
             leaf set-name {
               description "Set name";
               type string {
               }
             }
             leaf weight {
               description "Weight for set segment";
               type union {
                 type string {
                   pattern "<.*>|$.*";
                 }
                 type uint32 {
                   range "1 .. 255";
                 }
               }
             }
           }
           container egress-te-backup-segment {
             description "Backup segment for FRR";
             uses apply-advanced;
             container label {
               description "Backup segment label from static label pool";
               uses apply-advanced;
               leaf label-value {
                 description "Backup segment label value from static label pool";
                 type union {
                   type string {
                     pattern "<.*>|$.*";
                   }
                   type uint32 {
                     range "16 .. 1048575";
                   }
                 }
               }
             }
           }
         }
         list egress-te-adj-segment {
           key name;
           description "Configure BGP-Peer-Adj segment";
           leaf name {
             description "The BGP-Adj-Set segment name";
             type string {
             }
           }
           uses apply-advanced;
           container label {
             description "BGP-Peer-Adj SID label from static label pool";
             uses apply-advanced;
             leaf label-value {
               description "BGP-Peer-Adj SID label value from static label pool";
               type union {
                 type string {
                   pattern "<.*>|$.*";
                 }
                 type uint32 {
                   range "16 .. 1048575";
                 }
               }
             }
           }
           container next-hop {
             description "Address of directly connected next-hop to use";
             uses apply-advanced;
             leaf next-hop-addr {
               description "Address of directly connected next-hop";
               type jt:ipaddr;
             }
           }
           container egress-te-set {
             description "Configure as a member of a SET segment";
             uses apply-advanced;
             leaf set-name {
               description "Set name";
               type string {
               }
             }
             leaf weight {
               description "Weight for set segment";
               type union {
                 type string {
                   pattern "<.*>|$.*";
                 }
                 type uint32 {
                   range "1 .. 255";
                 }
               }
             }
           }
           container egress-te-backup-segment {
             description "Backup segment for FRR";
             uses apply-advanced;
             container label {
               description "Backup segment label from static label pool";
               uses apply-advanced;
               leaf label-value {
                 description "Backup segment label value from static label pool";
                 type union {
                   type string {
                     pattern "<.*>|$.*";
                   }
                   type uint32 {
                     range "16 .. 1048575";
                   }
                 }
               }
             }
           }
         }
         container traceoptions {
           description "Trace options for BGP";
           uses apply-advanced;
           container file {
             description "Trace file options";
             leaf filename {
               description "Name of file in which to write trace information";
               type string {
                 length "1 .. 1024";
               }
             }
             leaf replace {
               description "Replace trace file rather than appending to it";
               status deprecated;
               type empty;
             }
             leaf size {
               description "Maximum trace file size";
               type string;
             }
             leaf files {
               description "Maximum number of trace files";
               default "10";
               type union {
                 type string {
                   pattern "<.*>|$.*";
                 }
                 type uint32 {
                   range "2 .. 1000";
                 }
               }
             }
             leaf no-stamp {
               description "Do not timestamp trace file";
               status deprecated;
               type empty;
             }
             choice world-readable-choice {
               leaf world-readable {
                 description "Allow any user to read the log file";
                 type empty;
               }
               leaf no-world-readable {
                 description "Don't allow any user to read the log file";
                 type empty;
               }
             }
           }
           list flag {
             key name;
             ordered-by user;
             description "Tracing parameters";
             leaf name {
               type enumeration {
                 enum "damping" {
                   description "Trace BGP damping information";
                 }
                 enum "packets" {
                   description "Trace all BGP protocol packets";
                 }
                 enum "open" {
                   description "Trace BGP open packets";
                 }
                 enum "update" {
                   description "Trace BGP update packets";
                 }
                 enum "keepalive" {
                   description "Trace BGP keepalive packets";
                 }
                 enum "refresh" {
                   description "Trace BGP refresh packets";
                 }
                 enum "nsr-synchronization" {
                   description "Trace NSR synchronization events";
                 }
                 enum "bfd" {
                   description "Trace BFD events";
                 }
                 enum "4byte-as" {
                   description "Trace 4 byte AS events";
                 }
                 enum "add-path" {
                   description "Trace add-path events";
                 }
                 enum "graceful-restart" {
                   description "Trace Graceful Restart events";
                 }
                 enum "egress-te" {
                   description "Egress Peering Traffic-Engineering events";
                 }
                 enum "thread-io" {
                   description "Trace threaded I/O processing";
                 }
                 enum "thread-update-io" {
                   description "Trace threaded update I/O processing";
                 }
                 enum "route" {
                   description "Trace routing information";
                 }
                 enum "normal" {
                   description "Trace normal events";
                 }
                 enum "general" {
                   description "Trace general events";
                 }
                 enum "state" {
                   description "Trace state transitions";
                 }
                 enum "policy" {
                   description "Trace policy processing";
                 }
                 enum "task" {
                   description "Trace routing protocol task processing";
                 }
                 enum "timer" {
                   description "Trace routing protocol timer processing";
                 }
                 enum "all" {
                   description "Trace everything";
                 }
               }
             }
             leaf send {
               description "Trace transmitted packets";
               type empty;
             }
             leaf receive {
               description "Trace received packets";
               type empty;
             }
             leaf detail {
               description "Trace detailed information";
               type empty;
             }
             leaf disable {
               description "Disable this trace flag";
               type empty;
             }
             container filter {
               description "Filter to apply to this flag";
               presence "enable filter";
               uses bgp_filter_obj;
             }
           }
         }
         leaf description {
           description "Text description";
           type string {
             length "1 .. 255";
           }
         }
         container metric-out {
           description "Route metric sent in MED";
           choice metric_param {
             case case_1 {
               leaf metric-value {
                 description "Metric value";
                 type union {
                   type string {
                     pattern "<.*>|$.*";
                   }
                   type uint32 {
                     range "0 .. 4294967295";
                   }
                 }
               }
             }
             case case_2 {
               container minimum-igp {
                 presence "enable minimum-igp";
                 description "Track the minimum IGP metric";
                 leaf metric-offset {
                   description "Metric offset for MED";
                   type union {
                     type int32;
                     type string {
                       pattern "<.*>|$.*";
                     }
                   }
                 }
               }
             }
             case case_3 {
               container igp {
                 presence "enable igp";
                 description "Track the IGP metric";
                 leaf metric-offset {
                   description "Metric offset for MED";
                   type union {
                     type int32;
                     type string {
                       pattern "<.*>|$.*";
                     }
                   }
                 }
                 leaf delay-med-update {
                   description "Delay updating MED when IGP metric increases";
                   type empty;
                 }
               }
             }
           }
         }
         container multihop {
           presence "enable multihop";
           description "Configure an EBGP multihop session";
           uses apply-advanced;
           leaf ttl {
             description "TTL value for the session";
             type union {
               type string {
                 pattern "<.*>|$.*";
               }
               type uint8 {
                 range "1 .. 255";
               }
             }
           }
           leaf no-nexthop-change {
             description "Do not change next hop to self in advertisements";
             type empty;
           }
         }
         leaf route-server-client {
           description "Enable route server client behavior";
           type empty;
         }
         leaf accept-remote-nexthop {
           description "Allow import policy to specify a non-directly connected next-hop";
           type empty;
         }
         leaf preference {
           description "Preference value";
           type union {
             type uint32;
             type string {
               pattern "<.*>|$.*";
             }
           }
         }
         leaf local-preference {
           description "Value of LOCAL_PREF path attribute";
           type union {
             type uint32;
             type string {
               pattern "<.*>|$.*";
             }
           }
         }
         leaf local-address {
           description "Address of local end of BGP session";
           type jt:ipaddr;
         }
         leaf local-interface {
           description "Local interface for IPv6 link local EBGP peering";
           type union {
             type jt:interface-name;
             type string {
               pattern "<.*>|$.*";
             }
           }
         }
         leaf forwarding-context {
           description "Routing-instance used for data-forwarding and transport-session";
           type string {
           }
         }
         leaf hold-time {
           description "Hold time used when negotiating with a peer";
           type union {
             type string {
               pattern "<.*>|$.*";
             }
             type uint32 {
               range "0 .. 65535";
             }
           }
         }
         leaf passive {
           description "Do not send open messages to a peer";
           type empty;
         }
         leaf advertise-inactive {
           description "Advertise inactive routes";
           type empty;
         }
         choice advertise-peer-as-choice {
           leaf advertise-peer-as {
             description "Advertise routes received from the same autonomous system";
             type empty;
           }
           leaf no-advertise-peer-as {
             description "Don't advertise routes received from the same autonomous system";
             type empty;
           }
         }
         container advertise-external {
           presence "enable advertise-external";
           description "Advertise best external routes";
           leaf conditional {
             description "Route matches active route upto med-comparison rule";
             type empty;
           }
         }
         leaf keep {
           description "How to retain routes in the routing table";
           type enumeration {
             enum "all" {
               description "Retain all routes";
             }
             enum "none" {
               description "Retain no routes";
             }
           }
         }
         leaf rfc6514-compliant-safi129 {
           description "Compliant with RFC6514 SAFI129 format";
           type empty;
         }
         leaf no-aggregator-id {
           description "Set router ID in aggregator path attribute to 0";
           type empty;
         }
         leaf mtu-discovery {
           description "Enable TCP path MTU discovery";
           type empty;
         }
         leaf enforce-first-as {
           description "Enforce first AS in AS-path is the neighbor's AS";
           type empty;
         }
         leaf out-delay {
           description "How long before exporting routes from routing table";
           type union {
             type string {
               pattern "<.*>|$.*";
             }
             type uint32 {
               range "0 .. 65535";
             }
           }
         }
         leaf ttl {
           description "TTL value for the single-hop peer";
           type enumeration {
             enum "1" {
             }
             enum "255" {
             }
           }
         }
         leaf log-updown {
           description "Log a message for peer state transitions";
           type empty;
         }
         leaf damping {
           description "Enable route flap damping";
           type empty;
         }
         leaf-list import {
           ordered-by user;
           description "Import policy";
           type jt:policy-algebra;
         }
         leaf-list nlri {
           ordered-by user;
           description "NLRI type to include in updates";
           status deprecated;
           type enumeration {
             enum "unicast" {
               description "Include unicast NLRI";
               status deprecated;
             }
             enum "multicast" {
               description "Include multicast NLRI";
               status deprecated;
             }
             enum "any" {
               description "Include any kind of NLRI";
               status deprecated;
             }
           }
         }
         container bgp-error-tolerance {
           presence "enable bgp-error-tolerance";
           description "Handle BGP malformed updates softly";
           uses apply-advanced;
           leaf malformed-update-log-interval {
             description "Time used when logging malformed update";
             default "300";
             units "seconds";
             type union {
               type string {
                 pattern "<.*>|$.*";
               }
               type uint32 {
                 range "10 .. 65535";
               }
             }
           }
           choice malformed-routes-limit-choice {
             case case_1 {
               leaf malformed-route-limit {
                 description "Maximum number of malformed routes from a peer";
                 default "1000";
                 type union {
                   type string {
                     pattern "<.*>|$.*";
                   }
                   type uint32 {
                     range "0 .. 4294967295";
                   }
                 }
               }
             }
             case case_2 {
               leaf no-malformed-route-limit {
                 description "No malformed route limit";
                 type empty;
               }
             }
           }
         }
         container family {
           description "Protocol family for NLRIs in updates";
           container inet {
             description "IPv4 NLRI parameters";
             uses apply-advanced;
             container unicast {
               description "Include unicast NLRI";
               presence "enable unicast";
               uses bgp-afi-topo;
             }
             container multicast {
               description "Include multicast NLRI";
               presence "enable multicast";
               uses bgp-afi-default;
             }
             container flow {
               description "Include flow NLRI";
               presence "enable flow";
               uses bgp-afi-flow-with-redirect-ip-action;
             }
             container any {
               description "Include unicast or multicast NLRI";
               presence "enable any";
               uses bgp-afi-default;
             }
             container labeled-unicast {
               description "Include labeled unicast NLRI";
               presence "enable labeled-unicast";
               uses bgp-afi-labeled;
             }
             container segment-routing-te {
               description "Include segment-routing TE policy";
               presence "enable segment-routing-te";
               uses bgp-afi-srte;
             }
           }
           container inet-vpn {
             description "IPv4 Layer 3 VPN NLRI parameters";
             uses apply-advanced;
             container unicast {
               description "Include unicast NLRI";
               presence "enable unicast";
               uses bgp-afi-vpn-protection;
             }
             container multicast {
               description "Include multicast NLRI";
               presence "enable multicast";
               uses bgp-afi-vpn;
             }
             container flow {
               description "Include flow VPN NLRI";
               presence "enable flow";
               uses bgp-afi-flow-with-redirect-ip-action;
             }
             container any {
               description "Include unicast or multicast NLRI";
               presence "enable any";
               uses bgp-afi-vpn;
             }
           }
           container inet6 {
             description "IPv6 NLRI parameters";
             uses apply-advanced;
             container unicast {
               description "Include unicast NLRI";
               presence "enable unicast";
               uses bgp-afi-topo;
             }
             container multicast {
               description "Include multicast NLRI";
               presence "enable multicast";
               uses bgp-afi-default;
             }
             container flow {
               description "Include flow NLRI";
               presence "enable flow";
               uses bgp-afi-flow;
             }
             container any {
               description "Include unicast or multicast NLRI";
               presence "enable any";
               uses bgp-afi-default;
             }
             container labeled-unicast {
               description "Include labeled unicast NLRI";
               presence "enable labeled-unicast";
               uses bgp-afi-inet6-labeled;
             }
             container segment-routing-te {
               description "Include segment-routing TE policy";
               presence "enable segment-routing-te";
               uses bgp-afi-srte;
             }
           }
           container inet6-vpn {
             description "IPv6 Layer 3 VPN NLRI parameters";
             uses apply-advanced;
             container unicast {
               description "Include unicast NLRI";
               presence "enable unicast";
               uses bgp-afi-vpn-protection;
             }
             container multicast {
               description "Include multicast NLRI";
               presence "enable multicast";
               uses bgp-afi-vpn;
             }
             container flow {
               description "Include flow VPN NLRI";
               presence "enable flow";
               uses bgp-afi-flow;
             }
             container any {
               description "Include unicast or multicast NLRI";
               presence "enable any";
               uses bgp-afi-vpn;
             }
           }
           container iso-vpn {
             description "ISO Layer 3 VPN NLRI parameters";
             uses apply-advanced;
             container unicast {
               description "Include unicast NLRI";
               presence "enable unicast";
               uses bgp-afi-vpn-protection;
             }
           }
           container l2vpn {
             description "MPLS-based Layer 2 VPN and VPLS NLRI parameters";
             uses apply-advanced;
             container auto-discovery-only {
               description "Include auto-discovery NLRI for LDP Layer 2 VPN and VPLS";
               presence "enable auto-discovery-only";
               uses bgp-afi-default;
             }
             container auto-discovery-mspw {
               description "Include auto-discovery NLRI for LDP Signalled MultiSegment PW";
               presence "enable auto-discovery-mspw";
               uses bgp-afi-default;
             }
             container signaling {
               description "Include Layer 2 VPN and VPLS signaling NLRI";
               presence "enable signaling";
               uses bgp-afi-l2vpn;
             }
           }
           container evpn {
             description "EVPN NLRI parameters";
             uses apply-advanced;
             container signaling {
               description "Include EVPN signaling NLRI";
               presence "enable signaling";
               uses bgp-afi-default;
             }
           }
           container inet-mvpn {
             description "IPv4 MVPN NLRI parameters";
             uses apply-advanced;
             container signaling {
               description "Include IPv4 multicast VPN signaling NLRI";
               presence "enable signaling";
               uses bgp-afi-default;
             }
           }
           container inet6-mvpn {
             description "IPv6 MVPN NLRI parameters";
             uses apply-advanced;
             container signaling {
               description "Include IPv6 multicast VPN signaling NLRI";
               presence "enable signaling";
               uses bgp-afi-default;
             }
           }
           container inet-mdt {
             description "IPv4 Multicast Distribution Tree (MDT) NLRI parameters";
             uses apply-advanced;
             container signaling {
               description "Include IPv4 multicast VPN auto-discovery NLRI";
               presence "enable signaling";
               uses bgp-afi-default;
             }
           }
           container traffic-engineering {
             description "Traffic Engineering (BGP-TE) NLRI parameters";
             uses apply-advanced;
             container unicast {
               description "Include BGP-TE NLRI";
               presence "enable unicast";
               uses bgp-afi-default;
             }
           }
           container route-target {
             presence "enable route-target";
             description "Route target NLRI used for VPN route filtering";
             uses apply-advanced;
             container prefix-limit {
               description "Limit maximum number of prefixes from a peer";
               uses bgpaf-prefix-limit;
             }
             container accepted-prefix-limit {
               description "Limit maximum number of prefixes accepted from a peer";
               uses bgpaf-accepted-prefix-limit;
             }
             container proxy-generate {
               presence "enable proxy-generate";
               description "Generate route target NLRI for peers that don't support it";
               uses apply-advanced;
               leaf-list route-target-policy {
                 ordered-by user;
                 description "Limit VPN routes that are used to generate proxy route-target filters";
                 type jt:policy-algebra;
               }
             }
             leaf external-paths {
               description "Number of external paths accepted for route filtering";
               type union {
                 type string {
                   pattern "<.*>|$.*";
                 }
                 type uint32 {
                   range "1 .. 256";
                 }
               }
             }
             leaf advertise-default {
               description "Advertise default and suppress more specific routes";
               type empty;
             }
             leaf damping {
               description "Enable route flap damping";
               type empty;
             }
             container graceful-restart {
               description "BGP graceful restart options";
               uses bgp-af-gr;
             }
             leaf local-ipv4-address {
               description "Local IPv4 address";
               type jt:ipv4addr;
             }
             container output-queue-priority {
               description "Default output-queue to assign updates to";
               uses bgp-output-queue-priority-class;
             }
             container route-refresh-priority {
               description "Default output-queue to assign route refreshes to";
               uses bgp-output-queue-priority-class;
             }
             container withdraw-priority {
               description "Default output-queue to assign withdrawn routes to";
               uses bgp-output-queue-priority-class;
             }
           }
         }
         leaf authentication-key {
           description "MD5 authentication key";
           type string {
             length "1 .. 126";
           }
         }
         leaf authentication-algorithm {
           description "Authentication algorithm name";
           type enumeration {
             enum "md5" {
               description "Message Digest 5";
             }
             enum "hmac-sha-1-96" {
               description "Hash-based Message Authentication Code (SHA1) (96 bits)";
             }
             enum "aes-128-cmac-96" {
               description "Cipher-based Message Authentication Code (AES128) (96 bits)";
             }
           }
         }
         leaf authentication-key-chain {
           description "Key chain name";
           type string {
             length "1 .. 128";
           }
         }
         leaf-list export {
           ordered-by user;
           description "Export policy";
           type jt:policy-algebra;
         }
         leaf vpn-apply-export {
           description "Apply BGP export policy when exporting VPN routes";
           type empty;
         }
         container egress-te {
           presence "enable egress-te";
           description "Use Egress Peering traffic engineering";
           uses apply-advanced;
           leaf backup-path {
             description "The 'egress-te-backup-paths template' to use for this peer";
             type string {
             }
           }
         }
         container remove-private {
           presence "enable remove-private";
           description "Remove well-known private AS numbers";
           uses apply-advanced;
           container all {
             presence "enable all";
             description "Remove all private AS numbers and do not stop at the first public AS number";
             container replace {
               presence "enable replace";
               description "Replace private AS numbers with the BGP Group's local AS number";
               leaf nearest {
                 description "Use closest public AS number to replace a private AS number";
                 type empty;
               }
             }
           }
           leaf no-peer-loop-check {
             description "Remove peer loop-check";
             type empty;
           }
         }
         leaf cluster {
           description "Cluster identifier";
           type jt:areaid;
         }
         leaf no-client-reflect {
           description "Disable intracluster route redistribution";
           type empty;
         }
         leaf peer-as {
           description " Autonomous system number in plain number or 'higher 16bits'.'Lower 16 bits' (asdot notation) format";
           type string {
           }
         }
         container local-as {
           description "Local autonomous system number";
           leaf as-number {
             description " Autonomous system number in plain number or 'higher 16bits'.'Lower 16 bits' (asdot notation) format";
             type string {
             }
           }
           leaf loops {
             description "Maximum number of times this AS can be in an AS path";
             type union {
               type string {
                 pattern "<.*>|$.*";
               }
               type int32 {
                 range "1 .. 10";
               }
             }
           }
           leaf private {
             description "Hide this local AS in paths learned from this peering";
             type empty;
           }
           leaf alias {
             description "Treat this AS as an alias to the system AS";
             type empty;
           }
           leaf no-prepend-global-as {
             description "Do not prepend global autonomous-system number in advertised paths";
             type empty;
           }
         }
         leaf ipsec-sa {
           description "IPSec SA name";
           type string {
             length "1 .. 32";
           }
         }
         leaf unconfigured-peer-graceful-restart {
           description "BGP unconfigured peer graceful restart options";
           type empty;
         }
         container graceful-restart {
           presence "enable graceful-restart";
           description "BGP graceful restart options";
           uses apply-advanced;
           choice enable-disable {
             case case_1 {
               leaf disable {
                 description "Disable graceful restart";
                 type empty;
               }
             }
           }
           leaf restart-time {
             description "Restart time used when negotiating with a peer";
             type union {
               type string {
                 pattern "<.*>|$.*";
               }
               type uint32 {
                 range "1 .. 1800";
               }
             }
           }
           leaf stale-routes-time {
             description "Maximum time for which stale routes are kept";
             type union {
               type string {
                 pattern "<.*>|$.*";
               }
               type uint32 {
                 range "1 .. 1800";
               }
             }
           }
           container long-lived {
             description "Long-lived graceful restart options";
             uses apply-advanced;
             container receiver {
               description "Long-lived graceful restart receiver (helper) options";
               uses apply-advanced;
               choice enable-disable {
                 case case_1 {
                   leaf disable {
                     description "Disable receiver (helper) functionality";
                     type empty;
                   }
                 }
               }
             }
             container advertise-to-non-llgr-neighbor {
               presence "enable advertise-to-non-llgr-neighbor";
               description "Advertise stale routes to non-LLGR neighbors";
               uses apply-advanced;
               leaf omit-no-export {
                 description "Do not attach no-export community to stale routes";
                 type empty;
               }
             }
           }
           leaf forwarding-state-bit {
             description "Control forwarding-state flag negotiation";
             type enumeration {
               enum "as-rr-client" {
                 description "As for a route reflector client";
               }
               enum "from-fib" {
                 description "Always use state of associated FIB(s)";
               }
             }
           }
           leaf dont-help-shared-fate-bfd-down {
             description "Honor BFD-Down(C=0) if GR-restart not in progress";
             type empty;
           }
         }
         leaf include-mp-next-hop {
           description "Include NEXT-HOP attribute in multiprotocol updates";
           type empty;
         }
         container idle-after-switch-over {
           description "Stop peer session from coming up after nonstop-routing switch-over";
           choice idle-interval {
             case case_1 {
               leaf forever {
                 description "Idle the peer until the user intervenes";
                 type empty;
               }
             }
             case case_2 {
               leaf timeout {
                 description "Timeout value, in seconds, for starting peer after switch over";
                 type union {
                   type string {
                     pattern "<.*>|$.*";
                   }
                   type uint32 {
                     range "1 .. 4294967295";
                   }
                 }
               }
             }
           }
         }
         container outbound-route-filter {
           description "Dynamically negotiated cooperative route filtering";
           uses apply-advanced;
           leaf bgp-orf-cisco-mode {
             description "Using BGP ORF capability code 130 and Prefix ORF type 128";
             type empty;
           }
           container extended-community {
             description "Extended community filtering";
             status deprecated;
             uses apply-advanced;
             choice accept-choice {
               leaf accept {
                 description "Honor remote requests for extended community ORF";
                 type empty;
               }
               leaf no-accept {
                 description "Don't honor remote requests for extended community ORF";
                 type empty;
               }
             }
             leaf vrf-filter {
               description "Request remote filtering using locally configured VRF import targets";
               type empty;
             }
           }
           container prefix-based {
             presence "enable prefix-based";
             description "Prefix-based outbound route filtering";
             uses apply-advanced;
             container accept {
               presence "enable accept";
               description "Honor Prefix-based ORFs from remote peers";
               uses apply-advanced;
               leaf inet {
                 description "Honor IPv4 prefix filters";
                 type empty;
               }
               leaf inet6 {
                 description "Honor IPv6 prefix filters";
                 type empty;
               }
             }
           }
         }
         container multipath {
           presence "enable multipath";
           description "Allow load sharing among multiple BGP paths";
           uses apply-advanced;
           leaf disable {
             description "Disable Multipath";
             type empty;
           }
           leaf multiple-as {
             description "Use paths received from different ASs";
             type empty;
           }
         }
         leaf tcp-mss {
           description "Maximum TCP segment size";
           type union {
             type string {
               pattern "<.*>|$.*";
             }
             type uint32 {
               range "1 .. 4096";
             }
           }
         }
         leaf tcp-aggressive-transmission {
           description "Enable aggressive transmission of pure TCP ACKs and retransmissions";
           type empty;
         }
         container bmp {
           description "Specific settings to override the routing-options settings";
           uses apply-advanced;
           leaf monitor {
             description "Enable/Disable monitoring";
             type enumeration {
               enum "enable" {
                 description "Enable monitoring of BGP peer(s)";
               }
               enum "disable" {
                 description "Disable monitoring of BGP peer(s)";
               }
             }
           }
           container route-monitoring {
             description "Control route monitoring settings";
             uses apply-advanced;
             leaf none {
               description "Do not send route montoring messages";
               type empty;
             }
             container pre-policy {
               presence "enable pre-policy";
               description "Send pre policy route montoring messages";
               leaf exclude-non-feasible {
                 description "Exclude looped routes, etc";
                 type empty;
               }
             }
             container post-policy {
               presence "enable post-policy";
               description "Send post policy route montoring messages";
               leaf exclude-non-eligible {
                 description "Exclude unresolved routes, etc.";
                 type empty;
               }
             }
           }
         }
         container advertise-bgp-static {
           presence "enable advertise-bgp-static";
           description "Advertise bgp-static routes";
           uses apply-advanced;
           leaf-list policy {
             ordered-by user;
             description "Static route advertisement policy";
             type jt:policy-algebra;
           }
         }
         leaf add-path-display-ipv4-address {
           description "Display add-path path-id in IPv4 address format";
           type empty;
         }
         container bfd-liveness-detection {
           description "Bidirectional Forwarding Detection (BFD) options";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
           container authentication {
             description "Authentication options";
             uses apply-advanced;
             leaf key-chain {
               description "Key chain name";
               type string;
             }
             leaf algorithm {
               description "Algorithm name";
               type enumeration {
                 enum "simple-password" {
                   description "Simple password";
                 }
                 enum "keyed-md5" {
                   description "Keyed message Digest 5";
                 }
                 enum "meticulous-keyed-md5" {
                   description "Meticulous keyed message Digest 5";
                 }
                 enum "keyed-sha-1" {
                   description "Keyed secure hash algorithm (SHA1) ";
                 }
                 enum "meticulous-keyed-sha-1" {
                   description "Meticulous keyed secure hash algorithm (SHA1) ";
                 }
               }
             }
             leaf loose-check {
               description "Verify authentication only if authentication is negotiated";
               type empty;
             }
           }
           leaf session-mode {
             description "BFD single-hop or multihop session-mode";
             default "automatic";
             type enumeration {
               enum "automatic" {
                 description "Choose session-mode automatically";
               }
               enum "single-hop" {
                 description "Use single-hop";
               }
               enum "multihop" {
                 description "Use multihop";
               }
             }
           }
           leaf holddown-interval {
             description "Time to hold the session-UP notification to the client";
             units "milliseconds";
             type union {
               type string {
                 pattern "<.*>|$.*";
               }
               type uint32 {
                 range "0 .. 255000";
               }
             }
           }
         }
         leaf as-override {
           description "Replace neighbor AS number with our AS number";
           type empty;
         }
       }
     }
     container multipath-build-priority {
       description "Configure the multipath build priority";
       uses apply-advanced;
       choice multipath-priority {
         case case_1 {
           leaf low {
             description "Do multipath build with low priority";
             type empty;
           }
         }
         case case_2 {
           leaf medium {
             description "Do multipath build with medium priority";
             type empty;
           }
         }
       }
     }
     leaf send-addpath-optimization {
       description "Enable BGP addpath advertisement optimization";
       type empty;
     }
     container traffic-statistics-labeled-path {
       presence "enable traffic-statistics-labeled-path";
       description "Collect periodic ingress labeled statistics for BGP label-switched paths ";
       uses apply-advanced;
       container file {
         description "Statistics file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       leaf interval {
         description "Time interval to collect statistics";
         units "seconds";
         type union {
           type string {
             pattern "<.*>|$.*";
           }
           type int32 {
             range "60 .. 65535";
           }
         }
       }
     }
   }
   grouping bgp-af-gr {
     uses apply-advanced;
     container long-lived {
       description "Long-lived graceful restart options";
       uses apply-advanced;
       container restarter {
         description "Long-lived graceful restart restarter options";
         uses apply-advanced;
         choice enable-disable {
           case case_1 {
             leaf disable {
               description "Disable restarter functionality";
               type empty;
             }
           }
         }
         leaf stale-time {
           description "Stale time in seconds or dhms notation (1..16777215)";
           type string;
         }
       }
     }
     leaf forwarding-state-bit {
       description "Control forwarding-state flag negotiation";
       type enumeration {
         enum "set" {
           description "Always set";
         }
         enum "from-fib" {
           description "Use state of associated FIB(s)";
         }
       }
     }
   }
   grouping bgp-afi-default {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       description "Delay route updates for this family until FIB-sync";
       uses apply-advanced;
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf no-install {
       description "Dont install received routes in forwarding";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
   }
   grouping apath-options {
     description "Number of paths to advertise";
     uses apply-advanced;
     leaf receive {
       description "Receive multiple paths from peer";
       type empty;
     }
     container send {
       presence "enable send";
       description "Send multiple paths to peer";
       uses apply-advanced;
       container path-selection-mode {
         description "Configure how to select add-path routes";
         uses apply-advanced;
         choice mode {
           case case_1 {
             leaf all-paths {
               description "Advertise all paths allowed by path count";
               type empty;
             }
           }
           case case_2 {
             leaf equal-cost-paths {
               description "Advertise equal cost paths";
               type empty;
             }
           }
         }
       }
       leaf-list prefix-policy {
         ordered-by user;
         description "Perform add-path only for prefixes that match policy";
         type jt:policy-algebra;
       }
       leaf path-count {
         description "Number of paths to advertise";
         type union {
           type string {
             pattern "<.*>|$.*";
           }
           type int32 {
             range "2 .. 64";
           }
         }
       }
       leaf include-backup-path {
         description "Number of backup paths to advertise";
         type union {
           type string {
             pattern "<.*>|$.*";
           }
           type int32 {
             range "1 .. 2";
           }
         }
       }
       leaf multipath {
         description "Include only multipath contributor routes";
         type empty;
       }
     }
   }
   grouping bgp-afi-flow {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       description "Delay route updates for this family until FIB-sync";
       uses apply-advanced;
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf no-install {
       description "Dont install received routes in forwarding";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf-list no-validate {
       ordered-by user;
       description "Bypass validation procedure for routes that match policy";
       type jt:policy-algebra;
     }
     leaf strip-nexthop {
       description "Strip the next-hop from the outgoing flow update";
       type empty;
     }
     leaf allow-policy-add-nexthop {
       description "Allow policy to add nexthop to a route without nexthop";
       status deprecated;
       type empty;
     }
   }
   grouping bgp-afi-flow-with-redirect-ip-action {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       description "Delay route updates for this family until FIB-sync";
       uses apply-advanced;
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf no-install {
       description "Dont install received routes in forwarding";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf-list no-validate {
       ordered-by user;
       description "Bypass validation procedure for routes that match policy";
       type jt:policy-algebra;
     }
     leaf strip-nexthop {
       description "Strip the next-hop from the outgoing flow update";
       type empty;
     }
     container legacy-redirect-ip-action {
       presence "enable legacy-redirect-ip-action";
       description "Configure legacy redirect to IP support";
       uses apply-advanced;
       leaf receive {
         description "Accept legacy encoded redirect-to-ip action attribute";
         type empty;
       }
       leaf send {
         description "Advertise Redirect action as legacy redirect attribute";
         type empty;
       }
     }
     leaf secondary-independent-resolution {
       description "Resolve FLOW routes in VRF table independent of VPN FLOW route";
       type empty;
     }
   }
   grouping bgp-afi-inet6-labeled {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       description "Delay route updates for this family until FIB-sync";
       uses apply-advanced;
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf no-install {
       description "Dont install received routes in forwarding";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     container aggregate-label {
       presence "enable aggregate-label";
       description "Aggregate labels of incoming routes with the same FEC";
       uses apply-advanced;
       leaf community {
         description "Community to identify the FEC of incoming routes";
         type string;
       }
     }
     leaf per-group-label {
       description "Advertise prefixes with unique labels per group";
       type empty;
     }
     container traffic-statistics {
       description "Collect statistics for BGP label-switched paths";
       presence "enable traffic-statistics";
       uses bgpaf-traffic-statistics;
     }
     container rib {
       description "Select table used by labeled unicast routes";
       uses apply-advanced;
       leaf inet6.3 {
         description "Use inet6.3 to exchange labeled unicast routes";
         type empty;
       }
     }
     container explicit-null {
       presence "enable explicit-null";
       description "Advertise explicit null";
       leaf connected-only {
         description "Advertise explicit null only for connected routes";
         type empty;
       }
     }
     container protection {
       presence "enable protection";
       description "Compute backup path for active nexthop failure";
     }
   }
   grouping bgp-afi-l2vpn {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       description "Delay route updates for this family until FIB-sync";
       uses apply-advanced;
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf no-install {
       description "Dont install received routes in forwarding";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     container egress-protection {
       presence "enable egress-protection";
       description "Egress router protection";
       uses apply-advanced;
       container context-identifier {
         description "Context identifier";
         uses apply-advanced;
         leaf context-id {
           description "IP address";
           type jt:ipv4addr;
         }
       }
       leaf-list keep-import {
         ordered-by user;
         description "Import policy";
         type jt:policy-algebra;
       }
     }
   }
   grouping bgp-afi-labeled {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       description "Delay route updates for this family until FIB-sync";
       uses apply-advanced;
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf no-install {
       description "Dont install received routes in forwarding";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     container aggregate-label {
       presence "enable aggregate-label";
       description "Aggregate labels of incoming routes with the same FEC";
       uses apply-advanced;
       leaf community {
         description "Community to identify the FEC of incoming routes";
         type string;
       }
     }
     leaf per-prefix-label {
       description "Allocate a unique label to each advertised prefix";
       type empty;
     }
     leaf per-group-label {
       description "Advertise prefixes with unique labels per group";
       type empty;
     }
     container traffic-statistics {
       description "Collect statistics for BGP label-switched paths";
       presence "enable traffic-statistics";
       uses bgpaf-traffic-statistics;
     }
     container rib {
       description "Select table used by labeled unicast routes";
       uses apply-advanced;
       leaf inet.3 {
         description "Use inet.3 to exchange labeled unicast routes";
         type empty;
       }
     }
     container explicit-null {
       presence "enable explicit-null";
       description "Advertise explicit null";
       leaf connected-only {
         description "Advertise explicit null only for connected routes";
         type empty;
       }
     }
     container protection {
       presence "enable protection";
       description "Compute backup path for active nexthop failure";
       uses apply-advanced;
     }
     container egress-protection {
       presence "enable egress-protection";
       description "Egress router protection";
       uses apply-advanced;
       container context-identifier {
         description "Context identifier";
         uses apply-advanced;
         leaf context-id {
           description "IP address";
           type jt:ipv4addr;
         }
       }
       leaf-list keep-import {
         ordered-by user;
         description "Import policy";
         type jt:policy-algebra;
       }
     }
     leaf resolve-vpn {
       description "Install received NLRI in inet.3 also";
       type empty;
     }
     container entropy-label {
       presence "enable entropy-label";
       description "Use entropy label for entropy label capable BGP LSPs";
       uses apply-advanced;
       leaf-list import {
         ordered-by user;
         description "Policy to select BGP LSPs to use entropy label";
         type jt:policy-algebra;
       }
       leaf no-next-hop-validation {
         description "Don't validate next hop field against route next hop";
         type empty;
       }
     }
   }
   grouping bgp-afi-srte {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     leaf damping {
       description "Enable route flap damping";
       type empty;
     }
     container loops {
       description "Allow local AS in received AS paths";
       uses bgpaf-loops;
     }
     container graceful-restart {
       description "BGP graceful restart options";
       uses bgp-af-gr;
     }
     leaf no-install {
       description "Dont install received routes in forwarding";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
   }
   grouping bgp-afi-topo {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       description "Delay route updates for this family until FIB-sync";
       uses apply-advanced;
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf no-install {
       description "Dont install received routes in forwarding";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     container protection {
       presence "enable protection";
       description "Compute backup path for active nexthop failure";
     }
     list topology {
       key name;
       ordered-by user;
       description "Multi topology routing tables";
       leaf name {
         description "Topology name";
         type string {
         }
       }
       uses apply-advanced;
       leaf community {
         description "Community to identify multi topology routes";
         type string;
       }
     }
   }
   grouping bgp-afi-vpn {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       description "Delay route updates for this family until FIB-sync";
       uses apply-advanced;
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf no-install {
       description "Dont install received routes in forwarding";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     container aggregate-label {
       presence "enable aggregate-label";
       description "Aggregate labels of incoming routes with the same FEC";
       uses apply-advanced;
       leaf community {
         description "Community to identify the FEC of incoming routes";
         type string;
       }
     }
   }
   grouping bgp-afi-vpn-protection {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       description "Delay route updates for this family until FIB-sync";
       uses apply-advanced;
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf no-install {
       description "Dont install received routes in forwarding";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     container aggregate-label {
       presence "enable aggregate-label";
       description "Aggregate labels of incoming routes with the same FEC";
       uses apply-advanced;
       leaf community {
         description "Community to identify the FEC of incoming routes";
         type string;
       }
     }
     container egress-protection {
       presence "enable egress-protection";
       description "Egress router protection";
       uses apply-advanced;
       container context-identifier {
         description "Context identifier";
         uses apply-advanced;
         leaf context-id {
           description "IP address";
           type jt:ipv4addr;
         }
       }
       leaf-list keep-import {
         ordered-by user;
         description "Import policy";
         type jt:policy-algebra;
       }
     }
   }
   grouping bgp-output-queue-priority-class {
     choice class {
       case case_1 {
         leaf priority {
           description "Output queue priority; higher is better";
           type union {
             type string {
               pattern "<.*>|$.*";
             }
             type uint32 {
               range "1 .. 16";
             }
           }
         }
       }
       case case_2 {
         leaf expedited {
           description "Expedited queue; highest priority";
           type empty;
         }
       }
     }
   }
   grouping bgp_filter_obj {
     description "Filter to apply to tracing";
     leaf match-on {
       description "Argument on which to match";
       type enumeration {
         enum "prefix" {
           description "Filter based on prefix";
         }
       }
     }
     leaf-list policy {
       ordered-by user;
       description "Filter policy";
       type jt:policy-algebra;
     }
   }
   grouping bgpaf-accepted-prefix-limit {
     uses apply-advanced;
     leaf maximum {
       description "Maximum number of prefixes accepted from a peer";
       type union {
         type string {
           pattern "<.*>|$.*";
         }
         type uint32 {
           range "1 .. 4294967295";
         }
       }
     }
     container teardown {
       presence "enable teardown";
       description "Clear peer connection on reaching limit";
       leaf limit-threshold {
         description "Percentage of prefix-limit to start warnings";
         type union {
           type string {
             pattern "<.*>|$.*";
           }
           type uint32 {
             range "1 .. 100";
           }
         }
       }
       container idle-timeout {
         presence "enable idle-timeout";
         description "Timeout before attempting to restart peer";
         choice idle-parm {
           case case_1 {
             leaf forever {
               description "Idle the peer until the user intervenes";
               type empty;
             }
           }
           case case_2 {
             leaf timeout {
               description "Timeout value, in minutes, for restarting peer";
               type union {
                 type string {
                   pattern "<.*>|$.*";
                 }
                 type uint32 {
                   range "1 .. 2400";
                 }
               }
             }
           }
         }
       }
     }
   }
   grouping bgpaf-aigp-options {
     uses apply-advanced;
     leaf disable {
       description "Disable sending and receiving of AIGP attribute";
       type empty;
     }
   }
   grouping bgpaf-loops {
     uses apply-advanced;
     leaf loops {
       description "AS-Path loop count";
       type union {
         type string {
           pattern "<.*>|$.*";
         }
         type int32 {
           range "1 .. 10";
         }
       }
     }
   }
   grouping bgpaf-prefix-limit {
     uses apply-advanced;
     leaf maximum {
       description "Maximum number of prefixes from a peer";
       type union {
         type string {
           pattern "<.*>|$.*";
         }
         type uint32 {
           range "1 .. 4294967295";
         }
       }
     }
     container teardown {
       presence "enable teardown";
       description "Clear peer connection on reaching limit";
       leaf limit-threshold {
         description "Percentage of prefix-limit to start warnings";
         type union {
           type string {
             pattern "<.*>|$.*";
           }
           type uint32 {
             range "1 .. 100";
           }
         }
       }
       container idle-timeout {
         presence "enable idle-timeout";
         description "Timeout before attempting to restart peer";
         choice idle-parm {
           case case_1 {
             leaf forever {
               description "Idle the peer until the user intervenes";
               type empty;
             }
           }
           case case_2 {
             leaf timeout {
               description "Timeout value, in minutes, for restarting peer";
               type union {
                 type string {
                   pattern "<.*>|$.*";
                 }
                 type uint32 {
                   range "1 .. 2400";
                 }
               }
             }
           }
         }
       }
     }
   }
   grouping bgpaf-traffic-statistics {
     uses apply-advanced;
     leaf labeled-path {
       description "Ingress labeled path statistics";
       type empty;
     }
     container file {
       description "Statistics file options";
       leaf filename {
         description "Name of file in which to write trace information";
         type string {
           length "1 .. 1024";
         }
       }
       leaf replace {
         description "Replace trace file rather than appending to it";
         status deprecated;
         type empty;
       }
       leaf size {
         description "Maximum trace file size";
         type string;
       }
       leaf files {
         description "Maximum number of trace files";
         default "10";
         type union {
           type string {
             pattern "<.*>|$.*";
           }
           type uint32 {
             range "2 .. 1000";
           }
         }
       }
       leaf no-stamp {
         description "Do not timestamp trace file";
         status deprecated;
         type empty;
       }
       choice world-readable-choice {
         leaf world-readable {
           description "Allow any user to read the log file";
           type empty;
         }
         leaf no-world-readable {
           description "Don't allow any user to read the log file";
           type empty;
         }
       }
     }
     leaf interval {
       description "Time to collect statistics (seconds)";
       type union {
         type string {
           pattern "<.*>|$.*";
         }
         type int32 {
           range "60 .. 65535";
         }
       }
     }
   }
   grouping juniper-protocols-bridge {
     uses apply-advanced;
     container traceoptions {
       description "Trace options for Layer 2 address service";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       leaf level {
         description "Level of debugging output";
         default "error";
         type enumeration {
           enum "error" {
             description "Match error conditions";
           }
           enum "warning" {
             description "Match warning messages";
           }
           enum "notice" {
             description "Match conditions that should be handled specially";
           }
           enum "info" {
             description "Match informational messages";
           }
           enum "verbose" {
             description "Match verbose messages";
           }
           enum "all" {
             description "Match all levels";
           }
         }
       }
       list flag {
         key name;
         ordered-by user;
         description "Type of operation or event to include in trace";
         leaf name {
           type enumeration {
             enum "configuration" {
               description "Configuration operations";
             }
             enum "routing-socket" {
               description "Routing socket operations";
             }
             enum "interface-device" {
               description "Interface device operations";
             }
             enum "interface-logical" {
               description "Logical interface operations";
             }
             enum "interface-family" {
               description "Interface family operations";
             }
             enum "bridging-domain" {
               description "Bridging domain operations";
             }
             enum "routing-instance" {
               description "Routing instance operations";
             }
             enum "bridge-interface" {
               description "Interface bridge operations";
             }
             enum "learning-domain" {
               description "Learning domain operations";
             }
             enum "ipc" {
               description "Inter-process communications operations";
             }
             enum "mac-learning" {
               description "MAC address learning operations";
             }
             enum "initialization" {
               description "Initialization operations";
             }
             enum "flood-next-hop" {
               description "Flood next hop operations";
             }
             enum "irb" {
               description "Integrated routing and bridging operations";
             }
             enum "vpls-ping" {
               description "VPLS ping operations";
             }
             enum "vpls-loop-prev" {
               description "VPLS loop prevention";
             }
             enum "logical-system" {
               description "Logical system operations";
             }
             enum "bmac-next-hop" {
               description "Backbone Mac Next hop operations ";
             }
             enum "bridge-bmac-next-hop" {
               description "Bmac Next hop bridge operations";
             }
             enum "isid" {
               description "I-Tagged Service ID";
             }
             enum "mc-ae" {
               description "Multi-chassis AE";
             }
             enum "kack" {
               description "Kernel-acknowledgment";
             }
             enum "storm-control" {
               description "Storm-control";
             }
             enum "redundant-trunk-group" {
               description "Redundant trunk group";
             }
             enum "unknown-unicast-forwarding" {
               description "Trace unknown unicast forwarding events";
             }
             enum "vxlan" {
               description "VXLAN";
             }
             enum "all" {
               description "All operations";
             }
           }
         }
       }
       container in-memory-debug {
         presence "enable in-memory-debug";
         description "Enable trace parameters in the memory";
       }
     }
     container global-mac-move {
       presence "enable global-mac-move";
       description "Enable mac move related options at global level";
       uses apply-advanced;
       leaf notification-time {
         description "Periodical time interval in secs during which MAC move notification occurs";
         units "seconds";
         type union {
           type uint32;
           type string {
             pattern "<.*>|$.*";
           }
         }
       }
       leaf threshold-time {
         description "Time during which if certain number of MAC moves happen warrant recording";
         units "seconds";
         type union {
           type uint32;
           type string {
             pattern "<.*>|$.*";
           }
         }
       }
       leaf reopen-time {
         description "Time after which a blocked interface is reopened";
         units "seconds";
         type union {
           type uint32;
           type string {
             pattern "<.*>|$.*";
           }
         }
       }
       leaf threshold-count {
         description "Count of MAC moves which warrant recording when happen in certain time";
         units "seconds";
         type union {
           type uint32;
           type string {
             pattern "<.*>|$.*";
           }
         }
       }
       container traceoptions {
         description "Enable logging for the MAC moves";
         uses apply-advanced;
         leaf no-remote-trace {
           description "Disable remote tracing";
           type empty;
         }
         container file {
           description "Trace file information";
           leaf filename {
             description "Name of file in which to write trace information";
             type string {
               length "1 .. 1024";
             }
           }
           leaf size {
             description "Maximum trace file size";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
       }
       leaf log {
         description "Syslog all the MAC moves as stored in the mac-move-buffer";
         type empty;
       }
       leaf disable-action {
         description "Disable mac move action globally";
         type empty;
       }
       leaf cooloff-time {
         description "Time interval in secs during which no further actions are taken";
         units "seconds";
         type union {
           type uint32;
           type string {
             pattern "<.*>|$.*";
           }
         }
       }
       leaf statistical-approach-wait-time {
         description "Time during which MAC moves are monitored to collect statistics";
         units "seconds";
         type union {
           type uint32;
           type string {
             pattern "<.*>|$.*";
           }
         }
       }
       leaf interface-recovery-time {
         description "Time interval after which interface is made operationally up";
         units "seconds";
         type union {
           type uint32;
           type string {
             pattern "<.*>|$.*";
           }
         }
       }
       list exclusive-mac {
         key name;
         ordered-by user;
         description "MAC addresses to be excluded in mac-move-limit or in VPLS loop prevention algorithm";
         leaf name {
           description "Source MAC address";
           type jt:mac-addr-prefix;
         }
         uses apply-advanced;
       }
     }
     leaf global-mac-table-aging-time {
       description "System level MAC table aging time";
       units "seconds";
       type union {
         type string {
           pattern "<.*>|$.*";
         }
         type uint32;
       }
     }
     leaf global-mac-ip-table-aging-time {
       description "System level MAC+IP table aging time";
       units "seconds";
       type union {
         type string {
           pattern "<.*>|$.*";
         }
         type uint32 {
           range "60 .. 1000000";
         }
       }
     }
     leaf global-mode {
       description "Global L2 Mode";
       default "switching";
       type enumeration {
         enum "transparent-bridge" {
           description "Transparent bridge mode";
         }
         enum "switching" {
           description "Switching mode";
         }
       }
     }
     leaf global-le-aging-time {
       description "Set LE aging time";
       units "seconds";
       type union {
         type string {
           pattern "<.*>|$.*";
         }
         type uint32 {
           range "120 .. 1000000";
         }
       }
     }
     leaf global-le-bridge-domain-aging-time {
       description "Set LE bridge-domain aging time";
       units "seconds";
       type union {
         type string {
           pattern "<.*>|$.*";
         }
         type uint32 {
           range "120 .. 1000000";
         }
       }
     }
     leaf mclag-arpreq-sync {
       description "Enable syncing ARP REQ packets to peer MCLAG PE";
       type empty;
     }
     leaf global-mac-pinning-discard-notification-interval {
       description "Set interval for MAC Pinning discard notification";
       units "seconds";
       type union {
         type string {
           pattern "<.*>|$.*";
         }
         type uint32 {
           range "2 .. 86400";
         }
       }
     }
     container global-mac-limit {
       presence "enable global-mac-limit";
       description "System level MAC limit options";
       uses apply-advanced;
       leaf mac-limit {
         description "System level MAC limit";
         type union {
           type string {
             pattern "<.*>|$.*";
           }
           type uint64;
         }
       }
       leaf packet-action {
         type enumeration {
           enum "drop" {
             description "Enable packet-action drop when MAC limit is reached";
           }
         }
       }
     }
     container global-mac-ip-limit {
       presence "enable global-mac-ip-limit";
       description "System level MAC+IP limit options";
       uses apply-advanced;
       leaf mac-ip-limit {
         description "System level MAC+IP limit";
         type union {
           type string {
             pattern "<.*>|$.*";
           }
           type uint64 {
             range "20 .. 1048575";
           }
         }
       }
     }
     leaf global-mac-statistics {
       description "Enable MAC address statistics at system level";
       type empty;
     }
     leaf global-no-mac-learning {
       description "Disable dynamic MAC address learning at system level";
       type empty;
     }
     leaf global-no-hw-mac-learning {
       description "Disable hardware MAC-address learning at system level";
       type empty;
     }
     leaf global-no-control-mac-aging {
       description "Disable control MAC-address aging from software";
       type empty;
     }
     leaf mclag-arp-nd-sync {
       description "Arp and ND entry sync from peer device.";
       type empty;
     }
     leaf no-mclag-ifa-sync {
       description "IFA entry disable sync from/to peer device.";
       type empty;
     }
   }
   grouping juniper-protocols-dot1x {
     uses apply-advanced;
     container traceoptions {
       description "Trace options for 802.1X";
       uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "dot1x-debug" {
               description "Trace dot1x events";
             }
             enum "parse" {
               description "Trace configuration parsing";
             }
             enum "esw-if" {
               description "Trace ESW Interactions";
             }
             enum "eapol" {
               description "Trace EAPOL Transmit/Receive";
             }
             enum "config-internal" {
               description "Trace configuration internals";
             }
             enum "normal" {
               description "Trace normal events";
             }
             enum "general" {
               description "Trace general events";
             }
             enum "state" {
               description "Trace state transitions";
             }
             enum "task" {
               description "Trace routing protocol task processing";
             }
             enum "timer" {
               description "Trace routing protocol task timer processing";
             }
             enum "vlan" {
               description "Trace VLAN transactions";
             }
             enum "all" {
               description "Trace everything";
             }
             enum "dot1x-ipc" {
               description "Trace dot1x IPC interactions";
             }
             enum "dot1x-event" {
               description "Trace dot1x events";
             }
             enum "iccp" {
               description "Trace iccp events";
             }
           }
         }
         leaf disable {
           description "Disable this trace flag";
           type empty;
         }
       }
     }
     container authenticator {
       presence "enable authenticator";
       description "802.1X authenticator options";
       uses apply-advanced;
       leaf authentication-profile-name {
         description "Access profile name to use for authentication";
         type string {
           length "1 .. 63";
         }
       }
       leaf no-mac-table-binding {
         description "Disable association between mac table and dot1x";
         type empty;
       }
       container radius-options {
         presence "enable radius-options";
         description "Info sent to radius server";
         uses apply-advanced;
         leaf add-interface-text-description {
           description "Appends interface text description to NAS-Port-Id";
           type empty;
         }
         choice vlan {
           case case_1 {
             leaf use-vlan-name {
               description "Vlan name";
               type empty;
             }
           }
           case case_2 {
             leaf use-vlan-id {
               description "Vlan id";
               type empty;
             }
           }
         }
       }
       list static {
         key name;
         ordered-by user;
         description "Static MAC configuration needed to bypass 802.1X";
         leaf name {
           description "MAC addresses to bypass authentication";
           type jt:mac-addr-prefix;
         }
         uses apply-advanced;
         leaf vlan-assignment {
           description "VLAN name or 802.1q tag for the MAC address";
           type string {
           }
         }
         leaf bridge-domain-assignment {
           description "Bridge-domain name or 802.1q tag for the MAC address";
           type string {
           }
         }
         leaf interface {
           description "Interface on which authentication is bypassed";
           type union {
             type jt:interface-name;
             type string {
               pattern "<.*>|$.*";
             }
           }
         }
       }
       list interface {
         key name;
         description "802.1X  interface specific options";
         leaf name {
           type string;
         }
         uses apply-advanced;
         leaf ignore-port-bounce {
           description "To ignore the port-bounce request received from RADIUS server";
           type empty;
         }
         leaf-list authentication-order {
           ordered-by user;
           description "Flexible authentication order";
           type enumeration {
             enum "dot1x" {
               description "Dot1x mode";
             }
             enum "mac-radius" {
               description "Mac radius mode";
             }
             enum "captive-portal" {
               description "Captive portal mode";
             }
           }
         }
         leaf disable {
           description "Disable 802.1X on this interface";
           type empty;
         }
         leaf supplicant {
           description "Set supplicant mode for this interface";
           default "single";
           type enumeration {
             enum "single" {
               description "Allow multiple clients; authenticate first client only";
             }
             enum "single-secure" {
               description "Allow and authenticate only a single client";
             }
             enum "multiple" {
               description "Allow multiple clients; authenticate each individually";
             }
           }
         }
         leaf retries {
           description "Number of retries after which port is placed into wait state";
           type union {
             type string {
               pattern "<.*>|$.*";
             }
             type uint32 {
               range "0 .. 10";
             }
           }
         }
         leaf quiet-period {
           description "Time to wait after an authentication failure";
           units "seconds";
           type union {
             type string {
               pattern "<.*>|$.*";
             }
             type uint32 {
               range "0 .. 65535";
             }
           }
         }
         leaf transmit-period {
           description "Interval before retransmitting initial EAPOL PDUs";
           units "seconds";
           type union {
             type string {
               pattern "<.*>|$.*";
             }
             type uint32 {
               range "1 .. 65535";
             }
           }
         }
         container multi-domain {
           presence "enable multi-domain";
           description "Enable multi domain authentication";
           uses apply-advanced;
           leaf packet-action {
             description "Set packet action for this interface";
             default "drop-and-log";
             type enumeration {
               enum "drop-and-log" {
                 description " Drop the client and generate the log message";
               }
               enum "shutdown" {
                 description "Disable port for excessive client authentication";
               }
             }
           }
           leaf max-data-session {
             description "Data session limit in multi domain authentication";
             type union {
               type string {
                 pattern "<.*>|$.*";
               }
               type uint32 {
                 range "1 .. 1000";
               }
             }
           }
           leaf recovery-timeout {
             description "Multi domain recovery timeout";
             units "seconds";
             type union {
               type string {
                 pattern "<.*>|$.*";
               }
               type uint32 {
                 range "60 .. 3600";
               }
             }
           }
         }
         container mac-radius {
           presence "enable mac-radius";
           description "Enable MAC-RADIUS";
           uses apply-advanced;
           leaf restrict {
             description "Bypass dot1x authentication, use MAC RADIUS only";
             type empty;
           }
           leaf flap-on-disconnect {
             description "Reset an interface on receiving a disconnect request";
             type empty;
           }
           container authentication-protocol {
             description "Set mac-radius authentication method";
             uses apply-advanced;
             choice protocols {
               case case_1 {
                 leaf eap-md5 {
                   description "Authentication protocol EAP-MD5";
                   type empty;
                 }
               }
               case case_2 {
                 leaf pap {
                   description "Authentication protocol PAP";
                   type empty;
                 }
               }
               case case_3 {
                 container eap-peap {
                   presence "enable eap-peap";
                   description "Authentication protocol EAP-PEAP";
                   uses apply-advanced;
                   leaf resume {
                     description "Enable resume functionality for faster authentication";
                     type empty;
                   }
                 }
               }
             }
           }
         }
         choice reauthentication-mode {
           case case_1 {
             leaf no-reauthentication {
               description "Disable reauthentication";
               type empty;
             }
           }
           case case_2 {
             leaf reauthentication {
               description "Reauthentication interval";
               units "seconds";
               type union {
                 type string {
                   pattern "<.*>|$.*";
                 }
                 type uint32 {
                   range "1 .. 65535";
                 }
               }
             }
           }
         }
         leaf supplicant-timeout {
           description "Time to wait for a client response";
           units "seconds";
           type union {
             type string {
               pattern "<.*>|$.*";
             }
             type uint32 {
               range "1 .. 60";
             }
           }
         }
         leaf server-timeout {
           description "Authentication server timeout interval";
           units "seconds";
           type union {
             type string {
               pattern "<.*>|$.*";
             }
             type uint32 {
               range "1 .. 60";
             }
           }
         }
         leaf maximum-requests {
           description "Number of EAPOL RequestIDs to send before timing out";
           type union {
             type string {
               pattern "<.*>|$.*";
             }
             type uint32 {
               range "1 .. 10";
             }
           }
         }
         leaf guest-vlan {
           description "VLAN name or 802.1q tag for unauthenticated or non-responsive hosts";
           type string {
           }
         }
         leaf guest-bridge-domain {
           description "Bridge-domain name or 802.1q tag for unauthenticated or non-responsive hosts";
           type string {
           }
         }
         container server-reject-vlan {
           description "VLAN name or 802.1q tag for authentication rejected clients";
           leaf vlan-name {
             description "VLAN name or VLAN Tag (1..4095)";
             type string {
             }
           }
           leaf block-interval {
             description "Interval for authenticator to ignore the EAP-Start packets.";
             units "seconds";
             type union {
               type string {
                 pattern "<.*>|$.*";
               }
               type uint32 {
                 range "120 .. 65535";
               }
             }
           }
           leaf eapol-block {
             description "Force the authenticator to ignore EAPOL-Start packets.";
             type empty;
           }
         }
         container server-reject-bridge-domain {
           description "VLAN name or 802.1q tag for authentication rejected clients";
           leaf bridge-domain {
             description "Bridge-domain name or VLAN Tag (1..4095)";
             type string {
             }
           }
           leaf block-interval {
             description "Interval for authenticator to ignore the EAP-Start packets.";
             units "seconds";
             type union {
               type string {
                 pattern "<.*>|$.*";
               }
               type uint32 {
                 range "120 .. 65535";
               }
             }
           }
           leaf eapol-block {
             description "Force the authenticator to ignore EAPOL-Start packets.";
             type empty;
           }
         }
         container eapol-block {
           description "Force the authenticator to ignore EAPOL-Start packets";
           uses apply-advanced;
           container server-fail {
             presence "enable server-fail";
             description "Block EAPOL-Start during RADIUS Timeout";
             uses apply-advanced;
             leaf block-interval {
               description "Interval for authenticator to ignore the EAP-Start packets.";
               units "seconds";
               type union {
                 type string {
                   pattern "<.*>|$.*";
                 }
                 type uint32 {
                   range "120 .. 65535";
                 }
               }
             }
           }
           container mac-radius {
             presence "enable mac-radius";
             description "Block EAPOL-Start when client is authenticated in mac-radius mode";
           }
           container captive-portal {
             presence "enable captive-portal";
             description "Block EAPOL-Start when client is authenticated in captive-portal mode";
           }
         }
         leaf lldp-med-bypass {
           description "Bypass dot1x authentication, use lldp-med based authentication";
           type empty;
         }
         container server-fail {
           description "Action to be taken when server is inaccessible";
           choice server-fail-options {
             case case_1 {
               leaf deny {
                 description "Force client authentication to fail";
                 type empty;
               }
             }
             case case_2 {
               leaf permit {
                 description "Force client authentication to succeed";
                 type empty;
               }
             }
             case case_3 {
               leaf vlan-name {
                 description "VLAN name or 802.1q tag for unreachable servers";
                 type string {
                 }
               }
             }
             case case_4 {
             }
             case case_5 {
               leaf use-cache {
                 description "Use the previous state of the client";
                 type empty;
               }
             }
           }
         }
         container server-fail-voip {
           description "Action to be taken for VOIP client when server is inaccessible";
           choice server-fail-options {
             case case_1 {
               leaf deny {
                 description "Force VoIP client authentication to fail";
                 type empty;
               }
             }
             case case_2 {
               leaf permit {
                 description "Force VoIP client authentication to succeed";
                 type empty;
               }
             }
             case case_3 {
               leaf vlan-name {
                 description "Configured VoIP VLAN name or 802.1q tag for unreachable servers";
                 type string {
                 }
               }
             }
             case case_4 {
               leaf use-cache {
                 description "Use the previous state of the VoIP client";
                 type empty;
               }
             }
           }
         }
         leaf redirect-url {
           description "CWA redirect URL to be used for unauthenticated users";
           type string {
             length "10 .. 247";
           }
         }
         leaf no-tagged-mac-authentication {
           description "Don't allow tagged mac for radius authentication";
           type empty;
         }
       }
     }
   }
   grouping juniper-protocols-esis {
     uses apply-advanced;
     choice enable-disable {
       case case_1 {
         leaf disable {
           description "Disable ES-IS";
           type empty;
         }
       }
     }
     container traceoptions {
       description "Trace options for ES-IS";
       uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "error" {
               description "Trace errored packets";
             }
             enum "esh" {
               description "Trace end system hello packets";
             }
             enum "ish" {
               description "Trace intermediate system hello packets";
             }
             enum "graceful-restart" {
               description "Trace graceful restart events";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     leaf preference {
       description "Preference of routes";
       type union {
         type uint32;
         type string {
           pattern "<.*>|$.*";
         }
       }
     }
     container graceful-restart {
       description "ES-IS graceful restart options";
       choice enable-disable {
         case case_1 {
           leaf disable {
             description "Disable graceful restart";
             type empty;
           }
         }
       }
       leaf restart-duration {
         description "Maximum time for graceful restart to finish";
         units "seconds";
         type union {
           type string {
             pattern "<.*>|$.*";
           }
           type uint32 {
             range "30 .. 300";
           }
         }
       }
     }
     list interface {
       key name;
       description "Interface configuration";
       leaf name {
         description "Interface name";
         type union {
           type jt:interface-name;
           type string {
             pattern "<.*>|$.*";
           }
         }
       }
       uses apply-advanced;
       leaf hold-time {
         description "Time after which neighbors think the interface is down";
         units "seconds";
         type union {
           type string {
             pattern "<.*>|$.*";
           }
           type uint32 {
             range "1 .. 65535";
           }
         }
       }
       leaf end-system-configuration-timer {
         description "Suggested end system configuration timer";
         units "seconds";
         type union {
           type string {
             pattern "<.*>|$.*";
           }
           type uint32 {
             range "1 .. 65535";
           }
         }
       }
       choice enable-disable {
         case case_1 {
           leaf disable {
             description "Disable ES-IS on this interface";
             type empty;
           }
         }
       }
     }
   }
   grouping juniper-protocols-isis {
     uses apply-advanced;
     choice enable-disable {
       case case_1 {
         leaf disable {
           description "Disable IS-IS";
           type empty;
         }
       }
     }
     container traceoptions {
       description "Trace options for IS-IS";
       uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "error" {
               description "Trace errored packets";
             }
             enum "spf" {
               description "Trace SPF events";
             }
             enum "packets" {
               description "Trace IS-IS packets";
             }
             enum "hello" {
               description "Trace hello packets";
             }
             enum "lsp" {
               description "Trace link-state packets";
             }
             enum "psn" {
               description "Trace partial sequence number (PSN) packets";
             }
             enum "csn" {
               description "Trace complete sequence number (CSN) packets";
             }
             enum "layer2-map" {
               description "Trace ARP/ND kernel state manipulation";
             }
             enum "lsp-generation" {
               description "Trace LSP generation";
             }
             enum "graceful-restart" {
               description "Trace graceful restart events";
             }
             enum "ldp-synchronization" {
               description "Trace synchronization between IS-IS and LDP";
             }
             enum "nsr-synchronization" {
               description "Trace NSR synchronization events";
             }
             enum "spring" {
               description "Trace source packet routing";
             }
             enum "traffic-statistics" {
               description "Trace traffic-statistics related events";
             }
             enum "prefix-sid" {
               description "Trace source packet routing, prefix-sids";
             }
             enum "adj-sid" {
               description "Trace adj-sid related events";
             }
             enum "post-convergence-lfa" {
               description "Trace post-convergence-lfa related events";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     leaf-list export {
       ordered-by user;
       description "Export policy";
       type jt:policy-algebra;
     }
     leaf-list import {
       ordered-by user;
       description "Import policy";
       type jt:policy-algebra;
     }
     leaf reference-bandwidth {
       description "Bandwidth for calculating metric defaults";
       type string;
     }
     choice layer2-map-choice {
       leaf layer2-map {
         description "Kernel ARP/ND creation for nexthops";
         type empty;
       }
       leaf no-layer2-map {
         description "Don't kernel ARP/ND creation for nexthops";
         type empty;
       }
     }
     leaf job-stats {
       description "Collect job statistics";
       type empty;
     }
     leaf lsp-lifetime {
       description "Lifetime of LSPs";
       units "seconds";
       type union {
         type string {
           pattern "<.*>|$.*";
         }
         type uint32 {
           range "350 .. 65535";
         }
       }
     }
     leaf max-lsp-size {
       description "Maximum size allowed for LSPs";
       default "1492";
       type union {
         type string {
           pattern "<.*>|$.*";
         }
         type uint32 {
           range "512 .. 1492";
         }
       }
     }
     leaf max-hello-size {
       description "Maximum size allowed for ISIS Hello PDUs";
       default "1492";
       type union {
         type string {
           pattern "<.*>|$.*";
         }
         type uint32 {
           range "512 .. 16000";
         }
       }
     }
     leaf max-snp-size {
       description "Maximum size allowed for Sequence Number (Complete/Partial) PDUs";
       default "1400";
       type union {
         type string {
           pattern "<.*>|$.*";
         }
         type uint32 {
           range "512 .. 1400";
         }
       }
     }
     leaf spf-delay {
       description "Time to wait before running an SPF";
       status deprecated;
       units "milliseconds";
       type union {
         type string {
           pattern "<.*>|$.*";
         }
         type uint32 {
           range "50 .. 120000";
         }
       }
     }
     leaf authentication-key {
       description "Authentication key (password)";
       status deprecated;
       type jt:unreadable;
     }
     leaf authentication-type {
       description "Authentication type";
       status deprecated;
       type enumeration {
         enum "md5" {
           description "MD5 authentication";
           status deprecated;
         }
         enum "simple" {
           description "Simple password authentication";
           status deprecated;
         }
       }
     }
     leaf loose-authentication-check {
       description "Verify authentication only if PDU has authentication TLV";
       type empty;
     }
     leaf max-areas {
       description "Maximum number of advertised Areas";
       default "3";
       type union {
         type string {
           pattern "<.*>|$.*";
         }
         type uint32 {
           range "3 .. 36";
         }
       }
     }
     leaf no-authentication-check {
       description "Disable authentication checking";
       type empty;
     }
     leaf no-ipv4-routing {
       description "Disable IPv4 routing";
       type empty;
     }
     leaf no-ipv6-routing {
       description "Disable IPv6 routing";
       type empty;
     }
     leaf clns-routing {
       description "Enable CLNS routing";
       type empty;
     }
     leaf clns-updown-compatibility {
       description "Set the Up/Down Bit in place of the I/E bit in CLNS TLVs";
       type empty;
     }
     leaf no-adjacency-holddown {
       description "Disable adjacency hold down";
       type empty;
     }
     leaf multicast-topology {
       description "Enable multicast topology";
       status deprecated;
       type empty;
     }
     leaf ignore-attached-bit {
       description "Ignore the attached bit in Level 1 LSPs";
       type empty;
     }
     container rib-group {
       description "Routing table group for importing IS-IS routes";
       uses rib_group_type;
     }
     container strict-dual-isis {
       presence "enable strict-dual-isis";
       description "Ensure both ipv4 and ipv6 connectivity for all adjacencies";
       uses apply-advanced;
       leaf holdown {
         description "Set the holddown timer for strict spf computation";
         default "12";
         type union {
           type uint32;
           type string {
             pattern "<.*>|$.*";
           }
         }
       }
     }
     container spf-options {
       description "Configure SPF attributes";
       uses apply-advanced;
       leaf delay {
         description "Time to wait before running an SPF";
         units "milliseconds";
         type union {
           type string {
             pattern "<.*>|$.*";
           }
           type uint32 {
             range "50 .. 1000";
           }
         }
       }
       leaf holddown {
         description "Time to hold down before running an SPF";
         units "milliseconds";
         type union {
           type string {
             pattern "<.*>|$.*";
           }
           type uint32 {
             range "2000 .. 10000";
           }
         }
       }
       leaf rapid-runs {
         description "Number of rapid SPF runs before SPF holddown";
         type union {
           type string {
             pattern "<.*>|$.*";
           }
           type uint32 {
             range "1 .. 5";
           }
         }
       }
       container multipath {
         description "Configure multipath options";
         uses apply-advanced;
         container weighted {
           description "Weighted multipath options";
           uses apply-advanced;
           leaf one-hop {
             description "Enable load balancing on onehop multipath based on interface bandwidth";
             type empty;
           }
         }
       }
     }
     container backup-spf-options {
       description "Configure backup SPF attributes";
       uses apply-advanced;
       leaf per-prefix-calculation {
         description "Calculate backup nexthops for non-best prefix originators";
         type empty;
       }
       container remote-backup-calculation {
         presence "enable remote-backup-calculation";
         description "Calculate Remote LFA backup nexthops";
         uses apply-advanced;
       }
       container use-post-convergence-lfa {
         presence "enable use-post-convergence-lfa";
         description "Calculate Post Convergence Backup Nexthops";
         uses apply-advanced;
         leaf maximum-labels {
           description "Set maximum number of label supported for post convergence path calculations";
           type union {
             type string {
               pattern "<.*>|$.*";
             }
             type uint32 {
               range "2 .. 5";
             }
           }
         }
         leaf maximum-backup-paths {
           description "Set maximum equal cost backup post convergence paths";
           type union {
             type string {
               pattern "<.*>|$.*";
             }
             type uint32 {
               range "1 .. 8";
             }
           }
         }
       }
       leaf node-link-degradation {
         description "Degrade to link protection when nodelink protection not available";
         type empty;
       }
       container use-source-packet-routing {
         presence "enable use-source-packet-routing";
         description "Use SPRING routed paths for protection";
         uses apply-advanced;
       }
     }
     container topologies {
       description "Enable topologies";
       uses apply-advanced;
       leaf ipv4-multicast {
         description "Enable IPv4-multicast topology";
         type empty;
       }
       leaf ipv6-unicast {
         description "Enable IPv6-unicast topology";
         type empty;
       }
       leaf ipv6-multicast {
         description "Enable IPv6-multicast topology";
         type empty;
       }
     }
     container overload {
       presence "enable overload";
       description "Set the overload bit (no transit traffic)";
       uses apply-advanced;
       leaf timeout {
         description "Time after which overload bit is reset";
         units "seconds";
         type union {
           type string {
             pattern "<.*>|$.*";
           }
           type uint32 {
             range "60 .. 1800";
           }
         }
       }
       leaf advertise-high-metrics {
         description "Advertise high metrics instead of setting the overload bit";
         type empty;
       }
       leaf allow-route-leaking {
         description "Allow routes to be leaked when overload is configured";
         type empty;
       }
       leaf internal-prefixes {
         description "Allow internal prefixes to be advertised with high metric";
         type empty;
       }
       leaf external-prefixes {
         description "Allow external prefixes to be advertised with high metric";
         type empty;
       }
     }
     container traffic-engineering {
       description "Configure traffic engineering attributes";
       uses apply-advanced;
       choice enable-disable {
         case case_1 {
           leaf disable {
             description "Disable traffic engineering";
             type empty;
           }
         }
       }
       leaf igp-topology {
         description "Download IGP topology into TED";
         type empty;
       }
       leaf credibility-protocol-preference {
         description "Follow IGP protocol preference for TED protocol credibility";
         type empty;
       }
       leaf ipv4-multicast-rpf-routes {
         description "Install IPv4 routes for multicast RPF checks into inet.2";
         status deprecated;
         type empty;
       }
       leaf ignore-lsp-metrics {
         description "Ignore label-switched path metrics when doing shortcuts";
         type empty;
       }
       container tunnel-source-protocol {
         description "Protocols from which to pick label-switched paths";
         uses apply-advanced;
         container rsvp {
           presence "enable rsvp";
           description "Pick label-switched paths from rsvp";
           uses apply-advanced;
           leaf preference {
             description "Preference for label-switched paths from this protocol";
             type union {
               type string {
                 pattern "<.*>|$.*";
               }
               type uint32 {
                 range "1 .. 255";
               }
             }
           }
         }
         container spring-te {
           presence "enable spring-te";
           description "Pick label-switched paths from spring-te";
           uses apply-advanced;
           leaf preference {
             description "Preference for label-switched paths from this protocol";
             type union {
               type string {
                 pattern "<.*>|$.*";
               }
               type uint32 {
                 range "1 .. 255";
               }
             }
           }
         }
       }
       list family {
         key name;
         ordered-by user;
         description "Address family specific traffic-engineering attributes";
         leaf name {
           type enumeration {
             enum "inet" {
               description "IPv4 family";
             }
             enum "inet6" {
               description "IPv6 family";
             }
             enum "inet-mpls" {
               description "IPv4-MPLS family";
             }
             enum "inet6-mpls" {
               description "IPv6-MPLS family";
             }
           }
         }
         uses apply-advanced;
         container shortcuts {
           presence "enable shortcuts";
           description "Use label-switched paths as next hops, if possible";
           uses apply-advanced;
           leaf multicast-rpf-routes {
             description "Install routes for multicast RPF checks into multicast RIB";
             type empty;
           }
         }
       }
       container shortcuts {
         presence "enable shortcuts";
         description "Use label-switched paths as next hops, if possible";
         status deprecated;
         uses apply-advanced;
         leaf ignore-lsp-metrics {
           description "Ignore label-switched path metrics when doing shortcuts";
           status deprecated;
           type empty;
         }
       }
       container multipath {
         description "Configure label-switched-path multipath behavior";
         uses apply-advanced;
         leaf lsp-equal-cost {
           description "Include equal cost label-switched-paths";
           type empty;
         }
       }
     }
     container graceful-restart {
       description "IS-IS graceful restart options";
       choice enable-disable {
         case case_1 {
           leaf disable {
             description "Disable graceful restart";
             type empty;
           }
         }
       }
       leaf helper-disable {
         description "Disable graceful restart helper capability";
         type empty;
       }
       leaf restart-duration {
         description "Maximum time for graceful restart to finish";
         units "seconds";
         type union {
           type string {
             pattern "<.*>|$.*";
           }
           type uint32 {
             range "30 .. 300";
           }
         }
       }
     }
     container source-packet-routing {
       presence "enable source-packet-routing";
       description "Enable Source Packet Routing (SPRING)";
       uses apply-advanced;
       container adjacency-segment {
         description "Configure attributes for Adjacency Segments in SPRING";
         uses apply-advanced;
         leaf hold-time {
           description "Duration(ms) for which adjacency segments will be retained after isolating from an interface";
           type union {
             type string {
               pattern "<.*>|$.*";
             }
             type uint32 {
               range "180000 .. 900000";
             }
           }
         }
       }
       container sensor-based-stats {
         description "Configure sensor based stats in SPRING";
         uses apply-advanced;
         container per-interface-per-member-link {
           description "Configure sensor based stats per nexthop";
           leaf ingress {
             description "Enable sensor based stats on ingress interface";
             type empty;
           }
           leaf egress {
             description "Enable sensor based stats on egress interface";
             type empty;
           }
         }
         container per-sid {
           description "Configure sensor based stats per spring route";
           leaf ingress {
             description "Enable sensor based stats for per-sid ingress accounting";
             type empty;
           }
           leaf egress {
             description "Enable sensor based stats for IP-MPLS egress accounting";
             type empty;
           }
         }
       }
       container srgb {
         description "Set the SRGB global block in SPRING";
         leaf start-label {
           description "Start range for SRGB label block";
           type union {
             type string {
               pattern "<.*>|$.*";
             }
             type uint32;
           }
         }
         leaf index-range {
           description "Index to the SRGB start label block";
           type union {
             type string {
               pattern "<.*>|$.*";
             }
             type uint32;
           }
         }
       }
       container node-segment {
         description "Enable support for Node segments in SPRING";
         uses apply-advanced;
         leaf ipv4-index {
           description "Set IPv4 Node Segment index";
           type union {
             type string {
               pattern "<.*>|$.*";
             }
             type uint32 {
               range "0 .. 199999";
             }
           }
         }
         leaf ipv6-index {
           description "Set IPv6 Node Segment index";
           type union {
             type string {
               pattern "<.*>|$.*";
             }
             type uint32 {
               range "0 .. 199999";
             }
           }
         }
         leaf index-range {
           description "Set Range of Node Segment indices allowed";
           type union {
             type string {
               pattern "<.*>|$.*";
             }
             type uint32 {
               range "32 .. 16385";
             }
           }
         }
       }
       container traffic-statistics {
         description "Enable support for traffic statistics in SPRING";
         uses apply-advanced;
         container statistics-granularity {
           description "Granularity for traffic statistics in SPRING";
           uses apply-advanced;
           leaf per-interface {
             description "Interface Based traffic statistics in SPRING";
             type empty;
           }
         }
         leaf auto-bandwidth {
           description "Auto bandwidth name";
           type string;
         }
       }
       leaf explicit-null {
         description "Set E and P bits in all Prefix SID advertisements";
         type empty;
       }
       leaf mapping-server {
         description "Mapping server name";
         type string;
       }
       leaf ldp-stitching {
         description "Enable SR to LDP stitching";
         type empty;
       }
     }
     list level {
       key name;
       ordered-by user;
       description "Configure global level attributes";
       leaf name {
         description "IS-IS level number";
         type union {
           type string {
             pattern "<.*>|$.*";
           }
           type uint32 {
             range "1 .. 2";
           }
         }
       }
       uses apply-advanced;
       choice enable-disable {
         case case_1 {
           leaf disable {
             description "Disable IS-IS on this level";
             type empty;
           }
         }
       }
       leaf authentication-key {
         description "Authentication key (password)";
         type jt:unreadable;
       }
       leaf authentication-type {
         description "Authentication type";
         type enumeration {
           enum "md5" {
             description "MD5 authentication";
           }
           enum "simple" {
             description "Simple password authentication";
           }
         }
       }
       leaf purge-originator {
         description "Add Purge Originator information";
         type enumeration {
           enum "self" {
             description "Add POI only for self-originated purge LSPs";
           }
           enum "empty" {
             description "Add POI for purge LSPs who do not have POI information";
           }
         }
       }
       leaf no-hello-authentication {
         description "Disable authentication for hello packets";
         type empty;
       }
       leaf no-csnp-authentication {
         description "Disable authentication for CSN packets";
         type empty;
       }
       leaf no-psnp-authentication {
         description "Disable authentication for PSN packets";
         type empty;
       }
       leaf authentication-key-chain {
         description "Key chain name";
         type string {
           length "1 .. 128";
         }
       }
       leaf wide-metrics-only {
         description "Generate wide metrics only";
         type empty;
       }
       leaf preference {
         description "Preference of internal routes";
         type union {
           type uint32;
           type string {
             pattern "<.*>|$.*";
           }
         }
       }
       leaf external-preference {
         description "Preference of external routes";
         type union {
           type uint32;
           type string {
             pattern "<.*>|$.*";
           }
         }
       }
       leaf labeled-preference {
         description "Preference of labeled IS-IS routes";
         type union {
           type uint32;
           type string {
             pattern "<.*>|$.*";
           }
         }
       }
       leaf prefix-export-limit {
         description "Maximum number of external prefixes that can be exported";
         type union {
           type string {
             pattern "<.*>|$.*";
           }
           type uint32 {
             range "0 .. 4294967295";
           }
         }
       }
       container source-packet-routing {
         presence "enable source-packet-routing";
         description "Enable Source Packet Routing (SPRING)";
         uses apply-advanced;
         choice enable-disable {
           case case_1 {
             leaf disable {
               description "Disable Source Packet Routing on this level";
               type empty;
             }
           }
         }
       }
     }
     list interface {
       key name;
       description "Interface configuration";
       leaf name {
         description "Interface name";
         type union {
           type jt:interface-name;
           type string {
             pattern "<.*>|$.*";
           }
         }
       }
       uses apply-advanced;
       choice enable-disable {
         case case_1 {
           leaf disable {
             description "Disable IS-IS on this interface";
             type empty;
           }
         }
       }
       leaf authentication-key {
         description "Authentication key (password)";
         status deprecated;
         type jt:unreadable;
       }
       leaf authentication-type {
         description "Authentication type";
         status deprecated;
         type enumeration {
           enum "md5" {
             description "MD5 authentication";
             status deprecated;
           }
           enum "simple" {
             description "Simple password authentication";
             status deprecated;
           }
         }
       }
       container auto-bandwidth {
         description "Auto bandwidth configuration";
         uses apply-advanced;
         leaf template-name {
           description "Auto bandwidth template name";
           type string;
         }
         choice enable-disable {
           case case_1 {
             leaf disable {
               description "Disable Auto bandwidth on this interface";
               type empty;
             }
           }
         }
       }
       leaf flood-group {
         description "ISO Area that this interface should send LSPs to";
         type string {
         }
       }
       leaf no-advertise-adjacency-segment {
         description "Do not advertise an adjacency segment for this interface";
         type empty;
       }
       leaf hello-authentication-key {
         description "Authentication key (password) for hello packets";
         status deprecated;
         type jt:unreadable;
       }
       leaf hello-authentication-type {
         description "Authentication type for hello packets";
         status deprecated;
         type enumeration {
           enum "md5" {
             description "MD5 authentication";
             status deprecated;
           }
           enum "simple" {
             description "Simple password authentication";
             status deprecated;
           }
         }
       }
       leaf hello-padding-type {
         description "Type of padding for hello packets";
         default "loose";
         type enumeration {
           enum "strict" {
             description "Padding for all adjacency states";
           }
           enum "adaptive" {
             description "Padding until state of neighbor adjacency is 'up'";
           }
           enum "loose" {
             description "Padding until state of adjacency is 'initializing'";
           }
           enum "disable" {
             description "Do not add any padding for hello packets";
           }
         }
       }
       leaf interface-group-holddown-delay {
         description "Time to wait before including in BBM calculation";
         units "seconds";
         type union {
           type string {
             pattern "<.*>|$.*";
           }
           type uint32 {
             range "0 .. 60";
           }
         }
       }
       choice layer2-map-choice {
         leaf layer2-map {
           description "Kernel ARP/ND creation for nexthops";
           type empty;
         }
         leaf no-layer2-map {
           description "Don't kernel ARP/ND creation for nexthops";
           type empty;
         }
       }
       container ldp-synchronization {
         description "Advertise maximum metric until LDP is operational";
         presence "enable ldp-synchronization";
         uses ldp-sync-obj;
       }
       leaf max-hello-size {
         description "Maximum size allowed for ISIS Hello PDUs";
         type union {
           type string {
             pattern "<.*>|$.*";
           }
           type uint32 {
             range "512 .. 16000";
           }
         }
       }
       leaf lsp-interval {
         description "Interval between LSP transmissions";
         default "100";
         units "milliseconds";
         type union {
           type string {
             pattern "<.*>|$.*";
           }
           type uint32 {
             range "1 .. 1000";
           }
         }
       }
       container csnp-interval {
         description "Rate of CSN packets (for LAN interfaces only)";
         choice csnp_interval_option {
           case case_1 {
             leaf csnp-interval-number {
               description "Interval between CSN packets";
               units "seconds";
               type union {
                 type string {
                   pattern "<.*>|$.*";
                 }
                 type uint32 {
                   range "1 .. 65535";
                 }
               }
             }
           }
           case case_2 {
             leaf disable {
               description "Do not send CSN packets on this interface";
               type empty;
             }
           }
         }
       }
       container strict-dual-isis {
         presence "enable strict-dual-isis";
         description "Ensure both ipv4 and ipv6 connectivity for adjacencies on this interface";
         uses apply-advanced;
         leaf holdown {
           description "Set the holddown timer for strict spf computation";
           default "12";
           type union {
             type uint32;
             type string {
               pattern "<.*>|$.*";
             }
           }
         }
       }
       container mesh-group {
         description "Add the interface to a mesh group";
         choice mesh_group_option {
           case case_1 {
             leaf mesh-group-number {
               description "Mesh group number for this interface";
               type union {
                 type uint32;
                 type string {
                   pattern "<.*>|$.*";
                 }
               }
             }
           }
           case case_2 {
             leaf blocked {
               description "Do not flood new LSPs on this interface";
               type empty;
             }
           }
         }
       }
       leaf point-to-point {
         description "Treat interface as point to point";
         type empty;
       }
       choice protection-type {
         case case_1 {
           leaf link-protection {
             description "Protect interface from link faults only";
             type empty;
           }
         }
         case case_2 {
           leaf node-link-protection {
             description "Protect interface from both link and node faults";
             type empty;
           }
         }
       }
       leaf no-eligible-backup {
         description "Not eligible for backup traffic from protected interfaces";
         type empty;
       }
       container passive {
         presence "enable passive";
         description "Do not run IS-IS, but advertise it";
         uses apply-advanced;
         leaf remote-node-iso {
           description "ISO System-ID of the remote node";
           type jt:sysid;
         }
         leaf remote-node-id {
           description "Remote address of the link";
           type jt:ipv4addr;
         }
       }
       leaf no-eligible-remote-backup {
         description "Not eligible for Remote-LFA backup traffic from protected interfaces";
         type empty;
       }
       leaf checksum {
         description "Enable checksum for packets on this interface";
         type empty;
       }
       leaf no-unicast-topology {
         description "Do not include this interface in the unicast topology";
         type empty;
       }
       leaf no-ipv4-multicast {
         description "Do not include this interface in the IPv4 multicast topology";
         type empty;
       }
       leaf no-ipv6-unicast {
         description "Do not include this interface in the IPv6 unicast topology";
         type empty;
       }
       leaf no-ipv6-multicast {
         description "Do not include this interface in the IPv6 multicast topology";
         type empty;
       }
       leaf no-adjacency-down-notification {
         description "Do not inform other protocols about adjacency down events";
         type empty;
       }
       container bfd-liveness-detection {
         description "Bidirectional Forwarding Detection options";
         status deprecated;
         uses apply-advanced;
         leaf version {
           description "BFD protocol version number";
           default "automatic";
           type enumeration {
             enum "0" {
               description "BFD version 0 (deprecated)";
             }
             enum "1" {
               description "BFD version 1";
             }
             enum "automatic" {
               description "Choose BFD version automatically";
             }
           }
         }
         leaf minimum-interval {
           description "Minimum transmit and receive interval";
           units "milliseconds";
           type union {
             type string {
               pattern "<.*>|$.*";
             }
             type uint32 {
               range "1 .. 255000";
             }
           }
         }
         leaf minimum-transmit-interval {
           description "Minimum transmit interval";
           status deprecated;
           units "milliseconds";
           type union {
             type string {
               pattern "<.*>|$.*";
             }
             type uint32 {
               range "1 .. 255000";
             }
           }
         }
         leaf minimum-receive-interval {
           description "Minimum receive interval";
           units "milliseconds";
           type union {
             type string {
               pattern "<.*>|$.*";
             }
             type uint32 {
               range "1 .. 255000";
             }
           }
         }
         leaf multiplier {
           description "Detection time multiplier";
           default "3";
           type union {
             type string {
               pattern "<.*>|$.*";
             }
             type uint32 {
               range "1 .. 255";
             }
           }
         }
         choice adaptation-choice {
           case case_1 {
             leaf no-adaptation {
               description "Disable adaptation";
               type empty;
             }
           }
         }
         container transmit-interval {
           description "Transmit-interval options";
           uses apply-advanced;
           leaf minimum-interval {
             description "Minimum transmit interval";
             units "milliseconds";
             type union {
               type string {
                 pattern "<.*>|$.*";
               }
               type uint32 {
                 range "1 .. 255000";
               }
             }
           }
           leaf threshold {
             description "High transmit interval triggering a trap";
             units "milliseconds";
             type union {
               type uint32;
               type string {
                 pattern "<.*>|$.*";
               }
             }
           }
         }
         container detection-time {
           description "Detection-time options";
           uses apply-advanced;
           leaf threshold {
             description "High detection-time triggering a trap";
             units "milliseconds";
             type union {
               type uint32;
               type string {
                 pattern "<.*>|$.*";
               }
             }
           }
         }
         container authentication {
           description "Authentication options";
           uses apply-advanced;
           leaf key-chain {
             description "Key chain name";
             type string;
           }
           leaf algorithm {
             description "Algorithm name";
             type enumeration {
               enum "simple-password" {
                 description "Simple password";
               }
               enum "keyed-md5" {
                 description "Keyed message Digest 5";
               }
               enum "meticulous-keyed-md5" {
                 description "Meticulous keyed message Digest 5";
               }
               enum "keyed-sha-1" {
                 description "Keyed secure hash algorithm (SHA1) ";
               }
               enum "meticulous-keyed-sha-1" {
                 description "Meticulous keyed secure hash algorithm (SHA1) ";
               }
             }
           }
           leaf loose-check {
             description "Verify authentication only if authentication is negotiated";
             type empty;
           }
         }
       }
       list family {
         key name;
         ordered-by user;
         description "Address family specific interface attributes";
         leaf name {
           type enumeration {
             enum "inet" {
               description "IPv4 family";
             }
             enum "inet6" {
               description "IPv6 family";
             }
           }
         }
         uses apply-advanced;
         container bfd-liveness-detection {
           description "Bidirectional Forwarding Detection options";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
           container authentication {
             description "Authentication options";
             uses apply-advanced;
             leaf key-chain {
               description "Key chain name";
               type string;
             }
             leaf algorithm {
               description "Algorithm name";
               type enumeration {
                 enum "simple-password" {
                   description "Simple password";
                 }
                 enum "keyed-md5" {
                   description "Keyed message Digest 5";
                 }
                 enum "meticulous-keyed-md5" {
                   description "Meticulous keyed message Digest 5";
                 }
                 enum "keyed-sha-1" {
                   description "Keyed secure hash algorithm (SHA1) ";
                 }
                 enum "meticulous-keyed-sha-1" {
                   description "Meticulous keyed secure hash algorithm (SHA1) ";
                 }
               }
             }
             leaf loose-check {
               description "Verify authentication only if authentication is negotiated";
               type empty;
             }
           }
         }
       }
       list level {
         key name;
         ordered-by user;
         description "Configure levels on this interface";
         leaf name {
           description "IS-IS level number";
           type union {
             type string {
               pattern "<.*>|$.*";
             }
             type uint32 {
               range "1 .. 2";
             }
           }
         }
         uses apply-advanced;
         choice enable-disable {
           case case_1 {
             leaf disable {
               description "Disable IS-IS for this level";
               type empty;
             }
           }
         }
         container post-convergence-lfa {
           presence "enable post-convergence-lfa";
           description "Configure backup along post convergence on this interface";
           uses apply-advanced;
           container node-protection {
             presence "enable node-protection";
             description "Enable node protection";
             uses apply-advanced;
             leaf cost {
               description "Cost for node protection";
               type union {
                 type string {
                   pattern "<.*>|$.*";
                 }
                 type uint32 {
                   range "0 .. 16777215";
                 }
               }
             }
           }
           leaf fate-sharing-protection {
             description "Enable fate-sharing protection";
             type empty;
           }
         }
         leaf metric {
           description "Metric for this level";
           type union {
             type string {
               pattern "<.*>|$.*";
             }
             type uint32 {
               range "0 .. 16777215";
             }
           }
         }
         leaf ipv4-multicast-metric {
           description "IPv4 multicast metric for this level";
           type union {
             type string {
               pattern "<.*>|$.*";
             }
             type uint32 {
               range "0 .. 16777215";
             }
           }
         }
         leaf ipv6-unicast-metric {
           description "IPv6 unicast metric for this level";
           type union {
             type string {
               pattern "<.*>|$.*";
             }
             type uint32 {
               range "0 .. 16777215";
             }
           }
         }
         leaf ipv6-multicast-metric {
           description "IPv6 multicast metric for this level";
           type union {
             type string {
               pattern "<.*>|$.*";
             }
             type uint32 {
               range "0 .. 16777215";
             }
           }
         }
         leaf no-advertise-adjacency-segment {
           description "Do not advertise an adjacency segment for this level";
           type empty;
         }
         leaf te-metric {
           description "Traffic engineering metric";
           type union {
             type string {
               pattern "<.*>|$.*";
             }
             type uint32 {
               range "0 .. 16777215";
             }
           }
         }
         list topology {
           key name;
           ordered-by user;
           description "Topology specific attributes";
           leaf name {
             description "Topology name";
             type enumeration {
               enum "default" {
                 description "Default topology";
               }
               enum "ipv4-multicast" {
                 description "IPv4 multicast topology";
               }
               enum "ipv6-unicast" {
                 description "IPv6 unicast topology";
               }
               enum "ipv6-multicast" {
                 description "IPv6 multicast topology";
               }
             }
           }
           uses apply-advanced;
           leaf metric {
             description "Topology metric";
             type union {
               type string {
                 pattern "<.*>|$.*";
               }
               type uint32 {
                 range "0 .. 16777215";
               }
             }
           }
           container bandwidth-based-metrics {
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint32 {
                     range "0 .. 16777215";
                   }
                 }
               }
             }
           }
         }
         leaf authentication-key {
           description "Authentication key (password)";
           status deprecated;
           type jt:unreadable;
         }
         leaf authentication-type {
           description "Authentication type";
           status deprecated;
           type enumeration {
             enum "md5" {
               description "MD5 authentication";
               status deprecated;
             }
             enum "simple" {
               description "Simple password authentication";
               status deprecated;
             }
           }
         }
         leaf hello-authentication-key {
           description "Authentication key (password) for hello packets";
           type jt:unreadable;
         }
         leaf hello-authentication-type {
           description "Authentication type for hello packets";
           type enumeration {
             enum "md5" {
               description "MD5 authentication";
             }
             enum "simple" {
               description "Simple password authentication";
             }
           }
         }
         leaf hello-authentication-key-chain {
           description "Key chain name";
           type string {
             length "1 .. 128";
           }
         }
         leaf hello-interval {
           description "Interval between hello packet transmissions";
           units "seconds";
           type union {
             type string {
               pattern "<.*>|$.*";
             }
             type uint32 {
               range "1 .. 21845";
             }
           }
         }
         leaf hold-time {
           description "Time after which neighbors think the interface is down";
           units "seconds";
           type union {
             type string {
               pattern "<.*>|$.*";
             }
             type uint32 {
               range "1 .. 65535";
             }
           }
         }
         leaf priority {
           description "Designated router election priority";
           type union {
             type string {
               pattern "<.*>|$.*";
             }
             type uint32 {
               range "0 .. 127";
             }
           }
         }
         container passive {
           presence "enable passive";
           description "Do not run IS-IS at this level, but advertise it";
           uses apply-advanced;
           leaf remote-node-iso {
             description "ISO System-ID of the remote node";
             type jt:sysid;
           }
           leaf remote-node-id {
             description "Remote address of the link";
             type jt:ipv4addr;
           }
         }
         container ipv4-adjacency-segment {
           description "Configure ipv4 adjacency segment";
           uses apply-advanced;
           container protected {
             description "Adjacency SID is eligible for protection";
             choice adjsid-type {
               case case_1 {
                 container index {
                   description "Adjacency SID indexed from SRGB";
                   leaf index-number {
                     type union {
                       type string {
                         pattern "<.*>|$.*";
                       }
                       type uint32 {
                         range "0 .. 199999";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
           container unprotected {
             description "Adjacency SID uneligible for protection";
             choice adjsid-type {
               case case_1 {
                 container index {
                   description "Adjacency SID indexed from SRGB";
                   leaf index-number {
                     type union {
                       type string {
                         pattern "<.*>|$.*";
                       }
                       type uint32 {
                         range "0 .. 199999";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
         }
         container ipv6-adjacency-segment {
           description "Configure ipv6 adjacency segment";
           uses apply-advanced;
           container protected {
             description "Adjacency SID is eligible for protection";
             choice adjsid-type {
               case case_1 {
                 container index {
                   description "Adjacency SID indexed from SRGB";
                   leaf index-number {
                     type union {
                       type string {
                         pattern "<.*>|$.*";
                       }
                       type uint32 {
                         range "0 .. 199999";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
           container unprotected {
             description "Adjacency SID uneligible for protection";
             choice adjsid-type {
               case case_1 {
                 container index {
                   description "Adjacency SID indexed from SRGB";
                   leaf index-number {
                     type union {
                       type string {
                         pattern "<.*>|$.*";
                       }
                       type uint32 {
                         range "0 .. 199999";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
         }
         list lan-neighbor {
           key name;
           ordered-by user;
           description "Configuration specific to a LAN neighbor";
           leaf name {
             description "Neighbor's sysid";
             type jt:sysid;
           }
           uses apply-advanced;
           container ipv4-adjacency-segment {
             description "Configure ipv4 adjacency segment";
             uses apply-advanced;
             container protected {
               description "Adjacency SID is eligible for protection";
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
             container unprotected {
               description "Adjacency SID uneligible for protection";
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
           }
           container ipv6-adjacency-segment {
             description "Configure ipv6 adjacency segment";
             uses apply-advanced;
             container protected {
               description "Adjacency SID is eligible for protection";
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
             container unprotected {
               description "Adjacency SID uneligible for protection";
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
           }
         }
       }
       container link-degradation-threshold {
         presence "enable link-degradation-threshold";
         description "Link up and down thresholds (in %) for proactive link protection";
         leaf link-down {
           description "Signal degradation threshold above which link marked down";
           type union {
             type string {
               pattern "<.*>|$.*";
             }
             type uint32 {
               range "0 .. 100";
             }
           }
         }
         leaf link-up {
           description "Signal degradation threshold below which link is marked up.";
           type union {
             type string {
               pattern "<.*>|$.*";
             }
             type uint32 {
               range "0 .. 100";
             }
           }
         }
       }
     }
     list interface-group {
       key name;
       description "Interface grouping configuration";
       leaf name {
         description "Interface group name";
         type string;
       }
       uses apply-advanced;
       list interface {
         key name;
         description "List interfaces for this group";
         leaf name {
           description "Interface name";
           type union {
             type jt:interface-name;
             type string {
               pattern "<.*>|$.*";
             }
           }
         }
         uses apply-advanced;
         leaf weight {
           description "Interface weight for adjacency set";
           type union {
             type string {
               pattern "<.*>|$.*";
             }
             type uint32 {
               range "1 .. 255";
             }
           }
         }
       }
       list level {
         key name;
         ordered-by user;
         description "Configure levels on this interface-group";
         leaf name {
           description "IS-IS level number";
           type union {
             type string {
               pattern "<.*>|$.*";
             }
             type uint32 {
               range "1 .. 2";
             }
           }
         }
         uses apply-advanced;
         list topology {
           key name;
           ordered-by user;
           description "Topology specific attributes";
           leaf name {
             description "Topology name";
             type enumeration {
               enum "default" {
                 description "Default topology";
               }
               enum "ipv4-multicast" {
                 description "IPv4 multicast topology";
               }
               enum "ipv6-unicast" {
                 description "IPv6 unicast topology";
               }
               enum "ipv6-multicast" {
                 description "IPv6 multicast topology";
               }
             }
           }
           uses apply-advanced;
           leaf metric {
             description "Topology metric";
             type union {
               type string {
                 pattern "<.*>|$.*";
               }
               type uint32 {
                 range "0 .. 16777215";
               }
             }
           }
           container bandwidth-based-metrics {
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint32 {
                     range "0 .. 16777215";
                   }
                 }
               }
             }
           }
         }
         container ipv4-adjacency-segment {
           description "Configure ipv4 adjacency segment";
           uses apply-advanced;
           container protected {
             description "Adjacency SID is eligible for protection";
             choice adjsid-type {
               case case_1 {
                 container index {
                   description "Adjacency SID indexed from SRGB";
                   leaf index-number {
                     type union {
                       type string {
                         pattern "<.*>|$.*";
                       }
                       type uint32 {
                         range "0 .. 199999";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
           container unprotected {
             description "Adjacency SID uneligible for protection";
             choice adjsid-type {
               case case_1 {
                 container index {
                   description "Adjacency SID indexed from SRGB";
                   leaf index-number {
                     type union {
                       type string {
                         pattern "<.*>|$.*";
                       }
                       type uint32 {
                         range "0 .. 199999";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
         }
         container ipv6-adjacency-segment {
           description "Configure ipv6 adjacency segment";
           uses apply-advanced;
           container protected {
             description "Adjacency SID is eligible for protection";
             choice adjsid-type {
               case case_1 {
                 container index {
                   description "Adjacency SID indexed from SRGB";
                   leaf index-number {
                     type union {
                       type string {
                         pattern "<.*>|$.*";
                       }
                       type uint32 {
                         range "0 .. 199999";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
           container unprotected {
             description "Adjacency SID uneligible for protection";
             choice adjsid-type {
               case case_1 {
                 container index {
                   description "Adjacency SID indexed from SRGB";
                   leaf index-number {
                     type union {
                       type string {
                         pattern "<.*>|$.*";
                       }
                       type uint32 {
                         range "0 .. 199999";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
         }
       }
       container link-group-protection {
         description "Configure link group protection";
         uses apply-advanced;
         leaf minimum-bandwidth {
           description "Minimum bandwidth to carry traffic";
           type string;
         }
         leaf revert-bandwidth {
           description "Revert bandwidth to carry traffic";
           type string;
         }
       }
     }
     list label-switched-path {
       key name;
       ordered-by user;
       description "Configuration for advertisement of a label-switched path";
       leaf name {
         description "Name of label-switched path to be advertised";
         type string {
           length "1 .. 64";
         }
       }
       uses apply-advanced;
       list level {
         key name;
         ordered-by user;
         description "Level to advertise this label-switched path";
         leaf name {
           description "IS-IS level number";
           type union {
             type string {
               pattern "<.*>|$.*";
             }
             type uint32 {
               range "1 .. 2";
             }
           }
         }
         uses apply-advanced;
         choice enable-disable {
           case case_1 {
             leaf disable {
               description "Disable advertisements to this level";
               type empty;
             }
           }
         }
         leaf metric {
           description "SPF metric for this level";
           type union {
             type string {
               pattern "<.*>|$.*";
             }
             type uint32 {
               range "0 .. 16777215";
             }
           }
         }
       }
     }
     list context-identifier {
       key name;
       ordered-by user;
       description "Configuration for advertisement of a context-identifier ";
       leaf name {
         description "Context identifier range";
         type jt:ipprefix;
       }
       uses apply-advanced;
       list level {
         key name;
         ordered-by user;
         description "Level to advertise this context-identifier";
         leaf name {
           description "IS-IS level number";
           type union {
             type string {
               pattern "<.*>|$.*";
             }
             type uint32 {
               range "1 .. 2";
             }
           }
         }
         uses apply-advanced;
         choice enable-disable {
           case case_1 {
             leaf disable {
               description "Disable advertisements to this level";
               type empty;
             }
           }
         }
       }
     }
   }
   grouping juniper-protocols-l2control {
     uses apply-advanced;
     container traceoptions {
       description "Global tracing options for STP";
       uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "parse" {
               description "Trace configuration parsing";
             }
             enum "regex-parse" {
               description "Trace regular-expression parsing";
             }
             enum "config-internal" {
               description "Trace configuration internals";
             }
             enum "normal" {
               description "Trace normal events";
             }
             enum "general" {
               description "Trace general events";
             }
             enum "state" {
               description "Trace state transitions";
             }
             enum "task" {
               description "Trace routing protocol task processing";
             }
             enum "timer" {
               description "Trace routing protocol task timer processing";
             }
             enum "ppmlite" {
               description "Trace libppmlite processing";
             }
             enum "all" {
               description "Trace everything";
             }
           }
         }
         leaf disable {
           description "Disable this trace flag";
           type empty;
         }
       }
     }
     leaf nonstop-bridging {
       description "Enable nonstop operation";
       type empty;
     }
     container bpdu-block {
       presence "enable bpdu-block";
       description "Block BPDU on interface (BPDU Protect)";
       uses apply-advanced;
       list interface {
         key name;
         ordered-by user;
         description "Interface name to block BPDU on";
         leaf name {
           type string;
         }
         uses apply-advanced;
         leaf disable {
           description "Disable bpdu-block on a port";
           type empty;
         }
         leaf drop {
           description "Drop xSTP BPDUs";
           type empty;
         }
       }
       leaf disable-timeout {
         description "Disable timeout for BPDU Protect";
         units "seconds";
         type union {
           type string {
             pattern "<.*>|$.*";
           }
           type int32 {
             range "10 .. 3600";
           }
         }
       }
     }
     container mac-rewrite {
       description "Mac rewrite functionality";
       uses apply-advanced;
       list interface {
         key name;
         ordered-by user;
         leaf name {
           type union {
             type jt:interface-device;
             type string {
               pattern "<.*>|$.*";
             }
           }
         }
         uses apply-advanced;
         leaf enable-all-ifl {
           description "Enable tunneling for all the IFLs under the interface";
           type empty;
         }
         container protocol {
           presence "enable protocol";
           description "Protocols for which mac rewrite need to be enabled";
           uses apply-advanced;
           container stp {
             presence "enable stp";
             description "Enable mac rewrite for STP";
           }
           container vtp {
             presence "enable vtp";
             description "Enable mac rewrite for VTP";
           }
           container cdp {
             presence "enable cdp";
             description "Enable mac rewrite for CDP";
           }
           container pvstp {
             presence "enable pvstp";
             description "Enable mac rewrite for PVSTP+";
           }
         }
       }
     }
   }
   grouping juniper-protocols-ldp {
     uses apply-advanced;
     container traceoptions {
       description "Trace options for LDP";
       uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "error" {
               description "Trace errored packets";
             }
             enum "event" {
               description "Trace LDP state machine events";
             }
             enum "packet-dump" {
               description "Dump the contents of selected packet types";
             }
             enum "packets" {
               description "Trace all LDP packets";
             }
             enum "periodic" {
               description "Trace periodic (hello and keepalive) packets";
             }
             enum "initialization" {
               description "Trace initialization packets";
             }
             enum "notification" {
               description "Trace notification packets";
             }
             enum "address" {
               description "Trace address packets";
             }
             enum "label" {
               description "Trace label packets";
             }
             enum "binding" {
               description "Trace label binding state";
             }
             enum "path" {
               description "Trace label path state";
             }
             enum "ppmd" {
               description "Trace state and events for ppmd process";
             }
             enum "nsr-synchronization" {
               description "Trace NSR synchronization events";
             }
             enum "link-protection" {
               description "Trace link protection events";
             }
             enum "p2mp-nsr-synchronization" {
               description "Trace p2mp NSR synchronization events";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
         container filter {
           description "Filter to apply to this flag";
           presence "enable filter";
           uses ldp_filter_obj;
         }
       }
     }
     container traffic-statistics {
       description "Collect statistics for LDP label-switched paths";
       uses apply-advanced;
       container file {
         description "Statistics file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       leaf interval {
         description "Time to collect statistics (seconds)";
         type union {
           type string {
             pattern "<.*>|$.*";
           }
           type int32 {
             range "60 .. 65535";
           }
         }
       }
       leaf no-penultimate-hop {
         description "No penultimate hop statistics collection";
         type empty;
       }
     }
     container graceful-restart {
       description "Configure graceful restart attributes";
       uses apply-advanced;
       choice enable-disable {
         case case_1 {
           leaf disable {
             description "Disable graceful restart";
             type empty;
           }
         }
       }
       leaf helper-disable {
         description "Disable the graceful restart helper capability";
         type empty;
       }
       leaf recovery-time {
         description "Time required for recovery";
         units "seconds";
         type union {
           type string {
             pattern "<.*>|$.*";
           }
           type uint32 {
             range "120 .. 1800";
           }
         }
       }
       leaf maximum-neighbor-recovery-time {
         description "Maximum time stale mappings are maintained";
         units "seconds";
         type union {
           type string {
             pattern "<.*>|$.*";
           }
           type uint32 {
             range "140 .. 1900";
           }
         }
       }
       leaf reconnect-time {
         description "Time required to reestablish session after graceful restart";
         units "seconds";
         type union {
           type string {
             pattern "<.*>|$.*";
           }
           type uint32 {
             range "30 .. 300";
           }
         }
       }
       leaf maximum-neighbor-reconnect-time {
         description "Maximum reconnect time allowed from a restarting neighbor";
         units "seconds";
         type union {
           type string {
             pattern "<.*>|$.*";
           }
           type uint32 {
             range "30 .. 300";
           }
         }
       }
     }
     container auto-targeted-session {
       presence "enable auto-targeted-session";
       description "Configure auto targeted session parameters";
       uses apply-advanced;
       leaf teardown-delay {
         description "Auto targeted session tear down delay";
         default "90";
         units "seconds";
         type union {
           type string {
             pattern "<.*>|$.*";
           }
           type uint32 {
             range "1 .. 300";
           }
         }
       }
       leaf maximum-sessions {
         description "Auto targeted maximum sessions";
         default "100";
         type union {
           type string {
             pattern "<.*>|$.*";
           }
           type uint32 {
             range "1 .. 1000";
           }
         }
       }
       leaf no-rlfa {
         description "Do not allow RLFA in auto targeted sessions";
         type empty;
       }
       leaf no-dynamic-tunnels {
         description "Do not allow dynamic tunnels in auto targeted sessions";
         type empty;
       }
     }
     leaf preference {
       description "Route preference";
       type union {
         type uint32;
         type string {
           pattern "<.*>|$.*";
         }
       }
     }
     leaf no-forwarding {
       description "Do not use LDP ingress routes for forwarding";
       type empty;
     }
     leaf rib-group {
       description "Routing table group for importing ingress routes";
       type string;
     }
     leaf l2-smart-policy {
       description "Do not export or import Layer 3 FECs for Layer 2 sessions";
       type empty;
     }
     leaf track-igp-metric {
       description "Track the IGP metric";
       type empty;
     }
     leaf strict-targeted-hellos {
       description "Do not send targeted hellos to unconfigured neighbors";
       type empty;
     }
     container longest-match {
       presence "enable longest-match";
       description "Configure longest match";
       uses apply-advanced;
       leaf-list policy {
         ordered-by user;
         description "Longest match import policy";
         type jt:policy-algebra;
       }
     }
     leaf-list import {
       ordered-by user;
       description "Import policy";
       type jt:policy-algebra;
     }
     leaf-list export {
       ordered-by user;
       description "Export policy";
       type jt:policy-algebra;
     }
     leaf-list egress-policy {
       ordered-by user;
       description "Configure LSP egress policy";
       type jt:policy-algebra;
     }
     leaf-list dod-request-policy {
       ordered-by user;
       description "Configure DoD label request policy";
       type jt:policy-algebra;
     }
     container next-hop {
       description "LDP next-hop control";
       uses apply-advanced;
       container merged {
         description "Merged next hop";
         uses apply-advanced;
         leaf-list policy {
           ordered-by user;
           description "Merged next-hop policy";
           type jt:policy-algebra;
         }
       }
       container no-rsvp-tunneling {
         description "No rsvp tunneling";
         uses apply-advanced;
         leaf-list policy {
           ordered-by user;
           description "No rsvp tunneling next-hop policy";
           type jt:policy-algebra;
         }
       }
     }
     choice mtu-discovery-choice {
       leaf mtu-discovery {
         description "Enable TCP path MTU discovery";
         type empty;
       }
       leaf no-mtu-discovery {
         description "Don't enable TCP path MTU discovery";
         type empty;
       }
     }
     choice deaggregate-choice {
       leaf deaggregate {
         description "Deaggregate FECs into separate labels";
         type empty;
       }
       leaf no-deaggregate {
         description "Don't deaggregate FECs into separate labels";
         type empty;
       }
     }
     leaf explicit-null {
       description "Advertise the EXPLICIT_NULL label for egress FECs";
       type empty;
     }
     leaf label-withdrawal-delay {
       description "Delay label withdrawal for FECs to avoid label churn";
       default "60";
       units "seconds";
       type union {
         type string {
           pattern "<.*>|$.*";
         }
         type uint32 {
           range "0 .. 120";
         }
       }
     }
     container make-before-break {
       presence "enable make-before-break";
       description "Configure make before break";
       uses apply-advanced;
       leaf timeout {
         description "Make before break timeout";
         default "30";
         units "seconds";
         type union {
           type string {
             pattern "<.*>|$.*";
           }
           type uint32 {
             range "1 .. 300";
           }
         }
       }
       leaf switchover-delay {
         description "Make before break switchover delay";
         default "3";
         units "seconds";
         type union {
           type string {
             pattern "<.*>|$.*";
           }
           type uint32 {
             range "1 .. 300";
           }
         }
       }
     }
     container transport-address {
       description "Address used for TCP sessions";
       choice address-choice {
         case case_1 {
           leaf router-id {
             description "Use router ID for TCP connections";
             type empty;
           }
         }
         case case_2 {
           leaf interface {
             description "Use interface address for TCP connections";
             type empty;
           }
         }
         case case_3 {
           leaf address {
             description "Use specified address for TCP connections";
             type jt:ipaddr;
           }
         }
       }
     }
     leaf keepalive-interval {
       description "Keepalive interval (seconds)";
       type union {
         type string {
           pattern "<.*>|$.*";
         }
         type uint32 {
           range "1 .. 65535";
         }
       }
     }
     leaf keepalive-timeout {
       description "Keepalive timeout (seconds)";
       type union {
         type string {
           pattern "<.*>|$.*";
         }
         type uint32 {
           range "1 .. 65535";
         }
       }
     }
     list interface {
       key name;
       description "Enable LDP on this interface";
       leaf name {
         description "Interface name";
         type union {
           type jt:interface-name;
           type string {
             pattern "<.*>|$.*";
           }
         }
       }
       uses apply-advanced;
       choice enable-disable {
         case case_1 {
           leaf disable {
             description "Disable LDP on this interface";
             type empty;
           }
         }
       }
       leaf hello-interval {
         description "Hello interval (seconds)";
         type union {
           type string {
             pattern "<.*>|$.*";
           }
           type uint32 {
             range "1 .. 65535";
           }
         }
       }
       leaf hold-time {
         description "Hello hold time (seconds)";
         type union {
           type string {
             pattern "<.*>|$.*";
           }
           type uint32 {
             range "1 .. 65535";
           }
         }
       }
       container link-protection {
         presence "enable link-protection";
         description "Enable link protection to protect interface for link faults only";
         uses apply-advanced;
         choice enable-disable {
           case case_1 {
             leaf disable {
               description "Disable link-protection";
               type empty;
             }
           }
         }
         leaf dynamic-rsvp-lsp {
           description "Enable setup of dynamic rsvp lsp for link protection";
           type empty;
         }
       }
       container transport-address {
         description "Address used for TCP sessions";
         choice address-choice {
           case case_1 {
             leaf router-id {
               description "Use router ID for TCP connections";
               type empty;
             }
           }
           case case_2 {
             leaf interface {
               description "Use interface address for TCP connections";
               type empty;
             }
           }
           case case_3 {
             leaf address {
               description "Use specified address for TCP connections";
               type jt:ipaddr;
             }
           }
         }
       }
       choice allow-subnet-mismatch-choice {
         leaf allow-subnet-mismatch {
           description "Allow subnet mismatch for source address in hello packet";
           type empty;
         }
         leaf no-allow-subnet-mismatch {
           description "Don't allow subnet mismatch for source address in hello packet";
           type empty;
         }
       }
     }
     list neighbor {
       key name;
       description "Configure a remote LDP neighbor";
       leaf name {
         description "Neighbor address";
         type jt:ipaddr;
       }
       uses apply-advanced;
     }
     list session {
       key name;
       description "Configure session parameters";
       leaf name {
         description "Session destination address";
         type jt:ipaddr;
       }
       uses apply-advanced;
       leaf authentication-key {
         description "MD5 authentication key";
         type string {
           length "1 .. 126";
         }
       }
       leaf authentication-algorithm {
         description "Authentication algorithm name";
         default "hmac-sha-1-96";
         type enumeration {
           enum "md5" {
             description "Message Digest 5";
           }
           enum "hmac-sha-1-96" {
             description "Hash-based Message Authentication Code (SHA1) (96 bits)";
           }
           enum "aes-128-cmac-96" {
             description "Cipher-based Message Authentication Code (AES128) (96 bits)";
           }
         }
       }
       leaf authentication-key-chain {
         description "Key chain name";
         type string {
           length "1 .. 128";
         }
       }
       leaf downstream-on-demand {
         description "Configure downstream on demand label distribution mode";
         type empty;
       }
       leaf transport-address {
         description "Address used for TCP sessions to the neighbor";
         type jt:ipaddr;
       }
       choice mtu-discovery-choice {
         leaf mtu-discovery {
           description "Enable TCP path MTU discovery";
           type empty;
         }
         leaf no-mtu-discovery {
           description "Don't enable TCP path MTU discovery";
           type empty;
         }
       }
     }
     list session-group {
       key name;
       description "Configure session group parameters";
       leaf name {
         description "Session destination address/prefix length";
         type jt:ipprefix;
       }
       uses apply-advanced;
       leaf authentication-key {
         description "MD5 authentication key";
         type string {
           length "1 .. 126";
         }
       }
       leaf authentication-algorithm {
         description "Authentication algorithm name";
         default "hmac-sha-1-96";
         type enumeration {
           enum "md5" {
             description "Message Digest 5";
           }
           enum "hmac-sha-1-96" {
             description "Hash-based Message Authentication Code (SHA1) (96 bits)";
           }
           enum "aes-128-cmac-96" {
             description "Cipher-based Message Authentication Code (AES128) (96 bits)";
           }
         }
       }
       leaf authentication-key-chain {
         description "Key chain name";
         type string {
           length "1 .. 128";
         }
       }
       leaf downstream-on-demand {
         description "Configure downstream on demand label distribution mode";
         type empty;
       }
       leaf transport-address {
         description "Address used for TCP sessions to the neighbor";
         type jt:ipaddr;
       }
       choice mtu-discovery-choice {
         leaf mtu-discovery {
           description "Enable TCP path MTU discovery";
           type empty;
         }
         leaf no-mtu-discovery {
           description "Don't enable TCP path MTU discovery";
           type empty;
         }
       }
     }
     container session-protection {
       presence "enable session-protection";
       description "Configure session protection";
       leaf timeout {
         description "Session protection timeout";
         units "seconds";
         type union {
           type string {
             pattern "<.*>|$.*";
           }
           type uint16 {
             range "1 .. 65535";
           }
         }
       }
     }
     container igp-synchronization {
       description "Configure IGP synchronization parameters";
       uses apply-advanced;
       leaf holddown-interval {
         description "Time to hold the up notification to the IGPs";
         units "seconds";
         type union {
           type string {
             pattern "<.*>|$.*";
           }
           type uint32 {
             range "10 .. 60";
           }
         }
       }
     }
     container log-updown {
       description "Logging actions for LSP up/down events";
       uses apply-advanced;
       container trap {
         description "SNMP traps options";
         choice enable-disable {
           case case_1 {
             leaf disable {
               description "Disable LDP LSP up/down trap";
               type empty;
             }
           }
         }
       }
     }
     container policing {
       description "Configure policing for an LDP FEC";
       uses apply-advanced;
       list fec {
         key name;
         ordered-by user;
         description "Forwarding equivalence class";
         leaf name {
           description "Forwarding equivalence class address";
           type jt:ipv4prefix;
         }
         uses apply-advanced;
         leaf ingress-traffic {
           description "Name of filter to use for policing ingress LDP traffic";
           type string {
           }
         }
         leaf transit-traffic {
           description "Name of filter to use for policing transit LDP traffic";
           type string {
           }
         }
       }
     }
     container entropy-label {
       description "Insert entropy label for  a LDP FEC";
       uses apply-advanced;
       leaf-list ingress-policy {
         ordered-by user;
         description "Entropy label ingress policy";
         type jt:policy-algebra;
       }
     }
     container oam {
       description "Configure periodic OAM for a LDP FEC";
       uses apply-advanced;
       leaf-list ingress-policy {
         ordered-by user;
         description "OAM ingress policy";
         type jt:policy-algebra;
       }
       leaf-list bfd-port-egress-policy {
         ordered-by user;
         description "OAM egress policy";
         type jt:policy-algebra;
       }
       list fec {
         key name;
         ordered-by user;
         description "Forwarding equivalence class";
         leaf name {
           description "Forwarding equivalence class address";
           type jt:ipv4prefix;
         }
         uses apply-advanced;
         choice bfd_liveness_detection_type {
           case case_1 {
             container bfd-liveness-detection {
               description "Bidirectional Forwarding Detection (BFD) options";
               uses apply-advanced;
               leaf version {
                 description "BFD protocol version number";
                 default "automatic";
                 type enumeration {
                   enum "0" {
                     description "BFD version 0 (deprecated)";
                   }
                   enum "1" {
                     description "BFD version 1";
                   }
                   enum "automatic" {
                     description "Choose BFD version automatically";
                   }
                 }
               }
               leaf minimum-interval {
                 description "Minimum transmit and receive interval";
                 units "milliseconds";
                 type union {
                   type string {
                     pattern "<.*>|$.*";
                   }
                   type uint32 {
                     range "1 .. 255000";
                   }
                 }
               }
               leaf minimum-transmit-interval {
                 description "Minimum transmit interval";
                 status deprecated;
                 units "milliseconds";
                 type union {
                   type string {
                     pattern "<.*>|$.*";
                   }
                   type uint32 {
                     range "1 .. 255000";
                   }
                 }
               }
               leaf minimum-receive-interval {
                 description "Minimum receive interval";
                 units "milliseconds";
                 type union {
                   type string {
                     pattern "<.*>|$.*";
                   }
                   type uint32 {
                     range "1 .. 255000";
                   }
                 }
               }
               leaf multiplier {
                 description "Detection time multiplier";
                 default "3";
                 type union {
                   type string {
                     pattern "<.*>|$.*";
                   }
                   type uint32 {
                     range "1 .. 255";
                   }
                 }
               }
               choice adaptation-choice {
                 case case_1 {
                   leaf no-adaptation {
                     description "Disable adaptation";
                     type empty;
                   }
                 }
               }
               container transmit-interval {
                 description "Transmit-interval options";
                 uses apply-advanced;
                 leaf minimum-interval {
                   description "Minimum transmit interval";
                   units "milliseconds";
                   type union {
                     type string {
                       pattern "<.*>|$.*";
                     }
                     type uint32 {
                       range "1 .. 255000";
                     }
                   }
                 }
                 leaf threshold {
                   description "High transmit interval triggering a trap";
                   units "milliseconds";
                   type union {
                     type uint32;
                     type string {
                       pattern "<.*>|$.*";
                     }
                   }
                 }
               }
               container detection-time {
                 description "Detection-time options";
                 uses apply-advanced;
                 leaf threshold {
                   description "High detection-time triggering a trap";
                   units "milliseconds";
                   type union {
                     type uint32;
                     type string {
                       pattern "<.*>|$.*";
                     }
                   }
                 }
               }
               leaf ecmp {
                 description "Enable equal cost multipath (ECMP) support for BFD";
                 type empty;
               }
               container failure-action {
                 description "Action to take when BFD session goes down";
                 choice action-choice {
                   case case_1 {
                     leaf remove-route {
                       description "Remove LDP route from the ribs";
                       type empty;
                     }
                   }
                   case case_2 {
                     leaf remove-nexthop {
                       description "Remove LDP nexthop from the route";
                       type empty;
                     }
                   }
                 }
               }
               leaf holddown-interval {
                 description "Time to hold the session-UP notification to the client";
                 default "0";
                 units "milliseconds";
                 type union {
                   type string {
                     pattern "<.*>|$.*";
                   }
                   type uint32 {
                     range "0 .. 255000";
                   }
                 }
               }
               leaf no-router-alert-option {
                 description "Do not set Router-Alert options in IP header for MPLS-BFD";
                 type empty;
               }
               leaf use-ip-ttl-1 {
                 description "Set TTL value to 1 in IP header for MPLS-BFD";
                 type empty;
               }
             }
           }
           case case_2 {
             leaf no-bfd-liveness-detection {
               description "Disable BFD liveness detection";
               type empty;
             }
           }
         }
         container periodic-traceroute {
           presence "enable periodic-traceroute";
           description "Configure periodic traceroute";
           uses apply-advanced;
           leaf frequency {
             description "Time between traceroute attempts";
             units "minutes";
             type union {
               type string {
                 pattern "<.*>|$.*";
               }
               type uint16 {
                 range "15 .. 120";
               }
             }
           }
           leaf ttl {
             description "Maximum time-to-live value";
             type union {
               type string {
                 pattern "<.*>|$.*";
               }
               type uint16 {
                 range "1 .. 255";
               }
             }
           }
           leaf retries {
             description "Number of times to resend probe";
             type union {
               type string {
                 pattern "<.*>|$.*";
               }
               type uint16 {
                 range "1 .. 9";
               }
             }
           }
           leaf wait {
             description "Time to wait before resending probe";
             units "seconds";
             type union {
               type string {
                 pattern "<.*>|$.*";
               }
               type uint16 {
                 range "5 .. 15";
               }
             }
           }
           leaf paths {
             description "Maximum number of paths to traverse";
             type union {
               type string {
                 pattern "<.*>|$.*";
               }
               type uint16 {
                 range "1 .. 255";
               }
             }
           }
           leaf source {
             description "Source address to use when sending probes";
             type jt:ipv4addr;
           }
           leaf exp {
             description "Class-of-service value to use when sending probes";
             type union {
               type string {
                 pattern "<.*>|$.*";
               }
               type uint16 {
                 range "0 .. 7";
               }
             }
           }
           leaf fanout {
             description "Maximum number of nexthops to search per node";
             type union {
               type string {
                 pattern "<.*>|$.*";
               }
               type uint16 {
                 range "1 .. 64";
               }
             }
           }
           leaf disable {
             description "Disable periodic traceroute for a FEC";
             type empty;
           }
         }
       }
       container bfd-liveness-detection {
         description "Bidirectional Forwarding Detection (BFD) options";
         uses apply-advanced;
         leaf version {
           description "BFD protocol version number";
           default "automatic";
           type enumeration {
             enum "0" {
               description "BFD version 0 (deprecated)";
             }
             enum "1" {
               description "BFD version 1";
             }
             enum "automatic" {
               description "Choose BFD version automatically";
             }
           }
         }
         leaf minimum-interval {
           description "Minimum transmit and receive interval";
           units "milliseconds";
           type union {
             type string {
               pattern "<.*>|$.*";
             }
             type uint32 {
               range "1 .. 255000";
             }
           }
         }
         leaf minimum-transmit-interval {
           description "Minimum transmit interval";
           status deprecated;
           units "milliseconds";
           type union {
             type string {
               pattern "<.*>|$.*";
             }
             type uint32 {
               range "1 .. 255000";
             }
           }
         }
         leaf minimum-receive-interval {
           description "Minimum receive interval";
           units "milliseconds";
           type union {
             type string {
               pattern "<.*>|$.*";
             }
             type uint32 {
               range "1 .. 255000";
             }
           }
         }
         leaf multiplier {
           description "Detection time multiplier";
           default "3";
           type union {
             type string {
               pattern "<.*>|$.*";
             }
             type uint32 {
               range "1 .. 255";
             }
           }
         }
         choice adaptation-choice {
           case case_1 {
             leaf no-adaptation {
               description "Disable adaptation";
               type empty;
             }
           }
         }
         container transmit-interval {
           description "Transmit-interval options";
           uses apply-advanced;
           leaf minimum-interval {
             description "Minimum transmit interval";
             units "milliseconds";
             type union {
               type string {
                 pattern "<.*>|$.*";
               }
               type uint32 {
                 range "1 .. 255000";
               }
             }
           }
           leaf threshold {
             description "High transmit interval triggering a trap";
             units "milliseconds";
             type union {
               type uint32;
               type string {
                 pattern "<.*>|$.*";
               }
             }
           }
         }
         container detection-time {
           description "Detection-time options";
           uses apply-advanced;
           leaf threshold {
             description "High detection-time triggering a trap";
             units "milliseconds";
             type union {
               type uint32;
               type string {
                 pattern "<.*>|$.*";
               }
             }
           }
         }
         leaf ecmp {
           description "Enable equal cost multipath (ECMP) support for BFD";
           type empty;
         }
         container failure-action {
           description "Action to take when BFD session goes down";
           choice action-choice {
             case case_1 {
               leaf remove-route {
                 description "Remove LDP route from the ribs";
                 type empty;
               }
             }
             case case_2 {
               leaf remove-nexthop {
                 description "Remove LDP nexthop from the route";
                 type empty;
               }
             }
           }
         }
         leaf holddown-interval {
           description "Time to hold the session-UP notification to the client";
           default "0";
           units "milliseconds";
           type union {
             type string {
               pattern "<.*>|$.*";
             }
             type uint32 {
               range "0 .. 255000";
             }
           }
         }
         leaf no-router-alert-option {
           description "Do not set Router-Alert options in IP header for MPLS-BFD";
           type empty;
         }
         leaf use-ip-ttl-1 {
           description "Set TTL value to 1 in IP header for MPLS-BFD";
           type empty;
         }
       }
       container periodic-traceroute {
         presence "enable periodic-traceroute";
         description "Configure periodic traceroute";
         uses apply-advanced;
         leaf frequency {
           description "Time between traceroute attempts";
           units "minutes";
           type union {
             type string {
               pattern "<.*>|$.*";
             }
             type uint16 {
               range "15 .. 120";
             }
           }
         }
         leaf ttl {
           description "Maximum time-to-live value";
           type union {
             type string {
               pattern "<.*>|$.*";
             }
             type uint16 {
               range "1 .. 255";
             }
           }
         }
         leaf retries {
           description "Number of times to resend probe";
           type union {
             type string {
               pattern "<.*>|$.*";
             }
             type uint16 {
               range "1 .. 9";
             }
           }
         }
         leaf wait {
           description "Time to wait before resending probe";
           units "seconds";
           type union {
             type string {
               pattern "<.*>|$.*";
             }
             type uint16 {
               range "5 .. 15";
             }
           }
         }
         leaf paths {
           description "Maximum number of paths to traverse";
           type union {
             type string {
               pattern "<.*>|$.*";
             }
             type uint16 {
               range "1 .. 255";
             }
           }
         }
         leaf source {
           description "Source address to use when sending probes";
           type jt:ipv4addr;
         }
         leaf exp {
           description "Class-of-service value to use when sending probes";
           type union {
             type string {
               pattern "<.*>|$.*";
             }
             type uint16 {
               range "0 .. 7";
             }
           }
         }
         leaf fanout {
           description "Maximum number of nexthops to search per node";
           type union {
             type string {
               pattern "<.*>|$.*";
             }
             type uint16 {
               range "1 .. 64";
             }
           }
         }
       }
       leaf lsp-ping-interval {
         description "Time interval between LSP ping messages";
         default "60";
         units "seconds";
         type union {
           type string {
             pattern "<.*>|$.*";
           }
           type uint16 {
             range "30 .. 3600";
           }
         }
       }
     }
     container targeted-hello {
       description "Configure targeted hello parameters";
       uses apply-advanced;
       leaf hello-interval {
         description "Hello interval (seconds)";
         type union {
           type string {
             pattern "<.*>|$.*";
           }
           type uint32 {
             range "1 .. 65535";
           }
         }
       }
       leaf hold-time {
         description "Hold interval (seconds)";
         type union {
           type string {
             pattern "<.*>|$.*";
           }
           type uint32 {
             range "1 .. 65535";
           }
         }
       }
     }
     container p2mp {
       presence "enable p2mp";
       description "Advertise P2MP capability to peers";
       uses apply-advanced;
       container recursive {
         description "Configure P2MP recursive parameters";
         uses apply-advanced;
         leaf route {
           description "Allow recursive route resolution to signal P2MP FEC";
           type empty;
         }
       }
       list root-address {
         key name;
         description "Configure the root address of P2MP LSP";
         leaf name {
           description "Root address of the P2MP LSP";
           type jt:ipaddr;
         }
         uses apply-advanced;
         list lsp-id {
           key name;
           description "Configure the generic LSP identifier";
           leaf name {
             description "Generic LSP identifier value";
             type union {
               type string {
                 pattern "<.*>|$.*";
               }
               type uint32 {
                 range "1 .. 65535";
               }
             }
           }
           uses apply-advanced;
         }
         list group-address {
           key name;
           description "IPv4/Ipv6 group address for mLDP LSP";
           leaf name {
             description "IPv4/Ipv6 group address";
             type jt:ipaddr;
           }
           uses apply-advanced;
           list source-address {
             key name;
             description "IPv4/Ipv6 source address";
             leaf name {
               description "IPv4/Ipv6 source address for mLDP LSP";
               type jt:ipaddr;
             }
             uses apply-advanced;
           }
         }
       }
       leaf no-rsvp-tunneling {
         description "Do not allow LDP P2MP to use RSVP-TE LSPs for tunneling";
         type empty;
       }
     }
     container sr-mapping-client {
       presence "enable sr-mapping-client";
       description "Enable LDP to SR mapping-client functionality";
       uses apply-advanced;
       leaf-list policy {
         ordered-by user;
         description "SR mapping-client policy";
         type jt:policy-algebra;
       }
     }
     leaf upstream-label-assignment {
       description "Allow Upstream Label Assignment capability";
       type empty;
     }
     list family {
       key name;
       ordered-by user;
       description "Address family";
       leaf name {
         type enumeration {
           enum "inet" {
             description "IPv4 family";
           }
           enum "inet6" {
             description "IPv6 family";
           }
         }
       }
       uses apply-advanced;
     }
     leaf transport-preference {
       description "TCP transport preference";
       type enumeration {
         enum "ipv4" {
           description "Use IPv4 for TCP connections";
         }
         enum "ipv6" {
           description "Use IPv6 for TCP connections";
         }
       }
     }
     container dual-transport {
       presence "enable dual-transport";
       description "Use separate IPv4 and IPv6 TCP transport";
       uses apply-advanced;
       leaf inet-lsr-id {
         description "LSR identifier for address family inet";
         type jt:ipv4addr;
       }
       leaf inet6-lsr-id {
         description "LSR identifier for address family inet6";
         type jt:ipv4addr;
       }
     }
   }
   grouping juniper-protocols-lmp {
     uses apply-advanced;
     list te-link {
       key name;
       ordered-by user;
       description "Traffic engineering link";
       leaf name {
         description "Name of TE link";
         type string;
       }
       uses apply-advanced;
       leaf local-address {
         description "Address of the local end of the link";
         type jt:ipaddr;
       }
       leaf remote-address {
         description "Address of the remote end of the link";
         type jt:ipaddr;
       }
       leaf remote-id {
         description "Link ID for the remote end of the link";
         type union {
           type string {
             pattern "<.*>|$.*";
           }
           type uint32 {
             range "1 .. 4294967295";
           }
         }
       }
       leaf te-metric {
         description "Traffic engineering metric of the link";
         type union {
           type string {
             pattern "<.*>|$.*";
           }
           type uint32 {
             range "1 .. 65535";
           }
         }
       }
       choice enable-disable {
         case case_1 {
           leaf disable {
             description "Disable TE link";
             type empty;
           }
         }
       }
       container ethernet-vlan {
         presence "enable ethernet-vlan";
         description "TE link used for setup of  L2 VLAN LSP";
         uses apply-advanced;
         leaf-list vlan-id-range {
           description "VLAN id";
           type jt:vlan-range;
           max-elements 1;
         }
       }
       choice resource-option {
         case case_1 {
           list interface {
             key name;
             ordered-by user;
             description "Member interface of TE link";
             leaf name {
               description "Interface name";
               type union {
                 type jt:interface-device;
                 type string {
                   pattern "<.*>|$.*";
                 }
               }
             }
             uses apply-advanced;
             leaf local-address {
               description "Local address of the resource";
               type jt:ipaddr;
             }
             leaf remote-address {
               description "Remote address of the resource";
               type jt:ipaddr;
             }
             leaf remote-id {
               description "Interface ID for the remote end of the resource";
               type union {
                 type string {
                   pattern "<.*>|$.*";
                 }
                 type uint32 {
                   range "1 .. 4294967295";
                 }
               }
             }
             choice enable-disable {
               case case_1 {
                 leaf disable {
                   description "Disable resource on this TE link";
                   type empty;
                 }
               }
             }
           }
         }
         case case_2 {
           list label-switched-path {
             key name;
             ordered-by user;
             description "Member forwarding adjacency LSP of TE link";
             max-elements 1;
             leaf name {
               description "Name of label-switched path";
               type string;
             }
             uses apply-advanced;
             leaf local-address {
               description "Local address of the resource";
               type jt:ipaddr;
             }
             leaf remote-address {
               description "Remote address of the resource";
               type jt:ipaddr;
             }
             leaf remote-id {
               description "Interface ID for the remote end of the resource";
               type union {
                 type string {
                   pattern "<.*>|$.*";
                 }
                 type uint32 {
                   range "1 .. 4294967295";
                 }
               }
             }
             choice enable-disable {
               case case_1 {
                 leaf disable {
                   description "Disable resource on this TE link";
                   type empty;
                 }
               }
             }
           }
         }
       }
     }
     list peer {
       key name;
       ordered-by user;
       description "Define a network or LMP peer";
       leaf name {
         description "Name of peer";
         type string;
       }
       uses apply-advanced;
       leaf address {
         description "Address of peer";
         type jt:ipaddr;
       }
       container lmp-protocol {
         presence "enable lmp-protocol";
         description "LMP protocol attributes";
         uses apply-advanced;
         leaf hello-interval {
           description "Interval between Hello messages";
           units "milliseconds";
           type union {
             type string {
               pattern "<.*>|$.*";
             }
             type uint32 {
               range "150 .. 21845";
             }
           }
         }
         leaf hello-dead-interval {
           description "Delay for control channel shutdown when no Hello received";
           units "milliseconds";
           type union {
             type string {
               pattern "<.*>|$.*";
             }
             type uint32 {
               range "500 .. 65535";
             }
           }
         }
         leaf retransmission-interval {
           description "Minimum time before retransmitting a message";
           units "milliseconds";
           type union {
             type string {
               pattern "<.*>|$.*";
             }
             type uint32 {
               range "500 .. 300000";
             }
           }
         }
         leaf retry-limit {
           description "Number of times to retransmit a message";
           type union {
             type string {
               pattern "<.*>|$.*";
             }
             type uint32 {
               range "3 .. 1000";
             }
           }
         }
         leaf passive {
           description "Do not send Config messages to peer";
           type empty;
         }
       }
       leaf-list control-channel {
         ordered-by user;
         description "Control channel interfaces by priority";
         type union {
           type jt:interface-name;
           type string {
             pattern "<.*>|$.*";
           }
         }
       }
       list lmp-control-channel {
         key name;
         ordered-by user;
         description "Control channel IDs";
         uses lmp_control_channel_type;
       }
       leaf-list te-link {
         ordered-by user;
         description "List of TE links managed by this peer";
         type string;
       }
     }
     container traceoptions {
       description "LMP trace options";
       uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "init" {
               description "Trace initialization events";
             }
             enum "show" {
               description "Trace show command servicing";
             }
             enum "route-socket" {
               description "Trace route-socket events";
             }
             enum "parse" {
               description "Trace parser processing";
             }
             enum "process" {
               description "Trace general configuration processing";
             }
             enum "server" {
               description "Trace server processing";
             }
             enum "routing" {
               description "Trace routing protocols interworking";
             }
             enum "packets" {
               description "Trace packet processing";
             }
             enum "hello-packets" {
               description "Trace hello packet processing";
             }
             enum "state" {
               description "Trace state transitions";
             }
             enum "nsr-synchronization" {
               description "Trace mirror and nsr transitions";
             }
             enum "all" {
               description "Trace everything";
             }
           }
         }
         leaf send {
           description "Trace transmitted packets";
           status deprecated;
           type empty;
         }
         leaf receive {
           description "Trace received packets";
           status deprecated;
           type empty;
         }
         leaf detail {
           description "Trace detailed information";
           status deprecated;
           type empty;
         }
         leaf disable {
           description "Disable this trace flag";
           status deprecated;
           type empty;
         }
       }
     }
   }
   grouping juniper-protocols-mpls {
     description "Multiprotocol Label Switching options";
     uses apply-advanced;
     choice enable-disable {
       case case_1 {
         leaf disable {
           description "Disable MPLS";
           type empty;
         }
       }
     }
     list lsp-external-controller {
       key name;
       ordered-by user;
       description "External path computing entity";
       leaf name {
         description "Name of the external path computing entity";
         type string {
         }
       }
       uses apply-advanced;
       container label-switched-path-template {
         description "Template for externally provisioned LSP parameters";
         uses apply-advanced;
         choice dynamic-template {
           case case_1 {
             leaf template-name {
               description "Name of point-to-point LSP template";
               type string {
                 length "1 .. 32";
               }
             }
           }
           case case_2 {
             leaf default-template {
               description "Use default parameters";
               type empty;
             }
           }
         }
       }
       container label-switched-path-p2mp-template {
         description "Template for externally provisioned P2MP LSP parameters";
         uses apply-advanced;
         choice dynamic-template {
           case case_1 {
             leaf template-name {
               description "Name of point-to-multipoint LSP template";
               type string {
                 length "1 .. 32";
               }
             }
           }
           case case_2 {
             leaf default-template {
               description "Use default parameters";
               type empty;
             }
           }
         }
       }
       list pce-controlled-lsp {
         key name;
         ordered-by user;
         description "Template for externally provisioned LSP using regular expression";
         leaf name {
           description "Template regular expression";
           type string {
           }
         }
         uses apply-advanced;
         container label-switched-path-template {
           description "Template for externally provisioned LSP parameters";
           uses apply-advanced;
           leaf template-name {
             description "Name of point-to-point LSP template";
             type string {
               length "1 .. 64";
             }
           }
         }
         container label-switched-path-p2mp-template {
           description "Template for externally provisioned P2MP LSP parameters";
           uses apply-advanced;
           leaf template-name {
             description "Name of point-to-multipoint LSP template";
             type string {
               length "1 .. 64";
             }
           }
         }
       }
     }
     container path-mtu {
       presence "enable path-mtu";
       description "Path MTU configuration";
       uses apply-advanced;
       leaf allow-fragmentation {
         description "If needed, fragment IP before encapsulating in MPLS";
         type empty;
       }
       container rsvp {
         presence "enable rsvp";
         description "RSVP-specific path MTU options";
         uses apply-advanced;
         leaf mtu-signaling {
           description "Enable RSVP path MTU signaling";
           type empty;
         }
       }
     }
     container diffserv-te {
       description "Global diffserv-traffic-engineering options";
       uses apply-advanced;
       leaf bandwidth-model {
         description "Bandwidth constraint model supported";
         type enumeration {
           enum "extended-mam" {
             description "Maximum allocation model with support for E-LSPs";
           }
           enum "mam" {
             description "Maximum allocation model";
           }
           enum "rdm" {
             description "Russian dolls model";
           }
         }
       }
       container te-class-matrix {
         description "Supported combinations of traffic-class and preemption";
         uses apply-advanced;
         container te0 {
           description "Definition for traffic-engineering class te0";
           uses te-class-object;
         }
         container te1 {
           description "Definition for traffic-engineering class te1";
           uses te-class-object;
         }
         container te2 {
           description "Definition for traffic-engineering class te2";
           uses te-class-object;
         }
         container te3 {
           description "Definition for traffic-engineering class te3";
           uses te-class-object;
         }
         container te4 {
           description "Definition for traffic-engineering class te4";
           uses te-class-object;
         }
         container te5 {
           description "Definition for traffic-engineering class te5";
           uses te-class-object;
         }
         container te6 {
           description "Definition for traffic-engineering class te6";
           uses te-class-object;
         }
         container te7 {
           description "Definition for traffic-engineering class te7";
           uses te-class-object;
         }
       }
     }
     container auto-policing {
       description "Automatic policing of LSPs";
       uses apply-advanced;
       list class {
         key name;
         ordered-by user;
         description "Forwarding class";
         leaf name {
           type enumeration {
             enum "all" {
               description "All forwarding classes";
             }
             enum "ct0" {
               description "Forwarding class 0";
             }
             enum "ct1" {
               description "Forwarding class 1";
             }
             enum "ct2" {
               description "Forwarding class 2";
             }
             enum "ct3" {
               description "Forwarding class 3";
             }
           }
         }
         uses apply-advanced;
         choice policing-action {
           case case_1 {
             leaf drop {
               description "Drop packets if bandwidth is exceeded";
               type empty;
             }
           }
           case case_2 {
             leaf loss-priority-high {
               description "Set loss priority to high if bandwidth is exceeded";
               type empty;
             }
           }
           case case_3 {
             leaf loss-priority-low {
               description "Set loss priority to low if bandwidth is exceeded";
               type empty;
             }
           }
         }
       }
     }
     container statistics {
       description "Collect statistics for signaled label-switched paths";
       uses apply-advanced;
       container file {
         presence "enable file";
         description "Statistics file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       leaf interval {
         description "Time to collect statistics (seconds)";
         type union {
           type string {
             pattern "<.*>|$.*";
           }
           type int32 {
             range "1 .. 65535";
           }
         }
       }
       leaf auto-bandwidth {
         description "Enable auto bandwidth allocation";
         type empty;
       }
       leaf no-transit-statistics {
         description "Disable transit LSP statistics collection";
         type empty;
       }
       choice transit-polling-type {
         case case_1 {
           leaf no-transit-statistics-polling {
             description "Disable polling and display of transit lsp statistics";
             status deprecated;
             type empty;
           }
         }
         case case_2 {
           leaf transit-statistics-polling {
             description "Enable polling and display of transit lsp statistics";
             type empty;
           }
         }
       }
       leaf statistics-query-batch-size {
         description "Number of LSPs for which statistics will be queried together";
         type union {
           type string {
             pattern "<.*>|$.*";
           }
           type int32 {
             range "1 .. 25";
           }
         }
       }
     }
     container log-updown {
       description "Logging actions for LSP up/down events";
       uses apply-advanced;
       choice syslog-choice {
         leaf syslog {
           description "Send syslog messages";
           type empty;
         }
         leaf no-syslog {
           description "Don't send syslog messages";
           type empty;
         }
       }
       choice trap-choice {
         case case_1 {
           leaf trap {
             description "Send SNMP traps";
             type empty;
           }
         }
         case case_2 {
           container no-trap {
             presence "enable no-trap";
             description "Don't send SNMP traps";
             uses apply-advanced;
             leaf mpls-lsp-traps {
               description "Dont send mpls lsp up/down traps";
               type empty;
             }
             leaf rfc3812-traps {
               description "Dont send rfc3812 traps";
               type empty;
             }
           }
         }
       }
       leaf trap-path-down {
         description "Send SNMP traps when a path goes down";
         type empty;
       }
       leaf trap-path-up {
         description "Send SNMP traps when a path goes up";
         type empty;
       }
     }
     container optimize-adaptive-teardown {
       description "Post make before break adaptive teardown";
       uses apply-advanced;
       leaf p2p {
         description "Turn on post make before break adaptive teardown for p2p";
         type empty;
       }
       leaf timeout {
         description "Timeout for adaptive teardown to clean up LSP";
         units "seconds";
         type union {
           type string {
             pattern "<.*>|$.*";
           }
           type int32 {
             range "1 .. 65535";
           }
         }
       }
     }
     container traffic-engineering {
       presence "enable traffic-engineering";
       description "Traffic-engineering control";
       uses apply-advanced;
       choice protocols {
         case case_1 {
           leaf bgp {
             description "BGP destinations only";
             type empty;
           }
         }
         case case_2 {
           leaf bgp-igp {
             description "BGP and IGP destinations";
             type empty;
           }
         }
         case case_3 {
           leaf bgp-igp-both-ribs {
             description "BGP and IGP destinations with routes in both routing tables";
             type empty;
           }
         }
         case case_4 {
           leaf mpls-forwarding {
             description "Use MPLS routes for forwarding, not routing";
             type empty;
           }
         }
       }
       container database {
         description "Traffic engineering database";
         uses apply-advanced;
         container import {
           description "Configure TED import parameters";
           uses apply-advanced;
           container igp-topology {
             presence "enable igp-topology";
             description "Download IGP topology into RIB";
             uses apply-advanced;
             leaf bgp-link-state {
               description "Export IGP topology, instead of TE topology, into BGP-LS";
               type empty;
             }
           }
           leaf-list policy {
             ordered-by user;
             description "Configure import policy";
             type jt:policy-algebra;
           }
           leaf identifier {
             description "BGP-TE identifier";
             type union {
               type string {
                 pattern "<.*>|$.*";
               }
               type uint64 {
                 range "2 .. 18446744073709551615";
               }
             }
           }
           leaf bgp-ls-identifier {
             description "BGP-TE domain identifier";
             type union {
               type uint32;
               type string {
                 pattern "<.*>|$.*";
               }
             }
           }
         }
         container export {
           description "Configure TED export related parameters";
           uses apply-advanced;
           leaf-list policy {
             ordered-by user;
             description "Export policy";
             type jt:policy-algebra;
           }
           container credibility {
             description "TED credibility value for entries from BGP-TE";
             uses apply-advanced;
             leaf unknown {
               description "Entries sourced from unknown entities";
               type union {
                 type string {
                   pattern "<.*>|$.*";
                 }
                 type uint32 {
                   range "0 .. 512";
                 }
               }
             }
             leaf direct {
               description "Entries sourced from directly connected links";
               type union {
                 type string {
                   pattern "<.*>|$.*";
                 }
                 type uint32 {
                   range "0 .. 512";
                 }
               }
             }
             leaf static {
               description "Entries sourced from static configuration";
               type union {
                 type string {
                   pattern "<.*>|$.*";
                 }
                 type uint32 {
                   range "0 .. 512";
                 }
               }
             }
             leaf ospf {
               description "Entries sourced from ospf";
               type union {
                 type string {
                   pattern "<.*>|$.*";
                 }
                 type uint32 {
                   range "0 .. 512";
                 }
               }
             }
             leaf isis-level-1 {
               description "Entries sourced from ISIS Level 1";
               type union {
                 type string {
                   pattern "<.*>|$.*";
                 }
                 type uint32 {
                   range "0 .. 512";
                 }
               }
             }
             leaf isis-level-2 {
               description "Entries sourced from ISIS Level 2";
               type union {
                 type string {
                   pattern "<.*>|$.*";
                 }
                 type uint32 {
                   range "0 .. 512";
                 }
               }
             }
           }
         }
       }
     }
     container traceoptions {
       description "Trace options for MPLS";
       uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "connection" {
               description "Trace CCC activity";
             }
             enum "connection-detail" {
               description "Trace CCC activity in detail";
             }
             enum "cspf" {
               description "Trace CSPF computation";
             }
             enum "cspf-node" {
               description "Trace nodes visited during CSPF";
             }
             enum "cspf-link" {
               description "Trace links visited during CSPF";
             }
             enum "cspf-abstract" {
               description "Trace abstract hop based CSPF details";
             }
             enum "state" {
               description "Trace state transitions";
             }
             enum "error" {
               description "Trace error conditions";
             }
             enum "lsping" {
               description "Trace LSP ping packets received";
             }
             enum "graceful-restart" {
               description "Trace graceful-restart-related events";
             }
             enum "nsr-synchronization" {
               description "Trace NSR synchronization events";
             }
             enum "nsr-synchronization-detail" {
               description "Trace NSR synchronization events in detail";
             }
             enum "static" {
               description "Trace static label-switched path";
             }
             enum "egress-protection" {
               description "Trace egress protection events";
             }
             enum "all" {
               description "Trace everything";
             }
             enum "autobw-state" {
               description "Trace autobandwidth events in mpls trace";
             }
             enum "externally-controlled-lsp" {
               description "Trace externally controlled LSP events in mpls trace";
             }
             enum "ted-import" {
               description "Trace leaking TED entries into lsdist.0 table";
             }
             enum "ted-export" {
               description "Trace leaking of entries from lsdist.0 table into TED";
             }
             enum "lsp-history" {
               description "Trace LSP history events";
             }
             enum "abstract-hop" {
               description "Trace abstract hop related events";
             }
           }
         }
       }
     }
     list admin-groups {
       key name;
       ordered-by user;
       description "Administrative groups";
       leaf name {
         description "Group name";
         type string;
       }
       uses apply-advanced;
       leaf group-value {
         description "Group bit position";
         type union {
           type string {
             pattern "<.*>|$.*";
           }
           type uint32 {
             range "0 .. 31";
           }
         }
       }
     }
     leaf advertisement-hold-time {
       description "Time that an 'LSP down' advertisement will be delayed";
       default "5";
       units "seconds";
       type union {
         type string {
           pattern "<.*>|$.*";
         }
         type uint32 {
           range "0 .. 65535";
         }
       }
     }
     leaf rsvp-error-hold-time {
       description "Time that RSVP PathErr events will be remembered";
       default "25";
       units "seconds";
       type union {
         type string {
           pattern "<.*>|$.*";
         }
         type uint32 {
           range "0 .. 240";
         }
       }
     }
     leaf optimize-aggressive {
       description "Run aggressive optimization algorithm based on IGP metric only";
       type empty;
     }
     leaf smart-optimize-timer {
       description "Path optimization interval after a link traversed by the path goes down";
       units "seconds";
       type union {
         type string {
           pattern "<.*>|$.*";
         }
         type int32 {
           range "0 .. 65535";
         }
       }
     }
     leaf optimize-switchover-delay {
       description "Delay before switching LSP to newly optimized path";
       units "seconds";
       type union {
         type string {
           pattern "<.*>|$.*";
         }
         type int32 {
           range "1 .. 900";
         }
       }
     }
     leaf no-propagate-ttl {
       description "Disable TTL propagation from IP to MPLS (on push) and MPLS to IP (on pop)";
       type empty;
     }
     leaf explicit-null {
       description "Advertise the EXPLICIT_NULL label when the router is the egress";
       type empty;
     }
     leaf ipv6-tunneling {
       description "Allow MPLS LSPs to be used for tunneling IPv6 traffic";
       type empty;
     }
     leaf icmp-tunneling {
       description "Allow MPLS LSPs to be used for tunneling ICMP error packets";
       type empty;
     }
     leaf revert-timer {
       description "Hold-down window before reverting back to primary path, 0 means disable";
       units "seconds";
       type union {
         type string {
           pattern "<.*>|$.*";
         }
         type int32 {
           range "0 .. 65535";
         }
       }
     }
     leaf optimize-hold-dead-delay {
       description "Delay before tearing down the old optimized path";
       units "seconds";
       type union {
         type string {
           pattern "<.*>|$.*";
         }
         type int32 {
           range "0 .. 65535";
         }
       }
     }
     leaf expand-loose-hop {
       description "Perform CSPF path computation to expand loose hops";
       type empty;
     }
     leaf mib-mpls-show-p2mp {
       description "Show p2mp tunnels entries in mpls mib walk";
       type empty;
     }
     container bandwidth {
       description "Bandwidth to reserve (bps)";
       uses bandwidth-type;
     }
     leaf class-of-service {
       description "Class-of-service value";
       type union {
         type string {
           pattern "<.*>|$.*";
         }
         type int32 {
           range "0 .. 7";
         }
       }
     }
     leaf no-decrement-ttl {
       description "Do not decrement the TTL within an LSP";
       type empty;
     }
     leaf hop-limit {
       description "Maximum allowed router hops";
       type union {
         type string {
           pattern "<.*>|$.*";
         }
         type int32 {
           range "2 .. 255";
         }
       }
     }
     leaf no-cspf {
       description "Disable automatic path computation";
       type empty;
     }
     leaf admin-down {
       description "Set GMPLS LSP to administrative down state";
       type empty;
     }
     leaf optimize-timer {
       description "Periodical path reoptimizations";
       units "seconds";
       type union {
         type string {
           pattern "<.*>|$.*";
         }
         type int32 {
           range "0 .. 65535";
         }
       }
     }
     leaf preference {
       description "Preference value";
       type union {
         type uint32;
         type string {
           pattern "<.*>|$.*";
         }
       }
     }
     container priority {
       presence "enable priority";
       description "Preemption priorities";
     }
     leaf setup-priority {
       description "Set-up priority";
       type union {
         type string {
           pattern "<.*>|$.*";
         }
         type uint32 {
           range "0 .. 7";
         }
       }
     }
     leaf reservation-priority {
       description "Reservation priority";
       type union {
         type string {
           pattern "<.*>|$.*";
         }
         type uint32 {
           range "0 .. 7";
         }
       }
     }
     choice record-choice {
       leaf record {
         description "Record transit routers";
         type empty;
       }
       leaf no-record {
         description "Don't record transit routers";
         type empty;
       }
     }
     leaf standby {
       description "Keep backup paths in continuous standby";
       type empty;
     }
     leaf exclude-srlg {
       description "Exclude SRLG links for secondary path";
       type empty;
     }
     container admin-group {
       description "Administrative group policy";
       uses admin_group_include_exclude;
     }
     container admin-group-extended {
       description "Extended administrative group policy";
       uses admin_group_include_exclude;
     }
     container oam {
       description "Periodic OAM";
       uses periodic_oam;
     }
     leaf ultimate-hop-popping {
       description "Request ultimate hop popping from egress";
       type empty;
     }
     leaf sync-active-path-bandwidth {
       description "Signal standby path with bandwidth obtained from active path";
       type empty;
     }
     leaf cross-credibility-cspf {
       description "Compute paths across multi-protocol links and nodes";
       type empty;
     }
     list label-switched-path {
       key name;
       ordered-by user;
       description "Label-switched path";
       leaf name {
         description "Name of path";
         type string {
         }
       }
       uses apply-advanced;
       choice enable-disable {
         case case_1 {
           leaf disable {
             description "Disable MPLS label-switched path";
             type empty;
           }
         }
       }
       container traceoptions {
         description "Trace options for MPLS label-switched path";
         uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "cspf" {
                 description "Trace CSPF computation";
               }
               enum "cspf-node" {
                 description "Trace nodes visited during CSPF";
               }
               enum "cspf-link" {
                 description "Trace links visited during CSPF";
               }
               enum "cspf-abstract" {
                 description "Trace abstract hop based CSPF details";
               }
               enum "state" {
                 description "Trace state transitions";
               }
               enum "all" {
                 description "Trace everything";
               }
             }
           }
         }
       }
       leaf no-install-to-address {
         description "Don't install host route 'to' address into routing tables";
         type empty;
       }
       leaf backup {
         description "Use LSP for IGP backup";
         type empty;
       }
       leaf from {
         description "Address of ingress router";
         type jt:ipv4addr;
       }
       container pop-and-forward {
         presence "enable pop-and-forward";
         description "Enable LSP as pop-and-forward with auto-delegation";
       }
       choice label-switched-path-or-template {
         case case_1 {
           leaf to {
             description "Address of egress router";
             type jt:ipv4addr;
           }
         }
         case case_2 {
           leaf template {
             description "Template for dynamic lsp paramaters";
             type empty;
           }
         }
       }
       leaf corouted-bidirectional {
         description "Setup the LSP as a corouted bidirectional LSP";
         type empty;
       }
       leaf corouted-bidirectional-passive {
         description "Associate LSP with incoming corouted bidirectional LSP";
         type empty;
       }
       leaf metric {
         description "Metric value";
         type union {
           type string {
             pattern "<.*>|$.*";
           }
           type uint32 {
             range "1 .. 16777215";
           }
         }
       }
       leaf ldp-tunneling {
         description "Allow LDP to use this LSP for tunneling";
         type empty;
       }
       leaf soft-preemption {
         description "Attempt make-before-break service while preempting this LSP";
         type empty;
       }
       list install {
         key name;
         ordered-by user;
         description "Install prefix";
         leaf name {
           description "Destination prefix";
           type jt:ipprefix;
         }
         leaf active {
           description "Install prefix into forwarding table";
           type empty;
         }
       }
       leaf retry-timer {
         description "Time before retrying the primary path";
         units "seconds";
         type union {
           type string {
             pattern "<.*>|$.*";
           }
           type uint32 {
             range "1 .. 600";
           }
         }
       }
       leaf retry-limit {
         description "Maximum number of times to retry primary path";
         type union {
           type string {
             pattern "<.*>|$.*";
           }
           type uint32 {
             range "0 .. 10000";
           }
         }
       }
       container lsp-attributes {
         description "Attributes for generalized LSP";
         uses apply-advanced;
         leaf signal-bandwidth {
           description "Signal bandwidth for the LSP";
           type enumeration {
             enum "ds1" {
               description "1.544 Mbps";
             }
             enum "vt1-5" {
               description "1.728 Mbps";
             }
             enum "e1" {
               description "2.048 Mbps";
             }
             enum "vt2" {
               description "2.304 Mbps";
             }
             enum "ethernet" {
               description "10 Mbps";
             }
             enum "e3" {
               description "34.368 Mbps";
             }
             enum "ds3" {
               description "44.736 Mbps";
             }
             enum "sts-1" {
               description "51.84 Mbps";
             }
             enum "fastether" {
               description "100.00 Mbps";
             }
             enum "stm-1" {
               description "155.52 Mbps";
             }
             enum "stm-4" {
               description "622.08 Mbps";
             }
             enum "gigether" {
               description "1000.00 Mbps";
             }
             enum "stm-16" {
               description "2488.32 Mbps";
             }
             enum "stm-64" {
               description "9953.28 Mbps";
             }
             enum "10gigether" {
               description "10000.00 Mbps";
             }
             enum "stm-256" {
               description "39813.12 Mbps";
             }
             enum "100gige" {
               description "100000.00 Mbps";
             }
           }
         }
         leaf switching-type {
           description "LSP switching type desired";
           type enumeration {
             enum "psc-1" {
               description "Packet switching";
             }
             enum "lambda" {
               description "Lambda switching";
             }
             enum "fiber" {
               description "Fiber switching";
             }
             enum "tdm" {
               description "TDM switching";
             }
             enum "ethernet-vlan" {
               description "Ethernet VLAN switching";
             }
           }
         }
         leaf encoding-type {
           description "LSP encoding type desired";
           type enumeration {
             enum "packet" {
               description "Packet encoding";
             }
             enum "ethernet" {
               description "Ethernet encoding";
             }
             enum "pdh" {
               description "PDH encoding";
             }
             enum "sonet-sdh" {
               description "SONET-SDH encoding";
             }
           }
         }
         leaf gpid {
           description "Generalized PID";
           type enumeration {
             enum "ipv4" {
             }
             enum "ethernet" {
             }
             enum "ppp" {
             }
             enum "hdlc" {
             }
             enum "pos-no-scrambling-crc-16" {
             }
             enum "pos-no-scrambling-crc-32" {
             }
             enum "pos-scrambling-crc-16" {
             }
             enum "pos-scrambling-crc-32" {
             }
           }
         }
         container upstream-label {
           description "Upstream Label for the bidirectional label-switched path";
           uses apply-advanced;
           leaf vlan-id {
             description "VLAN ID label for the label-switched path";
             type union {
               type string {
                 pattern "<.*>|$.*";
               }
               type uint32 {
                 range "1 .. 4094";
               }
             }
           }
         }
       }
       leaf revert-timer {
         description "Hold-down window before reverting back to primary path, 0 means disable";
         units "seconds";
         type union {
           type string {
             pattern "<.*>|$.*";
           }
           type int32 {
             range "0 .. 65535";
           }
         }
       }
       leaf optimize-hold-dead-delay {
         description "Delay before tearing down the old optimized path";
         units "seconds";
         type union {
           type string {
             pattern "<.*>|$.*";
           }
           type int32 {
             range "0 .. 65535";
           }
         }
       }
       container bandwidth {
         description "Bandwidth to reserve (bps)";
         uses bandwidth-type;
       }
       leaf class-of-service {
         description "Class-of-service value";
         type union {
           type string {
             pattern "<.*>|$.*";
           }
           type int32 {
             range "0 .. 7";
           }
         }
       }
       leaf no-decrement-ttl {
         description "Do not decrement the TTL within an LSP";
         type empty;
       }
       leaf hop-limit {
         description "Maximum allowed router hops";
         type union {
           type string {
             pattern "<.*>|$.*";
           }
           type int32 {
             range "2 .. 255";
           }
         }
       }
       leaf no-cspf {
         description "Disable automatic path computation";
         type empty;
       }
       leaf admin-down {
         description "Set GMPLS LSP to administrative down state";
         type empty;
       }
       leaf optimize-timer {
         description "Periodical path reoptimizations";
         units "seconds";
         type union {
           type string {
             pattern "<.*>|$.*";
           }
           type int32 {
             range "0 .. 65535";
           }
         }
       }
       leaf preference {
         description "Preference value";
         type union {
           type uint32;
           type string {
             pattern "<.*>|$.*";
           }
         }
       }
       container priority {
         presence "enable priority";
         description "Preemption priorities";
       }
       leaf setup-priority {
         description "Set-up priority";
         type union {
           type string {
             pattern "<.*>|$.*";
           }
           type uint32 {
             range "0 .. 7";
           }
         }
       }
       leaf reservation-priority {
         description "Reservation priority";
         type union {
           type string {
             pattern "<.*>|$.*";
           }
           type uint32 {
             range "0 .. 7";
           }
         }
       }
       choice record-choice {
         leaf record {
           description "Record transit routers";
           type empty;
         }
         leaf no-record {
           description "Don't record transit routers";
           type empty;
         }
       }
       leaf standby {
         description "Keep backup paths in continuous standby";
         type empty;
       }
       leaf exclude-srlg {
         description "Exclude SRLG links for secondary path";
         type empty;
       }
       container admin-group {
         description "Administrative group policy";
         uses admin_group_include_exclude;
       }
       container admin-group-extended {
         description "Extended administrative group policy";
         uses admin_group_include_exclude;
       }
       container oam {
         description "Periodic OAM";
         uses periodic_oam;
       }
       leaf ultimate-hop-popping {
         description "Request ultimate hop popping from egress";
         type empty;
       }
       leaf sync-active-path-bandwidth {
         description "Signal standby path with bandwidth obtained from active path";
         type empty;
       }
       leaf cross-credibility-cspf {
         description "Compute paths across multi-protocol links and nodes";
         type empty;
       }
       leaf entropy-label {
         description "Enable entropy label";
         type empty;
       }
       leaf self-ping-duration {
         description "Duration over which to run self-ping (65535 = until success). Default = 1800s";
         units "seconds";
         type union {
           type string {
             pattern "<.*>|$.*";
           }
           type int32 {
             range "1 .. 65535";
           }
         }
       }
       leaf no-self-ping {
         description "Do not run self-ping for this LSP";
         type empty;
       }
       choice cspf-attribute {
         case case_1 {
           leaf random {
             description "Randomly select among equal-cost paths";
             type empty;
           }
         }
         case case_2 {
           leaf least-fill {
             description "Select the least filled among equal-cost paths";
             type empty;
           }
         }
         case case_3 {
           leaf most-fill {
             description "Select the most filled among equal-cost paths";
             type empty;
           }
         }
       }
       leaf description {
         description "Text description of label-switched path";
         type string {
         }
       }
       choice lp-type {
         case case_1 {
           leaf link-protection {
             description "Protect LSP from link faults only";
             type empty;
           }
         }
         case case_2 {
           leaf node-link-protection {
             description "Protect LSP from both link and node faults";
             type empty;
           }
         }
       }
       leaf intra-domain {
         description "Intra-domain LSP";
         status deprecated;
         type empty;
       }
       leaf inter-domain {
         description "Inter-domain LSP";
         type empty;
       }
       leaf adaptive {
         description "Have the LSP smoothly cut over to new routes";
         type empty;
       }
       container fast-reroute {
         presence "enable fast-reroute";
         description "Fast reroute";
         uses apply-advanced;
         leaf hop-limit {
           description "Maximum allowed router hops";
           type union {
             type string {
               pattern "<.*>|$.*";
             }
             type int32 {
               range "0 .. 255";
             }
           }
         }
         choice bw-attribute {
           case case_1 {
             leaf bandwidth {
               description "Bandwidth to reserve (bps)";
               type string;
             }
           }
           case case_2 {
             leaf bandwidth-percent {
               description "Percentage of main path bandwidth to reserve";
               type union {
                 type string {
                   pattern "<.*>|$.*";
                 }
                 type int32 {
                   range "1 .. 100";
                 }
               }
             }
           }
         }
         choice include_any_or_no_include_any {
           case case_1 {
             leaf no-include-any {
               description "Disable include-any checking";
               type empty;
             }
           }
           case case_2 {
             leaf-list include-any {
               ordered-by user;
               description "Groups, one or more of which must be present";
               type string;
             }
           }
         }
         choice include_all_or_no_include_all {
           case case_1 {
             leaf no-include-all {
               description "Disable include-all checking";
               type empty;
             }
           }
           case case_2 {
             leaf-list include-all {
               ordered-by user;
               description "Groups, all of which must be present";
               type string;
             }
           }
         }
         choice exclude_or_no_exclude {
           case case_1 {
             leaf no-exclude {
               description "Disable exclude checking";
               type empty;
             }
           }
           case case_2 {
             leaf-list exclude {
               ordered-by user;
               description "Groups, all of which must be absent";
               type string;
             }
           }
         }
       }
       container p2mp {
         presence "enable p2mp";
         description "Point-to-multipoint label-switched path";
         leaf path_name {
           description "Name of point-to-multipoint LSP";
           type string {
           }
         }
       }
       container auto-bandwidth {
         presence "enable auto-bandwidth";
         description "Do auto bandwidth allocation for this LSP";
         uses apply-advanced;
         leaf adjust-interval {
           description "Time to adjust LSP bandwidth";
           default "86400";
           units "seconds";
           type union {
             type string {
               pattern "<.*>|$.*";
             }
             type uint32 {
               range "300 .. 315360000";
             }
           }
         }
         leaf adjust-threshold {
           description "Percentage change in average LSP utilization to trigger auto-adjustment";
           default "0";
           units "percent";
           type union {
             type string {
               pattern "<.*>|$.*";
             }
             type uint32 {
               range "0 .. 50";
             }
           }
         }
         leaf adjust-threshold-absolute {
           description "Change in average LSP utilization to trigger auto-adjustment";
           default "0";
           units "bps";
           type string;
         }
         leaf adjust-threshold-activate-bandwidth {
           description "Adjusts signaled bw if greater than this value";
           units "bps";
           type string;
         }
         leaf minimum-bandwidth {
           description "Minimum LSP bandwidth";
           units "bps";
           type string;
         }
         leaf maximum-bandwidth {
           description "Maximum LSP bandwidth";
           units "bps";
           type string;
         }
         leaf minimum-bandwidth-adjust-interval {
           description "Duration for which minimum bandwidth will be frozen";
           units "seconds";
           type union {
             type string {
               pattern "<.*>|$.*";
             }
             type uint32 {
               range "300 .. 31536000";
             }
           }
         }
         leaf minimum-bandwidth-adjust-threshold-change {
           description "Change in max average bandwidth to freeze min bandwidth";
           units "percent";
           type union {
             type string {
               pattern "<.*>|$.*";
             }
             type uint32 {
               range "0 .. 100";
             }
           }
         }
         leaf minimum-bandwidth-adjust-threshold-value {
           description "Freeze min bandwidth if max average bandwidth falls below this bw";
           status deprecated;
           units "bps";
           type string;
         }
         leaf monitor-bandwidth {
           description "Monitor LSP bandwidth without adjustments";
           type empty;
         }
         leaf adjust-threshold-overflow-limit {
           description "Number of consecutive overflow samples to trigger auto-adjustment";
           type union {
             type string {
               pattern "<.*>|$.*";
             }
             type uint32 {
               range "1 .. 65535";
             }
           }
         }
         leaf adjust-threshold-underflow-limit {
           description "Number of consecutive underflow samples to trigger auto-adjustment";
           type union {
             type string {
               pattern "<.*>|$.*";
             }
             type uint32 {
               range "1 .. 65535";
             }
           }
         }
         leaf resignal-minimum-bandwidth {
           description "Resignal the LSP using minimum-bandwidth";
           type empty;
         }
         leaf sync-active-path-bandwidth {
           description "Signal standby path with bandwidth obtained from active path";
           type empty;
         }
       }
       container optimize-on-change {
         description "Specify additional re-optimization triggers for this LSP";
         uses apply-advanced;
         leaf link-congestion {
           description "Optimize when a link becomes congested";
           type empty;
         }
       }
       container deselect-on-bandwidth-failure {
         presence "enable deselect-on-bandwidth-failure";
         description "Deselect active path if it cannot meet the bandwidth constraint";
         uses apply-advanced;
         leaf tear-lsp {
           description "Bring down active path when all paths fail to reserve required bandwidth";
           type empty;
         }
       }
       container track-igp-metric {
         description "Track IGP metric for LSP install prefixes";
         uses apply-advanced;
         leaf install-v4-prefixes {
           description "Track IGP metric for IPV4 prefixes";
           type empty;
         }
         leaf install-v6-prefixes {
           description "Track IGP metric for IPV6 prefixes";
           type empty;
         }
       }
       container associate-lsp {
         description "Associate the LSP for OAM";
         uses apply-advanced;
         leaf lsp-name {
           description "Name of assocation LSP";
           type string {
           }
         }
         leaf from {
           description "Address of ingress router of associated LSP";
           type jt:ipv4addr;
         }
       }
       list primary {
         key name;
         ordered-by user;
         description "Preferred path";
         leaf name {
           description "Name of path";
           type string {
           }
         }
         uses apply-advanced;
         container bandwidth {
           description "Bandwidth to reserve (bps)";
           uses bandwidth-type;
         }
         leaf class-of-service {
           description "Class-of-service value";
           type union {
             type string {
               pattern "<.*>|$.*";
             }
             type int32 {
               range "0 .. 7";
             }
           }
         }
         leaf no-decrement-ttl {
           description "Do not decrement the TTL within an LSP";
           type empty;
         }
         leaf hop-limit {
           description "Maximum allowed router hops";
           type union {
             type string {
               pattern "<.*>|$.*";
             }
             type int32 {
               range "2 .. 255";
             }
           }
         }
         leaf no-cspf {
           description "Disable automatic path computation";
           type empty;
         }
         leaf admin-down {
           description "Set GMPLS LSP to administrative down state";
           type empty;
         }
         leaf optimize-timer {
           description "Periodical path reoptimizations";
           units "seconds";
           type union {
             type string {
               pattern "<.*>|$.*";
             }
             type int32 {
               range "0 .. 65535";
             }
           }
         }
         leaf preference {
           description "Preference value";
           type union {
             type uint32;
             type string {
               pattern "<.*>|$.*";
             }
           }
         }
         container priority {
           presence "enable priority";
           description "Preemption priorities";
         }
         leaf setup-priority {
           description "Set-up priority";
           type union {
             type string {
               pattern "<.*>|$.*";
             }
             type uint32 {
               range "0 .. 7";
             }
           }
         }
         leaf reservation-priority {
           description "Reservation priority";
           type union {
             type string {
               pattern "<.*>|$.*";
             }
             type uint32 {
               range "0 .. 7";
             }
           }
         }
         choice record-choice {
           leaf record {
             description "Record transit routers";
             type empty;
           }
           leaf no-record {
             description "Don't record transit routers";
             type empty;
           }
         }
         leaf standby {
           description "Keep backup paths in continuous standby";
           type empty;
         }
         leaf exclude-srlg {
           description "Exclude SRLG links for secondary path";
           type empty;
         }
         container admin-group {
           description "Administrative group policy";
           uses admin_group_include_exclude;
         }
         container admin-group-extended {
           description "Extended administrative group policy";
           uses admin_group_include_exclude;
         }
         container oam {
           description "Periodic OAM";
           uses periodic_oam;
         }
         leaf ultimate-hop-popping {
           description "Request ultimate hop popping from egress";
           type empty;
         }
         leaf sync-active-path-bandwidth {
           description "Signal standby path with bandwidth obtained from active path";
           type empty;
         }
         leaf cross-credibility-cspf {
           description "Compute paths across multi-protocol links and nodes";
           type empty;
         }
         leaf adaptive {
           description "Have the LSP smoothly cut over to new routes";
           type empty;
         }
         leaf select {
           type enumeration {
             enum "manual" {
               description "Manual override as preferred active path, if up and stable";
             }
             enum "unconditional" {
               description "Unconditional override as preferred active path, regardless of up/down status";
             }
           }
         }
         container upstream-label {
           description "Upstream Label for the bidirectional label-switched path";
           uses apply-advanced;
           leaf vlan-id {
             description "VLAN ID label for the label-switched path";
             type union {
               type string {
                 pattern "<.*>|$.*";
               }
               type uint32 {
                 range "1 .. 4094";
               }
             }
           }
         }
         container optimize-on-change {
           description "Specify additional re-optimization triggers for this path";
           uses apply-advanced;
           leaf link-congestion {
             description "Optimize when a link becomes congested";
             type empty;
           }
         }
       }
       list secondary {
         key name;
         ordered-by user;
         description "Backup path";
         leaf name {
           description "Name of path";
           type string {
           }
         }
         uses apply-advanced;
         container bandwidth {
           description "Bandwidth to reserve (bps)";
           uses bandwidth-type;
         }
         leaf class-of-service {
           description "Class-of-service value";
           type union {
             type string {
               pattern "<.*>|$.*";
             }
             type int32 {
               range "0 .. 7";
             }
           }
         }
         leaf no-decrement-ttl {
           description "Do not decrement the TTL within an LSP";
           type empty;
         }
         leaf hop-limit {
           description "Maximum allowed router hops";
           type union {
             type string {
               pattern "<.*>|$.*";
             }
             type int32 {
               range "2 .. 255";
             }
           }
         }
         leaf no-cspf {
           description "Disable automatic path computation";
           type empty;
         }
         leaf admin-down {
           description "Set GMPLS LSP to administrative down state";
           type empty;
         }
         leaf optimize-timer {
           description "Periodical path reoptimizations";
           units "seconds";
           type union {
             type string {
               pattern "<.*>|$.*";
             }
             type int32 {
               range "0 .. 65535";
             }
           }
         }
         leaf preference {
           description "Preference value";
           type union {
             type uint32;
             type string {
               pattern "<.*>|$.*";
             }
           }
         }
         container priority {
           presence "enable priority";
           description "Preemption priorities";
         }
         leaf setup-priority {
           description "Set-up priority";
           type union {
             type string {
               pattern "<.*>|$.*";
             }
             type uint32 {
               range "0 .. 7";
             }
           }
         }
         leaf reservation-priority {
           description "Reservation priority";
           type union {
             type string {
               pattern "<.*>|$.*";
             }
             type uint32 {
               range "0 .. 7";
             }
           }
         }
         choice record-choice {
           leaf record {
             description "Record transit routers";
             type empty;
           }
           leaf no-record {
             description "Don't record transit routers";
             type empty;
           }
         }
         leaf standby {
           description "Keep backup paths in continuous standby";
           type empty;
         }
         leaf exclude-srlg {
           description "Exclude SRLG links for secondary path";
           type empty;
         }
         container admin-group {
           description "Administrative group policy";
           uses admin_group_include_exclude;
         }
         container admin-group-extended {
           description "Extended administrative group policy";
           uses admin_group_include_exclude;
         }
         container oam {
           description "Periodic OAM";
           uses periodic_oam;
         }
         leaf ultimate-hop-popping {
           description "Request ultimate hop popping from egress";
           type empty;
         }
         leaf sync-active-path-bandwidth {
           description "Signal standby path with bandwidth obtained from active path";
           type empty;
         }
         leaf cross-credibility-cspf {
           description "Compute paths across multi-protocol links and nodes";
           type empty;
         }
         leaf adaptive {
           description "Have the LSP smoothly cut over to new routes";
           type empty;
         }
         leaf select {
           type enumeration {
             enum "manual" {
               description "Manual override as preferred active path, if up and stable";
             }
             enum "unconditional" {
               description "Unconditional override as preferred active path, regardless of up/down status";
             }
           }
         }
         container upstream-label {
           description "Upstream Label for the bidirectional label-switched path";
           uses apply-advanced;
           leaf vlan-id {
             description "VLAN ID label for the label-switched path";
             type union {
               type string {
                 pattern "<.*>|$.*";
               }
               type uint32 {
                 range "1 .. 4094";
               }
             }
           }
         }
         container optimize-on-change {
           description "Specify additional re-optimization triggers for this path";
           uses apply-advanced;
           leaf link-congestion {
             description "Optimize when a link becomes congested";
             type empty;
           }
         }
       }
       container policing {
         description "Traffic policing for this LSP";
         leaf filter {
           description "Name of filter to use for policing LSP traffic";
           type string {
           }
         }
         leaf no-auto-policing {
           description "Turn off automatic policing for this LSP";
           type empty;
         }
       }
       leaf lsp-external-controller {
         description "Name of the external path computing entity";
         type string {
         }
       }
       leaf associate-backup-pe-groups {
         description "Associate this LSP with backup-pe groups";
         type empty;
       }
       leaf egress-protection {
         description "Use this LSP for egress protection data transport";
         type empty;
       }
     }
     container deselect-on-bandwidth-failure {
       presence "enable deselect-on-bandwidth-failure";
       description "Deselect active path if it cannot meet the bandwidth constraint";
       uses apply-advanced;
       leaf tear-lsp {
         description "Bring down active path when all paths fail to reserve required bandwidth";
         type empty;
       }
     }
     container track-igp-metric {
       description "Track IGP metric for LSP install prefixes";
       uses apply-advanced;
       leaf install-v4-prefixes {
         description "Track IGP metric for IPV4 prefixes";
         type empty;
       }
       leaf install-v6-prefixes {
         description "Track IGP metric for IPV6 prefixes";
         type empty;
       }
     }
     list container-label-switched-path {
       key name;
       ordered-by user;
       leaf name {
         description "Name of container-lsp";
         type string {
         }
       }
       uses apply-advanced;
       choice enable-disable {
         case case_1 {
           leaf disable {
             description "Disable MPLS container-label-switched path";
             type empty;
           }
         }
       }
       leaf description {
         description "Text description of label-switched path";
         type string {
         }
       }
       container label-switched-path-template {
         description "Template for dynamic point-to-point LSP parameters";
         uses apply-advanced;
         choice dynamic-template {
           case case_1 {
             leaf template-name {
               description "Name of point-to-point LSP template";
               type string {
                 length "1 .. 64";
               }
             }
           }
           case case_2 {
             leaf default-template {
               description "Use default parameters";
               type empty;
             }
           }
         }
       }
       leaf to {
         description "Address of egress router";
         type jt:ipv4addr;
       }
       leaf suffix {
         description "Suffix to generate names of members of container LSP";
         type string {
         }
       }
       container splitting-merging {
         description "Do splitting and merging";
         uses apply-advanced;
         leaf maximum-member-lsps {
           description "Maximum number of LSPs";
           type union {
             type string {
               pattern "<.*>|$.*";
             }
             type int32 {
               range "1 .. 64";
             }
           }
         }
         leaf minimum-member-lsps {
           description "Minimum number of LSPs";
           type union {
             type string {
               pattern "<.*>|$.*";
             }
             type int32 {
               range "1 .. 64";
             }
           }
         }
         leaf splitting-bandwidth {
           description "Maximum bandwidth threshold for splitting";
           units "bps";
           type string;
         }
         leaf merging-bandwidth {
           description "Minimum bandwidth threshold for merging";
           units "bps";
           type string;
         }
         leaf maximum-signaling-bandwidth {
           description "Maximum bandwidth for signaling during normalization";
           units "bps";
           type string;
         }
         leaf minimum-signaling-bandwidth {
           description "Minimum bandwidth for signaling during normalization";
           units "bps";
           type string;
         }
         leaf splitting-merging-threshold {
           description "Change in aggregate LSP utilization to trigger splitting or merging";
           default "10";
           units "percent";
           type union {
             type string {
               pattern "<.*>|$.*";
             }
             type uint32 {
               range "0 .. 100";
             }
           }
         }
         container normalization {
           description "Do normalization";
           uses apply-advanced;
           leaf normalize-interval {
             description "Time to normalize container LSP";
             default "86400";
             units "seconds";
             type union {
               type string {
                 pattern "<.*>|$.*";
               }
               type uint32 {
                 range "300 .. 315360000";
               }
             }
           }
           leaf failover-normalization {
             description "Do pre-mature normalization in case some LSPs go down before next normalization";
             type empty;
           }
           leaf no-incremental-normalize {
             description "Do not normalize unless all LSPs are successfully signaled";
             type empty;
           }
           leaf normalization-retry-duration {
             description "Time before retrying the container LSP normalization";
             units "seconds";
             type union {
               type string {
                 pattern "<.*>|$.*";
               }
               type uint32 {
                 range "1 .. 86400";
               }
             }
           }
           leaf normalization-retry-limits {
             description "Maximum number of times to retry container LSP normalization";
             type union {
               type string {
                 pattern "<.*>|$.*";
               }
               type uint32 {
                 range "1 .. 1000";
               }
             }
           }
         }
         container sampling {
           description "Sampling information";
           uses apply-advanced;
           leaf cut-off-threshold {
             description "Cut-off percentile to remove outliers from aggregate samples";
             default "0";
             type union {
               type string {
                 pattern "<.*>|$.*";
               }
               type uint32 {
                 range "0 .. 100";
               }
             }
           }
           choice sampling-mode {
             case case_1 {
               leaf use-average-aggregate {
                 description "Use average of the samples";
                 type empty;
               }
             }
             case case_2 {
               leaf use-percentile {
                 description "Use a percentile of the samples";
                 default "100";
                 type union {
                   type string {
                     pattern "<.*>|$.*";
                   }
                   type uint32 {
                     range "0 .. 100";
                   }
                 }
               }
             }
           }
         }
       }
       leaf lsp-external-controller {
         description "Name of the external path computing entity";
         type string {
         }
       }
     }
     list transit-lsp-association {
       key name;
       ordered-by user;
       description "Transit label switch path assoication";
       leaf name {
         description "Name of transit assocation LSP group";
         type string {
         }
       }
       uses apply-advanced;
       leaf lsp-name-1 {
         description "Name of assocation LSP 1";
         type string {
         }
       }
       leaf from-1 {
         description "Address of associated LSP 1";
         type jt:ipv4addr;
       }
       leaf lsp-name-2 {
         description "Name of assocation LSP 2";
         type string {
         }
       }
       leaf from-2 {
         description "Address of associated LSP 2";
         type jt:ipv4addr;
       }
     }
     list path {
       key name;
       ordered-by user;
       description "Route of a label-switched path";
       leaf name {
         description "Name of label-switched path";
         type string {
         }
       }
       uses apply-advanced;
       list path-list {
         key name;
         ordered-by user;
         description "List of routers in the label-switched path";
         leaf name {
           description "Address of next system in path";
           type string {
           }
         }
         leaf abstract {
           description "Next system in path is abstract";
           type empty;
         }
         choice loose_strict_none {
           case case_1 {
             leaf loose {
               description "Next hop might not be adjacent";
               type empty;
             }
           }
           case case_2 {
             leaf loose-link {
               description "Next hop link might not be adjacent";
               type empty;
             }
           }
           case case_3 {
             leaf strict {
               description "Next hop must be adjacent";
               type empty;
             }
           }
         }
       }
     }
     list static-label-switched-path {
       key name;
       ordered-by user;
       description "Static label-switched path";
       leaf name {
         description "Name of path";
         type string {
         }
       }
       uses apply-advanced;
       choice lsp-type {
         case case_1 {
           container bypass {
             description "Bypass ingress label-switched path";
             uses apply-advanced;
             leaf bandwidth {
               description "Bandwidth to reserve";
               units "bps";
               type string;
             }
             leaf description {
               description "Text description of label-switched path";
               type string {
               }
             }
             leaf next-hop {
               description "IPv4 or IPv6 address or interface of next-hop router";
               type union {
                 type jt:ipaddr-or-interface;
                 type string {
                   pattern "<.*>|$.*";
                 }
               }
             }
             leaf next-table {
               description "Next-table for lookup";
               type string;
             }
             leaf push {
               description "Label to push";
               type union {
                 type string {
                   pattern "<.*>|$.*";
                 }
                 type uint32 {
                   range "0 .. 1048575";
                 }
               }
             }
             leaf to {
               description "Address of egress router";
               type jt:ipaddr;
             }
           }
         }
         case case_2 {
           list transit {
             key name;
             ordered-by user;
             description "Transit label-switched path";
             leaf name {
               description "Incoming label value";
               type union {
                 type string {
                   pattern "<.*>|$.*";
                 }
                 type uint32 {
                   range "16 .. 1048575";
                 }
               }
             }
             uses apply-advanced;
             leaf bandwidth {
               description "Bandwidth to reserve";
               units "bps";
               type string;
             }
             leaf description {
               description "Text description of label-switched path";
               type string {
               }
             }
             container link-protection {
               description "Bypass link protection";
               leaf bypass-name {
                 description "Bypass label-switched path name";
                 type string {
                 }
               }
             }
             leaf next-hop {
               description "IPv4 or IPv6 address or interface of next-hop router";
               type union {
                 type jt:ipaddr-or-interface;
                 type string {
                   pattern "<.*>|$.*";
                 }
               }
             }
             leaf member-interface {
               description "AE member interface name";
               type union {
                 type jt:interface-unit;
                 type string {
                   pattern "<.*>|$.*";
                 }
               }
             }
             container node-protection {
               description "Bypass node protection";
               leaf bypass-name {
                 description "Bypass label-switched path name";
                 type string {
                 }
               }
               leaf next-next-label {
                 description "Label expected by next-next-hop";
                 type union {
                   type string {
                     pattern "<.*>|$.*";
                   }
                   type uint32 {
                     range "0 .. 1048575";
                   }
                 }
               }
             }
             choice label-action {
               case case_1 {
                 leaf swap {
                   description "Swap top label with this label";
                   type union {
                     type string {
                       pattern "<.*>|$.*";
                     }
                     type uint32 {
                       range "0 .. 1048575";
                     }
                   }
                 }
               }
               case case_2 {
                 leaf pop {
                   description "Pop the top label";
                   type empty;
                 }
               }
               case case_3 {
                 leaf stitch {
                   description "Swap top label with the resolved LSP";
                   type empty;
                 }
               }
             }
           }
         }
         case case_3 {
           container ingress {
             description "Ingress LSR configuration for a static LSP";
             uses apply-advanced;
             leaf bandwidth {
               description "Bandwidth to reserve";
               units "bps";
               type string;
             }
             leaf class-of-service {
               description "Class-of-service value";
               type union {
                 type string {
                   pattern "<.*>|$.*";
                 }
                 type int32 {
                   range "0 .. 7";
                 }
               }
             }
             leaf description {
               description "Text description of label-switched path";
               type string {
               }
             }
             list install {
               key name;
               ordered-by user;
               description "Install prefix";
               leaf name {
                 description "Destination prefix";
                 type jt:ipv4prefix;
               }
               leaf active {
                 description "Install prefix into forwarding table";
                 type empty;
               }
             }
             leaf metric {
               description "Metric value";
               type union {
                 type string {
                   pattern "<.*>|$.*";
                 }
                 type uint32 {
                   range "1 .. 16777215";
                 }
               }
             }
             leaf next-hop {
               description "IPv4 address or interface of next-hop router";
               type union {
                 type jt:ipv4addr-or-interface;
                 type string {
                   pattern "<.*>|$.*";
                 }
               }
             }
             container link-protection {
               description "Bypass link protection";
               leaf bypass-name {
                 description "Bypass label-switched path name";
                 type string {
                 }
               }
             }
             container node-protection {
               description "Bypass node protection";
               leaf bypass-name {
                 description "Bypass label-switched path name";
                 type string {
                 }
               }
               leaf next-next-label {
                 description "Label expected by next-next-hop";
                 type union {
                   type string {
                     pattern "<.*>|$.*";
                   }
                   type uint32 {
                     range "0 .. 1048575";
                   }
                 }
               }
             }
             leaf no-install-to-address {
               description "Don't install host route 'to' address into routing tables";
               type empty;
             }
             container policing {
               description "Traffic policing for this LSP";
               leaf filter {
                 description "Name of filter to use for policing LSP traffic";
                 type string {
                 }
               }
               leaf no-auto-policing {
                 description "Turn off automatic policing for this LSP";
                 type empty;
               }
             }
             leaf preference {
               description "Preference value";
               type union {
                 type uint32;
                 type string {
                   pattern "<.*>|$.*";
                 }
               }
             }
             leaf to {
               description "Address of egress router";
               type jt:ipv4addr;
             }
             leaf push {
               description "Label to push";
               type union {
                 type string {
                   pattern "<.*>|$.*";
                 }
                 type uint32 {
                   range "0 .. 1048575";
                 }
               }
             }
             leaf entropy-label {
               description "Enable entropy label";
               type empty;
             }
           }
         }
         case case_4 {
           container segment {
             description "Segment for segment routing";
             uses apply-advanced;
             leaf sid-label {
               description "Segment identifier (SID) label";
               type union {
                 type string {
                   pattern "<.*>|$.*";
                 }
                 type uint32 {
                   range "16 .. 1048575";
                 }
               }
             }
             leaf description {
               description "Text description of label-switched path";
               type string {
               }
             }
             leaf next-hop {
               description "IPv4 address or interface of next-hop router";
               type union {
                 type jt:ipv4addr-or-interface;
                 type string {
                   pattern "<.*>|$.*";
                 }
               }
             }
             choice label-action {
               case case_1 {
                 leaf swap {
                   description "Swap the SID label to this label";
                   type union {
                     type string {
                       pattern "<.*>|$.*";
                     }
                     type uint32 {
                       range "0 .. 1048575";
                     }
                   }
                 }
               }
               case case_2 {
                 leaf pop {
                   description "Pop the SID label";
                   type empty;
                 }
               }
             }
           }
         }
       }
     }
     list constituent-list {
       key name;
       ordered-by user;
       description "MPLS constituent list for abstract hops";
       leaf name {
         description "Constituent list name";
         type string {
         }
       }
       uses apply-advanced;
       leaf-list srlg {
         ordered-by user;
         description "SRLG Name";
         type string;
         max-elements 16;
       }
       leaf-list admin-group {
         ordered-by user;
         description "Administrative groups";
         type string;
         max-elements 16;
       }
       leaf-list admin-group-extended {
         ordered-by user;
         description "Extended administrative groups";
         type string;
         max-elements 16;
       }
     }
     list abstract-hop {
       key name;
       ordered-by user;
       description "MPLS abstract hop";
       leaf name {
         description "Abstract hop name";
         type string {
         }
       }
       uses apply-advanced;
       leaf operator {
         description "Operation among constituent lists";
         type enumeration {
           enum "AND" {
             description "AND";
           }
           enum "OR" {
             description "OR";
           }
         }
       }
       list constituent-list {
         key name;
         ordered-by user;
         description "Building abstract hop using constituent lists";
         leaf name {
           description "Constituent list name";
           type string {
             length "1 .. 64";
           }
         }
         uses apply-advanced;
         choice list-type {
           case case_1 {
             leaf include-any-list {
               description "Include any";
               type empty;
             }
           }
           case case_2 {
             leaf include-all-list {
               description "Include all";
               type empty;
             }
           }
           case case_3 {
             leaf exclude-any-list {
               description "Exclude any";
               type empty;
             }
           }
           case case_4 {
             leaf exclude-all-list {
               description "Exclude all";
               type empty;
             }
           }
         }
       }
     }
     list interface {
       key name;
       ordered-by user;
       description "MPLS interface options";
       leaf name {
         description "Interface name";
         type union {
           type jt:interface-name;
           type string {
             pattern "<.*>|$.*";
           }
         }
       }
       uses apply-advanced;
       choice enable-disable {
         case case_1 {
           leaf disable {
             description "Disable MPLS on this interface";
             type empty;
           }
         }
       }
       leaf-list srlg {
         ordered-by user;
         description "SRLG Name";
         type string;
         max-elements 64;
       }
       leaf always-mark-connection-protection-tlv {
         description "Mark connection protection tlv on this interface";
         type empty;
       }
       leaf switch-away-lsps {
         description "Switch away protected LSPs to their bypass LSPs";
         type empty;
       }
       leaf-list admin-group {
         ordered-by user;
         description "Administrative groups";
         type string;
       }
       leaf-list admin-group-extended {
         ordered-by user;
         description "Extended administrative groups";
         type string;
       }
       container static {
         description "Static label-switch path related configurations";
         uses apply-advanced;
         leaf protection-revert-time {
           description "FRR revert wait time, 0 means disable";
           units "seconds";
           type union {
             type string {
               pattern "<.*>|$.*";
             }
             type uint32 {
               range "0 .. 65535";
             }
           }
         }
       }
     }
     container egress-protection {
       description "Egress router protection";
       uses apply-advanced;
       list context-identifier {
         key name;
         description "Context identifier";
         leaf name {
           description "IP address";
           type jt:ipv4addr;
         }
         uses apply-advanced;
         choice context-type {
           case case_1 {
             leaf primary {
               description "Primary";
               type empty;
             }
           }
           case case_2 {
             leaf protector {
               description "Protector";
               type empty;
             }
           }
         }
         leaf metric {
           description "IGP metric";
           type union {
             type string {
               pattern "<.*>|$.*";
             }
             type uint32 {
               range "2 .. 16777215";
             }
           }
         }
         leaf advertise-mode {
           description "Advertise mode";
           type enumeration {
             enum "stub-proxy" {
               description "Proxy";
             }
             enum "stub-alias" {
               description "Alias";
             }
           }
         }
         leaf-list admin-group {
           ordered-by user;
           description "Administrative groups";
           type string;
         }
       }
       container traceoptions {
         description "Trace options for egress-protection";
         uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "state" {
                 description "Trace state transitions";
               }
               enum "route" {
                 description "Trace route transitions";
               }
               enum "error" {
                 description "Trace error conditions";
               }
               enum "all" {
                 description "Trace everything";
               }
             }
           }
         }
       }
     }
     container label-history {
       presence "enable label-history";
       description "MPLS label history recording";
       uses apply-advanced;
       leaf max-entries {
         description "Limit for the number of history entry per label";
         type union {
           type string {
             pattern "<.*>|$.*";
           }
           type uint32;
         }
       }
     }
     container label-range {
       description "MPLS labels ranges";
       uses apply-advanced;
       list lsi-label-range {
         key name;
         ordered-by user;
         description "LSI-label-range";
         leaf name {
           description "Label_range_start";
           type union {
             type string {
               pattern "<.*>|$.*";
             }
             type uint32 {
               range "16 .. 1048575";
             }
           }
         }
         leaf range-end {
           description "Label_range_end";
           type union {
             type string {
               pattern "<.*>|$.*";
             }
             type uint32 {
               range "16 .. 1048575";
             }
           }
         }
       }
       list block-label-range {
         key name;
         ordered-by user;
         description "Block-label-range";
         leaf name {
           description "Label_range_start";
           type union {
             type string {
               pattern "<.*>|$.*";
             }
             type uint32 {
               range "16 .. 1048575";
             }
           }
         }
         leaf range-end {
           description "Label_range_end";
           type union {
             type string {
               pattern "<.*>|$.*";
             }
             type uint32 {
               range "16 .. 1048575";
             }
           }
         }
       }
       list dynamic-label-range {
         key name;
         ordered-by user;
         description "Dynamic-label-range";
         leaf name {
           description "Label_range_start";
           type union {
             type string {
               pattern "<.*>|$.*";
             }
             type uint32 {
               range "16 .. 1048575";
             }
           }
         }
         leaf range-end {
           description "Label_range_end";
           type union {
             type string {
               pattern "<.*>|$.*";
             }
             type uint32 {
               range "16 .. 1048575";
             }
           }
         }
       }
       list static-label-range {
         key name;
         ordered-by user;
         description "Static-label-range";
         leaf name {
           description "Label_range_start";
           type union {
             type string {
               pattern "<.*>|$.*";
             }
             type uint32 {
               range "16 .. 1048575";
             }
           }
         }
         leaf range-end {
           description "Label_range_end";
           type union {
             type string {
               pattern "<.*>|$.*";
             }
             type uint32 {
               range "16 .. 1048575";
             }
           }
         }
       }
       leaf label-limit {
         description "Limit for the number of concurrent active labels";
         type union {
           type string {
             pattern "<.*>|$.*";
           }
           type uint32;
         }
       }
     }
   }
   grouping admin_group_include_exclude {
     uses apply-advanced;
     choice include-any-choice {
       case case_1 {
         leaf-list include-any {
           ordered-by user;
           description "Groups, one or more of which must be present";
           type string;
         }
       }
     }
     choice include-all-choice {
       case case_1 {
         leaf-list include-all {
           ordered-by user;
           description "Groups, all of which must be present";
           type string;
         }
       }
     }
     choice exclude-choice {
       case case_1 {
         leaf-list exclude {
           ordered-by user;
           description "Groups, all of which must be absent";
           type string;
         }
       }
     }
   }
   grouping juniper-protocols-msdp {
     uses apply-advanced;
     leaf data-encapsulation {
       description "Set encapsulation of data packets";
       type enumeration {
         enum "disable" {
           description "Disable data encapsulation";
         }
         enum "enable" {
           description "Enable data encapsulation";
         }
       }
     }
     container rib-group {
       description "Routing table group";
       uses rib_group_inet_type;
     }
     container active-source-limit {
       description "Limit the number of active sources accepted";
       uses apply-advanced;
       leaf maximum {
         description "Maximum number of active sources accepted";
         default "25000";
         type union {
           type string {
             pattern "<.*>|$.*";
           }
           type uint32 {
             range "1 .. 1000000";
           }
         }
       }
       leaf threshold {
         description "RED threshold for active source acceptance";
         default "24000";
         type union {
           type string {
             pattern "<.*>|$.*";
           }
           type uint32 {
             range "1 .. 1000000";
           }
         }
       }
       leaf log-warning {
         description "Percentage of maximum at which to start generating warnings";
         default "100";
         type union {
           type string {
             pattern "<.*>|$.*";
           }
           type uint32 {
             range "1 .. 100";
           }
         }
       }
       leaf log-interval {
         description "Time between log messages";
         type union {
           type string {
             pattern "<.*>|$.*";
           }
           type uint32 {
             range "6 .. 32767";
           }
         }
       }
     }
     choice enable-disable {
       case case_1 {
         leaf disable {
           description "Disable MSDP";
           type empty;
         }
       }
     }
     leaf-list export {
       ordered-by user;
       description "Export policy";
       type jt:policy-algebra;
     }
     leaf-list import {
       ordered-by user;
       description "Import policy";
       type jt:policy-algebra;
     }
     leaf local-address {
       description "Local address";
       type jt:ipv4addr;
     }
     container traceoptions {
       description "Trace options for MSDP";
       uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "packets" {
               description "Trace all MSDP packets";
             }
             enum "route" {
               description "Trace routing information";
             }
             enum "nsr-synchronization" {
               description "Trace NSR synchronization events";
             }
             enum "source-active" {
               description "Trace source-active messages";
             }
             enum "source-active-request" {
               description "Trace source-active request messages";
             }
             enum "source-active-response" {
               description "Trace source-active response messages";
             }
             enum "keepalive" {
               description "Trace keepalive messages";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     list peer {
       key name;
       ordered-by user;
       description "Configure an MSDP peer";
       leaf name {
         description "Peer address";
         type jt:ipv4addr;
       }
       uses apply-advanced;
       choice enable-disable {
         case case_1 {
           leaf disable {
             description "Disable MSDP";
             type empty;
           }
         }
       }
       leaf-list export {
         ordered-by user;
         description "Export policy";
         type jt:policy-algebra;
       }
       leaf-list import {
         ordered-by user;
         description "Import policy";
         type jt:policy-algebra;
       }
       leaf local-address {
         description "Local address";
         type jt:ipv4addr;
       }
       container traceoptions {
         description "Trace options for MSDP";
         uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "packets" {
                 description "Trace all MSDP packets";
               }
               enum "route" {
                 description "Trace routing information";
               }
               enum "nsr-synchronization" {
                 description "Trace NSR synchronization events";
               }
               enum "source-active" {
                 description "Trace source-active messages";
               }
               enum "source-active-request" {
                 description "Trace source-active request messages";
               }
               enum "source-active-response" {
                 description "Trace source-active response messages";
               }
               enum "keepalive" {
                 description "Trace keepalive messages";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       container active-source-limit {
         description "Limit the number of active sources accepted";
         uses apply-advanced;
         leaf maximum {
           description "Maximum number of active sources accepted";
           default "25000";
           type union {
             type string {
               pattern "<.*>|$.*";
             }
             type uint32 {
               range "1 .. 1000000";
             }
           }
         }
         leaf threshold {
           description "RED threshold for active source acceptance";
           default "24000";
           type union {
             type string {
               pattern "<.*>|$.*";
             }
             type uint32 {
               range "1 .. 1000000";
             }
           }
         }
         leaf log-warning {
           description "Percentage of maximum at which to start generating warnings";
           default "100";
           type union {
             type string {
               pattern "<.*>|$.*";
             }
             type uint32 {
               range "1 .. 100";
             }
           }
         }
         leaf log-interval {
           description "Time between log messages";
           type union {
             type string {
               pattern "<.*>|$.*";
             }
             type uint32 {
               range "6 .. 32767";
             }
           }
         }
       }
       leaf keep-alive {
         description "Time limit for sending out periodic keep alive to peer";
         units "seconds";
         type union {
           type string {
             pattern "<.*>|$.*";
           }
           type uint32 {
             range "10 .. 60";
           }
         }
       }
       leaf hold-time {
         description "Max time to terminating a peer for having not received any message from ";
         units "seconds";
         type union {
           type string {
             pattern "<.*>|$.*";
           }
           type uint32 {
             range "15 .. 150";
           }
         }
       }
       leaf sa-hold-time {
         description "Max time for holding a sa message before timing out";
         units "seconds";
         type union {
           type string {
             pattern "<.*>|$.*";
           }
           type uint32 {
             range "75 .. 300";
           }
         }
       }
       leaf default-peer {
         description "Default RPF peer";
         type empty;
       }
       leaf authentication-key {
         description "MD5 authentication key";
         type string {
           length "1 .. 126";
         }
       }
     }
     leaf keep-alive {
       description "Time limit for sending out periodic keep alive to peer";
       units "seconds";
       type union {
         type string {
           pattern "<.*>|$.*";
         }
         type uint32 {
           range "10 .. 60";
         }
       }
     }
     leaf hold-time {
       description "Max time to terminating a peer for having not received any message from ";
       units "seconds";
       type union {
         type string {
           pattern "<.*>|$.*";
         }
         type uint32 {
           range "15 .. 150";
         }
       }
     }
     leaf sa-hold-time {
       description "Max time for holding a sa message before timing out";
       units "seconds";
       type union {
         type string {
           pattern "<.*>|$.*";
         }
         type uint32 {
           range "75 .. 300";
         }
       }
     }
     list source {
       key name;
       ordered-by user;
       description "Configure parameters for each source";
       leaf name {
         description "Source address or prefix";
         type jt:ipprefix;
       }
       uses apply-advanced;
       container active-source-limit {
         description "Limit the number of active sources accepted";
         uses apply-advanced;
         leaf maximum {
           description "Maximum number of active sources accepted";
           default "25000";
           type union {
             type string {
               pattern "<.*>|$.*";
             }
             type uint32 {
               range "1 .. 1000000";
             }
           }
         }
         leaf threshold {
           description "RED threshold for active source acceptance";
           default "24000";
           type union {
             type string {
               pattern "<.*>|$.*";
             }
             type uint32 {
               range "1 .. 1000000";
             }
           }
         }
         leaf log-warning {
           description "Percentage of maximum at which to start generating warnings";
           default "100";
           type union {
             type string {
               pattern "<.*>|$.*";
             }
             type uint32 {
               range "1 .. 100";
             }
           }
         }
         leaf log-interval {
           description "Time between log messages";
           type union {
             type string {
               pattern "<.*>|$.*";
             }
             type uint32 {
               range "6 .. 32767";
             }
           }
         }
       }
     }
     list group {
       key name;
       ordered-by user;
       description "Configure MSDP peer groups";
       leaf name {
         description "MSDP peer group name";
         type string;
       }
       uses apply-advanced;
       leaf mode {
         description "MSDP group source-active flooding mode";
         default "standard";
         type enumeration {
           enum "standard" {
             description "Use standard MSDP source-active flooding rules";
           }
           enum "mesh-group" {
             description "Group peers are mesh group members";
           }
         }
       }
       choice enable-disable {
         case case_1 {
           leaf disable {
             description "Disable MSDP";
             type empty;
           }
         }
       }
       leaf-list export {
         ordered-by user;
         description "Export policy";
         type jt:policy-algebra;
       }
       leaf-list import {
         ordered-by user;
         description "Import policy";
         type jt:policy-algebra;
       }
       leaf local-address {
         description "Local address";
         type jt:ipv4addr;
       }
       container traceoptions {
         description "Trace options for MSDP";
         uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "packets" {
                 description "Trace all MSDP packets";
               }
               enum "route" {
                 description "Trace routing information";
               }
               enum "nsr-synchronization" {
                 description "Trace NSR synchronization events";
               }
               enum "source-active" {
                 description "Trace source-active messages";
               }
               enum "source-active-request" {
                 description "Trace source-active request messages";
               }
               enum "source-active-response" {
                 description "Trace source-active response messages";
               }
               enum "keepalive" {
                 description "Trace keepalive messages";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       list peer {
         key name;
         ordered-by user;
         description "Configure an MSDP peer";
         leaf name {
           description "Peer address";
           type jt:ipv4addr;
         }
         uses apply-advanced;
         choice enable-disable {
           case case_1 {
             leaf disable {
               description "Disable MSDP";
               type empty;
             }
           }
         }
         leaf-list export {
           ordered-by user;
           description "Export policy";
           type jt:policy-algebra;
         }
         leaf-list import {
           ordered-by user;
           description "Import policy";
           type jt:policy-algebra;
         }
         leaf local-address {
           description "Local address";
           type jt:ipv4addr;
         }
         container traceoptions {
           description "Trace options for MSDP";
           uses apply-advanced;
           container file {
             description "Trace file options";
             leaf filename {
               description "Name of file in which to write trace information";
               type string {
                 length "1 .. 1024";
               }
             }
             leaf replace {
               description "Replace trace file rather than appending to it";
               status deprecated;
               type empty;
             }
             leaf size {
               description "Maximum trace file size";
               type string;
             }
             leaf files {
               description "Maximum number of trace files";
               default "10";
               type union {
                 type string {
                   pattern "<.*>|$.*";
                 }
                 type uint32 {
                   range "2 .. 1000";
                 }
               }
             }
             leaf no-stamp {
               description "Do not timestamp trace file";
               status deprecated;
               type empty;
             }
             choice world-readable-choice {
               leaf world-readable {
                 description "Allow any user to read the log file";
                 type empty;
               }
               leaf no-world-readable {
                 description "Don't allow any user to read the log file";
                 type empty;
               }
             }
           }
           list flag {
             key name;
             ordered-by user;
             description "Tracing parameters";
             leaf name {
               type enumeration {
                 enum "packets" {
                   description "Trace all MSDP packets";
                 }
                 enum "route" {
                   description "Trace routing information";
                 }
                 enum "nsr-synchronization" {
                   description "Trace NSR synchronization events";
                 }
                 enum "source-active" {
                   description "Trace source-active messages";
                 }
                 enum "source-active-request" {
                   description "Trace source-active request messages";
                 }
                 enum "source-active-response" {
                   description "Trace source-active response messages";
                 }
                 enum "keepalive" {
                   description "Trace keepalive messages";
                 }
                 enum "normal" {
                   description "Trace normal events";
                 }
                 enum "general" {
                   description "Trace general events";
                 }
                 enum "state" {
                   description "Trace state transitions";
                 }
                 enum "policy" {
                   description "Trace policy processing";
                 }
                 enum "task" {
                   description "Trace routing protocol task processing";
                 }
                 enum "timer" {
                   description "Trace routing protocol timer processing";
                 }
                 enum "all" {
                   description "Trace everything";
                 }
               }
             }
             leaf send {
               description "Trace transmitted packets";
               type empty;
             }
             leaf receive {
               description "Trace received packets";
               type empty;
             }
             leaf detail {
               description "Trace detailed information";
               type empty;
             }
             leaf disable {
               description "Disable this trace flag";
               type empty;
             }
           }
         }
         container active-source-limit {
           description "Limit the number of active sources accepted";
           uses apply-advanced;
           leaf maximum {
             description "Maximum number of active sources accepted";
             default "25000";
             type union {
               type string {
                 pattern "<.*>|$.*";
               }
               type uint32 {
                 range "1 .. 1000000";
               }
             }
           }
           leaf threshold {
             description "RED threshold for active source acceptance";
             default "24000";
             type union {
               type string {
                 pattern "<.*>|$.*";
               }
               type uint32 {
                 range "1 .. 1000000";
               }
             }
           }
           leaf log-warning {
             description "Percentage of maximum at which to start generating warnings";
             default "100";
             type union {
               type string {
                 pattern "<.*>|$.*";
               }
               type uint32 {
                 range "1 .. 100";
               }
             }
           }
           leaf log-interval {
             description "Time between log messages";
             type union {
               type string {
                 pattern "<.*>|$.*";
               }
               type uint32 {
                 range "6 .. 32767";
               }
             }
           }
         }
         leaf keep-alive {
           description "Time limit for sending out periodic keep alive to peer";
           units "seconds";
           type union {
             type string {
               pattern "<.*>|$.*";
             }
             type uint32 {
               range "10 .. 60";
             }
           }
         }
         leaf hold-time {
           description "Max time to terminating a peer for having not received any message from ";
           units "seconds";
           type union {
             type string {
               pattern "<.*>|$.*";
             }
             type uint32 {
               range "15 .. 150";
             }
           }
         }
         leaf sa-hold-time {
           description "Max time for holding a sa message before timing out";
           units "seconds";
           type union {
             type string {
               pattern "<.*>|$.*";
             }
             type uint32 {
               range "75 .. 300";
             }
           }
         }
         leaf default-peer {
           description "Default RPF peer";
           type empty;
         }
         leaf authentication-key {
           description "MD5 authentication key";
           type string {
             length "1 .. 126";
           }
         }
       }
     }
   }
   grouping juniper-protocols-mstp {
     uses apply-advanced;
     choice enable-disable {
       case case_1 {
         leaf disable {
           description "Disable MSTP";
           type empty;
         }
       }
     }
     leaf bpdu-destination-mac-address {
       description "Destination MAC address in the spanning tree BPDUs";
       type enumeration {
         enum "provider-bridge-group" {
           description "802.1ad provider bridge group address";
         }
       }
     }
     leaf configuration-name {
       description "Configuration name (part of MST configuration identifier)";
       type string {
         length "1 .. 32";
       }
     }
     leaf revision-level {
       description "Revision level (part of MST configuration identifier)";
       type union {
         type uint16;
         type string {
           pattern "<.*>|$.*";
         }
       }
     }
     leaf max-hops {
       description "Maximum number of hops";
       type union {
         type string {
           pattern "<.*>|$.*";
         }
         type uint16 {
           range "1 .. 255";
         }
       }
     }
     leaf max-age {
       description "Maximum age of received protocol bpdu";
       units "seconds";
       type union {
         type string {
           pattern "<.*>|$.*";
         }
         type uint16 {
           range "6 .. 40";
         }
       }
     }
     leaf hello-time {
       description "Time interval between configuration BPDUs";
       units "seconds";
       type union {
         type string {
           pattern "<.*>|$.*";
         }
         type uint16 {
           range "1 .. 10";
         }
       }
     }
     leaf forward-delay {
       description "Time spent in listening or learning state";
       units "seconds";
       type union {
         type string {
           pattern "<.*>|$.*";
         }
         type uint16 {
           range "4 .. 30";
         }
       }
     }
     leaf system-identifier {
       description "Sytem identifier to represent this node";
       type jt:mac-unicast;
     }
     container traceoptions {
       description "Tracing options for debugging protocol operation";
       uses stp-trace-options;
     }
     leaf bridge-priority {
       description "Priority of the bridge (in increments of 4k - 0,4k,8k,..60k)";
       type string {
       }
     }
     leaf backup-bridge-priority {
       description "Priority of the bridge (in increments of 4k - 4k,8k,..60k)";
       type string {
       }
     }
     leaf bpdu-block-on-edge {
       description "Block BPDU on all interfaces configured as edge (BPDU Protect)";
       type empty;
     }
     leaf vpls-flush-on-topology-change {
       description "Enable VPLS MAC flush on root protected CE interface receving topology change";
       type empty;
     }
     leaf priority-hold-time {
       description "Hold time before switching to primary priority when core domain becomes up";
       units "seconds";
       type union {
         type string {
           pattern "<.*>|$.*";
         }
         type uint16 {
           range "1 .. 255";
         }
       }
     }
     list system-id {
       key name;
       ordered-by user;
       description "System ID to IP mapping";
       uses system-id-ip-map;
     }
     list interface {
       key name;
       description "Interface options";
       uses mstp-interface;
     }
     list msti {
       key name;
       description "Per-MSTI options";
       leaf name {
         type union {
           type string {
             pattern "<.*>|$.*";
           }
           type int32 {
             range "1 .. 64";
           }
         }
       }
       uses apply-advanced;
       leaf bridge-priority {
         description "Priority of the bridge (in increments of 4k - 0,4k,8k,..60k)";
         type string {
         }
       }
       leaf backup-bridge-priority {
         description "Priority of the bridge (in increments of 4k - 4k,8k,..60k)";
         type string {
         }
       }
       leaf-list vlan {
         ordered-by user;
         description "VLAN ID or VLAN ID range [1..4094]";
         type string;
       }
       list interface {
         key name;
         description "Interface options";
         uses mstp-interface;
       }
     }
   }
   grouping juniper-protocols-mvpn {
     description "BGP-MVPN configuration";
     uses apply-advanced;
     container traceoptions {
       description "Trace options for BGP-MVPN";
       uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "error" {
               description "Trace errors";
             }
             enum "nlri" {
               description "Trace MVPN advertisements";
             }
             enum "topology" {
               description "Trace MVPN topology changes";
             }
             enum "tunnel" {
               description "Trace provider tunnel events";
             }
             enum "umh" {
               description "Trace Upstream Multicast Hop (UMH) events";
             }
             enum "intra-as-ad" {
               description "Trace MVPN intra-AS auto discovery routes";
             }
             enum "inter-as-ad" {
               description "Trace MVPN inter-AS auto discovery routes";
             }
             enum "spmsi-ad" {
               description "Trace MVPN SPMSI auto discovery routes";
             }
             enum "leaf-ad" {
               description "Trace MVPN leaf auto discovery routes";
             }
             enum "source-active" {
               description "Trace MVPN source active routes";
             }
             enum "cmcast-join" {
               description "Trace MVPN c-multicast join routes";
             }
             enum "mdt-safi-ad" {
               description "Trace MVPN MDT SAFI auto discovery routes";
             }
             enum "mvpn-limit" {
               description "Trace MVPN spmsi and cmcast limit events";
             }
             enum "nsr-synchronization" {
               description "Trace NSR synchronization events";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     container autodiscovery-only {
       description "Use MVPN exclusively for PE router autodiscovery";
       status deprecated;
       uses apply-advanced;
       container intra-as {
         description "Intra-AS autodiscovery options";
         uses apply-advanced;
         leaf inclusive {
           description "Inclusive provider tunnel autodiscovery";
           type empty;
         }
       }
     }
     container family {
       description "BGP-MVPN address family";
       uses apply-advanced;
       container any {
         presence "enable any";
         description "BGP-MVPN properties for all families";
         uses apply-advanced;
         leaf disable {
           description "Disable all families";
           type empty;
         }
       }
       container inet {
         description "IPv4 BGP-MVPN properties";
         uses apply-advanced;
         container autodiscovery-only {
           description "Use MVPN exclusively for PE router autodiscovery";
           uses apply-advanced;
           container intra-as {
             description "Intra-AS autodiscovery options";
             uses apply-advanced;
             leaf inclusive {
               description "Inclusive provider tunnel autodiscovery";
               type empty;
             }
           }
         }
         leaf disable {
           description "Disable family IPv4";
           type empty;
         }
       }
       container inet6 {
         presence "enable inet6";
         description "IPv6 BGP-MVPN properties";
         uses apply-advanced;
         container autodiscovery-only {
           description "Use MVPN exclusively for PE router autodiscovery";
           uses apply-advanced;
           container intra-as {
             description "Intra-AS autodiscovery options";
             uses apply-advanced;
             leaf inclusive {
               description "Inclusive provider tunnel autodiscovery";
               type empty;
             }
           }
         }
         leaf disable {
           description "Disable family IPv6";
           type empty;
         }
       }
     }
     choice sender-receiver-site-choice {
       case case_1 {
         leaf receiver-site {
           description "MVPN instance has sites only with multicast receivers";
           type empty;
         }
       }
       case case_2 {
         leaf sender-site {
           description "MVPN instance has sites only with multicast sources";
           type empty;
         }
       }
     }
     leaf unicast-umh-election {
       description "Upstream Multicast Hop election based on unicast route preference";
       type empty;
     }
     container static-umh {
       description "Upstream Multicast Hop election based on static configuration";
       uses apply-advanced;
       leaf primary {
         description "Primary Upstream Multicast Hop";
         type jt:ipv4addr;
       }
       leaf backup {
         description "Secondary Upstream Multicast Hop";
         type jt:ipv4addr;
       }
       choice source-tree_choice {
         case case_1 {
           leaf source-tree {
             description "Mandatory attribute - static-umh applies only to MVPN source-tree c-multicast joins";
             type empty;
           }
         }
       }
     }
     leaf cmcast-joins-limit-inet {
       description "Maximum number of cmcast entries for v4";
       type union {
         type string {
           pattern "<.*>|$.*";
         }
         type uint32 {
           range "0 .. 15000";
         }
       }
     }
     leaf cmcast-joins-limit-inet6 {
       description "Maximum number of cmcast entries for v6";
       type union {
         type string {
           pattern "<.*>|$.*";
         }
         type uint32 {
           range "0 .. 15000";
         }
       }
     }
     container mvpn-mode {
       description "MVPN mode of operation";
       uses apply-advanced;
       choice mode {
         case case_1 {
           container rpt-spt {
             presence "enable rpt-spt";
             description "MVPN works in multicast RPT and SPT mode";
             uses apply-advanced;
             leaf spt-switch-timer {
               description "Timeout before a PE router switches between RPT and SPT";
               units "seconds";
               type union {
                 type string {
                   pattern "<.*>|$.*";
                 }
                 type uint32 {
                   range "0 .. 60";
                 }
               }
             }
           }
         }
         case case_2 {
           container spt-only {
             presence "enable spt-only";
             description "MVPN works in multicast SPT only mode (default mode)";
             uses apply-advanced;
             container source-active-advertisement {
               description "Attributes associated with advertising Source-Active A-D routes";
               uses apply-advanced;
               leaf dampen {
                 description "Time to wait before re-advertising source-active route";
                 units "minutes";
                 type union {
                   type string {
                     pattern "<.*>|$.*";
                   }
                   type uint32 {
                     range "1 .. 30";
                   }
                 }
               }
               leaf min-rate {
                 description "Minimum traffic rate required to advertise Source-Active route";
                 units "bits per second";
                 type string;
               }
             }
             leaf convert-sa-to-msdp {
               description "Turn on MVPN SA route to MSDP SA conversion";
               type empty;
             }
           }
         }
       }
     }
     container route-target {
       description "Configure route-targets for MVPN routes";
       uses apply-advanced;
       container import-target {
         description "Target communities used when importing routes";
         uses apply-advanced;
         container unicast {
           presence "enable unicast";
           description "Use the same target community as configured for unicast";
           choice receiver-sender-target-choice {
             case case_1 {
               leaf receiver {
                 description "Target community used when importing receiver site routes";
                 type empty;
               }
             }
             case case_2 {
               leaf sender {
                 description "Target community used when importing sender site routes";
                 type empty;
               }
             }
           }
         }
         container target {
           presence "enable target";
           description "Target community";
           leaf target-value {
             type string {
             }
           }
           choice receiver-sender-target-choice {
             case case_1 {
               leaf receiver {
                 description "Target community used when importing receiver site routes";
                 type empty;
               }
             }
             case case_2 {
               leaf sender {
                 description "Target community used when importing sender site routes";
                 type empty;
               }
             }
           }
         }
       }
       container export-target {
         description "Target communities used when exporting routes";
         uses apply-advanced;
         leaf unicast {
           description "Use the same target community as configured for unicast";
           type empty;
         }
         leaf target {
           description "Target community";
           type string {
           }
         }
       }
     }
     container mvpn-join-load-balance {
       description "MVPN Join Load Balancing Algorithm";
       uses apply-advanced;
       choice algorithm {
         case case_1 {
           container bytewise-xor-hash {
             presence "enable bytewise-xor-hash";
             description "Upstream selection using bytewise XOR hash";
           }
         }
       }
     }
     container hot-root-standby {
       description "MVPN live-live - hot root standby";
       uses apply-advanced;
       choice tree {
         case case_1 {
           container source-tree {
             presence "enable source-tree";
             description "MVPN live-live - hot root standby for source tree";
           }
         }
       }
       container min-rate {
         description "Minimum traffic rate for the provider tunnel below which switchover is initiated (in bps)";
         uses apply-advanced;
         leaf rate {
           description "Minium traffic rate for the provider tunnel below which switchover is initiated (in bps)";
           units "bits per second";
           type string;
         }
         leaf revert-delay {
           description "Time to delay updating of multicast routes to allow for multicast convergence";
           units "seconds";
           type union {
             type string {
               pattern "<.*>|$.*";
             }
             type uint32 {
               range "0 .. 20";
             }
           }
         }
       }
     }
     container inter-region-template {
       description "MVPN inter-region tunnel mapping template";
       uses apply-advanced;
       list template {
         key name;
         ordered-by user;
         description "Define a inter-region template";
         leaf name {
           description "MVPN Template Name";
           type string;
         }
         uses apply-advanced;
         list region {
           key name;
           ordered-by user;
           description "BGP peer group names used as region";
           leaf name {
             description "Region name";
             type string;
           }
           uses apply-advanced;
           choice tunnel-type {
             case case_1 {
               container rsvp-te {
                 description "RSVP-TE point-to-multipoint LSP for flooding";
                 uses apply-advanced;
                 choice static-or-dynamic {
                   case case_1 {
                     leaf static-lsp {
                       description "Name of point-to-multipoint LSP";
                       type string {
                       }
                     }
                   }
                   case case_2 {
                     container label-switched-path-template {
                       description "Template for dynamic point-to-multipoint LSP parameters";
                       uses apply-advanced;
                       choice dynamic-template {
                         case case_1 {
                           leaf template-name {
                             description "Name of point-to-multipoint LSP template";
                             type string {
                             }
                           }
                         }
                         case case_2 {
                           leaf default-template {
                             description "Use default parameters";
                             type empty;
                           }
                         }
                       }
                     }
                   }
                 }
               }
             }
             case case_2 {
               container ldp-p2mp {
                 presence "enable ldp-p2mp";
                 description "LDP point-to-multipoint LSP for flooding";
               }
             }
             case case_3 {
               container ingress-replication {
                 description "Ingress replication tunnel";
                 uses apply-advanced;
                 leaf create-new-ucast-tunnel {
                   description "Create new unicast tunnel for ingress replication";
                   type empty;
                 }
                 container label-switched-path {
                   presence "enable label-switched-path";
                   description "Point-to-point LSP unicast tunnel";
                   uses apply-advanced;
                   container label-switched-path-template {
                     description "Template for dynamic point-to-point LSP parameters";
                     uses apply-advanced;
                     choice dynamic-template {
                       case case_1 {
                         leaf template-name {
                           description "Name of point-to-point LSP template";
                           type string {
                           }
                         }
                       }
                       case case_2 {
                         leaf default-template {
                           description "Use default parameters";
                           type empty;
                         }
                       }
                     }
                   }
                 }
               }
             }
             case case_4 {
               leaf incoming {
                 description "Same as incoming provider tunnel";
                 type empty;
               }
             }
           }
         }
         container all-regions {
           description "Used for all regions not specified";
           uses apply-advanced;
           choice tunnel-type {
             case case_1 {
               container rsvp-te {
                 description "RSVP-TE point-to-multipoint LSP for flooding";
                 uses apply-advanced;
                 choice static-or-dynamic {
                   case case_1 {
                     leaf static-lsp {
                       description "Name of point-to-multipoint LSP";
                       type string {
                       }
                     }
                   }
                   case case_2 {
                     container label-switched-path-template {
                       description "Template for dynamic point-to-multipoint LSP parameters";
                       uses apply-advanced;
                       choice dynamic-template {
                         case case_1 {
                           leaf template-name {
                             description "Name of point-to-multipoint LSP template";
                             type string {
                             }
                           }
                         }
                         case case_2 {
                           leaf default-template {
                             description "Use default parameters";
                             type empty;
                           }
                         }
                       }
                     }
                   }
                 }
               }
             }
             case case_2 {
               container ldp-p2mp {
                 presence "enable ldp-p2mp";
                 description "LDP point-to-multipoint LSP for flooding";
               }
             }
             case case_3 {
               container ingress-replication {
                 description "Ingress replication tunnel";
                 uses apply-advanced;
                 leaf create-new-ucast-tunnel {
                   description "Create new unicast tunnel for ingress replication";
                   type empty;
                 }
                 container label-switched-path {
                   presence "enable label-switched-path";
                   description "Point-to-point LSP unicast tunnel";
                   uses apply-advanced;
                   container label-switched-path-template {
                     description "Template for dynamic point-to-point LSP parameters";
                     uses apply-advanced;
                     choice dynamic-template {
                       case case_1 {
                         leaf template-name {
                           description "Name of point-to-point LSP template";
                           type string {
                           }
                         }
                       }
                       case case_2 {
                         leaf default-template {
                           description "Use default parameters";
                           type empty;
                         }
                       }
                     }
                   }
                 }
               }
             }
             case case_4 {
               leaf incoming {
                 description "Same as incoming provider tunnel";
                 type empty;
               }
             }
           }
         }
       }
     }
     leaf source-redundancy {
       description "Assume all the sources for a particular group is sending same data";
       type empty;
     }
     container umh-selection-additional-input {
       description "Additional parameters to consider during UMH";
       uses apply-advanced;
       leaf source-active-preference {
         description "Use the preference set in the source active route";
         type empty;
       }
       leaf tunnel-status {
         description "Use the RSVP tunnel status";
         type empty;
       }
     }
   }
   grouping juniper-protocols-mvrp {
     description "MVRP Configuration";
     uses apply-advanced;
     container traceoptions {
       description "Tracing options for MVRP";
       uses mrp-trace-options;
     }
     leaf join-timer {
       description "Join timer interval";
       default "200";
       units "milliseconds";
       type union {
         type string {
           pattern "<.*>|$.*";
         }
         type uint16 {
           range "100 .. 500";
         }
       }
     }
     leaf leave-timer {
       description "Leave timer interval";
       default "800";
       units "milliseconds";
       type union {
         type string {
           pattern "<.*>|$.*";
         }
         type uint16 {
           range "300 .. 1000";
         }
       }
     }
     leaf leaveall-timer {
       description "Leaveall timer interval";
       default "10";
       units "seconds";
       type union {
         type string {
           pattern "<.*>|$.*";
         }
         type uint16 {
           range "10 .. 60";
         }
       }
     }
     leaf no-dynamic-vlan {
       description "Disable dynamic VLAN creation";
       type empty;
     }
     leaf no-attribute-length-in-pdu {
       description "No attribute length while sending pdu ";
       type empty;
     }
     leaf bpdu-destination-mac-address {
       description "Destination MAC address in the MVRP BPDUs";
       type enumeration {
         enum "provider-bridge-group" {
           description "802.1ad provider bridge group address";
         }
       }
     }
     list interface {
       key name;
       ordered-by user;
       description "Configure interface options";
       leaf name {
         description "Interface name";
         type union {
           type jt:interface-device;
           type string {
             pattern "<.*>|$.*";
           }
         }
       }
       uses apply-advanced;
       leaf join-timer {
         description "Join timer interval";
         units "milliseconds";
         type union {
           type string {
             pattern "<.*>|$.*";
           }
           type uint16 {
             range "100 .. 500";
           }
         }
       }
       leaf leave-timer {
         description "Leave timer interval";
         units "milliseconds";
         type union {
           type string {
             pattern "<.*>|$.*";
           }
           type uint16 {
             range "300 .. 1000";
           }
         }
       }
       leaf leaveall-timer {
         description "Leaveall timer interval";
         units "seconds";
         type union {
           type string {
             pattern "<.*>|$.*";
           }
           type uint16 {
             range "10 .. 60";
           }
         }
       }
       leaf point-to-point {
         description "Port is point to point";
         type empty;
       }
       leaf registration {
         description "Registration mode";
         default "normal";
         type enumeration {
           enum "normal" {
             description "Normal registration mode";
           }
           enum "restricted" {
             description "Restricted registration mode";
           }
           enum "forbidden" {
             description "Forbidden registration mode";
           }
         }
       }
     }
   }
   grouping juniper-protocols-ospf {
     uses apply-advanced;
     choice enable-disable {
       case case_1 {
         leaf disable {
           description "Disable OSPF";
           type empty;
         }
       }
     }
     container traceoptions {
       description "Trace options for OSPF";
       uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "spf" {
               description "Trace SPF calculations";
             }
             enum "error" {
               description "Trace errored packets";
             }
             enum "event" {
               description "Trace OSPF state machine events";
             }
             enum "packet-dump" {
               description "Dump the contents of selected packet types";
             }
             enum "flooding" {
               description "Trace LSA flooding";
             }
             enum "lsa-analysis" {
               description "Trace LSA analysis";
             }
             enum "packets" {
               description "Trace all OSPF packets";
             }
             enum "hello" {
               description "Trace hello packets";
             }
             enum "database-description" {
               description "Trace database description packets";
             }
             enum "lsa-request" {
               description "Trace LSA request packets";
             }
             enum "lsa-update" {
               description "Trace LSA update packets";
             }
             enum "lsa-ack" {
               description "Trace LSA acknowledgment packets";
             }
             enum "ldp-synchronization" {
               description "Trace synchronization between OSPF and LDP";
             }
             enum "on-demand" {
               description "Trace demand circuit extensions";
             }
             enum "nsr-synchronization" {
               description "Trace NSR synchronization events";
             }
             enum "graceful-restart" {
               description "Trace graceful restart";
             }
             enum "restart-signaling" {
               description "Trace restart signaling";
             }
             enum "backup-spf" {
               description "Trace backup SPF (LFA) specific events";
             }
             enum "source-packet-routing" {
               description "Trace source packet routing (SPRING) events";
             }
             enum "post-convergence-lfa" {
               description "Trace post-convergence-lfa related events";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     list topology {
       key name;
       ordered-by user;
       description "Topology parameters";
       leaf name {
         description "Topology name";
         type string;
       }
       uses apply-advanced;
       leaf disable {
         description "Disable this topology";
         type empty;
       }
       leaf topology-id {
         description "Topology identifier";
         type union {
           type string {
             pattern "<.*>|$.*";
           }
           type uint8 {
             range "32 .. 127";
           }
         }
       }
       leaf overload {
         description "Set the overload mode (repel transit traffic)";
         type empty;
       }
       leaf rib-group {
         description "Routing table group for importing routes";
         type string;
       }
       container spf-options {
         description "Configure options for SPF";
         uses apply-advanced;
         leaf delay {
           description "Time to wait before running an SPF";
           units "milliseconds";
           type union {
             type string {
               pattern "<.*>|$.*";
             }
             type uint32 {
               range "50 .. 8000";
             }
           }
         }
         leaf holddown {
           description "Time to hold down before running an SPF";
           units "milliseconds";
           type union {
             type string {
               pattern "<.*>|$.*";
             }
             type uint32 {
               range "2000 .. 20000";
             }
           }
         }
         leaf rapid-runs {
           description "Number of maximum rapid SPF runs before holddown";
           type union {
             type string {
               pattern "<.*>|$.*";
             }
             type uint32 {
               range "1 .. 10";
             }
           }
         }
         leaf no-ignore-our-externals {
           description "Do not ignore self-generated external and NSSA LSAs";
           type empty;
         }
       }
       container backup-spf-options {
         description "Configure options for backup SPF";
         uses apply-advanced;
         leaf disable {
           description "Do not run backup SPF";
           type empty;
         }
         leaf no-install {
           description "Do not install backup nexthops into the RIB";
           type empty;
         }
         leaf downstream-paths-only {
           description "Use only downstream backup paths";
           type empty;
         }
         container remote-backup-calculation {
           presence "enable remote-backup-calculation";
           description "Calculate Remote LFA backup nexthops";
           uses apply-advanced;
           container pq-nodes-nearest-to-source {
             description "PQ nodes selection based upon nearest to source";
             uses apply-advanced;
             leaf percent {
               description "Selection percentage for nearest to source";
               type union {
                 type string {
                   pattern "<.*>|$.*";
                 }
                 type uint32 {
                   range "10 .. 100";
                 }
               }
             }
           }
         }
         container use-post-convergence-lfa {
           presence "enable use-post-convergence-lfa";
           description "Calculate post-convergence backup paths";
           uses apply-advanced;
           leaf maximum-labels {
             description "Maximum number of labels installed for post-convergence paths";
             type union {
               type string {
                 pattern "<.*>|$.*";
               }
               type uint32 {
                 range "2 .. 5";
               }
             }
           }
           leaf maximum-backup-paths {
             description "Maximum number of equal-cost post-convergence paths installed";
             type union {
               type string {
                 pattern "<.*>|$.*";
               }
               type uint32 {
                 range "1 .. 8";
               }
             }
           }
         }
         container per-prefix-calculation {
           description "Calculate backup nexthops for non-best prefix originators";
           uses apply-advanced;
           leaf stubs {
             description "Per prefix calculation for stubs only";
             type empty;
           }
           leaf summary {
             description "Per prefix calculation for summary originators only";
             type empty;
           }
           leaf externals {
             description "Per prefix calculation for externals";
             type empty;
           }
           leaf all {
             description "Per prefix calculation for all";
             type empty;
           }
         }
         leaf node-link-degradation {
           description "Degrade to link protection when nodelink protection not available";
           type empty;
         }
         leaf use-source-packet-routing {
           description "Use spring backup paths for inet.0 routes";
           type empty;
         }
       }
       leaf prefix-export-limit {
         description "Maximum number of prefixes that can be exported";
         type union {
           type string {
             pattern "<.*>|$.*";
           }
           type uint32 {
             range "0 .. 4294967295";
           }
         }
       }
     }
     container spf-options {
       description "Configure options for SPF";
       uses apply-advanced;
       leaf delay {
         description "Time to wait before running an SPF";
         units "milliseconds";
         type union {
           type string {
             pattern "<.*>|$.*";
           }
           type uint32 {
             range "50 .. 8000";
           }
         }
       }
       leaf holddown {
         description "Time to hold down before running an SPF";
         units "milliseconds";
         type union {
           type string {
             pattern "<.*>|$.*";
           }
           type uint32 {
             range "2000 .. 20000";
           }
         }
       }
       leaf rapid-runs {
         description "Number of maximum rapid SPF runs before holddown";
         type union {
           type string {
             pattern "<.*>|$.*";
           }
           type uint32 {
             range "1 .. 10";
           }
         }
       }
       leaf no-ignore-our-externals {
         description "Do not ignore self-generated external and NSSA LSAs";
         type empty;
       }
     }
     container backup-spf-options {
       description "Configure options for backup SPF";
       uses apply-advanced;
       leaf disable {
         description "Do not run backup SPF";
         type empty;
       }
       leaf no-install {
         description "Do not install backup nexthops into the RIB";
         type empty;
       }
       leaf downstream-paths-only {
         description "Use only downstream backup paths";
         type empty;
       }
       container remote-backup-calculation {
         presence "enable remote-backup-calculation";
         description "Calculate Remote LFA backup nexthops";
         uses apply-advanced;
         container pq-nodes-nearest-to-source {
           description "PQ nodes selection based upon nearest to source";
           uses apply-advanced;
           leaf percent {
             description "Selection percentage for nearest to source";
             type union {
               type string {
                 pattern "<.*>|$.*";
               }
               type uint32 {
                 range "10 .. 100";
               }
             }
           }
         }
       }
       container use-post-convergence-lfa {
         presence "enable use-post-convergence-lfa";
         description "Calculate post-convergence backup paths";
         uses apply-advanced;
         leaf maximum-labels {
           description "Maximum number of labels installed for post-convergence paths";
           type union {
             type string {
               pattern "<.*>|$.*";
             }
             type uint32 {
               range "2 .. 5";
             }
           }
         }
         leaf maximum-backup-paths {
           description "Maximum number of equal-cost post-convergence paths installed";
           type union {
             type string {
               pattern "<.*>|$.*";
             }
             type uint32 {
               range "1 .. 8";
             }
           }
         }
       }
       container per-prefix-calculation {
         description "Calculate backup nexthops for non-best prefix originators";
         uses apply-advanced;
         leaf stubs {
           description "Per prefix calculation for stubs only";
           type empty;
         }
         leaf summary {
           description "Per prefix calculation for summary originators only";
           type empty;
         }
         leaf externals {
           description "Per prefix calculation for externals";
           type empty;
         }
         leaf all {
           description "Per prefix calculation for all";
           type empty;
         }
       }
       leaf node-link-degradation {
         description "Degrade to link protection when nodelink protection not available";
         type empty;
       }
       leaf use-source-packet-routing {
         description "Use spring backup paths for inet.0 routes";
         type empty;
       }
     }
     leaf prefix-export-limit {
       description "Maximum number of prefixes that can be exported";
       type union {
         type string {
           pattern "<.*>|$.*";
         }
         type uint32 {
           range "0 .. 4294967295";
         }
       }
     }
     container rib-groups {
       description "Routing table groups for importing OSPF routes";
       uses apply-advanced;
       leaf inet {
         description "Name of the IPv4/v6 routing table group";
         type string;
       }
       leaf inet3 {
         description "Name of the IPv4/v6 inet.3 routing table group";
         type string;
       }
     }
     leaf job-stats {
       description "Collect job statistics";
       type empty;
     }
     container overload {
       presence "enable overload";
       description "Set the overload mode (repel transit traffic)";
       uses apply-advanced;
       leaf timeout {
         description "Time after which overload mode is reset";
         units "seconds";
         type union {
           type string {
             pattern "<.*>|$.*";
           }
           type uint32 {
             range "60 .. 1800";
           }
         }
       }
       leaf allow-route-leaking {
         description "Allow routes to be leaked when overload is configured";
         type empty;
       }
       leaf stub-network {
         description "Advertise Stub Network with maximum metric";
         type empty;
       }
       leaf intra-area-prefix {
         description "Advertise Intra Area Prefix with maximum metric";
         type empty;
       }
       leaf as-external {
         description "Advertise As External with maximum usable metric";
         type empty;
       }
     }
     container database-protection {
       presence "enable database-protection";
       description "Configure database protection attributes";
       uses apply-advanced;
       leaf maximum-lsa {
         description "Maximum allowed non self-generated LSAs";
         type union {
           type string {
             pattern "<.*>|$.*";
           }
           type uint32 {
             range "1 .. 1000000";
           }
         }
       }
       leaf warning-only {
         description "Emit only a warning when LSA maximum limit is exceeded";
         type empty;
       }
       leaf warning-threshold {
         description "Percentage of LSA maximum above which to trigger warning";
         units "percent";
         type union {
           type string {
             pattern "<.*>|$.*";
           }
           type uint8 {
             range "30 .. 100";
           }
         }
       }
       leaf ignore-count {
         description "Maximum number of times to go into ignore state";
         type union {
           type string {
             pattern "<.*>|$.*";
           }
           type uint8 {
             range "1 .. 32";
           }
         }
       }
       leaf ignore-time {
         description "Time to stay in ignore state and ignore all neighbors";
         units "seconds";
         type union {
           type string {
             pattern "<.*>|$.*";
           }
           type uint16 {
             range "30 .. 3600";
           }
         }
       }
       leaf reset-time {
         description "Time after which the ignore count gets reset to zero";
         units "seconds";
         type union {
           type string {
             pattern "<.*>|$.*";
           }
           type uint32 {
             range "60 .. 86400";
           }
         }
       }
     }
     container graceful-restart {
       description "Configure graceful restart attributes";
       uses apply-advanced;
       choice enable-disable {
         case case_1 {
           leaf disable {
             description "Disable OSPF graceful restart capability";
             type empty;
           }
         }
       }
       leaf restart-duration {
         description "Time for all neighbors to become full";
         units "seconds";
         type union {
           type string {
             pattern "<.*>|$.*";
           }
           type uint32 {
             range "1 .. 3600";
           }
         }
       }
       leaf notify-duration {
         description "Time to send all max-aged grace LSAs";
         units "seconds";
         type union {
           type string {
             pattern "<.*>|$.*";
           }
           type uint32 {
             range "1 .. 3600";
           }
         }
       }
       container helper-disable {
         presence "enable helper-disable";
         description "Disable graceful restart helper capability";
         uses apply-advanced;
         choice disable-choices {
           case case_1 {
             leaf standard {
               description "Disable helper-mode for rfc3623 based GR";
               type empty;
             }
           }
           case case_2 {
             leaf restart-signaling {
               description "Disable helper mode for restart-signaling ";
               type empty;
             }
           }
           case case_3 {
             leaf both {
               description "Disable helper mode for both the types of GR";
               type empty;
             }
           }
         }
       }
       leaf no-strict-lsa-checking {
         description "Do not abort graceful helper mode upon LSA changes";
         type empty;
       }
     }
     container traffic-engineering {
       presence "enable traffic-engineering";
       description "Configure traffic engineering attributes";
       uses apply-advanced;
       leaf no-topology {
         description "Disable dissemination of TE link-state topology information";
         type empty;
       }
       leaf multicast-rpf-routes {
         description "Install routes for multicast RPF checks into inet.2";
         type empty;
       }
       leaf igp-topology {
         description "Download IGP topology into TED";
         type empty;
       }
       leaf ignore-lsp-metrics {
         description "Ignore label-switched path metrics when doing shortcuts";
         type empty;
       }
       container shortcuts {
         presence "enable shortcuts";
         description "Use label-switched paths as next hops, if possible";
         uses apply-advanced;
         leaf ignore-lsp-metrics {
           description "Ignore label-switched path metrics when doing shortcuts";
           status deprecated;
           type empty;
         }
         leaf lsp-metric-into-summary {
           description "Advertise LSP metric into summary LSAs";
           type empty;
         }
         list family {
           key name;
           ordered-by user;
           description "Address family specific traffic-engineering attributes";
           leaf name {
             type enumeration {
               enum "inet" {
                 description "IPv4 family";
               }
               enum "inet-mpls" {
                 description "IPv4-MPLS family";
               }
             }
           }
           uses apply-advanced;
         }
       }
       leaf advertise-unnumbered-interfaces {
         description "Advertise unnumbered interfaces";
         type empty;
       }
       leaf credibility-protocol-preference {
         description "TED protocol credibility follows protocol preference";
         type empty;
       }
     }
     leaf route-type-community {
       description "Specify BGP extended community value to encode OSPF route type";
       type enumeration {
         enum "iana" {
           description "BGP extended community value used is 0x0306";
         }
         enum "vendor" {
           description "Vendor BGP extended community value used is 0x8000";
         }
       }
     }
     container domain-id {
       description "Configure domain ID";
       choice domain_id_or_disable {
         case case_1 {
           leaf domain-id {
             description "Domain ID";
             type string;
           }
         }
         case case_2 {
           leaf disable {
             description "Disable domain ID";
             type empty;
           }
         }
       }
     }
     choice domain_vpn_tag_or_disable {
       case case_1 {
         leaf domain-vpn-tag {
           description "Domain VPN tag for external LSA";
           type union {
             type string {
               pattern "<.*>|$.*";
             }
             type uint32 {
               range "0 .. 4294967295";
             }
           }
         }
       }
       case case_2 {
         leaf no-domain-vpn-tag {
           description "Disable domain VPN tag";
           type empty;
         }
       }
     }
     leaf preference {
       description "Preference of internal routes";
       type union {
         type uint32;
         type string {
           pattern "<.*>|$.*";
         }
       }
     }
     leaf external-preference {
       description "Preference of external routes";
       type union {
         type uint32;
         type string {
           pattern "<.*>|$.*";
         }
       }
     }
     leaf labeled-preference {
       description "Preference of labeled routes";
       type union {
         type uint32;
         type string {
           pattern "<.*>|$.*";
         }
       }
     }
     leaf-list export {
       ordered-by user;
       description "Export policy";
       type jt:policy-algebra;
     }
     leaf-list import {
       ordered-by user;
       description "Import policy (for external routes or setting priority)";
       type jt:policy-algebra;
     }
     leaf reference-bandwidth {
       description "Bandwidth for calculating metric defaults";
       type string;
     }
     leaf lsa-refresh-interval {
       description "LSA refresh interval (minutes)";
       default "50";
       type union {
         type string {
           pattern "<.*>|$.*";
         }
         type uint32 {
           range "25 .. 50";
         }
       }
     }
     leaf spf-delay {
       description "Time to wait before running an SPF";
       status deprecated;
       units "milliseconds";
       type union {
         type string {
           pattern "<.*>|$.*";
         }
         type uint32 {
           range "50 .. 8000";
         }
       }
     }
     leaf no-rfc-1583 {
       description "Disable RFC1583 compatibility";
       type empty;
     }
     container source-packet-routing {
       presence "enable source-packet-routing";
       description "Enable source packet routing (SPRING)";
       uses apply-advanced;
       container adjacency-segment {
         description "Attributes for adjacency segments in spring";
         uses apply-advanced;
         leaf hold-time {
           description "Retain time of Adjacency segment after isolating from an interface";
           type union {
             type string {
               pattern "<.*>|$.*";
             }
             type uint32 {
               range "180000 .. 900000";
             }
           }
         }
       }
       leaf-list prefix-segment {
         ordered-by user;
         description "Prefix Segment policy";
         type jt:policy-algebra;
       }
       leaf explicit-null {
         description "Set E and P bits in all Prefix SID advertisements";
         type empty;
       }
       container node-segment {
         presence "enable node-segment";
         description "Enable support for Node segments in SPRING";
         uses apply-advanced;
         leaf ipv4-index {
           description "Set ipv4 node segment index";
           type union {
             type string {
               pattern "<.*>|$.*";
             }
             type uint32 {
               range "0 .. 16383";
             }
           }
         }
         leaf index-range {
           description "Set range of node segment indices allowed";
           type union {
             type string {
               pattern "<.*>|$.*";
             }
             type uint32 {
               range "32 .. 16384";
             }
           }
         }
       }
       leaf mapping-server {
         description "Mapping server name";
         type string;
       }
       leaf install-prefix-sid-for-best-route {
         description "For best route install a exact prefix sid route";
         type empty;
       }
     }
     leaf forwarding-address-to-broadcast {
       description "Set forwarding address in Type 5 LSA in broadcast network";
       type empty;
     }
     choice nssa-abr-option {
       case case_1 {
         leaf no-nssa-abr {
           description "Disable full NSSA functionality at ABR";
           type empty;
         }
       }
     }
     container sham-link {
       presence "enable sham-link";
       description "Configure parameters for sham links";
       uses apply-advanced;
       leaf local {
         description "Local sham link endpoint address";
         type jt:ipaddr;
       }
       leaf no-advertise-local {
         description "Don't advertise local sham link endpoint as stub in router LSA";
         status deprecated;
         type empty;
       }
     }
     list area {
       key name;
       ordered-by user;
       description "Configure an OSPF area";
       leaf name {
         description "Area ID";
         type jt:areaid;
       }
       uses apply-advanced;
       choice stub-option {
         case case_1 {
           container stub {
             presence "enable stub";
             description "Configure a stub area";
             leaf default-metric {
               description "Metric for the default route in this stub area";
               type union {
                 type string {
                   pattern "<.*>|$.*";
                 }
                 type uint32 {
                   range "1 .. 16777215";
                 }
               }
             }
             choice summaries-choice {
               leaf summaries {
                 description "Flood summary LSAs into this stub area";
                 type empty;
               }
               leaf no-summaries {
                 description "Don't flood summary LSAs into this stub area";
                 type empty;
               }
             }
           }
         }
         case case_2 {
           container nssa {
             presence "enable nssa";
             description "Configure a not-so-stubby area";
             uses apply-advanced;
             container default-lsa {
               presence "enable default-lsa";
               description "Configure a default LSA";
               uses apply-advanced;
               leaf default-metric {
                 description "Metric for the default route in this area";
                 type union {
                   type string {
                     pattern "<.*>|$.*";
                   }
                   type uint32 {
                     range "1 .. 16777215";
                   }
                 }
               }
               leaf metric-type {
                 description "External metric type for the default type 7 LSA";
                 type union {
                   type string {
                     pattern "<.*>|$.*";
                   }
                   type uint32 {
                     range "1 .. 2";
                   }
                 }
               }
               leaf type-7 {
                 description "Flood type 7 default LSA if no-summaries is configured";
                 type empty;
               }
             }
             leaf default-metric {
               description "Metric for the default route in this area";
               status deprecated;
               type union {
                 type string {
                   pattern "<.*>|$.*";
                 }
                 type uint32 {
                   range "1 .. 16777215";
                 }
               }
             }
             leaf metric-type {
               description "External metric type for the default type 7 LSA";
               status deprecated;
               type union {
                 type string {
                   pattern "<.*>|$.*";
                 }
                 type uint32 {
                   range "1 .. 2";
                 }
               }
             }
             choice summaries-choice {
               leaf summaries {
                 description "Flood summary LSAs into this NSSA area";
                 type empty;
               }
               leaf no-summaries {
                 description "Don't flood summary LSAs into this NSSA area";
                 type empty;
               }
             }
             list area-range {
               key name;
               ordered-by user;
               description "Configure NSSA area ranges";
               leaf name {
                 description "Range to summarize NSSA routes in this area";
                 type jt:ipprefix;
               }
               uses apply-advanced;
               leaf restrict {
                 description "Restrict advertisement of this area range";
                 type empty;
               }
               leaf exact {
                 description "Enforce exact match for advertisement of this area range";
                 type empty;
               }
               container override-metric {
                 presence "enable override-metric";
                 description "Override the dynamic metric for this area-range";
                 uses apply-advanced;
                 leaf metric {
                   description "Metric value";
                   type union {
                     type string {
                       pattern "<.*>|$.*";
                     }
                     type uint32 {
                       range "1 .. 16777215";
                     }
                   }
                 }
                 leaf metric-type {
                   description "Set the metric type for the override metric";
                   default "1";
                   type union {
                     type string {
                       pattern "<.*>|$.*";
                     }
                     type uint32 {
                       range "1 .. 2";
                     }
                   }
                 }
               }
             }
           }
         }
       }
       list area-range {
         key name;
         ordered-by user;
         description "Configure area ranges";
         leaf name {
           description "Range to summarize routes in this area";
           type jt:ipprefix;
         }
         uses apply-advanced;
         leaf restrict {
           description "Restrict advertisement of this area range";
           type empty;
         }
         leaf exact {
           description "Enforce exact match for advertisement of this area range";
           type empty;
         }
         leaf override-metric {
           description "Override the dynamic metric for this area-range";
           type union {
             type string {
               pattern "<.*>|$.*";
             }
             type uint32 {
               range "1 .. 16777215";
             }
           }
         }
       }
       leaf-list network-summary-export {
         ordered-by user;
         description "Export policy for Type 3 Summary LSAs";
         type jt:policy-algebra;
       }
       leaf-list network-summary-import {
         ordered-by user;
         description "Import policy for Type 3 Summary LSAs";
         type jt:policy-algebra;
       }
       leaf-list inter-area-prefix-export {
         ordered-by user;
         description "Export policy for Inter Area Prefix LSAs";
         type jt:policy-algebra;
       }
       leaf-list inter-area-prefix-import {
         ordered-by user;
         description "Import policy for Inter Area Prefix LSAs";
         type jt:policy-algebra;
       }
       leaf authentication-type {
         description "Authentication type";
         status deprecated;
         type enumeration {
           enum "none" {
             description "No authentication";
             status deprecated;
           }
           enum "simple" {
             description "Simple password authentication";
             status deprecated;
           }
           enum "md5" {
             description "MD5 authentication";
             status deprecated;
           }
         }
       }
       list virtual-link {
         key "neighbor-id transit-area";
         ordered-by user;
         description "Configure virtual links";
         leaf neighbor-id {
           description "Router ID of a virtual neighbor";
           type jt:ipv4addr;
         }
         leaf transit-area {
           description "Transit area in common with virtual neighbor";
           type jt:areaid;
         }
         uses apply-advanced;
         choice enable-disable {
           case case_1 {
             leaf disable {
               description "Disable this virtual link";
               type empty;
             }
           }
         }
         leaf retransmit-interval {
           description "Retransmission interval (seconds)";
           type union {
             type string {
               pattern "<.*>|$.*";
             }
             type uint32 {
               range "1 .. 65535";
             }
           }
         }
         leaf transit-delay {
           description "Transit delay (seconds)";
           type union {
             type string {
               pattern "<.*>|$.*";
             }
             type uint32 {
               range "1 .. 65535";
             }
           }
         }
         leaf hello-interval {
           description "Hello interval (seconds)";
           type union {
             type string {
               pattern "<.*>|$.*";
             }
             type uint32 {
               range "1 .. 255";
             }
           }
         }
         leaf dead-interval {
           description "Dead interval (seconds)";
           type union {
             type string {
               pattern "<.*>|$.*";
             }
             type uint32 {
               range "1 .. 65535";
             }
           }
         }
         leaf mtu {
           description "Maximum OSPF packet size";
           type union {
             type string {
               pattern "<.*>|$.*";
             }
             type uint32 {
               range "128 .. 65535";
             }
           }
         }
         choice auth {
           case case_1 {
             container authentication {
               uses juniper-ospf-authentication;
             }
           }
           case case_2 {
             container authentication-key {
               description "Authentication key";
               status deprecated;
               leaf keyname {
                 description "Authentication key value";
                 type jt:unreadable;
               }
               leaf key-id {
                 description "Key ID for MD5 authentication";
                 type union {
                   type string {
                     pattern "<.*>|$.*";
                   }
                   type uint32 {
                     range "0 .. 255";
                   }
                 }
               }
             }
           }
         }
         leaf demand-circuit {
           description "Interface functions as a demand circuit";
           type empty;
         }
         leaf flood-reduction {
           description "Enable flood reduction";
           type empty;
         }
         leaf no-neighbor-down-notification {
           description "Don't inform other protocols about neighbor down events";
           type empty;
         }
         leaf ipsec-sa {
           description "IPSec security association name";
           type string {
             length "1 .. 32";
           }
         }
         list topology {
           key name;
           ordered-by user;
           description "Topology specific attributes";
           leaf name {
             description "Topology name";
             type string;
           }
           uses apply-advanced;
           leaf disable {
             description "Disable this topology";
             type empty;
           }
           leaf metric {
             description "Topology metric";
             type union {
               type string {
                 pattern "<.*>|$.*";
               }
               type uint16 {
                 range "1 .. 65535";
               }
             }
           }
           container bandwidth-based-metrics {
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint16 {
                     range "1 .. 65535";
                   }
                 }
               }
             }
           }
         }
       }
       list sham-link-remote {
         key name;
         ordered-by user;
         description "Configure parameters for remote sham link endpoint";
         leaf name {
           description "Remote sham link endpoint address";
           type jt:ipaddr;
         }
         uses apply-advanced;
         leaf metric {
           description "Sham link metric";
           type union {
             type string {
               pattern "<.*>|$.*";
             }
             type uint16 {
               range "1 .. 65535";
             }
           }
         }
         leaf ipsec-sa {
           description "IPSec security association name";
           type string {
             length "1 .. 32";
           }
         }
         leaf demand-circuit {
           description "Interface functions as a demand circuit";
           type empty;
         }
         leaf flood-reduction {
           description "Enable flood reduction";
           type empty;
         }
         list topology {
           key name;
           ordered-by user;
           description "Topology specific attributes";
           leaf name {
             description "Topology name";
             type string;
           }
           uses apply-advanced;
           leaf disable {
             description "Disable this topology";
             type empty;
           }
           leaf metric {
             description "Topology metric";
             type union {
               type string {
                 pattern "<.*>|$.*";
               }
               type uint16 {
                 range "1 .. 65535";
               }
             }
           }
           container bandwidth-based-metrics {
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint16 {
                     range "1 .. 65535";
                   }
                 }
               }
             }
           }
         }
       }
       list interface {
         key name;
         ordered-by user;
         description "Include an interface in this area";
         leaf name {
           description "Interface name";
           type union {
             type jt:ipv4addr-or-interface;
             type string {
               pattern "<.*>|$.*";
             }
           }
         }
         uses apply-advanced;
         choice enable-disable {
           case case_1 {
             leaf disable {
               description "Disable OSPF on this interface";
               type empty;
             }
           }
         }
         leaf interface-type {
           description "Type of interface";
           type enumeration {
             enum "nbma" {
               description "Nonbroadcast multiaccess";
             }
             enum "p2mp" {
               description "Point-to-multipoint NBMA";
             }
             enum "p2p" {
               description "Point-to-point";
             }
             enum "p2mp-over-lan" {
               description "Point-to-multipoint over LAN mode";
             }
           }
         }
         container post-convergence-lfa {
           presence "enable post-convergence-lfa";
           description "Protect interface using post-convergence backup path";
           uses apply-advanced;
           container node-protection {
             presence "enable node-protection";
             description "Compute backup path assuming node failure";
             uses apply-advanced;
             leaf cost {
               description "Cost for node protection";
               type union {
                 type string {
                   pattern "<.*>|$.*";
                 }
                 type uint16 {
                   range "1 .. 65535";
                 }
               }
             }
           }
         }
         choice protection-type {
           case case_1 {
             leaf link-protection {
               description "Protect interface from link faults only";
               type empty;
             }
           }
           case case_2 {
             leaf node-link-protection {
               description "Protect interface from both link and node faults";
               type empty;
             }
           }
         }
         leaf no-eligible-backup {
           description "Not eligible to backup traffic from protected interfaces";
           type empty;
         }
         leaf no-eligible-remote-backup {
           description "Not eligible for Remote-LFA backup traffic from protected interfaces";
           type empty;
         }
         container passive {
           presence "enable passive";
           description "Do not run OSPF, but advertise it";
           uses apply-advanced;
           container traffic-engineering {
             description "Advertise TE link information";
             uses apply-advanced;
             leaf remote-node-id {
               description "Remote address of the link";
               type jt:ipaddr;
             }
             leaf remote-node-router-id {
               description "TE Router-ID of the remote node";
               type jt:ipv4addr;
             }
           }
         }
         leaf secondary {
           description "Treat interface as secondary";
           type empty;
         }
         leaf own-router-lsa {
           description "Generate a separate router LSA for this interface";
           type empty;
         }
         container bandwidth-based-metrics {
           description "Configure bandwidth based metrics";
           uses apply-advanced;
           list bandwidth {
             key name;
             description "Bandwidth threshold";
             leaf name {
               type string;
             }
             leaf metric {
               description "Metric associated with specified bandwidth";
               type union {
                 type string {
                   pattern "<.*>|$.*";
                 }
                 type uint16 {
                   range "1 .. 65535";
                 }
               }
             }
           }
         }
         leaf metric {
           description "Interface metric";
           type union {
             type string {
               pattern "<.*>|$.*";
             }
             type uint16 {
               range "1 .. 65535";
             }
           }
         }
         leaf te-metric {
           description "Traffic engineering metric";
           type union {
             type string {
               pattern "<.*>|$.*";
             }
             type uint32 {
               range "1 .. 4294967295";
             }
           }
         }
         leaf priority {
           description "Designated router priority";
           type union {
             type string {
               pattern "<.*>|$.*";
             }
             type uint32 {
               range "0 .. 255";
             }
           }
         }
         container ldp-synchronization {
           description "Advertise maximum metric until LDP is operational";
           presence "enable ldp-synchronization";
           uses ldp-sync-obj;
         }
         leaf retransmit-interval {
           description "Retransmission interval (seconds)";
           type union {
             type string {
               pattern "<.*>|$.*";
             }
             type uint32 {
               range "1 .. 65535";
             }
           }
         }
         leaf transit-delay {
           description "Transit delay (seconds)";
           type union {
             type string {
               pattern "<.*>|$.*";
             }
             type uint32 {
               range "1 .. 65535";
             }
           }
         }
         leaf hello-interval {
           description "Hello interval (seconds)";
           type union {
             type string {
               pattern "<.*>|$.*";
             }
             type uint32 {
               range "1 .. 255";
             }
           }
         }
         leaf dead-interval {
           description "Dead interval (seconds)";
           type union {
             type string {
               pattern "<.*>|$.*";
             }
             type uint32 {
               range "1 .. 65535";
             }
           }
         }
         leaf mtu {
           description "Maximum OSPF packet size";
           type union {
             type string {
               pattern "<.*>|$.*";
             }
             type uint32 {
               range "128 .. 65535";
             }
           }
         }
         choice auth {
           case case_1 {
             container authentication {
               uses juniper-ospf-authentication;
             }
           }
           case case_2 {
             container authentication-key {
               description "Authentication key";
               status deprecated;
               leaf keyname {
                 description "Authentication key value";
                 type jt:unreadable;
               }
               leaf key-id {
                 description "Key ID for MD5 authentication";
                 type union {
                   type string {
                     pattern "<.*>|$.*";
                   }
                   type uint32 {
                     range "0 .. 255";
                   }
                 }
               }
             }
           }
         }
         leaf demand-circuit {
           description "Interface functions as a demand circuit";
           type empty;
         }
         leaf flood-reduction {
           description "Enable flood reduction";
           type empty;
         }
         leaf no-neighbor-down-notification {
           description "Don't inform other protocols about neighbor down events";
           type empty;
         }
         leaf ipsec-sa {
           description "IPSec security association name";
           type string {
             length "1 .. 32";
           }
         }
         list topology {
           key name;
           ordered-by user;
           description "Topology specific attributes";
           leaf name {
             description "Topology name";
             type string;
           }
           uses apply-advanced;
           leaf disable {
             description "Disable this topology";
             type empty;
           }
           leaf metric {
             description "Topology metric";
             type union {
               type string {
                 pattern "<.*>|$.*";
               }
               type uint16 {
                 range "1 .. 65535";
               }
             }
           }
           container bandwidth-based-metrics {
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint16 {
                     range "1 .. 65535";
                   }
                 }
               }
             }
           }
         }
         leaf transmit-interval {
           description "OSPF packet transmit interval (milliseconds)";
           status deprecated;
           type union {
             type string {
               pattern "<.*>|$.*";
             }
             type uint32 {
               range "1 .. 4294967295";
             }
           }
         }
         container bfd-liveness-detection {
           description "Bidirectional Forwarding Detection options";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
           container authentication {
             description "Authentication options";
             uses apply-advanced;
             leaf key-chain {
               description "Key chain name";
               type string;
             }
             leaf algorithm {
               description "Algorithm name";
               type enumeration {
                 enum "simple-password" {
                   description "Simple password";
                 }
                 enum "keyed-md5" {
                   description "Keyed message Digest 5";
                 }
                 enum "meticulous-keyed-md5" {
                   description "Meticulous keyed message Digest 5";
                 }
                 enum "keyed-sha-1" {
                   description "Keyed secure hash algorithm (SHA1) ";
                 }
                 enum "meticulous-keyed-sha-1" {
                   description "Meticulous keyed secure hash algorithm (SHA1) ";
                 }
               }
             }
             leaf loose-check {
               description "Verify authentication only if authentication is negotiated";
               type empty;
             }
           }
           leaf full-neighbors-only {
             description "Setup BFD sessions only to Full neighbors";
             type empty;
           }
         }
         leaf dynamic-neighbors {
           description "Learn neighbors dynamically on a p2mp interface";
           type empty;
         }
         leaf no-advertise-adjacency-segment {
           description "Do not advertise an adjacency segment for this interface";
           type empty;
         }
         list neighbor {
           key name;
           ordered-by user;
           description "NBMA neighbor";
           leaf name {
             description "Address of neighbor";
             type jt:ipaddr;
           }
           leaf eligible {
             description "Eligible to be DR on an NBMA network";
             type empty;
           }
         }
         leaf poll-interval {
           description "Poll interval for NBMA interfaces";
           type union {
             type string {
               pattern "<.*>|$.*";
             }
             type uint32 {
               range "1 .. 65535";
             }
           }
         }
         leaf no-interface-state-traps {
           description "Do not send interface state change traps";
           type empty;
         }
       }
       leaf no-source-packet-routing {
         description "Disable SPRING in this area";
         type empty;
       }
       leaf no-context-identifier-advertisement {
         description "Disable context identifier advertisments in this area";
         type empty;
       }
       list context-identifier {
         key name;
         ordered-by user;
         description "Configure context identifier in support of edge protection";
         leaf name {
           description "Context identifier";
           type jt:ipv4addr;
         }
         uses apply-advanced;
       }
       list label-switched-path {
         key name;
         ordered-by user;
         description "Configuration for advertisement of a label-switched path";
         leaf name {
           description "Name of label-switched path to be advertised";
           type string {
             length "1 .. 64";
           }
         }
         uses apply-advanced;
         choice enable-disable {
           case case_1 {
             leaf disable {
               description "Disable OSPF on this label-switched path";
               type empty;
             }
           }
         }
         leaf metric {
           description "Interface metric";
           type union {
             type string {
               pattern "<.*>|$.*";
             }
             type uint16 {
               range "1 .. 65535";
             }
           }
         }
         list topology {
           key name;
           ordered-by user;
           description "Topology specific attributes";
           leaf name {
             description "Topology name";
             type string;
           }
           uses apply-advanced;
           leaf disable {
             description "Disable this topology";
             type empty;
           }
           leaf metric {
             description "Topology metric";
             type union {
               type string {
                 pattern "<.*>|$.*";
               }
               type uint16 {
                 range "1 .. 65535";
               }
             }
           }
           container bandwidth-based-metrics {
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint16 {
                     range "1 .. 65535";
                   }
                 }
               }
             }
           }
         }
       }
       list peer-interface {
         key name;
         ordered-by user;
         description "Configuration for peer interface";
         leaf name {
           description "Name of peer interface";
           type string;
         }
         uses apply-advanced;
         choice enable-disable {
           case case_1 {
             leaf disable {
               description "Disable OSPF on this control peer";
               type empty;
             }
           }
         }
         leaf retransmit-interval {
           description "Retransmission interval (seconds)";
           type union {
             type string {
               pattern "<.*>|$.*";
             }
             type uint32 {
               range "1 .. 65535";
             }
           }
         }
         leaf transit-delay {
           description "Transit delay (seconds)";
           type union {
             type string {
               pattern "<.*>|$.*";
             }
             type uint32 {
               range "1 .. 65535";
             }
           }
         }
         leaf hello-interval {
           description "Hello interval (seconds)";
           type union {
             type string {
               pattern "<.*>|$.*";
             }
             type uint32 {
               range "1 .. 255";
             }
           }
         }
         leaf dead-interval {
           description "Dead interval (seconds)";
           type union {
             type string {
               pattern "<.*>|$.*";
             }
             type uint32 {
               range "1 .. 65535";
             }
           }
         }
         leaf mtu {
           description "Maximum OSPF packet size";
           type union {
             type string {
               pattern "<.*>|$.*";
             }
             type uint32 {
               range "128 .. 65535";
             }
           }
         }
         choice auth {
           case case_1 {
             container authentication {
               uses juniper-ospf-authentication;
             }
           }
           case case_2 {
             container authentication-key {
               description "Authentication key";
               status deprecated;
               leaf keyname {
                 description "Authentication key value";
                 type jt:unreadable;
               }
               leaf key-id {
                 description "Key ID for MD5 authentication";
                 type union {
                   type string {
                     pattern "<.*>|$.*";
                   }
                   type uint32 {
                     range "0 .. 255";
                   }
                 }
               }
             }
           }
         }
         leaf demand-circuit {
           description "Interface functions as a demand circuit";
           type empty;
         }
         leaf flood-reduction {
           description "Enable flood reduction";
           type empty;
         }
         leaf no-neighbor-down-notification {
           description "Don't inform other protocols about neighbor down events";
           type empty;
         }
       }
     }
   }
   grouping juniper-protocols-overlayd {
     uses apply-advanced;
     container traceoptions {
       description "Overlayd trace options";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing flag parameters";
         leaf name {
           type enumeration {
             enum "socket" {
               description "Trace overlay daemon socket events";
             }
             enum "rtsock" {
               description "Trace overlay daemon rtsock events";
             }
             enum "config" {
               description "Trace overlay daemon config events";
             }
             enum "all" {
               description "Trace everything";
             }
           }
         }
       }
     }
   }
   grouping juniper-protocols-pgm {
     uses apply-advanced;
     container traceoptions {
       description "PGM trace options";
       uses apply-advanced;
       list flag {
         key name;
         ordered-by user;
         description "Tracing parameters";
         leaf name {
           type enumeration {
             enum "init" {
               description "Trace initialization events";
             }
             enum "show" {
               description "Trace show command servicing";
             }
             enum "route-socket" {
               description "Trace route-socket events";
             }
             enum "parse" {
               description "Trace parser processing";
             }
             enum "state" {
               description "Trace state transitions";
             }
             enum "packets" {
               description "Trace packet processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
   }
   grouping juniper-protocols-pim {
     uses apply-advanced;
     container family {
       description "Local address family";
       container any {
         presence "enable any";
         description "Default properties for all address families";
         uses apply-advanced;
         leaf disable {
           description "Disable all families";
           type empty;
         }
       }
       container inet {
         presence "enable inet";
         description "IPv4 specific properties";
         uses apply-advanced;
         choice enable-disable {
           case case_1 {
             leaf disable {
               description "Disable PIMv4 on all interfaces";
               type empty;
             }
           }
         }
       }
       container inet6 {
         presence "enable inet6";
         description "IPv6 specific properties";
         uses apply-advanced;
         choice enable-disable {
           case case_1 {
             leaf disable {
               description "Disable PIMv6 on all interfaces";
               type empty;
             }
           }
         }
       }
     }
     choice enable-disable {
       case case_1 {
         leaf disable {
           description "Disable PIM";
           type empty;
         }
       }
     }
     container nonstop-routing {
       description "Configure PIM nonstop-routing attributes";
       uses apply-advanced;
       choice enable-disable {
         case case_1 {
           leaf disable {
             description "Disable non-stop routing for PIM";
             type empty;
           }
         }
       }
     }
     container traceoptions {
       description "Trace options for PIM";
       uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "route" {
               description "Trace routing information";
             }
             enum "packets" {
               description "Trace all PIM packets";
             }
             enum "hello" {
               description "Trace hello packets";
             }
             enum "register" {
               description "Trace register/register-stop messages";
             }
             enum "join" {
               description "Trace join/prune/graft/graft-ack messages";
             }
             enum "prune" {
               description "Trace join/prune/graft/graft-ack messages";
             }
             enum "graft" {
               description "Trace join/prune/graft/graft-ack messages";
             }
             enum "bootstrap" {
               description "Trace bootstrap/RP/auto-RP messages";
             }
             enum "rp" {
               description "Trace bootstrap/RP/auto-RP messages";
             }
             enum "autorp" {
               description "Trace bootstrap/RP/auto-RP messages";
             }
             enum "assert" {
               description "Trace assert messages";
             }
             enum "mdt" {
               description "Trace messages related to multicast data tunnels";
             }
             enum "nsr-synchronization" {
               description "Trace NSR synchronization events";
             }
             enum "bidirectional-df-election" {
               description "Trace bidirectional PIM DF election events";
             }
             enum "mofrr" {
               description "Trace Multicast only Fast Re-Route messages";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
         container filter {
           description "Filter to apply to this flag";
           presence "enable filter";
           uses pim_filter_obj;
         }
       }
     }
     container dense-groups {
       description "Dense mode groups for sparse-dense mode";
       uses apply-advanced;
       leaf dynamic-reject {
         description "Reject dynamic autorp negative dense-mode prefixes learnt from network";
         type empty;
       }
       list pim-dense-group-type {
         key name;
         ordered-by user;
         leaf name {
           description "Group address or range to forward in dense mode";
           type jt:ipprefix;
         }
         choice dense-group-flags {
           case case_1 {
             leaf reject {
               description "Do not include prefix as dense mode; force sparse mode";
               type empty;
             }
           }
           case case_2 {
             leaf announce {
               description "Advertise as negative prefix in auto-RP announce messages";
               type empty;
             }
           }
         }
       }
     }
     leaf vpn-tunnel-source {
       description "Source address for the provider space mGRE tunnel";
       status deprecated;
       type jt:ipv4addr;
     }
     leaf vpn-group-address {
       description "Group address for the VPN in provider space";
       status deprecated;
       type jt:ipv4addr;
     }
     leaf-list tunnel-devices {
       ordered-by user;
       description "Tunnel devices to be used for creating mt interfaces";
       type union {
         type jt:interface-device;
         type string {
           pattern "<.*>|$.*";
         }
       }
     }
     container rpf-selection {
       description "Select RPF neighbor";
       uses apply-advanced;
       list group {
         key name;
         ordered-by user;
         description "IP prefix of multicast group";
         leaf name {
           description "IP prefix of group";
           type jt:ipprefix;
         }
         uses apply-advanced;
         container wildcard-source {
           presence "enable wildcard-source";
           description "Select RPF for (*,g) and unspecified (s,g) joins";
           uses apply-advanced;
           leaf next-hop {
             description "Next-hop address";
             type jt:ipaddr;
           }
         }
         list source {
           key name;
           ordered-by user;
           description "IP prefix of one or more multicast sources";
           leaf name {
             description "IP prefix of source";
             type jt:ipprefix;
           }
           uses apply-advanced;
           leaf next-hop {
             description "Next-hop address";
             type jt:ipaddr;
           }
         }
       }
       list prefix-list {
         key name;
         ordered-by user;
         description "Multicast group prefix list";
         leaf name {
           description "Name of prefix list to match against";
           type string;
         }
         uses apply-advanced;
         container wildcard-source {
           presence "enable wildcard-source";
           description "Select RPF for (*,g) and unspecified (s,g) joins";
           uses apply-advanced;
           leaf next-hop {
             description "Next-hop address";
             type jt:ipaddr;
           }
         }
         list source {
           key name;
           ordered-by user;
           description "IP prefix of one or more multicast sources";
           leaf name {
             description "IP prefix of source";
             type jt:ipprefix;
           }
           uses apply-advanced;
           leaf next-hop {
             description "Next-hop address";
             type jt:ipaddr;
           }
         }
       }
     }
     container mvpn {
       presence "enable mvpn";
       description "PIM MVPN control-plane options";
       uses apply-advanced;
       container autodiscovery {
         description "PE router autodiscovery options for SSM MDTs";
         status deprecated;
         uses apply-advanced;
         leaf inet-mdt {
           description "MDT-SAFI PE autodiscovery for SSM MDTs";
           type empty;
         }
       }
       container family {
         description "PIM MVPN address family";
         uses apply-advanced;
         container inet {
           description "IPv4 PIM MVPN specific properties";
           uses apply-advanced;
           leaf rosen-mvpn {
             status deprecated;
             type empty;
           }
           leaf ngen-mvpn {
             status deprecated;
             type empty;
           }
           container autodiscovery {
             description "PE router autodiscovery options for SSM MDTs";
             uses apply-advanced;
             leaf inet-mdt {
               description "MDT-SAFI PE autodiscovery for SSM MDTs";
               type empty;
             }
           }
           leaf disable {
             description "Disable family IPv4";
             type empty;
           }
         }
         container inet6 {
           description "IPv6 PIM MVPN specific properties";
           uses apply-advanced;
           leaf rosen-mvpn {
             status deprecated;
             type empty;
           }
           leaf ngen-mvpn {
             status deprecated;
             type empty;
           }
           container autodiscovery {
             description "PE router autodiscovery options for SSM MDTs";
             uses apply-advanced;
             leaf inet-mdt {
               description "MDT-SAFI PE autodiscovery for SSM MDTs";
               type empty;
             }
           }
           leaf disable {
             description "Disable family IPv6";
             type empty;
           }
         }
       }
     }
     container rib-group {
       description "Routing table group";
       uses rib_group_type;
     }
     leaf-list import {
       ordered-by user;
       description "PIM sparse import join policy";
       type jt:policy-algebra;
     }
     leaf-list export {
       ordered-by user;
       description "PIM sparse export join policy";
       type jt:policy-algebra;
     }
     container mldp-inband-signalling {
       presence "enable mldp-inband-signalling";
       uses apply-advanced;
       leaf-list policy {
         ordered-by user;
         description "PIM MLDP join translation filter policy";
         type jt:policy-algebra;
       }
     }
     container rpf-vector {
       description "RPF vector TLV";
       uses apply-advanced;
       leaf-list policy {
         ordered-by user;
         description "RPF vector TLV include policy";
         type jt:policy-algebra;
       }
     }
     leaf assert-timeout {
       description "Set assert timeout";
       default "180";
       type union {
         type string {
           pattern "<.*>|$.*";
         }
         type uint32 {
           range "5 .. 210";
         }
       }
     }
     leaf assert-robust-count {
       description "Number of assert messages an assert winner sends in one cycle";
       default "2";
       type union {
         type string {
           pattern "<.*>|$.*";
         }
         type uint32 {
           range "1 .. 5";
         }
       }
     }
     leaf join-prune-timeout {
       description "Set join/prune timeout";
       default "210";
       type union {
         type string {
           pattern "<.*>|$.*";
         }
         type uint32 {
           range "210 .. 420";
         }
       }
     }
     container spt-threshold {
       description "Set shortest-path-tree threshold policy";
       uses apply-advanced;
       leaf-list infinity {
         ordered-by user;
         description "Apply policy to always remain on shared tree";
         type jt:policy-algebra;
       }
     }
     container sglimit {
       description "Set limit on number of (S,G) states ";
       uses apply-advanced;
       list family {
         key name;
         ordered-by user;
         description "Protocol family";
         leaf name {
           type enumeration {
             enum "inet" {
               description "IPv4 family";
             }
             enum "inet6" {
               description "IPv6 family";
             }
           }
         }
         uses apply-advanced;
         leaf maximum {
           description "Maximum limit above which additional entries are not accepted";
           type union {
             type string {
               pattern "<.*>|$.*";
             }
             type uint32 {
               range "1 .. 65535";
             }
           }
         }
         leaf threshold {
           description "Percentage of maximum at which to start generating warnings";
           type union {
             type string {
               pattern "<.*>|$.*";
             }
             type uint32 {
               range "1 .. 100";
             }
           }
         }
         leaf log-interval {
           description "Time between successive log messages";
           type union {
             type string {
               pattern "<.*>|$.*";
             }
             type uint32 {
               range "1 .. 65535";
             }
           }
         }
       }
       leaf maximum {
         description "Maximum limit above which additional entries are not accepted";
         type union {
           type string {
             pattern "<.*>|$.*";
           }
           type uint32 {
             range "1 .. 65535";
           }
         }
       }
       leaf threshold {
         description "Percentage of maximum at which to start generating warnings";
         type union {
           type string {
             pattern "<.*>|$.*";
           }
           type uint32 {
             range "1 .. 100";
           }
         }
       }
       leaf log-interval {
         description "Time between successive log messages";
         type union {
           type string {
             pattern "<.*>|$.*";
           }
           type uint32 {
             range "1 .. 65535";
           }
         }
       }
     }
     container rp {
       description "Router's rendezvous point properties";
       uses apply-advanced;
       leaf bootstrap-priority {
         description "Eligibility to be the bootstrap router (IPv4 only)";
         type union {
           type string {
             pattern "<.*>|$.*";
           }
           type uint32 {
             range "0 .. 255";
           }
         }
       }
       leaf-list bootstrap-import {
         ordered-by user;
         description "Bootstrap import policy (IPv4 only)";
         type jt:policy-algebra;
       }
       leaf-list bootstrap-export {
         ordered-by user;
         description "Bootstrap export policy (IPv4 only)";
         type jt:policy-algebra;
       }
       container bootstrap {
         description "Bootstrap properties";
         uses apply-advanced;
         container family {
           description "Bootstrap address family";
           container inet {
             description "IPv4 bootstrap properties";
             uses pim_bootstrap_options_type;
           }
           container inet6 {
             description "IPv6 bootstrap properties";
             uses pim_bootstrap_options_type;
           }
         }
       }
       container register-limit {
         description "Set limit on incoming registers that create (S,G) state";
         uses apply-advanced;
         list family {
           key name;
           ordered-by user;
           description "Protocol family";
           leaf name {
             type enumeration {
               enum "inet" {
                 description "IPv4 family";
               }
               enum "inet6" {
                 description "IPv6 family";
               }
             }
           }
           uses apply-advanced;
           leaf maximum {
             description "Maximum limit above which additional entries are not accepted";
             type union {
               type string {
                 pattern "<.*>|$.*";
               }
               type uint32 {
                 range "1 .. 65535";
               }
             }
           }
           leaf threshold {
             description "Percentage of maximum at which to start generating warnings";
             type union {
               type string {
                 pattern "<.*>|$.*";
               }
               type uint32 {
                 range "1 .. 100";
               }
             }
           }
           leaf log-interval {
             description "Time between successive log messages";
             type union {
               type string {
                 pattern "<.*>|$.*";
               }
               type uint32 {
                 range "1 .. 65535";
               }
             }
           }
         }
         leaf maximum {
           description "Maximum limit above which additional entries are not accepted";
           type union {
             type string {
               pattern "<.*>|$.*";
             }
             type uint32 {
               range "1 .. 65535";
             }
           }
         }
         leaf threshold {
           description "Percentage of maximum at which to start generating warnings";
           type union {
             type string {
               pattern "<.*>|$.*";
             }
             type uint32 {
               range "1 .. 100";
             }
           }
         }
         leaf log-interval {
           description "Time between successive log messages";
           type union {
             type string {
               pattern "<.*>|$.*";
             }
             type uint32 {
               range "1 .. 65535";
             }
           }
         }
       }
       container group-rp-mapping {
         description "Group-rp-mapping";
         uses apply-advanced;
         list family {
           key name;
           ordered-by user;
           description "Protocol family";
           leaf name {
             type enumeration {
               enum "inet" {
                 description "IPv4 family";
               }
               enum "inet6" {
                 description "IPv6 family";
               }
             }
           }
           uses apply-advanced;
           leaf maximum {
             description "Maximum limit above which additional entries are not accepted";
             type union {
               type string {
                 pattern "<.*>|$.*";
               }
               type uint32 {
                 range "1 .. 65535";
               }
             }
           }
           leaf threshold {
             description "Percentage of maximum at which to start generating warnings";
             type union {
               type string {
                 pattern "<.*>|$.*";
               }
               type uint32 {
                 range "1 .. 100";
               }
             }
           }
           leaf log-interval {
             description "Time between successive log messages";
             type union {
               type string {
                 pattern "<.*>|$.*";
               }
               type uint32 {
                 range "1 .. 65535";
               }
             }
           }
         }
         leaf maximum {
           description "Maximum limit above which additional entries are not accepted";
           type union {
             type string {
               pattern "<.*>|$.*";
             }
             type uint32 {
               range "1 .. 65535";
             }
           }
         }
         leaf threshold {
           description "Percentage of maximum at which to start generating warnings";
           type union {
             type string {
               pattern "<.*>|$.*";
             }
             type uint32 {
               range "1 .. 100";
             }
           }
         }
         leaf log-interval {
           description "Time between successive log messages";
           type union {
             type string {
               pattern "<.*>|$.*";
             }
             type uint32 {
               range "1 .. 65535";
             }
           }
         }
       }
       leaf-list rp-register-policy {
         ordered-by user;
         description "RP policy applied to incoming register messages";
         type jt:policy-algebra;
       }
       leaf-list dr-register-policy {
         ordered-by user;
         description "DR policy applied to outgoing register messages";
         type jt:policy-algebra;
       }
       container local {
         description "Router's local RP properties";
         uses apply-advanced;
         leaf address {
           description "Local RP address (IPv4 only)";
           type jt:ipv4addr;
         }
         choice enable-disable {
           case case_1 {
             leaf disable {
               description "Disable this RP (IPv4 only)";
               type empty;
             }
           }
         }
         leaf priority {
           description "Router's priority for becoming an RP (IPv4 only)";
           type union {
             type string {
               pattern "<.*>|$.*";
             }
             type uint32 {
               range "0 .. 255";
             }
           }
         }
         leaf hold-time {
           description "How long neighbor considers this router to be up, in seconds (IPv4 only)";
           type union {
             type string {
               pattern "<.*>|$.*";
             }
             type uint32 {
               range "1 .. 65535";
             }
           }
         }
         list group-ranges {
           key name;
           ordered-by user;
           description "Group address range for which this router can be an RP (IPv4 only)";
           leaf name {
             type jt:ipv4prefix;
           }
           uses apply-advanced;
         }
         leaf override {
           description "Static RP mapping will take precedence over dynamic";
           type empty;
         }
         container family {
           description "Local RP address family";
           container inet {
             description "IPv4 local RP properties";
             uses apply-advanced;
             leaf address {
               description "Local RP address";
               type jt:ipv4addr;
             }
             choice enable-disable {
               case case_1 {
                 leaf disable {
                   description "Disable this RP";
                   type empty;
                 }
               }
             }
             leaf priority {
               description "Router's priority for becoming an RP";
               type union {
                 type string {
                   pattern "<.*>|$.*";
                 }
                 type uint32 {
                   range "0 .. 255";
                 }
               }
             }
             leaf hold-time {
               description "How long neighbor considers this router to be up, in seconds";
               type union {
                 type string {
                   pattern "<.*>|$.*";
                 }
                 type uint32 {
                   range "1 .. 65535";
                 }
               }
             }
             list group-ranges {
               key name;
               ordered-by user;
               description "Group address range for which this router can be an RP";
               leaf name {
                 type jt:ipv4prefix;
               }
               uses apply-advanced;
             }
             leaf override {
               description "Static RP mapping will take precedence over dynamic";
               type empty;
             }
             container anycast-pim {
               description "Attributes for IPv4 anycast PIM";
               uses apply-advanced;
               container rp-set {
                 description "Rendezvous points belonging to anycast RP set";
                 uses apply-advanced;
                 list address {
                   key name;
                   ordered-by user;
                   description "IPv4 address of one or more remote anycast RPs";
                   leaf name {
                     description "IPv4 address of remote anycast RP";
                     type jt:ipaddr;
                   }
                   uses apply-advanced;
                   leaf forward-msdp-sa {
                     description "Forward SAs learned from MSDP to this RP";
                     type empty;
                   }
                 }
               }
               leaf local-address {
                 description "Local address for replicating register messages to other RPs";
                 type jt:ipaddr;
               }
             }
           }
           container inet6 {
             description "IPv6 local RP properties";
             uses apply-advanced;
             leaf address {
               description "Local RP address";
               type jt:ipv6addr;
             }
             choice enable-disable {
               case case_1 {
                 leaf disable {
                   description "Disable this RP";
                   type empty;
                 }
               }
             }
             leaf priority {
               description "Router's priority for becoming an RP";
               type union {
                 type string {
                   pattern "<.*>|$.*";
                 }
                 type uint32 {
                   range "0 .. 255";
                 }
               }
             }
             leaf hold-time {
               description "How long neighbor considers this router to be up, in seconds";
               type union {
                 type string {
                   pattern "<.*>|$.*";
                 }
                 type uint32 {
                   range "1 .. 65535";
                 }
               }
             }
             list group-ranges {
               key name;
               ordered-by user;
               description "Group address range for which this router can be an RP";
               leaf name {
                 type jt:ipv6prefix;
               }
               uses apply-advanced;
             }
             leaf override {
               description "Static RP mapping will take precedence over dynamic";
               type empty;
             }
             container anycast-pim {
               description "Attributes for IPv6 anycast PIM";
               uses apply-advanced;
               container rp-set {
                 description "Rendezvous points belonging to anycast RP set";
                 uses apply-advanced;
                 list address {
                   key name;
                   ordered-by user;
                   description "IPv6 address of one or more remote anycast RPs";
                   leaf name {
                     description "IPv6 address of remote anycast RP";
                     type jt:ipv6addr;
                   }
                   uses apply-advanced;
                 }
               }
               leaf local-address {
                 description "Local address for replicating register messages to other RPs";
                 type jt:ipv6addr;
               }
             }
           }
         }
       }
       container embedded-rp {
         presence "enable embedded-rp";
         description "Set embedded-RP mode (IPv6 only)";
         uses apply-advanced;
         list group-ranges {
           key name;
           ordered-by user;
           description "Group address range of RP";
           uses pim_rp_group_range_type;
         }
         leaf maximum-rps {
           description "Maximum number of embedded RPs";
           default "100";
           type union {
             type string {
               pattern "<.*>|$.*";
             }
             type uint32 {
               range "1 .. 500";
             }
           }
         }
       }
       container auto-rp {
         description "Set auto-RP mode (IPv4 only)";
         uses apply-advanced;
         choice autorp-mode {
           case case_1 {
             leaf discovery {
               description "Listen for auto-RP discovery messages";
               type empty;
             }
           }
           case case_2 {
             leaf announce {
               description "Transmit auto-RP announcement messages";
               type empty;
             }
           }
           case case_3 {
             leaf mapping {
               description "Transmit auto-RP mapping messages";
               type empty;
             }
           }
         }
         choice mapping-agent-election-choice {
           leaf mapping-agent-election {
             description "Consider higher-addressed mapping agents as authoritative";
             type empty;
           }
           leaf no-mapping-agent-election {
             description "Don't consider higher-addressed mapping agents as authoritative";
             type empty;
           }
         }
       }
       container static {
         description "Configure static PIM RPs";
         uses apply-advanced;
         list address {
           key name;
           ordered-by user;
           description "RP address";
           leaf name {
             description "IP address of RP";
             type jt:ipaddr;
           }
           uses apply-advanced;
           leaf version {
             description "PIM version of RP";
             status deprecated;
             type union {
               type string {
                 pattern "<.*>|$.*";
               }
               type uint32 {
                 range "1 .. 2";
               }
             }
           }
           list group-ranges {
             key name;
             ordered-by user;
             description "Group address range of RP";
             uses pim_rp_group_range_type;
           }
           leaf override {
             description "Static RP mapping will take precedence over dynamic";
             type empty;
           }
         }
       }
     }
     leaf passive {
       description "Configure PIM protocol in passive mode";
       type empty;
     }
     list interface {
       key name;
       ordered-by user;
       description "PIM interface options";
       leaf name {
         description "Interface name";
         type string;
       }
       uses apply-advanced;
       container family {
         description "Local address family";
         container any {
           presence "enable any";
           description "Default properties for all families";
           uses apply-advanced;
           leaf disable {
             description "Disable all families";
             type empty;
           }
         }
         container inet {
           presence "enable inet";
           description "IPv4 specific properties";
           uses apply-advanced;
           container bfd-liveness-detection {
             description "Bidirectional Forwarding Detection options";
             uses apply-advanced;
             leaf version {
               description "BFD protocol version number";
               default "automatic";
               type enumeration {
                 enum "0" {
                   description "BFD version 0 (deprecated)";
                 }
                 enum "1" {
                   description "BFD version 1";
                 }
                 enum "automatic" {
                   description "Choose BFD version automatically";
                 }
               }
             }
             leaf minimum-interval {
               description "Minimum transmit and receive interval";
               units "milliseconds";
               type union {
                 type string {
                   pattern "<.*>|$.*";
                 }
                 type uint32 {
                   range "1 .. 255000";
                 }
               }
             }
             leaf minimum-transmit-interval {
               description "Minimum transmit interval";
               status deprecated;
               units "milliseconds";
               type union {
                 type string {
                   pattern "<.*>|$.*";
                 }
                 type uint32 {
                   range "1 .. 255000";
                 }
               }
             }
             leaf minimum-receive-interval {
               description "Minimum receive interval";
               units "milliseconds";
               type union {
                 type string {
                   pattern "<.*>|$.*";
                 }
                 type uint32 {
                   range "1 .. 255000";
                 }
               }
             }
             leaf multiplier {
               description "Detection time multiplier";
               default "3";
               type union {
                 type string {
                   pattern "<.*>|$.*";
                 }
                 type uint32 {
                   range "1 .. 255";
                 }
               }
             }
             choice adaptation-choice {
               case case_1 {
                 leaf no-adaptation {
                   description "Disable adaptation";
                   type empty;
                 }
               }
             }
             container transmit-interval {
               description "Transmit-interval options";
               uses apply-advanced;
               leaf minimum-interval {
                 description "Minimum transmit interval";
                 units "milliseconds";
                 type union {
                   type string {
                     pattern "<.*>|$.*";
                   }
                   type uint32 {
                     range "1 .. 255000";
                   }
                 }
               }
               leaf threshold {
                 description "High transmit interval triggering a trap";
                 units "milliseconds";
                 type union {
                   type uint32;
                   type string {
                     pattern "<.*>|$.*";
                   }
                 }
               }
             }
             container detection-time {
               description "Detection-time options";
               uses apply-advanced;
               leaf threshold {
                 description "High detection-time triggering a trap";
                 units "milliseconds";
                 type union {
                   type uint32;
                   type string {
                     pattern "<.*>|$.*";
                   }
                 }
               }
             }
             container authentication {
               description "Authentication options";
               uses apply-advanced;
               leaf key-chain {
                 description "Key chain name";
                 type string;
               }
               leaf algorithm {
                 description "Algorithm name";
                 type enumeration {
                   enum "simple-password" {
                     description "Simple password";
                   }
                   enum "keyed-md5" {
                     description "Keyed message Digest 5";
                   }
                   enum "meticulous-keyed-md5" {
                     description "Meticulous keyed message Digest 5";
                   }
                   enum "keyed-sha-1" {
                     description "Keyed secure hash algorithm (SHA1) ";
                   }
                   enum "meticulous-keyed-sha-1" {
                     description "Meticulous keyed secure hash algorithm (SHA1) ";
                   }
                 }
               }
               leaf loose-check {
                 description "Verify authentication only if authentication is negotiated";
                 type empty;
               }
             }
           }
           leaf mcae-mac-synchronize {
             description "Mclag mac synchronization";
             type empty;
           }
           choice enable-disable {
             case case_1 {
               leaf disable {
                 description "Disable PIMv4 on this interface";
                 type empty;
               }
             }
           }
         }
         container inet6 {
           presence "enable inet6";
           description "IPv6 specific properties";
           uses apply-advanced;
           container bfd-liveness-detection {
             description "Bidirectional Forwarding Detection options";
             uses apply-advanced;
             leaf version {
               description "BFD protocol version number";
               default "automatic";
               type enumeration {
                 enum "0" {
                   description "BFD version 0 (deprecated)";
                 }
                 enum "1" {
                   description "BFD version 1";
                 }
                 enum "automatic" {
                   description "Choose BFD version automatically";
                 }
               }
             }
             leaf minimum-interval {
               description "Minimum transmit and receive interval";
               units "milliseconds";
               type union {
                 type string {
                   pattern "<.*>|$.*";
                 }
                 type uint32 {
                   range "1 .. 255000";
                 }
               }
             }
             leaf minimum-transmit-interval {
               description "Minimum transmit interval";
               status deprecated;
               units "milliseconds";
               type union {
                 type string {
                   pattern "<.*>|$.*";
                 }
                 type uint32 {
                   range "1 .. 255000";
                 }
               }
             }
             leaf minimum-receive-interval {
               description "Minimum receive interval";
               units "milliseconds";
               type union {
                 type string {
                   pattern "<.*>|$.*";
                 }
                 type uint32 {
                   range "1 .. 255000";
                 }
               }
             }
             leaf multiplier {
               description "Detection time multiplier";
               default "3";
               type union {
                 type string {
                   pattern "<.*>|$.*";
                 }
                 type uint32 {
                   range "1 .. 255";
                 }
               }
             }
             choice adaptation-choice {
               case case_1 {
                 leaf no-adaptation {
                   description "Disable adaptation";
                   type empty;
                 }
               }
             }
             container transmit-interval {
               description "Transmit-interval options";
               uses apply-advanced;
               leaf minimum-interval {
                 description "Minimum transmit interval";
                 units "milliseconds";
                 type union {
                   type string {
                     pattern "<.*>|$.*";
                   }
                   type uint32 {
                     range "1 .. 255000";
                   }
                 }
               }
               leaf threshold {
                 description "High transmit interval triggering a trap";
                 units "milliseconds";
                 type union {
                   type uint32;
                   type string {
                     pattern "<.*>|$.*";
                   }
                 }
               }
             }
             container detection-time {
               description "Detection-time options";
               uses apply-advanced;
               leaf threshold {
                 description "High detection-time triggering a trap";
                 units "milliseconds";
                 type union {
                   type uint32;
                   type string {
                     pattern "<.*>|$.*";
                   }
                 }
               }
             }
             container authentication {
               description "Authentication options";
               uses apply-advanced;
               leaf key-chain {
                 description "Key chain name";
                 type string;
               }
               leaf algorithm {
                 description "Algorithm name";
                 type enumeration {
                   enum "simple-password" {
                     description "Simple password";
                   }
                   enum "keyed-md5" {
                     description "Keyed message Digest 5";
                   }
                   enum "meticulous-keyed-md5" {
                     description "Meticulous keyed message Digest 5";
                   }
                   enum "keyed-sha-1" {
                     description "Keyed secure hash algorithm (SHA1) ";
                   }
                   enum "meticulous-keyed-sha-1" {
                     description "Meticulous keyed secure hash algorithm (SHA1) ";
                   }
                 }
               }
               leaf loose-check {
                 description "Verify authentication only if authentication is negotiated";
                 type empty;
               }
             }
           }
           choice enable-disable {
             case case_1 {
               leaf disable {
                 description "Disable PIMv6 on this interface";
                 type empty;
               }
             }
           }
         }
       }
       choice enable-disable {
         case case_1 {
           leaf disable {
             description "Disable PIM on this interface";
             type empty;
           }
         }
       }
       leaf mode {
         description "Mode of interface";
         type enumeration {
           enum "dense" {
             description "Dense mode";
           }
           enum "sparse" {
             description "Sparse mode";
           }
           enum "sparse-dense" {
             description "Sparse-dense mode";
           }
           enum "bidirectional-sparse" {
             description "Bidirectional-sparse mode";
           }
           enum "bidirectional-sparse-dense" {
             description "Bidirectional-sparse-dense mode";
           }
         }
       }
       leaf priority {
         description "Hello option DR priority";
         type union {
           type string {
             pattern "<.*>|$.*";
           }
           type uint32 {
             range "0 .. 4294967295";
           }
         }
       }
       container stickydr {
         presence "enable stickydr";
         description "Make DR sticky";
         uses apply-advanced;
       }
       leaf version {
         description "Force PIM version";
         status deprecated;
         type union {
           type string {
             pattern "<.*>|$.*";
           }
           type uint32 {
             range "1 .. 2";
           }
         }
       }
       leaf hello-interval {
         description "Hello interval";
         units "seconds";
         type union {
           type string {
             pattern "<.*>|$.*";
           }
           type uint32 {
             range "0 .. 255";
           }
         }
       }
       leaf-list neighbor-policy {
         ordered-by user;
         description "PIM neighbor policy applied to incoming hello messages";
         type jt:policy-algebra;
       }
       leaf-list accept-join-always-from {
         ordered-by user;
         description "Accept pim join/prune messages based on the policy configured";
         type jt:policy-algebra;
       }
       leaf accept-remote-source {
         description "Accept traffic from remote source";
         type empty;
       }
       container dual-dr {
         presence "enable dual-dr";
         description "Configure PIM Dual DR";
         uses apply-advanced;
         leaf enhanced {
           description "Enable enhanced PIM Dual DR";
           type empty;
         }
       }
       leaf distributed-dr {
         description "PIM Distributed DR";
         type empty;
       }
       leaf reset-tracking-bit {
         description "Clear tracking-bit in PIM Hello LAN Prune Delay Option";
         type empty;
       }
       leaf propagation-delay {
         description "Propagation delay value";
         default "500";
         units "milliseconds";
         type union {
           type string {
             pattern "<.*>|$.*";
           }
           type uint32 {
             range "250 .. 2000";
           }
         }
       }
       leaf override-interval {
         description "Override interval value";
         default "2000";
         units "milliseconds";
         type union {
           type string {
             pattern "<.*>|$.*";
           }
           type uint32 {
             range "500 .. 6000";
           }
         }
       }
       container bfd-liveness-detection {
         description "Bidirectional Forwarding Detection options (ipv4 only)";
         status deprecated;
         uses apply-advanced;
         leaf version {
           description "BFD protocol version number";
           default "automatic";
           type enumeration {
             enum "0" {
               description "BFD version 0 (deprecated)";
             }
             enum "1" {
               description "BFD version 1";
             }
             enum "automatic" {
               description "Choose BFD version automatically";
             }
           }
         }
         leaf minimum-interval {
           description "Minimum transmit and receive interval";
           units "milliseconds";
           type union {
             type string {
               pattern "<.*>|$.*";
             }
             type uint32 {
               range "1 .. 255000";
             }
           }
         }
         leaf minimum-transmit-interval {
           description "Minimum transmit interval";
           status deprecated;
           units "milliseconds";
           type union {
             type string {
               pattern "<.*>|$.*";
             }
             type uint32 {
               range "1 .. 255000";
             }
           }
         }
         leaf minimum-receive-interval {
           description "Minimum receive interval";
           units "milliseconds";
           type union {
             type string {
               pattern "<.*>|$.*";
             }
             type uint32 {
               range "1 .. 255000";
             }
           }
         }
         leaf multiplier {
           description "Detection time multiplier";
           default "3";
           type union {
             type string {
               pattern "<.*>|$.*";
             }
             type uint32 {
               range "1 .. 255";
             }
           }
         }
         choice adaptation-choice {
           case case_1 {
             leaf no-adaptation {
               description "Disable adaptation";
               type empty;
             }
           }
         }
         container transmit-interval {
           description "Transmit-interval options";
           uses apply-advanced;
           leaf minimum-interval {
             description "Minimum transmit interval";
             units "milliseconds";
             type union {
               type string {
                 pattern "<.*>|$.*";
               }
               type uint32 {
                 range "1 .. 255000";
               }
             }
           }
           leaf threshold {
             description "High transmit interval triggering a trap";
             units "milliseconds";
             type union {
               type uint32;
               type string {
                 pattern "<.*>|$.*";
               }
             }
           }
         }
         container detection-time {
           description "Detection-time options";
           uses apply-advanced;
           leaf threshold {
             description "High detection-time triggering a trap";
             units "milliseconds";
             type union {
               type uint32;
               type string {
                 pattern "<.*>|$.*";
               }
             }
           }
         }
         container authentication {
           description "Authentication options";
           uses apply-advanced;
           leaf key-chain {
             description "Key chain name";
             type string;
           }
           leaf algorithm {
             description "Algorithm name";
             type enumeration {
               enum "simple-password" {
                 description "Simple password";
               }
               enum "keyed-md5" {
                 description "Keyed message Digest 5";
               }
               enum "meticulous-keyed-md5" {
                 description "Meticulous keyed message Digest 5";
               }
               enum "keyed-sha-1" {
                 description "Keyed secure hash algorithm (SHA1) ";
               }
               enum "meticulous-keyed-sha-1" {
                 description "Meticulous keyed secure hash algorithm (SHA1) ";
               }
             }
           }
           leaf loose-check {
             description "Verify authentication only if authentication is negotiated";
             type empty;
           }
         }
       }
     }
     container mdt {
       description "Configure multicast data tunnel parameters";
       status deprecated;
       uses apply-advanced;
       container threshold {
         description "Threshold for creation of multicast tunnels";
         uses apply-advanced;
         list group {
           key name;
           ordered-by user;
           description "IP prefix of multicast group";
           leaf name {
             description "IP prefix of group";
             type jt:ipprefix;
           }
           uses apply-advanced;
           list source {
             key name;
             ordered-by user;
             description "IP prefix of one or more multicast sources ";
             leaf name {
               description "IP prefix of source";
               type jt:ipprefix;
             }
             uses apply-advanced;
             leaf rate {
               description "Data threshold to create new tunnel";
               units "kilobits";
               type union {
                 type string {
                   pattern "<.*>|$.*";
                 }
                 type uint32 {
                   range "10 .. 1000000";
                 }
               }
             }
           }
         }
       }
       leaf data-mdt-reuse {
         description "Allow multiple customer streams to be transmitted over one data tunnel ";
         type empty;
       }
       leaf tunnel-limit {
         description "Maximum multicast data tunnels";
         type union {
           type string {
             pattern "<.*>|$.*";
           }
           type uint32 {
             range "0 .. 8192";
           }
         }
       }
       leaf group-range {
         description "Group address range for multicast data tunnels";
         type jt:ipprefix;
       }
     }
     container graceful-restart {
       description "Configure graceful restart attributes";
       uses apply-advanced;
       choice enable-disable {
         case case_1 {
           leaf disable {
             description "Disable PIM graceful restart capability";
             type empty;
           }
         }
       }
       leaf restart-duration {
         description "Maximum time for graceful restart to finish (seconds)";
         units "seconds";
         type union {
           type string {
             pattern "<.*>|$.*";
           }
           type uint32 {
             range "30 .. 300";
           }
         }
       }
       leaf no-bidirectional-mode {
         description "Disable PIM graceful restart for bidirectional mode";
         type empty;
       }
       leaf restart-complete-duration {
         description "Maximum time for graceful restart to complete (seconds)";
         units "seconds";
         type union {
           type string {
             pattern "<.*>|$.*";
           }
           type uint32 {
             range "5 .. 300";
           }
         }
       }
     }
     container join-load-balance {
       presence "enable join-load-balance";
       description "Configure PIM join load balancing";
       uses apply-advanced;
       leaf automatic {
         description "Enable automatic PIM join load balancing";
         type empty;
       }
     }
     leaf standby-path-creation-delay {
       description "Amount of time to wait before creating standby path";
       units "seconds";
       type union {
         type string {
           pattern "<.*>|$.*";
         }
         type uint32 {
           range "1 .. 300";
         }
       }
     }
     leaf idle-standby-path-switchover-delay {
       description "Amount of time to wait before switching over to idle standby path";
       units "seconds";
       type union {
         type string {
           pattern "<.*>|$.*";
         }
         type uint32 {
           range "1 .. 300";
         }
       }
     }
     leaf dr-election-on-p2p {
       description "Enable DR election on Point-to-Point Interfaces";
       type empty;
     }
     leaf no-wildcard-register-stop {
       description "Disable sending of wildcard register stop message";
       type empty;
     }
     leaf nexthop-hold-time {
       description "Nexthop hold time in milliseconds";
       units "milliseconds";
       type union {
         type string {
           pattern "<.*>|$.*";
         }
         type uint32 {
           range "1 .. 1000";
         }
       }
     }
     leaf mpls-internet-multicast {
       description "Enable support for Internet Multicast over MPLS";
       type empty;
     }
     container join-make-before-break {
       description "Enable PIM Join Make-Before-Break during RPF neighbor change";
       uses apply-advanced;
       choice enable-disable {
         case case_1 {
           leaf disable {
             description "Disable Make-Before-Break for PIM RPF neighbor change";
             type empty;
           }
         }
       }
     }
     leaf reset-tracking-bit {
       description "Clear tracking-bit in PIM Hello LAN Prune Delay Option";
       type empty;
     }
     leaf propagation-delay {
       description "Propagation delay value";
       default "500";
       units "milliseconds";
       type union {
         type string {
           pattern "<.*>|$.*";
         }
         type uint32 {
           range "250 .. 2000";
         }
       }
     }
     leaf override-interval {
       description "Override interval value";
       default "2000";
       units "milliseconds";
       type union {
         type string {
           pattern "<.*>|$.*";
         }
         type uint32 {
           range "500 .. 6000";
         }
       }
     }
     container default-vpn-source {
       presence "enable default-vpn-source";
       description "Let all VRFs use master loopback address for mt interfaces";
       uses apply-advanced;
       leaf interface-name {
         description "Master loopback interface name";
         type union {
           type jt:interface-unit;
           type string {
             pattern "<.*>|$.*";
           }
         }
       }
     }
     container static {
       description "Static PIM Join";
       uses apply-advanced;
       leaf distributed {
         description "Distributed all PIM Joins";
         type empty;
       }
       list group {
         key name;
         ordered-by user;
         description "IP multicast group address";
         leaf name {
           description "IP multicast group address";
           type jt:ipaddr;
         }
         uses apply-advanced;
         leaf distributed {
           description "Distributed static group";
           type empty;
         }
         list source {
           key name;
           ordered-by user;
           description "IP multicast source address";
           leaf name {
             description "IP multicast source address";
             type jt:ipaddr;
           }
           uses apply-advanced;
           leaf distributed {
             description "Distributed static source";
             type empty;
           }
           leaf no-upstream-join {
             description "Prevent sending PIM join";
             type empty;
           }
         }
       }
     }
   }
   grouping juniper-protocols-protection-group {
     uses apply-advanced;
     container ethernet-aps {
       description "Ethernet APS configuration";
       uses juniper-protocols-protection-group-eaps;
     }
     container traceoptions {
       description "Tracing options for debugging protocol operation";
       uses erp-trace-options;
     }
     leaf restore-interval {
       description "Wait to restore interval";
       default "5";
       units "minutes";
       type union {
         type string {
           pattern "<.*>|$.*";
         }
         type uint32 {
           range "1 .. 12";
         }
       }
     }
     leaf guard-interval {
       description "Guard timer interval in 10ms steps";
       default "500";
       units "milliseconds";
       type union {
         type string {
           pattern "<.*>|$.*";
         }
         type uint32 {
           range "10 .. 2000";
         }
       }
     }
     leaf hold-interval {
       description "Hold off timer interval in 100ms steps";
       default "0";
       units "milliseconds";
       type union {
         type string {
           pattern "<.*>|$.*";
         }
         type uint32 {
           range "0 .. 10000";
         }
       }
     }
     list ethernet-ring {
       key name;
       ordered-by user;
       description "Ethernet ring";
       uses juniper-protocols-protection-group-ethernet-ring;
     }
   }
   grouping erp-trace-options {
     description "Trace options for Ethernet Ring Protocol";
     uses apply-advanced;
     list flag {
       key name;
       ordered-by user;
       description "Tracing parameters";
       leaf name {
         type enumeration {
           enum "events" {
             description "Trace events to the protocol state machine";
           }
           enum "pdu" {
             description "Trace R-APS PDU reception and transmission";
           }
           enum "timers" {
             description "Trace protocol timers";
           }
           enum "state-machine" {
             description "Trace R-APS state machine";
           }
           enum "periodic-packet-management" {
             description "Trace periodic packet management state and events";
           }
           enum "config" {
             description "Trace protocol configuration";
           }
           enum "normal" {
             description "Trace protocol general log messages";
           }
           enum "debug" {
             description "Trace protocol debug log messages";
           }
           enum "all" {
             description "Trace all";
           }
         }
       }
     }
     container file {
       description "Trace file options";
       leaf filename {
         description "Name of file in which to write trace information";
         type string {
           length "1 .. 1024";
         }
       }
       leaf replace {
         description "Replace trace file rather than appending to it";
         status deprecated;
         type empty;
       }
       leaf size {
         description "Maximum trace file size";
         type string;
       }
       leaf files {
         description "Maximum number of trace files";
         default "10";
         type union {
           type string {
             pattern "<.*>|$.*";
           }
           type uint32 {
             range "2 .. 1000";
           }
         }
       }
       leaf no-stamp {
         description "Do not timestamp trace file";
         status deprecated;
         type empty;
       }
       choice world-readable-choice {
         leaf world-readable {
           description "Allow any user to read the log file";
           type empty;
         }
         leaf no-world-readable {
           description "Don't allow any user to read the log file";
           type empty;
         }
       }
     }
   }
   grouping juniper-protocols-protection-group-eaps {
     uses apply-advanced;
     list profile {
       key name;
       uses juniper-protocols-protection-group-eaps-profile;
     }
   }
   grouping juniper-protocols-protection-group-eaps-profile {
     description "Ethernet APS profile";
     leaf name {
       description "Profile name";
       type string {
         length "1 .. 32";
       }
     }
     uses apply-advanced;
     leaf protocol {
       description "Protocol value";
       type enumeration {
         enum "ccm" {
           description "Use CCM packets for protection.";
         }
         enum "G.8031" {
           description "Use G.8031 packets for protection.";
         }
       }
     }
     leaf revert-time {
       description "Reversion time in minutes, 0 would mean no reversion";
       default "4";
       units "minutes";
       type union {
         type string {
           pattern "<.*>|$.*";
         }
         type uint32 {
           range "0 .. 15";
         }
       }
     }
     leaf hold-time {
       description "Hold time in seconds";
       default "0";
       units "milli seconds";
       type union {
         type string {
           pattern "<.*>|$.*";
         }
         type uint32 {
           range "0 .. 10000";
         }
       }
     }
     leaf local-request {
       description "Local APS request";
       type enumeration {
         enum "lockout" {
           description "Lockout protection";
         }
       }
     }
   }
   grouping juniper-protocols-protection-group-ethernet-ring {
     description "Ethernet Ring protection group configuration";
     leaf name {
       description "Name of Ethernet Ring protection group";
       type string {
         length "1 .. 32";
       }
     }
     uses apply-advanced;
     leaf node-id {
       description "Node ID of the protection group, by default bridge's MAC";
       type jt:mac-unicast;
     }
     leaf ring-protection-link-owner {
       description "Ring protection link owner flag, one ring should have only one node as a ring protection link owner";
       type empty;
     }
     leaf level {
       description "MPG Level value for R-APS PDU";
       type union {
         type string {
           pattern "<.*>|$.*";
         }
         type uint32 {
           range "0 .. 7";
         }
       }
     }
     leaf restore-interval {
       description "Wait to restore interval";
       units "minutes";
       type union {
         type string {
           pattern "<.*>|$.*";
         }
         type uint32 {
           range "1 .. 12";
         }
       }
     }
     leaf guard-interval {
       description "Guard timer interval in 10ms";
       units "milliseconds";
       type union {
         type string {
           pattern "<.*>|$.*";
         }
         type uint32 {
           range "10 .. 2000";
         }
       }
     }
     leaf hold-interval {
       description "Hold off timer interval in 100ms steps";
       units "milliseconds";
       type union {
         type string {
           pattern "<.*>|$.*";
         }
         type uint32 {
           range "0 .. 10000";
         }
       }
     }
     container east-interface {
       description "East interface configuration";
       presence "enable east-interface";
       uses erp-interface;
     }
     container west-interface {
       description "West interface configuration";
       presence "enable west-interface";
       uses erp-interface;
     }
     leaf control-vlan {
       description "Dedicated VLAN identifier - VLAN id or VLAN name";
       type string;
     }
     container data-channel {
       description "Ring instance data channel";
       presence "enable data-channel";
       uses erp-data-channel;
     }
   }
   grouping erp-data-channel {
     uses apply-advanced;
     leaf-list vlan {
       ordered-by user;
       description "VLAN ID or VLAN ID range [1..4094]";
       type string;
     }
   }
   grouping erp-interface {
     uses apply-advanced;
     container control-channel {
       presence "enable control-channel";
       description "Control channel of ring port";
       uses apply-advanced;
       leaf vlan {
         description "Dedicated VLAN identifier";
         type union {
           type string {
             pattern "<.*>|$.*";
           }
           type uint16 {
             range "1 .. 4094";
           }
         }
       }
       leaf control-channel-name {
         type union {
           type jt:interface-name;
           type string {
             pattern "<.*>|$.*";
           }
         }
       }
     }
     leaf ring-protection-link-end {
       description "Port is connecting to ring protection link";
       type empty;
     }
     leaf interface-none {
       description "Port is not used";
       type empty;
     }
   }
   grouping juniper-protocols-rip {
     uses apply-advanced;
     container traceoptions {
       description "Trace options for RIP";
       uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "auth" {
               description "Trace RIP authentication";
             }
             enum "error" {
               description "Trace RIP errors";
             }
             enum "expiration" {
               description "Trace RIP route expiration processing";
             }
             enum "holddown" {
               description "Trace RIP hold-down processing";
             }
             enum "packets" {
               description "Trace all RIP packets";
             }
             enum "request" {
               description "Trace RIP information packets";
             }
             enum "trigger" {
               description "Trace RIP triggered updates";
             }
             enum "update" {
               description "Trace RIP update packets";
             }
             enum "nsr-synchronization" {
               description "Trace NSR synchronization events";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
         container filter {
           description "Filter to apply to this flag";
           presence "enable filter";
           uses rip_filter_obj;
         }
       }
     }
     container rib-group {
       description "Routing table group for importing RIP routes";
       uses rib_group_inet_type;
     }
     leaf metric-in {
       description "Metric value to add to incoming routes";
       type union {
         type string {
           pattern "<.*>|$.*";
         }
         type uint32 {
           range "1 .. 15";
         }
       }
     }
     container send {
       description "Configure RIP send options";
       choice send-opts {
         case case_1 {
           leaf broadcast {
             description "Broadcast RIPv2 packets (RIPv1 compatible)";
             type empty;
           }
         }
         case case_2 {
           leaf multicast {
             description "Multicast RIPv2 packets";
             type empty;
           }
         }
         case case_3 {
           leaf none {
             description "Do not send RIP updates";
             type empty;
           }
         }
         case case_4 {
           leaf version-1 {
             description "Broadcast RIPv1 packets";
             type empty;
           }
         }
       }
     }
     container receive {
       description "Configure RIP receive options";
       choice receive-opts {
         case case_1 {
           leaf both {
             description "Accept both RIPv1 and RIPv2 packets";
             type empty;
           }
         }
         case case_2 {
           leaf none {
             description "Do not receive RIP packets";
             type empty;
           }
         }
         case case_3 {
           leaf version-1 {
             description "Accept RIPv1 packets only";
             type empty;
           }
         }
         case case_4 {
           leaf version-2 {
             description "Accept only RIPv2 packets";
             type empty;
           }
         }
       }
     }
     choice check-zero-choice {
       leaf check-zero {
         description "Check reserved fields on incoming RIPv2 packets";
         type empty;
       }
       leaf no-check-zero {
         description "Don't check reserved fields on incoming RIPv2 packets";
         type empty;
       }
     }
     leaf message-size {
       description "Number of route entries per update message";
       type union {
         type string {
           pattern "<.*>|$.*";
         }
         type uint32 {
           range "25 .. 255";
         }
       }
     }
     leaf-list import {
       ordered-by user;
       description "Import policy";
       type jt:policy-algebra;
     }
     leaf holddown {
       description "Hold-down time";
       units "seconds";
       type union {
         type string {
           pattern "<.*>|$.*";
         }
         type uint32 {
           range "10 .. 180";
         }
       }
     }
     leaf route-timeout {
       description "Delay before routes time out";
       units "seconds";
       type union {
         type string {
           pattern "<.*>|$.*";
         }
         type uint32 {
           range "30 .. 360";
         }
       }
     }
     leaf update-interval {
       description "Interval between regular route updates";
       units "seconds";
       type union {
         type string {
           pattern "<.*>|$.*";
         }
         type uint32 {
           range "10 .. 60";
         }
       }
     }
     leaf authentication-type {
       description "Authentication type";
       type enumeration {
         enum "none" {
           description "No authentication";
         }
         enum "simple" {
           description "Simple password authentication";
         }
         enum "md5" {
           description "MD5 authentication";
         }
       }
     }
     leaf authentication-key {
       description "Authentication key (password)";
       type jt:unreadable;
     }
     list group {
       key name;
       ordered-by user;
       description "Instance configuration";
       leaf name {
         description "Group name";
         type string {
         }
       }
       uses apply-advanced;
       leaf route-timeout {
         description "Delay before routes time out";
         units "seconds";
         type union {
           type string {
             pattern "<.*>|$.*";
           }
           type uint32 {
             range "30 .. 360";
           }
         }
       }
       leaf update-interval {
         description "Interval between regular route updates";
         units "seconds";
         type union {
           type string {
             pattern "<.*>|$.*";
           }
           type uint32 {
             range "10 .. 60";
           }
         }
       }
       leaf preference {
         description "Preference of routes learned by this group";
         type union {
           type uint32;
           type string {
             pattern "<.*>|$.*";
           }
         }
       }
       leaf metric-out {
         description "Default metric of exported routes";
         type union {
           type string {
             pattern "<.*>|$.*";
           }
           type uint32 {
             range "1 .. 15";
           }
         }
       }
       leaf-list export {
         ordered-by user;
         description "Export policy";
         type jt:policy-algebra;
       }
       leaf-list import {
         ordered-by user;
         description "Import policy";
         type jt:policy-algebra;
       }
       leaf demand-circuit {
         description "Enable demand circuit on this interface";
         type empty;
       }
       leaf max-retrans-time {
         description "Maximum time to re-transmit a message in demand-circuit";
         type union {
           type string {
             pattern "<.*>|$.*";
           }
           type uint32 {
             range "5 .. 180";
           }
         }
       }
       container bfd-liveness-detection {
         description "Bidirectional Forwarding Detection options";
         uses apply-advanced;
         leaf version {
           description "BFD protocol version number";
           default "automatic";
           type enumeration {
             enum "0" {
               description "BFD version 0 (deprecated)";
             }
             enum "1" {
               description "BFD version 1";
             }
             enum "automatic" {
               description "Choose BFD version automatically";
             }
           }
         }
         leaf minimum-interval {
           description "Minimum transmit and receive interval";
           units "milliseconds";
           type union {
             type string {
               pattern "<.*>|$.*";
             }
             type uint32 {
               range "1 .. 255000";
             }
           }
         }
         leaf minimum-transmit-interval {
           description "Minimum transmit interval";
           status deprecated;
           units "milliseconds";
           type union {
             type string {
               pattern "<.*>|$.*";
             }
             type uint32 {
               range "1 .. 255000";
             }
           }
         }
         leaf minimum-receive-interval {
           description "Minimum receive interval";
           units "milliseconds";
           type union {
             type string {
               pattern "<.*>|$.*";
             }
             type uint32 {
               range "1 .. 255000";
             }
           }
         }
         leaf multiplier {
           description "Detection time multiplier";
           default "3";
           type union {
             type string {
               pattern "<.*>|$.*";
             }
             type uint32 {
               range "1 .. 255";
             }
           }
         }
         choice adaptation-choice {
           case case_1 {
             leaf no-adaptation {
               description "Disable adaptation";
               type empty;
             }
           }
         }
         container transmit-interval {
           description "Transmit-interval options";
           uses apply-advanced;
           leaf minimum-interval {
             description "Minimum transmit interval";
             units "milliseconds";
             type union {
               type string {
                 pattern "<.*>|$.*";
               }
               type uint32 {
                 range "1 .. 255000";
               }
             }
           }
           leaf threshold {
             description "High transmit interval triggering a trap";
             units "milliseconds";
             type union {
               type uint32;
               type string {
                 pattern "<.*>|$.*";
               }
             }
           }
         }
         container detection-time {
           description "Detection-time options";
           uses apply-advanced;
           leaf threshold {
             description "High detection-time triggering a trap";
             units "milliseconds";
             type union {
               type uint32;
               type string {
                 pattern "<.*>|$.*";
               }
             }
           }
         }
         container authentication {
           description "Authentication options";
           uses apply-advanced;
           leaf key-chain {
             description "Key chain name";
             type string;
           }
           leaf algorithm {
             description "Algorithm name";
             type enumeration {
               enum "simple-password" {
                 description "Simple password";
               }
               enum "keyed-md5" {
                 description "Keyed message Digest 5";
               }
               enum "meticulous-keyed-md5" {
                 description "Meticulous keyed message Digest 5";
               }
               enum "keyed-sha-1" {
                 description "Keyed secure hash algorithm (SHA1) ";
               }
               enum "meticulous-keyed-sha-1" {
                 description "Meticulous keyed secure hash algorithm (SHA1) ";
               }
             }
           }
           leaf loose-check {
             description "Verify authentication only if authentication is negotiated";
             type empty;
           }
         }
       }
       list neighbor {
         key name;
         ordered-by user;
         description "Neighbor configuration";
         leaf name {
           description "Interface name";
           type union {
             type jt:interface-name;
             type string {
               pattern "<.*>|$.*";
             }
           }
         }
         uses apply-advanced;
         leaf route-timeout {
           description "Delay before routes time out";
           units "seconds";
           type union {
             type string {
               pattern "<.*>|$.*";
             }
             type uint32 {
               range "30 .. 360";
             }
           }
         }
         leaf update-interval {
           description "Interval between regular route updates";
           units "seconds";
           type union {
             type string {
               pattern "<.*>|$.*";
             }
             type uint32 {
               range "10 .. 60";
             }
           }
         }
         leaf interface-type {
           description "Interface type for the neighbor";
           type enumeration {
             enum "p2mp" {
               description "Point-to-multipoint link";
             }
           }
         }
         leaf dynamic-peers {
           description "Learn peers dynamically on a p2mp interface";
           type empty;
         }
         list peer {
           key name;
           ordered-by user;
           description "P2MP peer";
           leaf name {
             description "Address of peer";
             type jt:ipaddr;
           }
         }
         leaf metric-in {
           description "Metric value to add to incoming routes";
           type union {
             type string {
               pattern "<.*>|$.*";
             }
             type uint32 {
               range "1 .. 15";
             }
           }
         }
         container send {
           description "Configure RIP send options";
           choice send-opts {
             case case_1 {
               leaf broadcast {
                 description "Broadcast RIPv2 packets (RIPv1 compatible)";
                 type empty;
               }
             }
             case case_2 {
               leaf multicast {
                 description "Multicast RIPv2 packets";
                 type empty;
               }
             }
             case case_3 {
               leaf none {
                 description "Do not send RIP updates";
                 type empty;
               }
             }
             case case_4 {
               leaf version-1 {
                 description "Broadcast RIPv1 packets";
                 type empty;
               }
             }
           }
         }
         container receive {
           description "Configure RIP receive options";
           choice receive-opts {
             case case_1 {
               leaf both {
                 description "Accept both RIPv1 and RIPv2 packets";
                 type empty;
               }
             }
             case case_2 {
               leaf none {
                 description "Do not receive RIP packets";
                 type empty;
               }
             }
             case case_3 {
               leaf version-1 {
                 description "Accept RIPv1 packets only";
                 type empty;
               }
             }
             case case_4 {
               leaf version-2 {
                 description "Accept only RIPv2 packets";
                 type empty;
               }
             }
           }
         }
         leaf demand-circuit {
           description "Enable demand circuit on this interface";
           type empty;
         }
         leaf max-retrans-time {
           description "Maximum time to re-transmit a msg in demand-circuit";
           type union {
             type string {
               pattern "<.*>|$.*";
             }
             type uint32 {
               range "5 .. 180";
             }
           }
         }
         choice check-zero-choice {
           leaf check-zero {
             description "Check reserved fields on incoming RIPv1 packets";
             type empty;
           }
           leaf no-check-zero {
             description "Don't check reserved fields on incoming RIPv1 packets";
             type empty;
           }
         }
         leaf any-sender {
           description "Disable strict checks on sender address";
           type empty;
         }
         leaf message-size {
           description "Number of route entries per update message";
           type union {
             type string {
               pattern "<.*>|$.*";
             }
             type uint32 {
               range "25 .. 255";
             }
           }
         }
         leaf-list import {
           ordered-by user;
           description "Import policy";
           type jt:policy-algebra;
         }
         leaf authentication-type {
           description "Authentication type";
           type enumeration {
             enum "none" {
               description "No authentication";
             }
             enum "simple" {
               description "Simple password authentication";
             }
             enum "md5" {
               description "MD5 authentication";
             }
           }
         }
         leaf authentication-key {
           description "Authentication key (password)";
           type jt:unreadable;
         }
         container bfd-liveness-detection {
           description "Bidirectional Forwarding Detection options";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
           container authentication {
             description "Authentication options";
             uses apply-advanced;
             leaf key-chain {
               description "Key chain name";
               type string;
             }
             leaf algorithm {
               description "Algorithm name";
               type enumeration {
                 enum "simple-password" {
                   description "Simple password";
                 }
                 enum "keyed-md5" {
                   description "Keyed message Digest 5";
                 }
                 enum "meticulous-keyed-md5" {
                   description "Meticulous keyed message Digest 5";
                 }
                 enum "keyed-sha-1" {
                   description "Keyed secure hash algorithm (SHA1) ";
                 }
                 enum "meticulous-keyed-sha-1" {
                   description "Meticulous keyed secure hash algorithm (SHA1) ";
                 }
               }
             }
             leaf loose-check {
               description "Verify authentication only if authentication is negotiated";
               type empty;
             }
           }
         }
       }
     }
     container graceful-restart {
       presence "enable graceful-restart";
       description "RIP graceful restart options";
       uses apply-advanced;
       choice enable-disable {
         case case_1 {
           leaf disable {
             description "Disable graceful restart";
             type empty;
           }
         }
       }
       leaf restart-time {
         description "Time after which RIP is declared out of restart";
         type union {
           type string {
             pattern "<.*>|$.*";
           }
           type uint32 {
             range "1 .. 600";
           }
         }
       }
     }
   }
   grouping juniper-protocols-ripng {
     uses apply-advanced;
     container traceoptions {
       description "Trace options for RIPng";
       uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "error" {
               description "Trace RIPng errors";
             }
             enum "expiration" {
               description "Trace RIPng route expiration processing";
             }
             enum "holddown" {
               description "Trace RIPng hold-down processing";
             }
             enum "packets" {
               description "Trace all RIPng packets";
             }
             enum "request" {
               description "Trace RIPng information packets";
             }
             enum "trigger" {
               description "Trace RIPng triggered updates";
             }
             enum "update" {
               description "Trace RIPng update packets";
             }
             enum "nsr-synchronization" {
               description "Trace NSR synchronization events";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     leaf metric-in {
       description "Metric value to add to incoming routes";
       type union {
         type string {
           pattern "<.*>|$.*";
         }
         type uint32 {
           range "1 .. 15";
         }
       }
     }
     container send {
       description "Configure RIPng send options";
       choice send-opts {
         case case_1 {
           leaf none {
             description "Do not send RIPng updates";
             type empty;
           }
         }
       }
     }
     container receive {
       description "Configure RIPng receive options";
       choice receive-opts {
         case case_1 {
           leaf none {
             description "Do not receive RIPng packets";
             type empty;
           }
         }
       }
     }
     leaf-list import {
       ordered-by user;
       description "Import policy";
       type jt:policy-algebra;
     }
     leaf holddown {
       description "Hold-down time";
       units "seconds";
       type union {
         type string {
           pattern "<.*>|$.*";
         }
         type uint32 {
           range "10 .. 180";
         }
       }
     }
     leaf route-timeout {
       description "Delay before routes time out";
       units "seconds";
       type union {
         type string {
           pattern "<.*>|$.*";
         }
         type uint32 {
           range "30 .. 360";
         }
       }
     }
     leaf update-interval {
       description "Interval between regular route updates";
       units "seconds";
       type union {
         type string {
           pattern "<.*>|$.*";
         }
         type uint32 {
           range "10 .. 60";
         }
       }
     }
     list group {
       key name;
       ordered-by user;
       description "Instance configuration";
       leaf name {
         description "Group name";
         type string {
         }
       }
       uses apply-advanced;
       leaf route-timeout {
         description "Delay before routes time out";
         units "seconds";
         type union {
           type string {
             pattern "<.*>|$.*";
           }
           type uint32 {
             range "30 .. 360";
           }
         }
       }
       leaf update-interval {
         description "Interval between regular route updates";
         units "seconds";
         type union {
           type string {
             pattern "<.*>|$.*";
           }
           type uint32 {
             range "10 .. 60";
           }
         }
       }
       leaf preference {
         description "Preference of routes learned by this group";
         type union {
           type uint32;
           type string {
             pattern "<.*>|$.*";
           }
         }
       }
       leaf metric-out {
         description "Default metric of exported routes";
         type union {
           type string {
             pattern "<.*>|$.*";
           }
           type uint32 {
             range "1 .. 15";
           }
         }
       }
       leaf-list export {
         ordered-by user;
         description "Export policy";
         type jt:policy-algebra;
       }
       leaf-list import {
         ordered-by user;
         description "Import policy";
         type jt:policy-algebra;
       }
       list neighbor {
         key name;
         ordered-by user;
         description "Neighbor configuration";
         leaf name {
           description "Interface name";
           type union {
             type jt:interface-name;
             type string {
               pattern "<.*>|$.*";
             }
           }
         }
         uses apply-advanced;
         leaf route-timeout {
           description "Delay before routes time out";
           units "seconds";
           type union {
             type string {
               pattern "<.*>|$.*";
             }
             type uint32 {
               range "30 .. 360";
             }
           }
         }
         leaf update-interval {
           description "Interval between regular route updates";
           units "seconds";
           type union {
             type string {
               pattern "<.*>|$.*";
             }
             type uint32 {
               range "10 .. 60";
             }
           }
         }
         leaf metric-in {
           description "Metric value to add to incoming routes";
           type union {
             type string {
               pattern "<.*>|$.*";
             }
             type uint32 {
               range "1 .. 15";
             }
           }
         }
         container send {
           description "Configure RIPng send options";
           choice send-opts {
             case case_1 {
               leaf none {
                 description "Do not send RIPng updates";
                 type empty;
               }
             }
           }
         }
         container receive {
           description "Configure RIPng receive options";
           choice receive-opts {
             case case_1 {
               leaf none {
                 description "Do not receive RIPng packets";
                 type empty;
               }
             }
           }
         }
         leaf-list import {
           ordered-by user;
           description "Import policy";
           type jt:policy-algebra;
         }
       }
     }
     container graceful-restart {
       presence "enable graceful-restart";
       description "RIPng graceful restart options";
       uses apply-advanced;
       choice enable-disable {
         case case_1 {
           leaf disable {
             description "Disable graceful restart";
             type empty;
           }
         }
       }
       leaf restart-time {
         description "Time after which RIPng is declared out of restart";
         type union {
           type string {
             pattern "<.*>|$.*";
           }
           type uint32 {
             range "1 .. 600";
           }
         }
       }
     }
   }
   grouping juniper-protocols-router-discovery {
     uses apply-advanced;
     choice enable-disable {
       case case_1 {
         leaf disable {
           description "Disable router discovery";
           type empty;
         }
       }
     }
     container traceoptions {
       description "Trace options for router discovery";
       uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
       }
     }
     list interface {
       key name;
       ordered-by user;
       description "Interfaces on which to configure router discovery";
       leaf name {
         description "Interface name";
         type union {
           type jt:interface-name;
           type string {
             pattern "<.*>|$.*";
           }
         }
       }
       uses apply-advanced;
       leaf max-advertisement-interval {
         description "Maximum time before sending advertisements";
         units "seconds";
         type union {
           type string {
             pattern "<.*>|$.*";
           }
           type uint32 {
             range "4 .. 1800";
           }
         }
       }
       leaf min-advertisement-interval {
         description "Minimum time before sending advertisements";
         units "seconds";
         type union {
           type string {
             pattern "<.*>|$.*";
           }
           type uint32 {
             range "3 .. 1800";
           }
         }
       }
       leaf lifetime {
         description "How long addresses in advertisements are valid";
         units "seconds";
         type union {
           type string {
             pattern "<.*>|$.*";
           }
           type uint32 {
             range "3 .. 9000";
           }
         }
       }
     }
     list address {
       key name;
       ordered-by user;
       description "IP addresses to include in advertisements";
       leaf name {
         description "IP addresses to include in router advertisements";
         type jt:ipv4addr;
       }
       uses apply-advanced;
       leaf advertise {
         description "Advertise the IP address in advertisements";
         type empty;
       }
       leaf ignore {
         description "Do not advertise the IP address in advertisements";
         type empty;
       }
       leaf broadcast {
         description "Include IP address only in broadcast advertisements";
         type empty;
       }
       leaf multicast {
         description "Include IP address only in multicast advertisements";
         type empty;
       }
       leaf ineligible {
         description "IP address can never become a default router";
         type empty;
       }
       leaf priority {
         description "Preference of the address to become a default router";
         type union {
           type int32;
           type string {
             pattern "<.*>|$.*";
           }
         }
       }
     }
   }
   grouping juniper-protocols-rsvp {
     description "RSVP options";
     uses apply-advanced;
     choice enable-disable {
       case case_1 {
         leaf disable {
           description "Disable RSVP";
           type empty;
         }
       }
     }
     container graceful-restart {
       description "Configure graceful restart attributes";
       uses apply-advanced;
       choice enable-disable {
         case case_1 {
           leaf disable {
             description "Disable RSVP graceful restart capability";
             type empty;
           }
         }
       }
       leaf helper-disable {
         description "Disable graceful restart helper capability";
         type empty;
       }
       leaf maximum-helper-restart-time {
         description "Maximum wait time from down event to neighbor dead";
         default "20";
         units "seconds";
         type union {
           type string {
             pattern "<.*>|$.*";
           }
           type uint32 {
             range "1 .. 1800";
           }
         }
       }
       leaf maximum-helper-recovery-time {
         description "Maximum time restarting neighbor states are kept";
         default "180";
         units "seconds";
         type union {
           type string {
             pattern "<.*>|$.*";
           }
           type uint32 {
             range "1 .. 3600";
           }
         }
       }
     }
     container tunnel-services {
       presence "enable tunnel-services";
       description "Use tunnel services for P2MP LSP ultimate-hop popping";
       uses apply-advanced;
       leaf-list devices {
         ordered-by user;
         description "Tunnel services devices to use for P2MP LSPs";
         type union {
           type jt:interface-device;
           type string {
             pattern "<.*>|$.*";
           }
         }
       }
     }
     leaf no-p2mp-sublsp {
       description "Disable P2MP sub-LSP object generation";
       type empty;
     }
     leaf no-node-id-subobject {
       description "Do not include the node-id sub-object in the RRO";
       type empty;
     }
     leaf no-interface-hello {
       description "Disble interface Hellos on all RSVP interfaces";
       type empty;
     }
     container pop-and-forward {
       description "RSVP pop-and-forward specific global parameters";
       uses apply-advanced;
       container application-label {
         description "Number of application labels under the RSVP transport";
         uses apply-advanced;
         leaf depth {
           description "Application label depth";
           default "1";
           type union {
             type string {
               pattern "<.*>|$.*";
             }
             type uint32 {
               range "0 .. 3";
             }
           }
         }
       }
     }
     leaf hello-acknowledgements {
       description "Acknowledge Hellos on RSVP interfaces not having sessions";
       type empty;
     }
     leaf no-hello-acknowledgements {
       description "Do not ack Hellos on RSVP interfaces not having sessions";
       type empty;
     }
     container node-hello {
       presence "enable node-hello";
       description "Enable node-ID based Hellos on all RSVP interfaces";
       leaf hello-interval {
         description "Hello interval";
         default "9";
         units "seconds";
         type union {
           type string {
             pattern "<.*>|$.*";
           }
           type uint32 {
             range "0 .. 60";
           }
         }
       }
     }
     leaf no-node-hello {
       description "Disable node-ID based Hellos on the router";
       type empty;
     }
     leaf allow-bidirectional {
       description "Enable bidirectional support in RSVP";
       status deprecated;
       type empty;
     }
     leaf local-reversion {
       description "Enable local reversion at this Point of Local Repair";
       type empty;
     }
     leaf no-local-reversion {
       description "Disable local reversion at this Point of Local Repair";
       type empty;
     }
     container fast-reroute {
       description "One-to-one fast-reroute protection mechanism";
       uses apply-advanced;
       leaf optimize-timer {
         description "Frequency of reoptimization for fast-reroute detour";
         units "seconds";
         type union {
           type string {
             pattern "<.*>|$.*";
           }
           type int32 {
             range "0 .. 65535";
           }
         }
       }
     }
     container load-balance {
       description "Per-packet load-balancing algorithm";
       uses apply-advanced;
       leaf bandwidth {
         description "Per-packet load balancing proportional to LSP bandwidth";
         type empty;
       }
     }
     container traceoptions {
       description "Trace options for RSVP";
       uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "io-event" {
               description "Trace RSVP IO task related events";
             }
             enum "io-packets" {
               description "Trace all RSVP periodic refresh activity";
             }
             enum "packets" {
               description "Trace all RSVP trigger packets";
             }
             enum "path" {
               description "Trace RSVP trigger path messages";
             }
             enum "resv" {
               description "Trace RSVP trigger Resv messages";
             }
             enum "pathtear" {
               description "Trace RSVP PathTear messages";
             }
             enum "resvtear" {
               description "Trace RSVP ResvTear messages";
             }
             enum "state" {
               description "Trace state transitions";
             }
             enum "error" {
               description "Trace error conditions";
             }
             enum "route" {
               description "Trace routing information";
             }
             enum "lmp" {
               description "Trace RSVP-LMP related interactions";
             }
             enum "event" {
               description "Trace RSVP related events";
             }
             enum "nsr-synchronization" {
               description "Trace NSR synchronization events";
             }
             enum "lsp-prefix" {
               description "Prefix the trace messages with LSP information";
             }
             enum "enhanced-frr" {
               description "Enhanced FRR related information";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     leaf refresh-time {
       description "Refresh time in seconds";
       default "1200";
       type union {
         type string {
           pattern "<.*>|$.*";
         }
         type uint32 {
           range "1 .. 65535";
         }
       }
     }
     leaf keep-multiplier {
       description "Keep multiplier";
       default "3";
       type union {
         type string {
           pattern "<.*>|$.*";
         }
         type uint32 {
           range "1 .. 255";
         }
       }
     }
     leaf graceful-deletion-timeout {
       description "Time to complete graceful deletion signaling";
       default "30";
       units "seconds";
       type union {
         type string {
           pattern "<.*>|$.*";
         }
         type uint32 {
           range "1 .. 300";
         }
       }
     }
     leaf setup-protection {
       description "Enable setup protection";
       type empty;
     }
     leaf cross-credibility-cspf {
       description "Compute CSPF paths spanning protocols for bypass LSP, detour LSP and loose hop expansion";
       type empty;
     }
     container preemption {
       description "Set RSVP session preemption attributes";
       uses apply-advanced;
       choice preemption-type {
         case case_1 {
           leaf disabled {
             description "No RSVP session preemption";
             type empty;
           }
         }
         case case_2 {
           leaf normal {
             description "Run RSVP session preemption to accommodate new sessions";
             type empty;
           }
         }
         case case_3 {
           leaf aggressive {
             description "Run RSVP session preemption whenever necessary";
             type empty;
           }
         }
       }
       container soft-preemption {
         description "Options for establishing new path before tearing down a preempted LSP";
         uses apply-advanced;
         leaf cleanup-timer {
           description "Time a soft-preempted LSP will be maintained";
           units "seconds";
           type union {
             type string {
               pattern "<.*>|$.*";
             }
             type int32 {
               range "0 .. 180";
             }
           }
         }
       }
     }
     leaf authentication-key {
       description "Authentication password";
       type jt:unreadable;
     }
     leaf no-authentication-check {
       description "Skip authentication check for received messages";
       type empty;
     }
     container associated-bidirectional-lsp {
       description "Set associated bidirectional LSP attributes";
       uses apply-advanced;
       leaf single-sided-provisioning {
         description "Enable unidirectional reverse LSP setup for single sided provisioned forward LSP";
         type empty;
       }
     }
     leaf no-enhanced-frr-bypass {
       description "Disable enhanced facility backup FRR";
       type empty;
     }
     list interface {
       key name;
       ordered-by user;
       description "RSVP interface options";
       leaf name {
         description "Interface name";
         type union {
           type jt:interface-name;
           type string {
             pattern "<.*>|$.*";
           }
         }
       }
       uses apply-advanced;
       choice enable-disable {
         case case_1 {
           leaf disable {
             description "Disable RSVP on this interface";
             type empty;
           }
         }
       }
       leaf authentication-key {
         description "Authentication password";
         type jt:unreadable;
       }
       choice aggregate-choice {
         leaf aggregate {
           description "Permit refresh reduction extensions on the interface";
           status deprecated;
           type empty;
         }
         leaf no-aggregate {
           description "Don't permit refresh reduction extensions on the interface";
           status deprecated;
           type empty;
         }
       }
       choice reliable-choice {
         leaf reliable {
           description "Permit reliable message delivery on the interface";
           type empty;
         }
         leaf no-reliable {
           description "Don't permit reliable message delivery on the interface";
           type empty;
         }
       }
       leaf hello-interval {
         description "Hello interval";
         default "9";
         units "seconds";
         type union {
           type string {
             pattern "<.*>|$.*";
           }
           type uint32 {
             range "0 .. 60";
           }
         }
       }
       container subscription {
         description "Link bandwidth percentage for RSVP reservation";
         uses subscription-type;
       }
       leaf bandwidth {
         description "Available bandwidth for the interface units bps";
         type string;
       }
       leaf update-threshold {
         description "Percentage change in reserved bandwidth to trigger IGP update";
         default "10";
         units "percent";
         type union {
           type string {
             pattern "<.*>|$.*";
           }
           type uint32 {
             range "1 .. 20";
           }
         }
       }
       container update-threshold-max-reservable {
         description "Change in non-rsvp bandwidth to trigger IGP update ";
         uses apply-advanced;
         leaf bandwidth {
           description "Change in non-rsvp bandwidth to trigger IGP update units bps";
           type string;
         }
         leaf percent {
           description "Percentage change in max-reservable bandwidth to trigger IGP update";
           units "percent";
           type union {
             type string {
               pattern "<.*>|$.*";
             }
             type uint32 {
               range "1 .. 100";
             }
           }
         }
       }
       container link-protection {
         presence "enable link-protection";
         description "Protect traffic with a label-stacked LSP";
         uses apply-advanced;
         choice enable-disable {
           case case_1 {
             leaf disable {
               description "Disable link protection on this interface";
               type empty;
             }
           }
         }
         container bandwidth {
           description "Bandwidth for each bypass";
           uses bandwidth-type;
         }
         leaf max-bypasses {
           description "Max number of bypasses permitted for protecting this interface";
           default "1";
           type union {
             type string {
               pattern "<.*>|$.*";
             }
             type uint32 {
               range "0 .. 99";
             }
           }
         }
         leaf subscription {
           description "Percent of bandwidth guaranteed when admitting protected LSPs into bypasses";
           default "100";
           type union {
             type string {
               pattern "<.*>|$.*";
             }
             type uint32 {
               range "1 .. 65535";
             }
           }
         }
         leaf no-node-protection {
           description "Disallow node protection on this interface";
           type empty;
         }
         leaf optimize-timer {
           description "Interval between bypass reoptimizations";
           default "0";
           units "seconds";
           type union {
             type string {
               pattern "<.*>|$.*";
             }
             type uint32 {
               range "0 .. 65535";
             }
           }
         }
         leaf class-of-service {
           description "Class of service for the bypass LSP";
           type union {
             type string {
               pattern "<.*>|$.*";
             }
             type int32 {
               range "0 .. 7";
             }
           }
         }
         leaf hop-limit {
           description "Maximum allowed router hops for bypass";
           type union {
             type string {
               pattern "<.*>|$.*";
             }
             type uint32 {
               range "2 .. 255";
             }
           }
         }
         leaf no-cspf {
           description "Disable automatic path computation";
           type empty;
         }
         leaf exclude-srlg {
           description "Exclude SRLG links";
           type empty;
         }
         container priority {
           presence "enable priority";
           description "Preemption priorities for the bypass LSP";
         }
         leaf setup-priority {
           description "Set-up priority";
           type union {
             type string {
               pattern "<.*>|$.*";
             }
             type uint32 {
               range "0 .. 7";
             }
           }
         }
         leaf reservation-priority {
           description "Reservation priority";
           type union {
             type string {
               pattern "<.*>|$.*";
             }
             type uint32 {
               range "0 .. 7";
             }
           }
         }
         list path {
           key name;
           ordered-by user;
           description "Explicit route of bypass path";
           leaf name {
             description "Address of next system in path";
             type jt:ipv4addr;
           }
           choice loose_strict_none {
             case case_1 {
               leaf loose {
                 description "Next hop might not be adjacent";
                 type empty;
               }
             }
             case case_2 {
               leaf strict {
                 description "Next hop must be adjacent";
                 type empty;
               }
             }
           }
         }
         container admin-group {
           description "Administrative group policy";
           uses admin_group_include_exclude;
         }
         list bypass {
           key name;
           ordered-by user;
           description "Bypass with specific constraints";
           leaf name {
             description "Name of bypass";
             type string {
               length "1 .. 64";
             }
           }
           uses apply-advanced;
           leaf to {
             description "Address of egress router";
             type jt:ipv4addr;
           }
           container bandwidth {
             description "Bandwidth for each bypass";
             uses bandwidth-type;
           }
           leaf description {
             description "Text description of bypass";
             type string {
               length "1 .. 80";
             }
           }
           container priority {
             presence "enable priority";
             description "Preemption priorities for bypass";
           }
           leaf setup-priority {
             description "Set-up priority";
             type union {
               type string {
                 pattern "<.*>|$.*";
               }
               type uint32 {
                 range "0 .. 7";
               }
             }
           }
           leaf reservation-priority {
             description "Reservation priority";
             type union {
               type string {
                 pattern "<.*>|$.*";
               }
               type uint32 {
                 range "0 .. 7";
               }
             }
           }
           leaf class-of-service {
             description "Class of service for the bypass LSP";
             type union {
               type string {
                 pattern "<.*>|$.*";
               }
               type int32 {
                 range "0 .. 7";
               }
             }
           }
           leaf hop-limit {
             description "Maximum allowed router hops for bypass";
             type union {
               type string {
                 pattern "<.*>|$.*";
               }
               type uint32 {
                 range "2 .. 255";
               }
             }
           }
           leaf no-cspf {
             description "Disable automatic path computation";
             type empty;
           }
           leaf exclude-srlg {
             description "Exclude SRLG links";
             type empty;
           }
           list path {
             key name;
             ordered-by user;
             description "Explicit route of bypass path";
             leaf name {
               description "Address of next system in path";
               type jt:ipv4addr;
             }
             choice loose_strict_none {
               case case_1 {
                 leaf loose {
                   description "Next hop might not be adjacent";
                   type empty;
                 }
               }
               case case_2 {
                 leaf strict {
                   description "Next hop must be adjacent";
                   type empty;
                 }
               }
             }
           }
           container admin-group {
             description "Administrative group policy";
             uses admin_group_include_exclude;
           }
         }
       }
     }
     list peer-interface {
       key name;
       ordered-by user;
       description "Configuration for peer interface";
       leaf name {
         description "Name of peer interface";
         type string;
       }
       uses apply-advanced;
       choice enable-disable {
         case case_1 {
           leaf disable {
             description "Disable RSVP on this control peer";
             type empty;
           }
         }
       }
       leaf authentication-key {
         description "Authentication password";
         type jt:unreadable;
       }
       choice aggregate-choice {
         leaf aggregate {
           description "Permit refresh reduction extensions on the interface";
           status deprecated;
           type empty;
         }
         leaf no-aggregate {
           description "Don't permit refresh reduction extensions on the interface";
           status deprecated;
           type empty;
         }
       }
       choice reliable-choice {
         leaf reliable {
           description "Permit reliable message delivery on the interface";
           type empty;
         }
         leaf no-reliable {
           description "Don't permit reliable message delivery on the interface";
           type empty;
         }
       }
       leaf hello-interval {
         description "Hello interval";
         default "9";
         units "seconds";
         type union {
           type string {
             pattern "<.*>|$.*";
           }
           type uint32 {
             range "0 .. 60";
           }
         }
       }
       container dynamic-bidirectional-transport {
         presence "enable dynamic-bidirectional-transport";
         description "Enable dynamic setup of bidirectional packet LSP for transporting non-packet GMPLS LSP";
         uses apply-advanced;
         leaf template {
           description "Template for the dynamic bidirectional packet LSP";
           type string {
           }
         }
       }
     }
     list lsp-set {
       key name;
       ordered-by user;
       description "Configuration for lsp set";
       leaf name {
         description "Name of lsp set";
         type string;
       }
       uses apply-advanced;
       choice enable-disable {
         case case_1 {
           leaf disable {
             description "Disable this lsp set";
             type empty;
           }
         }
       }
       container match-criteria {
         description "Match criteria for this lsp set";
         uses lsp-set-match-type;
       }
       container traceoptions {
         description "Trace options for this lsp set";
         uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "io-event" {
                 description "Trace RSVP IO task related events";
               }
               enum "io-packets" {
                 description "Trace all RSVP periodic refresh activity";
               }
               enum "packets" {
                 description "Trace all RSVP packets";
               }
               enum "path" {
                 description "Trace RSVP path messages";
               }
               enum "resv" {
                 description "Trace RSVP Resv messages";
               }
               enum "pathtear" {
                 description "Trace RSVP PathTear messages";
               }
               enum "resvtear" {
                 description "Trace RSVP ResvTear messages";
               }
               enum "state" {
                 description "Trace state transitions";
               }
               enum "error" {
                 description "Trace error conditions";
               }
               enum "route" {
                 description "Trace routing information";
               }
               enum "lmp" {
                 description "Trace RSVP-LMP related interactions";
               }
               enum "event" {
                 description "Trace RSVP related events";
               }
               enum "nsr-synchronization" {
                 description "Trace NSR synchronization events";
               }
               enum "lsp-prefix" {
                 description "Prefix the trace messages with LSP information";
               }
               enum "enhanced-frr" {
                 description "Enhanced FRR related information";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
     }
   }
   grouping juniper-protocols-stp {
     uses apply-advanced;
     choice enable-disable {
       case case_1 {
         leaf disable {
           description "Disable STP";
           type empty;
         }
       }
     }
     leaf bpdu-destination-mac-address {
       description "Destination MAC address in the spanning tree BPDUs";
       type enumeration {
         enum "provider-bridge-group" {
           description "802.1ad provider bridge group address";
         }
       }
     }
     leaf bridge-priority {
       description "Priority of the bridge (in increments of 4k - 0,4k,8k,..60k)";
       type string {
       }
     }
     leaf backup-bridge-priority {
       description "Priority of the bridge (in increments of 4k - 4k,8k,..60k)";
       type string {
       }
     }
     leaf max-age {
       description "Maximum age of received protocol bpdu";
       units "seconds";
       type union {
         type string {
           pattern "<.*>|$.*";
         }
         type uint16 {
           range "6 .. 40";
         }
       }
     }
     leaf hello-time {
       description "Time interval between configuration BPDUs";
       units "seconds";
       type union {
         type string {
           pattern "<.*>|$.*";
         }
         type uint16 {
           range "1 .. 10";
         }
       }
     }
     leaf forward-delay {
       description "Time spent in listening or learning state";
       units "seconds";
       type union {
         type string {
           pattern "<.*>|$.*";
         }
         type uint16 {
           range "4 .. 30";
         }
       }
     }
     leaf system-identifier {
       description "Sytem identifier to represent this node";
       type jt:mac-unicast;
     }
     container traceoptions {
       description "Tracing options for debugging protocol operation";
       uses stp-trace-options;
     }
     leaf vpls-flush-on-topology-change {
       description "Enable VPLS MAC flush on root protected CE interface receving topology change";
       type empty;
     }
     leaf priority-hold-time {
       description "Hold time before switching to primary priority when core domain becomes up";
       units "seconds";
       type union {
         type string {
           pattern "<.*>|$.*";
         }
         type uint16 {
           range "1 .. 255";
         }
       }
     }
     list system-id {
       key name;
       ordered-by user;
       description "System ID to IP mapping";
       uses system-id-ip-map;
     }
     list interface {
       key name;
       description "Interface options";
       uses stp-interface;
     }
     leaf extended-system-id {
       description "Extended system identifier";
       type union {
         type string {
           pattern "<.*>|$.*";
         }
         type uint16 {
           range "0 .. 4095";
         }
       }
     }
     leaf force-version {
       description "Force protocol version";
       type enumeration {
         enum "stp" {
           description "Spanning tree protocol";
         }
       }
     }
     leaf bpdu-block-on-edge {
       description "Block BPDU on all interfaces configured as edge (BPDU Protect)";
       type empty;
     }
   }
   grouping juniper-protocols-vni-options {
     uses apply-advanced;
     list vni {
       key name;
       description "Per-vni options";
       leaf name {
         type union {
           type string {
             pattern "<.*>|$.*";
           }
           type int32 {
             range "1 .. 16777214";
           }
         }
       }
       uses apply-advanced;
       container vrf-target {
         description "VRF target community configuration";
         uses apply-advanced;
         leaf export {
           description "Target community to use when marking routes on export";
           status deprecated;
           type string {
           }
         }
         leaf community {
           description "Target community";
           type string {
           }
         }
       }
     }
   }
   grouping juniper-protocols-vstp {
     uses apply-advanced;
     choice enable-disable {
       case case_1 {
         leaf disable {
           description "Disable VSTP";
           type empty;
         }
       }
     }
     leaf force-version {
       description "Force protocol version";
       type enumeration {
         enum "stp" {
           description "Spanning tree protocol";
         }
       }
     }
     leaf bpdu-block-on-edge {
       description "Block BPDU on all interfaces configured as edge (BPDU Protect)";
       type empty;
     }
     leaf vpls-flush-on-topology-change {
       description "Enable VPLS MAC flush on root protected CE interface receving topology change";
       type empty;
     }
     leaf priority-hold-time {
       description "Hold time before switching to primary priority when core domain becomes up";
       units "seconds";
       type union {
         type string {
           pattern "<.*>|$.*";
         }
         type uint16 {
           range "1 .. 255";
         }
       }
     }
     list system-id {
       key name;
       ordered-by user;
       description "System ID to IP mapping";
       uses system-id-ip-map;
     }
     list interface {
       key name;
       description "Interface options";
       uses stp-interface;
     }
     list vlan {
       key name;
       description "VLAN spanning tree options";
       leaf name {
         description "VLAN id or all";
         type string;
       }
       uses apply-advanced;
       leaf bridge-priority {
         description "Priority of the bridge (in increments of 4k - 0,4k,8k,..60k)";
         type string {
         }
       }
       leaf backup-bridge-priority {
         description "Priority of the bridge (in increments of 4k - 4k,8k,..60k)";
         type string {
         }
       }
       leaf max-age {
         description "Maximum age of received protocol bpdu";
         units "seconds";
         type union {
           type string {
             pattern "<.*>|$.*";
           }
           type uint16 {
             range "6 .. 40";
           }
         }
       }
       leaf hello-time {
         description "Time interval between configuration BPDUs";
         units "seconds";
         type union {
           type string {
             pattern "<.*>|$.*";
           }
           type uint16 {
             range "1 .. 10";
           }
         }
       }
       leaf forward-delay {
         description "Time spent in listening or learning state";
         units "seconds";
         type union {
           type string {
             pattern "<.*>|$.*";
           }
           type uint16 {
             range "4 .. 30";
           }
         }
       }
       leaf system-identifier {
         description "Sytem identifier to represent this node";
         type jt:mac-unicast;
       }
       container traceoptions {
         description "Tracing options for debugging protocol operation";
         uses stp-trace-options;
       }
       list interface {
         key name;
         description "Interface options";
         uses stp-interface;
       }
     }
     container vlan-group {
       presence "enable vlan-group";
       description "Spanning tree options for group of VLANs";
       uses apply-advanced;
       list group {
         key name;
         ordered-by user;
         description "Name if VLAN group";
         leaf name {
           description "VLAN group name";
           type string {
             length "1 .. 63";
           }
         }
         uses apply-advanced;
         leaf-list vlan {
           ordered-by user;
           description "VLAN ID or VLAN ID range [1..4094]";
           type string;
         }
         leaf bridge-priority {
           description "Priority of the bridge (in increments of 4k - 0,4k,8k,..60k)";
           type string {
           }
         }
         leaf backup-bridge-priority {
           description "Priority of the bridge (in increments of 4k - 4k,8k,..60k)";
           type string {
           }
         }
         leaf max-age {
           description "Maximum age of received protocol bpdu";
           units "seconds";
           type union {
             type string {
               pattern "<.*>|$.*";
             }
             type uint16 {
               range "6 .. 40";
             }
           }
         }
         leaf hello-time {
           description "Time interval between configuration BPDUs";
           units "seconds";
           type union {
             type string {
               pattern "<.*>|$.*";
             }
             type uint16 {
               range "1 .. 10";
             }
           }
         }
         leaf forward-delay {
           description "Time spent in listening or learning state";
           units "seconds";
           type union {
             type string {
               pattern "<.*>|$.*";
             }
             type uint16 {
               range "4 .. 30";
             }
           }
         }
         leaf system-identifier {
           description "Sytem identifier to represent this node";
           type jt:mac-unicast;
         }
         container traceoptions {
           description "Tracing options for debugging protocol operation";
           uses stp-trace-options;
         }
         list interface {
           key name;
           description "Interface options";
           uses stp-interface;
         }
       }
     }
   }
   grouping juniper-routing-instance {
     description "Routing instance";
     leaf name {
       description "Routing instance name";
       type string {
       }
     }
     uses apply-advanced;
     container vlans {
       description "VLAN configuration";
       uses apply-advanced;
       list vlan {
         key name;
         description "Virtual LAN";
         uses vlan-types;
       }
     }
     list interface {
       key name;
       description "Interface name for this routing instance";
       leaf name {
         type string;
       }
       uses apply-advanced;
       choice mode {
         case case_1 {
           leaf any {
             description "Interface used for both unicast and multicast traffic";
             type empty;
           }
         }
         case case_2 {
           leaf unicast {
             description "Interface used for unicast traffic only";
             type empty;
           }
         }
         case case_3 {
           leaf multicast {
             description "Interface used for multicast traffic only";
             type empty;
           }
         }
       }
       leaf primary {
         description "Preferred multicast vt interface for the routing-instance";
         type empty;
       }
       leaf protect-interface {
         description "Name of protect interface";
         type union {
           type jt:interface-name;
           type string {
             pattern "<.*>|$.*";
           }
         }
       }
     }
     leaf description {
       description "Text description of routing instance";
       type string {
       }
     }
     leaf vlan-model {
       description "Subscriber vlan-model in L2Wholesale framework";
       type enumeration {
         enum "one-to-one" {
           description "Customer VLAN model (1:1)";
         }
       }
     }
     container vtep-source-interface {
       description "Source layer-3 IFL for VXLAN";
       leaf interface-name {
         type union {
           type jt:interface-unit;
           type string {
             pattern "<.*>|$.*";
           }
         }
       }
       choice family {
         case case_1 {
           container inet {
             presence "enable inet";
             description "IPv4 source";
             uses apply-advanced;
           }
         }
         case case_2 {
           container inet6 {
             presence "enable inet6";
             description "IPv6 source";
             uses apply-advanced;
           }
         }
       }
     }
     container vtep-remote-interface {
       description "Remote VTEP interface";
       uses apply-advanced;
       list remote-ip {
         key name;
         ordered-by user;
         description "Remote VTEP IP address";
         leaf name {
           description "IP address";
           type jt:ipv4addr;
         }
         uses apply-advanced;
         leaf dynamic-profile {
           description "Define associate dynamic profile";
           type string;
         }
       }
       container default {
         description "To all remote vtep interface";
         uses apply-advanced;
         leaf dynamic-profile {
           description "Define associate dynamic profile";
           type string;
         }
       }
     }
     leaf-list remote-vtep-list {
       description "Configure static remote VXLAN tunnel endpoints";
       type jt:ipaddr;
       max-elements 1024;
     }
     leaf-list remote-vtep-v6-list {
       description "Configurate static ipv6 remote VXLAN tunnel endpoints";
       type jt:ipv6addr;
       max-elements 1024;
     }
     leaf instance-role {
       description "Primary role of L2Backhaul-vpn router";
       type enumeration {
         enum "access" {
           description "Role of Access/Aggregation router";
         }
         enum "nni" {
           description "Role of Provider network interfacing router";
         }
       }
     }
     leaf instance-type {
       description "Type of routing instance";
       type enumeration {
         enum "forwarding" {
           description "Forwarding instance";
         }
         enum "vrf" {
           description "Virtual routing forwarding instance";
         }
         enum "no-forwarding" {
           description "Nonforwarding instance";
         }
         enum "l2vpn" {
           description "Layer 2 VPN routing instance";
         }
         enum "vpls" {
           description "VPLS routing instance";
         }
         enum "virtual-switch" {
           description "Virtual switch routing instance";
         }
         enum "l2backhaul-vpn" {
           description "L2Backhaul/L2Wholesale routing instance";
         }
         enum "virtual-router" {
           description "Virtual routing instance";
         }
         enum "layer2-control" {
           description "Layer 2 control protocols";
         }
         enum "mpls-internet-multicast" {
           description "Internet Multicast over MPLS routing instance";
         }
         enum "evpn" {
           description "EVPN routing instance";
         }
         enum "mpls-forwarding" {
           description "Routing instance provides a MPLS forwarding-context";
         }
         enum "evpn-vpws" {
           description "EVPN VPWS routing instance";
         }
       }
     }
     choice vrf-propagate-ttl-or-no-vrf-propagate-ttl {
       case case_1 {
         leaf no-vrf-propagate-ttl {
           description "Disable TTL propagation from IP to MPLS (on push) and MPLS to IP (on pop)";
           type empty;
         }
       }
       case case_2 {
         leaf vrf-propagate-ttl {
           description "Enable TTL propagation from IP to MPLS (on push) and MPLS to IP (on pop)";
           type empty;
         }
       }
     }
     container egress-protection {
       description "Egress instance protection";
       uses apply-advanced;
       leaf protector {
         description "Enable Edge Protector functionality for this VPN";
         type empty;
       }
       container context-identifier {
         description "Context identifier";
         uses apply-advanced;
         leaf context-id {
           description "IP address";
           type jt:ipv4addr;
         }
       }
     }
     choice vlan_choice {
       case case_1 {
         leaf vlan-id {
           description "IEEE 802.1q VLAN identifier for bridging domain";
           type string;
         }
       }
       case case_2 {
         container vlan-tags {
           presence "enable vlan-tags";
           description "IEEE 802.1q VLAN tags for bridging domain";
           leaf outer {
             description "[tpid.]vlan-id, tpid format is 0xNNNN and is optional";
             type string {
             }
           }
           leaf inner {
             description "[tpid.]vlan-id, tpid format is 0xNNNN and is optional";
             type string {
             }
           }
         }
       }
     }
     container system {
       description "System parameters";
       uses apply-advanced;
       container services {
         description "System services";
         uses apply-advanced;
         container dhcp-local-server {
           description "Dynamic Host Configuration Protocol server configuration";
           uses jdhcp-local-server-type;
         }
         container static-subscribers {
           description "Static Subscriber Client configuration";
           uses jsscd-static-subscribers-type;
         }
       }
     }
     container access {
       description "Network access configuration";
       uses apply-advanced;
       container address-assignment {
         description "Address assignment configuration";
         uses address-assignment-type;
       }
       container address-protection {
         presence "enable address-protection";
         description "Initiate Duplicate Address Protection";
         uses apply-advanced;
         leaf reassign-on-match {
           description "Disconnect owning session and reassign to this session";
           type empty;
         }
       }
     }
     container access-profile {
       description "Access profile for this instance";
       leaf access-profile-name {
         description "Profile name";
         type string;
       }
     }
     leaf routing-interface {
       description "Routing interface name for this routing-instance";
       type union {
         type jt:interface-unit;
         type string {
           pattern "<.*>|$.*";
         }
       }
     }
     container vxlan {
       uses apply-advanced;
       leaf ovsdb-managed {
         description "Managed remotely via VXLAN OVSDB Controller";
         type empty;
       }
       leaf vni {
         description "VXLAN identifier";
         type union {
           type string {
             pattern "<.*>|$.*";
           }
           type uint32 {
             range "0 .. 16777214";
           }
         }
       }
       leaf multicast-group {
         description "Multicast group registered for VXLAN segment";
         type jt:ipv4addr;
       }
       leaf multicast-v6-group {
         description "Multicast IPv6 group registered for VXLAN segment";
         type jt:ipv6addr;
       }
       leaf encapsulate-inner-vlan {
         description "Retain inner VLAN in the packet";
         type empty;
       }
       leaf decapsulate-accept-inner-vlan {
         description "Accept VXLAN packets with inner VLAN";
         type empty;
       }
       leaf unreachable-vtep-aging-timer {
         description "Unreachable VXLAN tunnel endpoint removal timer";
         units "seconds";
         type union {
           type string {
             pattern "<.*>|$.*";
           }
           type uint16 {
             range "300 .. 1800";
           }
         }
       }
       leaf ingress-node-replication {
         description "Enable ingress node replication";
         type empty;
       }
     }
     leaf no-local-switching {
       description "Disable local switching within CE-facing interfaces";
       type empty;
     }
     leaf no-normalization {
       description "Disable vlan id normalization for interfaces";
       type empty;
     }
     leaf qualified-bum-pruning-mode {
       description "Enable BUM pruning for VPLS instance";
       type empty;
     }
     leaf no-irb-layer-2-copy {
       description "Disable transmission of layer-2 copy of packets of irb routing-interface";
       type empty;
     }
     container route-distinguisher {
       description "Route distinguisher for this instance";
       leaf rd-type {
         description "Number in (16 bit:32 bit) or (32 bit 'L':16 bit) or (IP address:16 bit) format";
         type string {
         }
       }
     }
     container l2vpn-id {
       description "Layer-2 vpn-id for this instance";
       uses apply-advanced;
       leaf community {
         description "L2VPN ID community for FEC129 VPLS/VPWS with BGP auto-discovery";
         type string {
         }
       }
     }
     container provider-tunnel {
       description "Provider tunnel configuration";
       uses apply-advanced;
       choice tunnel-type {
         case case_1 {
           container rsvp-te {
             description "RSVP-TE point-to-multipoint LSP for flooding";
             uses apply-advanced;
             choice static-or-dynamic {
               case case_1 {
                 leaf static-lsp {
                   description "Name of point-to-multipoint LSP";
                   type string {
                   }
                 }
               }
               case case_2 {
                 container label-switched-path-template {
                   description "Template for dynamic point-to-multipoint LSP parameters";
                   uses apply-advanced;
                   choice dynamic-template {
                     case case_1 {
                       leaf template-name {
                         description "Name of point-to-multipoint LSP template";
                         type string {
                         }
                       }
                     }
                     case case_2 {
                       leaf default-template {
                         description "Use default parameters";
                         type empty;
                       }
                     }
                   }
                 }
               }
             }
           }
         }
         case case_2 {
           container ldp-p2mp {
             presence "enable ldp-p2mp";
             description "LDP point-to-multipoint LSP for flooding";
           }
         }
         case case_3 {
           container ingress-replication {
             description "Ingress replication tunnel";
             uses apply-advanced;
             leaf create-new-ucast-tunnel {
               description "Create new unicast tunnel for ingress replication";
               type empty;
             }
             container label-switched-path {
               presence "enable label-switched-path";
               description "Point-to-point LSP unicast tunnel";
               uses apply-advanced;
               container label-switched-path-template {
                 description "Template for dynamic point-to-point LSP parameters";
                 uses apply-advanced;
                 choice dynamic-template {
                   case case_1 {
                     leaf template-name {
                       description "Name of point-to-point LSP template";
                       type string {
                       }
                     }
                   }
                   case case_2 {
                     leaf default-template {
                       description "Use default parameters";
                       type empty;
                     }
                   }
                 }
               }
             }
           }
         }
         case case_4 {
           container pim-asm {
             description "PIM-SM provider tunnel";
             uses apply-advanced;
             leaf group-address {
               description "PIM-SM provider tunnel group address";
               type jt:ipv4addr;
             }
             container family {
               presence "enable family";
               description "PIM-SM provider tunnel address family";
               status deprecated;
               uses apply-advanced;
               container inet {
                 presence "enable inet";
                 description "IPv4 PIM-SM provider tunnel";
                 uses apply-advanced;
                 leaf group-address {
                   description "PIM-SM provider tunnel group address for IPV4";
                   type jt:ipv4addr;
                 }
                 leaf tunnel-source {
                   description "Source address for the provider space mGRE tunnel";
                   type jt:ipv4addr;
                 }
               }
               container inet6 {
                 presence "enable inet6";
                 description "IPv6 PIM-SM provider tunnel";
                 uses apply-advanced;
                 leaf group-address {
                   description "PIM-SM provider tunnel group address for IPV6";
                   type jt:ipv4addr;
                 }
                 leaf tunnel-source {
                   description "Source address for the provider space mGRE tunnel";
                   type jt:ipv4addr;
                 }
               }
             }
           }
         }
         case case_5 {
           container pim-ssm {
             description "PIM-SSM provider tunnel";
             uses apply-advanced;
             leaf group-address {
               description "PIM-SSM provider tunnel group address";
               type jt:ipv4addr;
             }
             container family {
               presence "enable family";
               description "PIM-SSM provider tunnel address family";
               status deprecated;
               uses apply-advanced;
               container inet {
                 presence "enable inet";
                 description "IPv4 PIM-SSM provider tunnel";
                 uses apply-advanced;
                 leaf group-address {
                   description "PIM-SSM provider tunnel group address for IPV4";
                   type jt:ipv4addr;
                 }
                 leaf tunnel-source {
                   description "Source address for the provider space mGRE tunnel";
                   type jt:ipv4addr;
                 }
               }
               container inet6 {
                 presence "enable inet6";
                 description "IPv6 PIM-SSM provider tunnel";
                 uses apply-advanced;
                 leaf group-address {
                   description "PIM-SSM provider tunnel group address for IPV6";
                   type jt:ipv4addr;
                 }
                 leaf tunnel-source {
                   description "Source address for the provider space mGRE tunnel";
                   type jt:ipv4addr;
                 }
               }
             }
           }
         }
       }
       container inter-region {
         description "Inter-region segmented tunnels";
         uses apply-advanced;
         choice segmented-or-not {
           case case_1 {
             leaf template {
               description "Use inter-region segmentation template";
               type string;
             }
           }
           case case_2 {
             leaf no-inter-region-segmentation {
               description "Do not participate in inter-region segmentation";
               type empty;
             }
           }
         }
       }
       container inter-region-segmented {
         description "Inter-Region Segmented LSP triggered by fan-out factor only";
         uses apply-advanced;
         leaf fan-out {
           description "Number of remote Leaf-AD routes";
           type union {
             type string {
               pattern "<.*>|$.*";
             }
             type uint32 {
               range "1 .. 10000";
             }
           }
         }
       }
       container selective {
         description "Selective tunnels";
         uses apply-advanced;
         leaf tunnel-limit {
           description "Maximum number of selective tunnels";
           type union {
             type string {
               pattern "<.*>|$.*";
             }
             type uint32 {
               range "0 .. 30000";
             }
           }
         }
         leaf leaf-tunnel-limit-inet {
           description "Maximum number of selective leaf tunnels for v4";
           type union {
             type string {
               pattern "<.*>|$.*";
             }
             type uint32 {
               range "0 .. 15000";
             }
           }
         }
         leaf leaf-tunnel-limit-inet6 {
           description "Maximum number of selective leaf tunnels for v6";
           type union {
             type string {
               pattern "<.*>|$.*";
             }
             type uint32 {
               range "0 .. 15000";
             }
           }
         }
         container wildcard-group-inet {
           description "IPv4 wilcard group matching any group address";
           uses apply-advanced;
           container wildcard-source {
             presence "enable wildcard-source";
             description "Use Selective-Tunnel for wildcard-source (*,G) joins";
             uses apply-advanced;
             leaf threshold-rate {
               description "Data threshold to create new tunnel";
               units "kilobits";
               type union {
                 type string {
                   pattern "<.*>|$.*";
                 }
                 type uint32 {
                   range "0 .. 1000000";
                 }
               }
             }
             choice tunnel-type {
               case case_1 {
                 container ingress-replication {
                   description "Ingress replication tunnel";
                   uses apply-advanced;
                   leaf create-new-ucast-tunnel {
                     description "Create new unicast tunnel for ingress replication";
                     type empty;
                   }
                   container label-switched-path {
                     presence "enable label-switched-path";
                     description "Point-to-point LSP unicast tunnel";
                     uses apply-advanced;
                     container label-switched-path-template {
                       description "Template for dynamic point-to-point LSP parameters";
                       uses apply-advanced;
                       choice dynamic-template {
                         case case_1 {
                           leaf template-name {
                             description "Name of point-to-point LSP template";
                             type string {
                             }
                           }
                         }
                         case case_2 {
                           leaf default-template {
                             description "Use default parameters";
                             type empty;
                           }
                         }
                       }
                     }
                   }
                 }
               }
               case case_2 {
                 container rsvp-te {
                   description "RSVP-TE point-to-multipoint LSP for flooding";
                   uses apply-advanced;
                   choice static-or-dynamic {
                     case case_1 {
                       leaf static-lsp {
                         description "Name of point-to-multipoint LSP";
                         type string {
                         }
                       }
                     }
                     case case_2 {
                       container label-switched-path-template {
                         description "Template for dynamic point-to-multipoint LSP parameters";
                         uses apply-advanced;
                         choice dynamic-template {
                           case case_1 {
                             leaf template-name {
                               description "Name of point-to-multipoint LSP template";
                               type string {
                               }
                             }
                           }
                           case case_2 {
                             leaf default-template {
                               description "Use default parameters";
                               type empty;
                             }
                           }
                         }
                       }
                     }
                   }
                 }
               }
               case case_3 {
                 container ldp-p2mp {
                   presence "enable ldp-p2mp";
                   description "LDP point-to-multipoint LSP for flooding";
                 }
               }
               case case_4 {
                 container pim-ssm {
                   description "PIM-SSM provider tunnel";
                   uses apply-advanced;
                   leaf group-range {
                     description "PIM-SSM provider tunnel group range";
                     type jt:ipv4prefix;
                   }
                 }
               }
             }
             container inter-region-segmented {
               description "Inter-Region Segmented LSP triggered by fan-out factor only";
               uses apply-advanced;
               leaf fan-out {
                 description "Number of remote Leaf-AD routes";
                 type union {
                   type string {
                     pattern "<.*>|$.*";
                   }
                   type uint32 {
                     range "1 .. 10000";
                   }
                 }
               }
             }
           }
         }
         container wildcard-group-inet6 {
           description "IPv6 wilcard group matching any group address";
           uses apply-advanced;
           container wildcard-source {
             presence "enable wildcard-source";
             description "Use Selective-Tunnel for wildcard-source (*,G) joins";
             uses apply-advanced;
             leaf threshold-rate {
               description "Data threshold to create new tunnel";
               units "kilobits";
               type union {
                 type string {
                   pattern "<.*>|$.*";
                 }
                 type uint32 {
                   range "0 .. 1000000";
                 }
               }
             }
             choice tunnel-type {
               case case_1 {
                 container ingress-replication {
                   description "Ingress replication tunnel";
                   uses apply-advanced;
                   leaf create-new-ucast-tunnel {
                     description "Create new unicast tunnel for ingress replication";
                     type empty;
                   }
                   container label-switched-path {
                     presence "enable label-switched-path";
                     description "Point-to-point LSP unicast tunnel";
                     uses apply-advanced;
                     container label-switched-path-template {
                       description "Template for dynamic point-to-point LSP parameters";
                       uses apply-advanced;
                       choice dynamic-template {
                         case case_1 {
                           leaf template-name {
                             description "Name of point-to-point LSP template";
                             type string {
                             }
                           }
                         }
                         case case_2 {
                           leaf default-template {
                             description "Use default parameters";
                             type empty;
                           }
                         }
                       }
                     }
                   }
                 }
               }
               case case_2 {
                 container rsvp-te {
                   description "RSVP-TE point-to-multipoint LSP for flooding";
                   uses apply-advanced;
                   choice static-or-dynamic {
                     case case_1 {
                       leaf static-lsp {
                         description "Name of point-to-multipoint LSP";
                         type string {
                         }
                       }
                     }
                     case case_2 {
                       container label-switched-path-template {
                         description "Template for dynamic point-to-multipoint LSP parameters";
                         uses apply-advanced;
                         choice dynamic-template {
                           case case_1 {
                             leaf template-name {
                               description "Name of point-to-multipoint LSP template";
                               type string {
                               }
                             }
                           }
                           case case_2 {
                             leaf default-template {
                               description "Use default parameters";
                               type empty;
                             }
                           }
                         }
                       }
                     }
                   }
                 }
               }
               case case_3 {
                 container ldp-p2mp {
                   presence "enable ldp-p2mp";
                   description "LDP point-to-multipoint LSP for flooding";
                 }
               }
               case case_4 {
                 container pim-ssm {
                   description "PIM-SSM provider tunnel";
                   uses apply-advanced;
                   leaf group-range {
                     description "PIM-SSM provider tunnel group range";
                     type jt:ipv4prefix;
                   }
                 }
               }
             }
             container inter-region-segmented {
               description "Inter-Region Segmented LSP triggered by fan-out factor only";
               uses apply-advanced;
               leaf fan-out {
                 description "Number of remote Leaf-AD routes";
                 type union {
                   type string {
                     pattern "<.*>|$.*";
                   }
                   type uint32 {
                     range "1 .. 10000";
                   }
                 }
               }
             }
           }
         }
         list group {
           key name;
           ordered-by user;
           description "IP prefix of multicast group";
           leaf name {
             description "IP prefix of group";
             type jt:ipprefix;
           }
           uses apply-advanced;
           container wildcard-source {
             presence "enable wildcard-source";
             description "Use Selective-Tunnel for wildcard-source (*,G) joins";
             uses apply-advanced;
             leaf threshold-rate {
               description "Data threshold to create new tunnel";
               units "kilobits";
               type union {
                 type string {
                   pattern "<.*>|$.*";
                 }
                 type uint32 {
                   range "0 .. 1000000";
                 }
               }
             }
             choice tunnel-type {
               case case_1 {
                 container ingress-replication {
                   description "Ingress replication tunnel";
                   uses apply-advanced;
                   leaf create-new-ucast-tunnel {
                     description "Create new unicast tunnel for ingress replication";
                     type empty;
                   }
                   container label-switched-path {
                     presence "enable label-switched-path";
                     description "Point-to-point LSP unicast tunnel";
                     uses apply-advanced;
                     container label-switched-path-template {
                       description "Template for dynamic point-to-point LSP parameters";
                       uses apply-advanced;
                       choice dynamic-template {
                         case case_1 {
                           leaf template-name {
                             description "Name of point-to-point LSP template";
                             type string {
                             }
                           }
                         }
                         case case_2 {
                           leaf default-template {
                             description "Use default parameters";
                             type empty;
                           }
                         }
                       }
                     }
                   }
                 }
               }
               case case_2 {
                 container rsvp-te {
                   description "RSVP-TE point-to-multipoint LSP for flooding";
                   uses apply-advanced;
                   choice static-or-dynamic {
                     case case_1 {
                       leaf static-lsp {
                         description "Name of point-to-multipoint LSP";
                         type string {
                         }
                       }
                     }
                     case case_2 {
                       container label-switched-path-template {
                         description "Template for dynamic point-to-multipoint LSP parameters";
                         uses apply-advanced;
                         choice dynamic-template {
                           case case_1 {
                             leaf template-name {
                               description "Name of point-to-multipoint LSP template";
                               type string {
                               }
                             }
                           }
                           case case_2 {
                             leaf default-template {
                               description "Use default parameters";
                               type empty;
                             }
                           }
                         }
                       }
                     }
                   }
                 }
               }
               case case_3 {
                 container ldp-p2mp {
                   presence "enable ldp-p2mp";
                   description "LDP point-to-multipoint LSP for flooding";
                 }
               }
               case case_4 {
                 container pim-ssm {
                   description "PIM-SSM provider tunnel";
                   uses apply-advanced;
                   leaf group-range {
                     description "PIM-SSM provider tunnel group range";
                     type jt:ipv4prefix;
                   }
                 }
               }
             }
             container inter-region-segmented {
               description "Inter-Region Segmented LSP triggered by threshold rate and/or fan-out";
               uses apply-advanced;
               leaf threshold {
                 description "Data threshold rate to trigger segmentation";
                 units "kilobits";
                 type union {
                   type string {
                     pattern "<.*>|$.*";
                   }
                   type uint32 {
                     range "0 .. 1000000";
                   }
                 }
               }
               leaf fan-out {
                 description "Number of remote Leaf-AD routes";
                 type union {
                   type string {
                     pattern "<.*>|$.*";
                   }
                   type uint32 {
                     range "1 .. 10000";
                   }
                 }
               }
             }
           }
           list source {
             key name;
             ordered-by user;
             description "IP prefix of one or more multicast sources";
             leaf name {
               description "IP prefix of source";
               type jt:ipprefix;
             }
             uses apply-advanced;
             choice tunnel-type {
               case case_1 {
                 container ingress-replication {
                   description "Ingress replication tunnel";
                   uses apply-advanced;
                   leaf create-new-ucast-tunnel {
                     description "Create new unicast tunnel for ingress replication";
                     type empty;
                   }
                   container label-switched-path {
                     presence "enable label-switched-path";
                     description "Point-to-point LSP unicast tunnel";
                     uses apply-advanced;
                     container label-switched-path-template {
                       description "Template for dynamic point-to-point LSP parameters";
                       uses apply-advanced;
                       choice dynamic-template {
                         case case_1 {
                           leaf template-name {
                             description "Name of point-to-point LSP template";
                             type string {
                             }
                           }
                         }
                         case case_2 {
                           leaf default-template {
                             description "Use default parameters";
                             type empty;
                           }
                         }
                       }
                     }
                   }
                 }
               }
               case case_2 {
                 container rsvp-te {
                   description "RSVP-TE point-to-multipoint LSP for flooding";
                   uses apply-advanced;
                   choice static-or-dynamic {
                     case case_1 {
                       leaf static-lsp {
                         description "Name of point-to-multipoint LSP";
                         type string {
                         }
                       }
                     }
                     case case_2 {
                       container label-switched-path-template {
                         description "Template for dynamic point-to-multipoint LSP parameters";
                         uses apply-advanced;
                         choice dynamic-template {
                           case case_1 {
                             leaf template-name {
                               description "Name of point-to-multipoint LSP template";
                               type string {
                               }
                             }
                           }
                           case case_2 {
                             leaf default-template {
                               description "Use default parameters";
                               type empty;
                             }
                           }
                         }
                       }
                     }
                   }
                 }
               }
               case case_3 {
                 container pim-ssm {
                   description "PIM-SSM provider tunnel";
                   uses apply-advanced;
                   leaf group-range {
                     description "PIM-SSM provider tunnel group range";
                     type jt:ipv4prefix;
                   }
                 }
               }
               case case_4 {
                 container ldp-p2mp {
                   presence "enable ldp-p2mp";
                   description "LDP point-to-multipoint LSP for flooding";
                 }
               }
             }
             leaf threshold-rate {
               description "Data threshold to create new tunnel";
               units "kilobits";
               type union {
                 type string {
                   pattern "<.*>|$.*";
                 }
                 type uint32 {
                   range "0 .. 1000000";
                 }
               }
             }
             container inter-region-segmented {
               description "Inter-Region Segmented LSP triggered by threshold rate and/or fan-out";
               uses apply-advanced;
               leaf threshold {
                 description "Data threshold rate to trigger segmentation";
                 units "kilobits";
                 type union {
                   type string {
                     pattern "<.*>|$.*";
                   }
                   type uint32 {
                     range "0 .. 1000000";
                   }
                 }
               }
               leaf fan-out {
                 description "Number of remote Leaf-AD routes";
                 type union {
                   type string {
                     pattern "<.*>|$.*";
                   }
                   type uint32 {
                     range "1 .. 10000";
                   }
                 }
               }
             }
           }
         }
       }
       container mdt {
         description "Data MDT tunnels for PIM MVPN";
         status deprecated;
         uses apply-advanced;
         container threshold {
           description "Threshold for creation of multicast tunnels";
           uses apply-advanced;
           list group {
             key name;
             ordered-by user;
             description "IP prefix of multicast group";
             leaf name {
               description "IP prefix of group";
               type jt:ipprefix;
             }
             uses apply-advanced;
             list source {
               key name;
               ordered-by user;
               description "IP prefix of one or more multicast sources ";
               leaf name {
                 description "IP prefix of source";
                 type jt:ipprefix;
               }
               uses apply-advanced;
               leaf rate {
                 description "Data threshold to create new tunnel";
                 units "kilobits";
                 type union {
                   type string {
                     pattern "<.*>|$.*";
                   }
                   type uint32 {
                     range "10 .. 1000000";
                   }
                 }
               }
             }
           }
         }
         leaf data-mdt-reuse {
           description "Allow multiple customer streams to be transmitted over one data tunnel ";
           type empty;
         }
         leaf tunnel-limit {
           description "Maximum multicast data tunnels";
           type union {
             type string {
               pattern "<.*>|$.*";
             }
             type uint32 {
               range "0 .. 8192";
             }
           }
         }
         leaf group-range {
           description "Group address range for multicast data tunnels";
           type jt:ipprefix;
         }
       }
       container family {
         presence "enable family";
         uses apply-advanced;
         container inet {
           presence "enable inet";
           uses apply-advanced;
           choice tunnel-type {
             case case_1 {
               container rsvp-te {
                 description "RSVP-TE point-to-multipoint LSP for flooding";
                 uses apply-advanced;
                 choice static-or-dynamic {
                   case case_1 {
                     leaf static-lsp {
                       description "Name of point-to-multipoint LSP";
                       type string {
                       }
                     }
                   }
                   case case_2 {
                     container label-switched-path-template {
                       description "Template for dynamic point-to-multipoint LSP parameters";
                       uses apply-advanced;
                       choice dynamic-template {
                         case case_1 {
                           leaf template-name {
                             description "Name of point-to-multipoint LSP template";
                             type string {
                             }
                           }
                         }
                         case case_2 {
                           leaf default-template {
                             description "Use default parameters";
                             type empty;
                           }
                         }
                       }
                     }
                   }
                 }
               }
             }
             case case_2 {
               container ldp-p2mp {
                 presence "enable ldp-p2mp";
                 description "LDP point-to-multipoint LSP for flooding";
               }
             }
             case case_3 {
               container ingress-replication {
                 description "Ingress replication tunnel";
                 uses apply-advanced;
                 leaf create-new-ucast-tunnel {
                   description "Create new unicast tunnel for ingress replication";
                   type empty;
                 }
                 container label-switched-path {
                   presence "enable label-switched-path";
                   description "Point-to-point LSP unicast tunnel";
                   uses apply-advanced;
                   container label-switched-path-template {
                     description "Template for dynamic point-to-point LSP parameters";
                     uses apply-advanced;
                     choice dynamic-template {
                       case case_1 {
                         leaf template-name {
                           description "Name of point-to-point LSP template";
                           type string {
                           }
                         }
                       }
                       case case_2 {
                         leaf default-template {
                           description "Use default parameters";
                           type empty;
                         }
                       }
                     }
                   }
                 }
               }
             }
             case case_4 {
               container pim-asm {
                 description "PIM-SM provider tunnel";
                 uses apply-advanced;
                 leaf group-address {
                   description "PIM-SM provider tunnel group address";
                   type jt:ipv4addr;
                 }
                 leaf tunnel-source {
                   description "Source address for the provider space mGRE tunnel";
                   type jt:ipv4addr;
                 }
               }
             }
             case case_5 {
               container pim-ssm {
                 description "PIM-SSM provider tunnel";
                 uses apply-advanced;
                 leaf group-address {
                   description "PIM-SSM provider tunnel group address";
                   type jt:ipv4addr;
                 }
                 leaf tunnel-source {
                   description "Source address for the provider space mGRE tunnel";
                   type jt:ipv4addr;
                 }
               }
             }
           }
           container mdt {
             description "IPv4 Data MDT tunnels for PIM MVPN";
             uses apply-advanced;
             container threshold {
               description "Threshold for creation of multicast tunnels";
               uses apply-advanced;
               list group {
                 key name;
                 ordered-by user;
                 description "IP prefix of multicast group";
                 leaf name {
                   description "IP prefix of group";
                   type jt:ipprefix;
                 }
                 uses apply-advanced;
                 list source {
                   key name;
                   ordered-by user;
                   description "IP prefix of one or more multicast sources ";
                   leaf name {
                     description "IP prefix of source";
                     type jt:ipprefix;
                   }
                   uses apply-advanced;
                   leaf rate {
                     description "Data threshold to create new tunnel";
                     units "kilobits";
                     type union {
                       type string {
                         pattern "<.*>|$.*";
                       }
                       type uint32 {
                         range "10 .. 1000000";
                       }
                     }
                   }
                 }
               }
             }
             leaf data-mdt-reuse {
               description "Allow multiple customer streams to be transmitted over one data tunnel ";
               type empty;
             }
             leaf tunnel-limit {
               description "Maximum multicast data tunnels";
               type union {
                 type string {
                   pattern "<.*>|$.*";
                 }
                 type uint32 {
                   range "0 .. 8192";
                 }
               }
             }
             leaf group-range {
               description "Group address range for multicast data tunnels";
               type jt:ipprefix;
             }
           }
         }
         container inet6 {
           presence "enable inet6";
           uses apply-advanced;
           choice tunnel-type {
             case case_1 {
               container rsvp-te {
                 description "RSVP-TE point-to-multipoint LSP for flooding";
                 uses apply-advanced;
                 choice static-or-dynamic {
                   case case_1 {
                     leaf static-lsp {
                       description "Name of point-to-multipoint LSP";
                       type string {
                       }
                     }
                   }
                   case case_2 {
                     container label-switched-path-template {
                       description "Template for dynamic point-to-multipoint LSP parameters";
                       uses apply-advanced;
                       choice dynamic-template {
                         case case_1 {
                           leaf template-name {
                             description "Name of point-to-multipoint LSP template";
                             type string {
                             }
                           }
                         }
                         case case_2 {
                           leaf default-template {
                             description "Use default parameters";
                             type empty;
                           }
                         }
                       }
                     }
                   }
                 }
               }
             }
             case case_2 {
               container ldp-p2mp {
                 presence "enable ldp-p2mp";
                 description "LDP point-to-multipoint LSP for flooding";
               }
             }
             case case_3 {
               container ingress-replication {
                 description "Ingress replication tunnel";
                 uses apply-advanced;
                 leaf create-new-ucast-tunnel {
                   description "Create new unicast tunnel for ingress replication";
                   type empty;
                 }
                 container label-switched-path {
                   presence "enable label-switched-path";
                   description "Point-to-point LSP unicast tunnel";
                   uses apply-advanced;
                   container label-switched-path-template {
                     description "Template for dynamic point-to-point LSP parameters";
                     uses apply-advanced;
                     choice dynamic-template {
                       case case_1 {
                         leaf template-name {
                           description "Name of point-to-point LSP template";
                           type string {
                           }
                         }
                       }
                       case case_2 {
                         leaf default-template {
                           description "Use default parameters";
                           type empty;
                         }
                       }
                     }
                   }
                 }
               }
             }
             case case_4 {
               container pim-asm {
                 description "PIM-SM provider tunnel";
                 uses apply-advanced;
                 leaf group-address {
                   description "PIM-SM provider tunnel group address";
                   type jt:ipv4addr;
                 }
                 leaf tunnel-source {
                   description "Source address for the provider space mGRE tunnel";
                   type jt:ipv4addr;
                 }
               }
             }
             case case_5 {
               container pim-ssm {
                 description "PIM-SSM provider tunnel";
                 uses apply-advanced;
                 leaf group-address {
                   description "PIM-SSM provider tunnel group address";
                   type jt:ipv4addr;
                 }
                 leaf tunnel-source {
                   description "Source address for the provider space mGRE tunnel";
                   type jt:ipv4addr;
                 }
               }
             }
           }
           container mdt {
             description "IPv6 Data MDT tunnels for PIM MVPN";
             uses apply-advanced;
             container threshold {
               description "Threshold for creation of multicast tunnels";
               uses apply-advanced;
               list group {
                 key name;
                 ordered-by user;
                 description "IP prefix of multicast group";
                 leaf name {
                   description "IP prefix of group";
                   type jt:ipprefix;
                 }
                 uses apply-advanced;
                 list source {
                   key name;
                   ordered-by user;
                   description "IP prefix of one or more multicast sources ";
                   leaf name {
                     description "IP prefix of source";
                     type jt:ipprefix;
                   }
                   uses apply-advanced;
                   leaf rate {
                     description "Data threshold to create new tunnel";
                     units "kilobits";
                     type union {
                       type string {
                         pattern "<.*>|$.*";
                       }
                       type uint32 {
                         range "10 .. 1000000";
                       }
                     }
                   }
                 }
               }
             }
             leaf data-mdt-reuse {
               description "Allow multiple customer streams to be transmitted over one data tunnel ";
               type empty;
             }
             leaf tunnel-limit {
               description "Maximum multicast data tunnels";
               type union {
                 type string {
                   pattern "<.*>|$.*";
                 }
                 type uint32 {
                   range "0 .. 8192";
                 }
               }
             }
             leaf group-range {
               description "Group address range for multicast data tunnels";
               type jt:ipprefix;
             }
           }
         }
       }
     }
     leaf-list vrf-import {
       ordered-by user;
       description "Import policy for VRF instance RIBs";
       type jt:policy-algebra;
     }
     leaf-list vrf-export {
       ordered-by user;
       description "Export policy for VRF instance RIBs";
       type jt:policy-algebra;
     }
     container vrf-target {
       description "VRF target community configuration";
       uses apply-advanced;
       leaf community {
         description "Target community to use in import and export";
         type string {
         }
       }
       leaf import {
         description "Target community to use when filtering on import";
         type string {
         }
       }
       leaf export {
         description "Target community to use when marking routes on export";
         type string {
         }
       }
       leaf auto {
         description "Auto derive import and export target community from BGP AS & L2";
         type empty;
       }
     }
     leaf no-vrf-advertise {
       description "Don't advertise this instance to remote PEs";
       type empty;
     }
     leaf connector-id-advertise {
       description "Advertise connector-id attribute";
       type empty;
     }
     container vrf-advertise-selective {
       presence "enable vrf-advertise-selective";
       description "Override no-vrf-advertise knob for the specified address family";
       uses apply-advanced;
       container family {
         description "Protocol family to be selectively advertised";
         uses apply-advanced;
         leaf inet-mvpn {
           description "IPv4 MVPN Address Family";
           type empty;
         }
         leaf inet6-mvpn {
           description "IPv6 MVPN Address Family";
           type empty;
         }
       }
     }
     container vrf-table-label {
       presence "enable vrf-table-label";
       description "Advertise a single VPN label for all routes in the VRF";
       leaf static {
         description "Specify label value to be used";
         type union {
           type string {
             pattern "<.*>|$.*";
           }
           type uint32 {
             range "16 .. 1048575";
           }
         }
       }
       leaf source-class-usage {
         description "Enable source class usage";
         type empty;
       }
     }
     container routing-options {
       description "Protocol-independent routing option configuration";
       uses juniper-routing-options;
     }
     container forwarding-options {
       description "Forwarding options configuration";
       uses juniper-forwarding-options;
     }
     container multicast-snooping-options {
       description "Multicast snooping option configuration";
       uses juniper-multicast-snooping-options;
     }
     container igmp-snooping-options {
       description "IGMP snooping option configuration";
       uses juniper-igmp-snooping-options;
     }
     container mld-snooping-options {
       description "MLD snooping option configuration";
       uses juniper-mld-snooping-options;
     }
     container protocols {
       description "Routing protocol configuration";
       uses apply-advanced;
       container bgp {
         description "BGP options";
         uses juniper-protocols-bgp;
       }
       container mpls {
         description "MPLS configuration";
         uses juniper-protocols-mpls;
       }
       container rsvp {
         description "RSVP configuration";
         uses juniper-protocols-rsvp;
       }
       container ospf {
         description "OSPF configuration";
         uses juniper-protocols-ospf;
       }
       container ospf3 {
         description "OSPF3 configuration";
         list realm {
           key name;
           ordered-by user;
           description "OSPFv3 realm configuration";
           leaf name {
             description "OSPFv3 realm name";
             type enumeration {
               enum "ipv6-unicast" {
                 description "IPv6 unicast realm";
               }
               enum "ipv6-multicast" {
                 description "IPv6 multicast realm";
               }
               enum "ipv4-unicast" {
                 description "IPv4 unicast realm";
               }
               enum "ipv4-multicast" {
                 description "IPv4 multicast realm";
               }
             }
           }
           uses apply-advanced;
           choice enable-disable {
             case case_1 {
               leaf disable {
                 description "Disable OSPF";
                 type empty;
               }
             }
           }
           container traceoptions {
             description "Trace options for OSPF";
             uses apply-advanced;
             container file {
               description "Trace file options";
               leaf filename {
                 description "Name of file in which to write trace information";
                 type string {
                   length "1 .. 1024";
                 }
               }
               leaf replace {
                 description "Replace trace file rather than appending to it";
                 status deprecated;
                 type empty;
               }
               leaf size {
                 description "Maximum trace file size";
                 type string;
               }
               leaf files {
                 description "Maximum number of trace files";
                 default "10";
                 type union {
                   type string {
                     pattern "<.*>|$.*";
                   }
                   type uint32 {
                     range "2 .. 1000";
                   }
                 }
               }
               leaf no-stamp {
                 description "Do not timestamp trace file";
                 status deprecated;
                 type empty;
               }
               choice world-readable-choice {
                 leaf world-readable {
                   description "Allow any user to read the log file";
                   type empty;
                 }
                 leaf no-world-readable {
                   description "Don't allow any user to read the log file";
                   type empty;
                 }
               }
             }
             list flag {
               key name;
               ordered-by user;
               description "Tracing parameters";
               leaf name {
                 type enumeration {
                   enum "spf" {
                     description "Trace SPF calculations";
                   }
                   enum "error" {
                     description "Trace errored packets";
                   }
                   enum "event" {
                     description "Trace OSPF state machine events";
                   }
                   enum "packet-dump" {
                     description "Dump the contents of selected packet types";
                   }
                   enum "flooding" {
                     description "Trace LSA flooding";
                   }
                   enum "lsa-analysis" {
                     description "Trace LSA analysis";
                   }
                   enum "packets" {
                     description "Trace all OSPF packets";
                   }
                   enum "hello" {
                     description "Trace hello packets";
                   }
                   enum "database-description" {
                     description "Trace database description packets";
                   }
                   enum "lsa-request" {
                     description "Trace LSA request packets";
                   }
                   enum "lsa-update" {
                     description "Trace LSA update packets";
                   }
                   enum "lsa-ack" {
                     description "Trace LSA acknowledgment packets";
                   }
                   enum "ldp-synchronization" {
                     description "Trace synchronization between OSPF and LDP";
                   }
                   enum "on-demand" {
                     description "Trace demand circuit extensions";
                   }
                   enum "nsr-synchronization" {
                     description "Trace NSR synchronization events";
                   }
                   enum "graceful-restart" {
                     description "Trace graceful restart";
                   }
                   enum "restart-signaling" {
                     description "Trace restart signaling";
                   }
                   enum "backup-spf" {
                     description "Trace backup SPF (LFA) specific events";
                   }
                   enum "source-packet-routing" {
                     description "Trace source packet routing (SPRING) events";
                   }
                   enum "post-convergence-lfa" {
                     description "Trace post-convergence-lfa related events";
                   }
                   enum "route" {
                     description "Trace routing information";
                   }
                   enum "normal" {
                     description "Trace normal events";
                   }
                   enum "general" {
                     description "Trace general events";
                   }
                   enum "state" {
                     description "Trace state transitions";
                   }
                   enum "policy" {
                     description "Trace policy processing";
                   }
                   enum "task" {
                     description "Trace routing protocol task processing";
                   }
                   enum "timer" {
                     description "Trace routing protocol timer processing";
                   }
                   enum "all" {
                     description "Trace everything";
                   }
                 }
               }
               leaf send {
                 description "Trace transmitted packets";
                 type empty;
               }
               leaf receive {
                 description "Trace received packets";
                 type empty;
               }
               leaf detail {
                 description "Trace detailed information";
                 type empty;
               }
               leaf disable {
                 description "Disable this trace flag";
                 type empty;
               }
             }
           }
           list topology {
             key name;
             ordered-by user;
             description "Topology parameters";
             leaf name {
               description "Topology name";
               type string;
             }
             uses apply-advanced;
             leaf disable {
               description "Disable this topology";
               type empty;
             }
             leaf topology-id {
               description "Topology identifier";
               type union {
                 type string {
                   pattern "<.*>|$.*";
                 }
                 type uint8 {
                   range "32 .. 127";
                 }
               }
             }
             leaf overload {
               description "Set the overload mode (repel transit traffic)";
               type empty;
             }
             leaf rib-group {
               description "Routing table group for importing routes";
               type string;
             }
             container spf-options {
               description "Configure options for SPF";
               uses apply-advanced;
               leaf delay {
                 description "Time to wait before running an SPF";
                 units "milliseconds";
                 type union {
                   type string {
                     pattern "<.*>|$.*";
                   }
                   type uint32 {
                     range "50 .. 8000";
                   }
                 }
               }
               leaf holddown {
                 description "Time to hold down before running an SPF";
                 units "milliseconds";
                 type union {
                   type string {
                     pattern "<.*>|$.*";
                   }
                   type uint32 {
                     range "2000 .. 20000";
                   }
                 }
               }
               leaf rapid-runs {
                 description "Number of maximum rapid SPF runs before holddown";
                 type union {
                   type string {
                     pattern "<.*>|$.*";
                   }
                   type uint32 {
                     range "1 .. 10";
                   }
                 }
               }
               leaf no-ignore-our-externals {
                 description "Do not ignore self-generated external and NSSA LSAs";
                 type empty;
               }
             }
             container backup-spf-options {
               description "Configure options for backup SPF";
               uses apply-advanced;
               leaf disable {
                 description "Do not run backup SPF";
                 type empty;
               }
               leaf no-install {
                 description "Do not install backup nexthops into the RIB";
                 type empty;
               }
               leaf downstream-paths-only {
                 description "Use only downstream backup paths";
                 type empty;
               }
               container remote-backup-calculation {
                 presence "enable remote-backup-calculation";
                 description "Calculate Remote LFA backup nexthops";
                 uses apply-advanced;
                 container pq-nodes-nearest-to-source {
                   description "PQ nodes selection based upon nearest to source";
                   uses apply-advanced;
                   leaf percent {
                     description "Selection percentage for nearest to source";
                     type union {
                       type string {
                         pattern "<.*>|$.*";
                       }
                       type uint32 {
                         range "10 .. 100";
                       }
                     }
                   }
                 }
               }
               container use-post-convergence-lfa {
                 presence "enable use-post-convergence-lfa";
                 description "Calculate post-convergence backup paths";
                 uses apply-advanced;
                 leaf maximum-labels {
                   description "Maximum number of labels installed for post-convergence paths";
                   type union {
                     type string {
                       pattern "<.*>|$.*";
                     }
                     type uint32 {
                       range "2 .. 5";
                     }
                   }
                 }
                 leaf maximum-backup-paths {
                   description "Maximum number of equal-cost post-convergence paths installed";
                   type union {
                     type string {
                       pattern "<.*>|$.*";
                     }
                     type uint32 {
                       range "1 .. 8";
                     }
                   }
                 }
               }
               container per-prefix-calculation {
                 description "Calculate backup nexthops for non-best prefix originators";
                 uses apply-advanced;
                 leaf stubs {
                   description "Per prefix calculation for stubs only";
                   type empty;
                 }
                 leaf summary {
                   description "Per prefix calculation for summary originators only";
                   type empty;
                 }
                 leaf externals {
                   description "Per prefix calculation for externals";
                   type empty;
                 }
                 leaf all {
                   description "Per prefix calculation for all";
                   type empty;
                 }
               }
               leaf node-link-degradation {
                 description "Degrade to link protection when nodelink protection not available";
                 type empty;
               }
               leaf use-source-packet-routing {
                 description "Use spring backup paths for inet.0 routes";
                 type empty;
               }
             }
             leaf prefix-export-limit {
               description "Maximum number of prefixes that can be exported";
               type union {
                 type string {
                   pattern "<.*>|$.*";
                 }
                 type uint32 {
                   range "0 .. 4294967295";
                 }
               }
             }
           }
           container spf-options {
             description "Configure options for SPF";
             uses apply-advanced;
             leaf delay {
               description "Time to wait before running an SPF";
               units "milliseconds";
               type union {
                 type string {
                   pattern "<.*>|$.*";
                 }
                 type uint32 {
                   range "50 .. 8000";
                 }
               }
             }
             leaf holddown {
               description "Time to hold down before running an SPF";
               units "milliseconds";
               type union {
                 type string {
                   pattern "<.*>|$.*";
                 }
                 type uint32 {
                   range "2000 .. 20000";
                 }
               }
             }
             leaf rapid-runs {
               description "Number of maximum rapid SPF runs before holddown";
               type union {
                 type string {
                   pattern "<.*>|$.*";
                 }
                 type uint32 {
                   range "1 .. 10";
                 }
               }
             }
             leaf no-ignore-our-externals {
               description "Do not ignore self-generated external and NSSA LSAs";
               type empty;
             }
           }
           container backup-spf-options {
             description "Configure options for backup SPF";
             uses apply-advanced;
             leaf disable {
               description "Do not run backup SPF";
               type empty;
             }
             leaf no-install {
               description "Do not install backup nexthops into the RIB";
               type empty;
             }
             leaf downstream-paths-only {
               description "Use only downstream backup paths";
               type empty;
             }
             container remote-backup-calculation {
               presence "enable remote-backup-calculation";
               description "Calculate Remote LFA backup nexthops";
               uses apply-advanced;
               container pq-nodes-nearest-to-source {
                 description "PQ nodes selection based upon nearest to source";
                 uses apply-advanced;
                 leaf percent {
                   description "Selection percentage for nearest to source";
                   type union {
                     type string {
                       pattern "<.*>|$.*";
                     }
                     type uint32 {
                       range "10 .. 100";
                     }
                   }
                 }
               }
             }
             container use-post-convergence-lfa {
               presence "enable use-post-convergence-lfa";
               description "Calculate post-convergence backup paths";
               uses apply-advanced;
               leaf maximum-labels {
                 description "Maximum number of labels installed for post-convergence paths";
                 type union {
                   type string {
                     pattern "<.*>|$.*";
                   }
                   type uint32 {
                     range "2 .. 5";
                   }
                 }
               }
               leaf maximum-backup-paths {
                 description "Maximum number of equal-cost post-convergence paths installed";
                 type union {
                   type string {
                     pattern "<.*>|$.*";
                   }
                   type uint32 {
                     range "1 .. 8";
                   }
                 }
               }
             }
             container per-prefix-calculation {
               description "Calculate backup nexthops for non-best prefix originators";
               uses apply-advanced;
               leaf stubs {
                 description "Per prefix calculation for stubs only";
                 type empty;
               }
               leaf summary {
                 description "Per prefix calculation for summary originators only";
                 type empty;
               }
               leaf externals {
                 description "Per prefix calculation for externals";
                 type empty;
               }
               leaf all {
                 description "Per prefix calculation for all";
                 type empty;
               }
             }
             leaf node-link-degradation {
               description "Degrade to link protection when nodelink protection not available";
               type empty;
             }
             leaf use-source-packet-routing {
               description "Use spring backup paths for inet.0 routes";
               type empty;
             }
           }
           leaf prefix-export-limit {
             description "Maximum number of prefixes that can be exported";
             type union {
               type string {
                 pattern "<.*>|$.*";
               }
               type uint32 {
                 range "0 .. 4294967295";
               }
             }
           }
           container rib-groups {
             description "Routing table groups for importing OSPF routes";
             uses apply-advanced;
             leaf inet {
               description "Name of the IPv4/v6 routing table group";
               type string;
             }
             leaf inet3 {
               description "Name of the IPv4/v6 inet.3 routing table group";
               type string;
             }
           }
           leaf job-stats {
             description "Collect job statistics";
             type empty;
           }
           container overload {
             presence "enable overload";
             description "Set the overload mode (repel transit traffic)";
             uses apply-advanced;
             leaf timeout {
               description "Time after which overload mode is reset";
               units "seconds";
               type union {
                 type string {
                   pattern "<.*>|$.*";
                 }
                 type uint32 {
                   range "60 .. 1800";
                 }
               }
             }
             leaf allow-route-leaking {
               description "Allow routes to be leaked when overload is configured";
               type empty;
             }
             leaf stub-network {
               description "Advertise Stub Network with maximum metric";
               type empty;
             }
             leaf intra-area-prefix {
               description "Advertise Intra Area Prefix with maximum metric";
               type empty;
             }
             leaf as-external {
               description "Advertise As External with maximum usable metric";
               type empty;
             }
           }
           container database-protection {
             presence "enable database-protection";
             description "Configure database protection attributes";
             uses apply-advanced;
             leaf maximum-lsa {
               description "Maximum allowed non self-generated LSAs";
               type union {
                 type string {
                   pattern "<.*>|$.*";
                 }
                 type uint32 {
                   range "1 .. 1000000";
                 }
               }
             }
             leaf warning-only {
               description "Emit only a warning when LSA maximum limit is exceeded";
               type empty;
             }
             leaf warning-threshold {
               description "Percentage of LSA maximum above which to trigger warning";
               units "percent";
               type union {
                 type string {
                   pattern "<.*>|$.*";
                 }
                 type uint8 {
                   range "30 .. 100";
                 }
               }
             }
             leaf ignore-count {
               description "Maximum number of times to go into ignore state";
               type union {
                 type string {
                   pattern "<.*>|$.*";
                 }
                 type uint8 {
                   range "1 .. 32";
                 }
               }
             }
             leaf ignore-time {
               description "Time to stay in ignore state and ignore all neighbors";
               units "seconds";
               type union {
                 type string {
                   pattern "<.*>|$.*";
                 }
                 type uint16 {
                   range "30 .. 3600";
                 }
               }
             }
             leaf reset-time {
               description "Time after which the ignore count gets reset to zero";
               units "seconds";
               type union {
                 type string {
                   pattern "<.*>|$.*";
                 }
                 type uint32 {
                   range "60 .. 86400";
                 }
               }
             }
           }
           container graceful-restart {
             description "Configure graceful restart attributes";
             uses apply-advanced;
             choice enable-disable {
               case case_1 {
                 leaf disable {
                   description "Disable OSPF graceful restart capability";
                   type empty;
                 }
               }
             }
             leaf restart-duration {
               description "Time for all neighbors to become full";
               units "seconds";
               type union {
                 type string {
                   pattern "<.*>|$.*";
                 }
                 type uint32 {
                   range "1 .. 3600";
                 }
               }
             }
             leaf notify-duration {
               description "Time to send all max-aged grace LSAs";
               units "seconds";
               type union {
                 type string {
                   pattern "<.*>|$.*";
                 }
                 type uint32 {
                   range "1 .. 3600";
                 }
               }
             }
             container helper-disable {
               presence "enable helper-disable";
               description "Disable graceful restart helper capability";
               uses apply-advanced;
               choice disable-choices {
                 case case_1 {
                   leaf standard {
                     description "Disable helper-mode for rfc3623 based GR";
                     type empty;
                   }
                 }
                 case case_2 {
                   leaf restart-signaling {
                     description "Disable helper mode for restart-signaling ";
                     type empty;
                   }
                 }
                 case case_3 {
                   leaf both {
                     description "Disable helper mode for both the types of GR";
                     type empty;
                   }
                 }
               }
             }
             leaf no-strict-lsa-checking {
               description "Do not abort graceful helper mode upon LSA changes";
               type empty;
             }
           }
           container traffic-engineering {
             presence "enable traffic-engineering";
             description "Configure traffic engineering attributes";
             uses apply-advanced;
             leaf no-topology {
               description "Disable dissemination of TE link-state topology information";
               type empty;
             }
             leaf multicast-rpf-routes {
               description "Install routes for multicast RPF checks into inet.2";
               type empty;
             }
             leaf igp-topology {
               description "Download IGP topology into TED";
               type empty;
             }
             leaf ignore-lsp-metrics {
               description "Ignore label-switched path metrics when doing shortcuts";
               type empty;
             }
             container shortcuts {
               presence "enable shortcuts";
               description "Use label-switched paths as next hops, if possible";
               uses apply-advanced;
               leaf ignore-lsp-metrics {
                 description "Ignore label-switched path metrics when doing shortcuts";
                 status deprecated;
                 type empty;
               }
               leaf lsp-metric-into-summary {
                 description "Advertise LSP metric into summary LSAs";
                 type empty;
               }
               list family {
                 key name;
                 ordered-by user;
                 description "Address family specific traffic-engineering attributes";
                 leaf name {
                   type enumeration {
                     enum "inet" {
                       description "IPv4 family";
                     }
                     enum "inet-mpls" {
                       description "IPv4-MPLS family";
                     }
                   }
                 }
                 uses apply-advanced;
               }
             }
             leaf advertise-unnumbered-interfaces {
               description "Advertise unnumbered interfaces";
               type empty;
             }
             leaf credibility-protocol-preference {
               description "TED protocol credibility follows protocol preference";
               type empty;
             }
           }
           leaf route-type-community {
             description "Specify BGP extended community value to encode OSPF route type";
             type enumeration {
               enum "iana" {
                 description "BGP extended community value used is 0x0306";
               }
               enum "vendor" {
                 description "Vendor BGP extended community value used is 0x8000";
               }
             }
           }
           container domain-id {
             description "Configure domain ID";
             choice domain_id_or_disable {
               case case_1 {
                 leaf domain-id {
                   description "Domain ID";
                   type string;
                 }
               }
               case case_2 {
                 leaf disable {
                   description "Disable domain ID";
                   type empty;
                 }
               }
             }
           }
           choice domain_vpn_tag_or_disable {
             case case_1 {
               leaf domain-vpn-tag {
                 description "Domain VPN tag for external LSA";
                 type union {
                   type string {
                     pattern "<.*>|$.*";
                   }
                   type uint32 {
                     range "0 .. 4294967295";
                   }
                 }
               }
             }
             case case_2 {
               leaf no-domain-vpn-tag {
                 description "Disable domain VPN tag";
                 type empty;
               }
             }
           }
           leaf preference {
             description "Preference of internal routes";
             type union {
               type uint32;
               type string {
                 pattern "<.*>|$.*";
               }
             }
           }
           leaf external-preference {
             description "Preference of external routes";
             type union {
               type uint32;
               type string {
                 pattern "<.*>|$.*";
               }
             }
           }
           leaf labeled-preference {
             description "Preference of labeled routes";
             type union {
               type uint32;
               type string {
                 pattern "<.*>|$.*";
               }
             }
           }
           leaf-list export {
             ordered-by user;
             description "Export policy";
             type jt:policy-algebra;
           }
           leaf-list import {
             ordered-by user;
             description "Import policy (for external routes or setting priority)";
             type jt:policy-algebra;
           }
           leaf reference-bandwidth {
             description "Bandwidth for calculating metric defaults";
             type string;
           }
           leaf lsa-refresh-interval {
             description "LSA refresh interval (minutes)";
             default "50";
             type union {
               type string {
                 pattern "<.*>|$.*";
               }
               type uint32 {
                 range "25 .. 50";
               }
             }
           }
           leaf spf-delay {
             description "Time to wait before running an SPF";
             status deprecated;
             units "milliseconds";
             type union {
               type string {
                 pattern "<.*>|$.*";
               }
               type uint32 {
                 range "50 .. 8000";
               }
             }
           }
           leaf no-rfc-1583 {
             description "Disable RFC1583 compatibility";
             type empty;
           }
           container source-packet-routing {
             presence "enable source-packet-routing";
             description "Enable source packet routing (SPRING)";
             uses apply-advanced;
             container adjacency-segment {
               description "Attributes for adjacency segments in spring";
               uses apply-advanced;
               leaf hold-time {
                 description "Retain time of Adjacency segment after isolating from an interface";
                 type union {
                   type string {
                     pattern "<.*>|$.*";
                   }
                   type uint32 {
                     range "180000 .. 900000";
                   }
                 }
               }
             }
             leaf-list prefix-segment {
               ordered-by user;
               description "Prefix Segment policy";
               type jt:policy-algebra;
             }
             leaf explicit-null {
               description "Set E and P bits in all Prefix SID advertisements";
               type empty;
             }
             container node-segment {
               presence "enable node-segment";
               description "Enable support for Node segments in SPRING";
               uses apply-advanced;
               leaf ipv4-index {
                 description "Set ipv4 node segment index";
                 type union {
                   type string {
                     pattern "<.*>|$.*";
                   }
                   type uint32 {
                     range "0 .. 16383";
                   }
                 }
               }
               leaf index-range {
                 description "Set range of node segment indices allowed";
                 type union {
                   type string {
                     pattern "<.*>|$.*";
                   }
                   type uint32 {
                     range "32 .. 16384";
                   }
                 }
               }
             }
             leaf mapping-server {
               description "Mapping server name";
               type string;
             }
             leaf install-prefix-sid-for-best-route {
               description "For best route install a exact prefix sid route";
               type empty;
             }
           }
           leaf forwarding-address-to-broadcast {
             description "Set forwarding address in Type 5 LSA in broadcast network";
             type empty;
           }
           choice nssa-abr-option {
             case case_1 {
               leaf no-nssa-abr {
                 description "Disable full NSSA functionality at ABR";
                 type empty;
               }
             }
           }
           container sham-link {
             presence "enable sham-link";
             description "Configure parameters for sham links";
             uses apply-advanced;
             leaf local {
               description "Local sham link endpoint address";
               type jt:ipaddr;
             }
             leaf no-advertise-local {
               description "Don't advertise local sham link endpoint as stub in router LSA";
               status deprecated;
               type empty;
             }
           }
           list area {
             key name;
             ordered-by user;
             description "Configure an OSPF area";
             leaf name {
               description "Area ID";
               type jt:areaid;
             }
             uses apply-advanced;
             choice stub-option {
               case case_1 {
                 container stub {
                   presence "enable stub";
                   description "Configure a stub area";
                   leaf default-metric {
                     description "Metric for the default route in this stub area";
                     type union {
                       type string {
                         pattern "<.*>|$.*";
                       }
                       type uint32 {
                         range "1 .. 16777215";
                       }
                     }
                   }
                   choice summaries-choice {
                     leaf summaries {
                       description "Flood summary LSAs into this stub area";
                       type empty;
                     }
                     leaf no-summaries {
                       description "Don't flood summary LSAs into this stub area";
                       type empty;
                     }
                   }
                 }
               }
               case case_2 {
                 container nssa {
                   presence "enable nssa";
                   description "Configure a not-so-stubby area";
                   uses apply-advanced;
                   container default-lsa {
                     presence "enable default-lsa";
                     description "Configure a default LSA";
                     uses apply-advanced;
                     leaf default-metric {
                       description "Metric for the default route in this area";
                       type union {
                         type string {
                           pattern "<.*>|$.*";
                         }
                         type uint32 {
                           range "1 .. 16777215";
                         }
                       }
                     }
                     leaf metric-type {
                       description "External metric type for the default type 7 LSA";
                       type union {
                         type string {
                           pattern "<.*>|$.*";
                         }
                         type uint32 {
                           range "1 .. 2";
                         }
                       }
                     }
                     leaf type-7 {
                       description "Flood type 7 default LSA if no-summaries is configured";
                       type empty;
                     }
                   }
                   leaf default-metric {
                     description "Metric for the default route in this area";
                     status deprecated;
                     type union {
                       type string {
                         pattern "<.*>|$.*";
                       }
                       type uint32 {
                         range "1 .. 16777215";
                       }
                     }
                   }
                   leaf metric-type {
                     description "External metric type for the default type 7 LSA";
                     status deprecated;
                     type union {
                       type string {
                         pattern "<.*>|$.*";
                       }
                       type uint32 {
                         range "1 .. 2";
                       }
                     }
                   }
                   choice summaries-choice {
                     leaf summaries {
                       description "Flood summary LSAs into this NSSA area";
                       type empty;
                     }
                     leaf no-summaries {
                       description "Don't flood summary LSAs into this NSSA area";
                       type empty;
                     }
                   }
                   list area-range {
                     key name;
                     ordered-by user;
                     description "Configure NSSA area ranges";
                     leaf name {
                       description "Range to summarize NSSA routes in this area";
                       type jt:ipprefix;
                     }
                     uses apply-advanced;
                     leaf restrict {
                       description "Restrict advertisement of this area range";
                       type empty;
                     }
                     leaf exact {
                       description "Enforce exact match for advertisement of this area range";
                       type empty;
                     }
                     container override-metric {
                       presence "enable override-metric";
                       description "Override the dynamic metric for this area-range";
                       uses apply-advanced;
                       leaf metric {
                         description "Metric value";
                         type union {
                           type string {
                             pattern "<.*>|$.*";
                           }
                           type uint32 {
                             range "1 .. 16777215";
                           }
                         }
                       }
                       leaf metric-type {
                         description "Set the metric type for the override metric";
                         default "1";
                         type union {
                           type string {
                             pattern "<.*>|$.*";
                           }
                           type uint32 {
                             range "1 .. 2";
                           }
                         }
                       }
                     }
                   }
                 }
               }
             }
             list area-range {
               key name;
               ordered-by user;
               description "Configure area ranges";
               leaf name {
                 description "Range to summarize routes in this area";
                 type jt:ipprefix;
               }
               uses apply-advanced;
               leaf restrict {
                 description "Restrict advertisement of this area range";
                 type empty;
               }
               leaf exact {
                 description "Enforce exact match for advertisement of this area range";
                 type empty;
               }
               leaf override-metric {
                 description "Override the dynamic metric for this area-range";
                 type union {
                   type string {
                     pattern "<.*>|$.*";
                   }
                   type uint32 {
                     range "1 .. 16777215";
                   }
                 }
               }
             }
             leaf-list network-summary-export {
               ordered-by user;
               description "Export policy for Type 3 Summary LSAs";
               type jt:policy-algebra;
             }
             leaf-list network-summary-import {
               ordered-by user;
               description "Import policy for Type 3 Summary LSAs";
               type jt:policy-algebra;
             }
             leaf-list inter-area-prefix-export {
               ordered-by user;
               description "Export policy for Inter Area Prefix LSAs";
               type jt:policy-algebra;
             }
             leaf-list inter-area-prefix-import {
               ordered-by user;
               description "Import policy for Inter Area Prefix LSAs";
               type jt:policy-algebra;
             }
             leaf authentication-type {
               description "Authentication type";
               status deprecated;
               type enumeration {
                 enum "none" {
                   description "No authentication";
                   status deprecated;
                 }
                 enum "simple" {
                   description "Simple password authentication";
                   status deprecated;
                 }
                 enum "md5" {
                   description "MD5 authentication";
                   status deprecated;
                 }
               }
             }
             list virtual-link {
               key "neighbor-id transit-area";
               ordered-by user;
               description "Configure virtual links";
               leaf neighbor-id {
                 description "Router ID of a virtual neighbor";
                 type jt:ipv4addr;
               }
               leaf transit-area {
                 description "Transit area in common with virtual neighbor";
                 type jt:areaid;
               }
               uses apply-advanced;
               choice enable-disable {
                 case case_1 {
                   leaf disable {
                     description "Disable this virtual link";
                     type empty;
                   }
                 }
               }
               leaf retransmit-interval {
                 description "Retransmission interval (seconds)";
                 type union {
                   type string {
                     pattern "<.*>|$.*";
                   }
                   type uint32 {
                     range "1 .. 65535";
                   }
                 }
               }
               leaf transit-delay {
                 description "Transit delay (seconds)";
                 type union {
                   type string {
                     pattern "<.*>|$.*";
                   }
                   type uint32 {
                     range "1 .. 65535";
                   }
                 }
               }
               leaf hello-interval {
                 description "Hello interval (seconds)";
                 type union {
                   type string {
                     pattern "<.*>|$.*";
                   }
                   type uint32 {
                     range "1 .. 255";
                   }
                 }
               }
               leaf dead-interval {
                 description "Dead interval (seconds)";
                 type union {
                   type string {
                     pattern "<.*>|$.*";
                   }
                   type uint32 {
                     range "1 .. 65535";
                   }
                 }
               }
               leaf mtu {
                 description "Maximum OSPF packet size";
                 type union {
                   type string {
                     pattern "<.*>|$.*";
                   }
                   type uint32 {
                     range "128 .. 65535";
                   }
                 }
               }
               choice auth {
                 case case_1 {
                   container authentication {
                     uses juniper-ospf-authentication;
                   }
                 }
                 case case_2 {
                   container authentication-key {
                     description "Authentication key";
                     status deprecated;
                     leaf keyname {
                       description "Authentication key value";
                       type jt:unreadable;
                     }
                     leaf key-id {
                       description "Key ID for MD5 authentication";
                       type union {
                         type string {
                           pattern "<.*>|$.*";
                         }
                         type uint32 {
                           range "0 .. 255";
                         }
                       }
                     }
                   }
                 }
               }
               leaf demand-circuit {
                 description "Interface functions as a demand circuit";
                 type empty;
               }
               leaf flood-reduction {
                 description "Enable flood reduction";
                 type empty;
               }
               leaf no-neighbor-down-notification {
                 description "Don't inform other protocols about neighbor down events";
                 type empty;
               }
               leaf ipsec-sa {
                 description "IPSec security association name";
                 type string {
                   length "1 .. 32";
                 }
               }
               list topology {
                 key name;
                 ordered-by user;
                 description "Topology specific attributes";
                 leaf name {
                   description "Topology name";
                   type string;
                 }
                 uses apply-advanced;
                 leaf disable {
                   description "Disable this topology";
                   type empty;
                 }
                 leaf metric {
                   description "Topology metric";
                   type union {
                     type string {
                       pattern "<.*>|$.*";
                     }
                     type uint16 {
                       range "1 .. 65535";
                     }
                   }
                 }
                 container bandwidth-based-metrics {
                   description "Configure bandwidth based metrics";
                   uses apply-advanced;
                   list bandwidth {
                     key name;
                     description "Bandwidth threshold";
                     leaf name {
                       type string;
                     }
                     leaf metric {
                       description "Metric associated with specified bandwidth";
                       type union {
                         type string {
                           pattern "<.*>|$.*";
                         }
                         type uint16 {
                           range "1 .. 65535";
                         }
                       }
                     }
                   }
                 }
               }
             }
             list sham-link-remote {
               key name;
               ordered-by user;
               description "Configure parameters for remote sham link endpoint";
               leaf name {
                 description "Remote sham link endpoint address";
                 type jt:ipaddr;
               }
               uses apply-advanced;
               leaf metric {
                 description "Sham link metric";
                 type union {
                   type string {
                     pattern "<.*>|$.*";
                   }
                   type uint16 {
                     range "1 .. 65535";
                   }
                 }
               }
               leaf ipsec-sa {
                 description "IPSec security association name";
                 type string {
                   length "1 .. 32";
                 }
               }
               leaf demand-circuit {
                 description "Interface functions as a demand circuit";
                 type empty;
               }
               leaf flood-reduction {
                 description "Enable flood reduction";
                 type empty;
               }
               list topology {
                 key name;
                 ordered-by user;
                 description "Topology specific attributes";
                 leaf name {
                   description "Topology name";
                   type string;
                 }
                 uses apply-advanced;
                 leaf disable {
                   description "Disable this topology";
                   type empty;
                 }
                 leaf metric {
                   description "Topology metric";
                   type union {
                     type string {
                       pattern "<.*>|$.*";
                     }
                     type uint16 {
                       range "1 .. 65535";
                     }
                   }
                 }
                 container bandwidth-based-metrics {
                   description "Configure bandwidth based metrics";
                   uses apply-advanced;
                   list bandwidth {
                     key name;
                     description "Bandwidth threshold";
                     leaf name {
                       type string;
                     }
                     leaf metric {
                       description "Metric associated with specified bandwidth";
                       type union {
                         type string {
                           pattern "<.*>|$.*";
                         }
                         type uint16 {
                           range "1 .. 65535";
                         }
                       }
                     }
                   }
                 }
               }
             }
             list interface {
               key name;
               ordered-by user;
               description "Include an interface in this area";
               leaf name {
                 description "Interface name";
                 type union {
                   type jt:ipv4addr-or-interface;
                   type string {
                     pattern "<.*>|$.*";
                   }
                 }
               }
               uses apply-advanced;
               choice enable-disable {
                 case case_1 {
                   leaf disable {
                     description "Disable OSPF on this interface";
                     type empty;
                   }
                 }
               }
               leaf interface-type {
                 description "Type of interface";
                 type enumeration {
                   enum "nbma" {
                     description "Nonbroadcast multiaccess";
                   }
                   enum "p2mp" {
                     description "Point-to-multipoint NBMA";
                   }
                   enum "p2p" {
                     description "Point-to-point";
                   }
                   enum "p2mp-over-lan" {
                     description "Point-to-multipoint over LAN mode";
                   }
                 }
               }
               container post-convergence-lfa {
                 presence "enable post-convergence-lfa";
                 description "Protect interface using post-convergence backup path";
                 uses apply-advanced;
                 container node-protection {
                   presence "enable node-protection";
                   description "Compute backup path assuming node failure";
                   uses apply-advanced;
                   leaf cost {
                     description "Cost for node protection";
                     type union {
                       type string {
                         pattern "<.*>|$.*";
                       }
                       type uint16 {
                         range "1 .. 65535";
                       }
                     }
                   }
                 }
               }
               choice protection-type {
                 case case_1 {
                   leaf link-protection {
                     description "Protect interface from link faults only";
                     type empty;
                   }
                 }
                 case case_2 {
                   leaf node-link-protection {
                     description "Protect interface from both link and node faults";
                     type empty;
                   }
                 }
               }
               leaf no-eligible-backup {
                 description "Not eligible to backup traffic from protected interfaces";
                 type empty;
               }
               leaf no-eligible-remote-backup {
                 description "Not eligible for Remote-LFA backup traffic from protected interfaces";
                 type empty;
               }
               container passive {
                 presence "enable passive";
                 description "Do not run OSPF, but advertise it";
                 uses apply-advanced;
                 container traffic-engineering {
                   description "Advertise TE link information";
                   uses apply-advanced;
                   leaf remote-node-id {
                     description "Remote address of the link";
                     type jt:ipaddr;
                   }
                   leaf remote-node-router-id {
                     description "TE Router-ID of the remote node";
                     type jt:ipv4addr;
                   }
                 }
               }
               leaf secondary {
                 description "Treat interface as secondary";
                 type empty;
               }
               leaf own-router-lsa {
                 description "Generate a separate router LSA for this interface";
                 type empty;
               }
               container bandwidth-based-metrics {
                 description "Configure bandwidth based metrics";
                 uses apply-advanced;
                 list bandwidth {
                   key name;
                   description "Bandwidth threshold";
                   leaf name {
                     type string;
                   }
                   leaf metric {
                     description "Metric associated with specified bandwidth";
                     type union {
                       type string {
                         pattern "<.*>|$.*";
                       }
                       type uint16 {
                         range "1 .. 65535";
                       }
                     }
                   }
                 }
               }
               leaf metric {
                 description "Interface metric";
                 type union {
                   type string {
                     pattern "<.*>|$.*";
                   }
                   type uint16 {
                     range "1 .. 65535";
                   }
                 }
               }
               leaf te-metric {
                 description "Traffic engineering metric";
                 type union {
                   type string {
                     pattern "<.*>|$.*";
                   }
                   type uint32 {
                     range "1 .. 4294967295";
                   }
                 }
               }
               leaf priority {
                 description "Designated router priority";
                 type union {
                   type string {
                     pattern "<.*>|$.*";
                   }
                   type uint32 {
                     range "0 .. 255";
                   }
                 }
               }
               container ldp-synchronization {
                 description "Advertise maximum metric until LDP is operational";
                 presence "enable ldp-synchronization";
                 uses ldp-sync-obj;
               }
               leaf retransmit-interval {
                 description "Retransmission interval (seconds)";
                 type union {
                   type string {
                     pattern "<.*>|$.*";
                   }
                   type uint32 {
                     range "1 .. 65535";
                   }
                 }
               }
               leaf transit-delay {
                 description "Transit delay (seconds)";
                 type union {
                   type string {
                     pattern "<.*>|$.*";
                   }
                   type uint32 {
                     range "1 .. 65535";
                   }
                 }
               }
               leaf hello-interval {
                 description "Hello interval (seconds)";
                 type union {
                   type string {
                     pattern "<.*>|$.*";
                   }
                   type uint32 {
                     range "1 .. 255";
                   }
                 }
               }
               leaf dead-interval {
                 description "Dead interval (seconds)";
                 type union {
                   type string {
                     pattern "<.*>|$.*";
                   }
                   type uint32 {
                     range "1 .. 65535";
                   }
                 }
               }
               leaf mtu {
                 description "Maximum OSPF packet size";
                 type union {
                   type string {
                     pattern "<.*>|$.*";
                   }
                   type uint32 {
                     range "128 .. 65535";
                   }
                 }
               }
               choice auth {
                 case case_1 {
                   container authentication {
                     uses juniper-ospf-authentication;
                   }
                 }
                 case case_2 {
                   container authentication-key {
                     description "Authentication key";
                     status deprecated;
                     leaf keyname {
                       description "Authentication key value";
                       type jt:unreadable;
                     }
                     leaf key-id {
                       description "Key ID for MD5 authentication";
                       type union {
                         type string {
                           pattern "<.*>|$.*";
                         }
                         type uint32 {
                           range "0 .. 255";
                         }
                       }
                     }
                   }
                 }
               }
               leaf demand-circuit {
                 description "Interface functions as a demand circuit";
                 type empty;
               }
               leaf flood-reduction {
                 description "Enable flood reduction";
                 type empty;
               }
               leaf no-neighbor-down-notification {
                 description "Don't inform other protocols about neighbor down events";
                 type empty;
               }
               leaf ipsec-sa {
                 description "IPSec security association name";
                 type string {
                   length "1 .. 32";
                 }
               }
               list topology {
                 key name;
                 ordered-by user;
                 description "Topology specific attributes";
                 leaf name {
                   description "Topology name";
                   type string;
                 }
                 uses apply-advanced;
                 leaf disable {
                   description "Disable this topology";
                   type empty;
                 }
                 leaf metric {
                   description "Topology metric";
                   type union {
                     type string {
                       pattern "<.*>|$.*";
                     }
                     type uint16 {
                       range "1 .. 65535";
                     }
                   }
                 }
                 container bandwidth-based-metrics {
                   description "Configure bandwidth based metrics";
                   uses apply-advanced;
                   list bandwidth {
                     key name;
                     description "Bandwidth threshold";
                     leaf name {
                       type string;
                     }
                     leaf metric {
                       description "Metric associated with specified bandwidth";
                       type union {
                         type string {
                           pattern "<.*>|$.*";
                         }
                         type uint16 {
                           range "1 .. 65535";
                         }
                       }
                     }
                   }
                 }
               }
               leaf transmit-interval {
                 description "OSPF packet transmit interval (milliseconds)";
                 status deprecated;
                 type union {
                   type string {
                     pattern "<.*>|$.*";
                   }
                   type uint32 {
                     range "1 .. 4294967295";
                   }
                 }
               }
               container bfd-liveness-detection {
                 description "Bidirectional Forwarding Detection options";
                 uses apply-advanced;
                 leaf version {
                   description "BFD protocol version number";
                   default "automatic";
                   type enumeration {
                     enum "0" {
                       description "BFD version 0 (deprecated)";
                     }
                     enum "1" {
                       description "BFD version 1";
                     }
                     enum "automatic" {
                       description "Choose BFD version automatically";
                     }
                   }
                 }
                 leaf minimum-interval {
                   description "Minimum transmit and receive interval";
                   units "milliseconds";
                   type union {
                     type string {
                       pattern "<.*>|$.*";
                     }
                     type uint32 {
                       range "1 .. 255000";
                     }
                   }
                 }
                 leaf minimum-transmit-interval {
                   description "Minimum transmit interval";
                   status deprecated;
                   units "milliseconds";
                   type union {
                     type string {
                       pattern "<.*>|$.*";
                     }
                     type uint32 {
                       range "1 .. 255000";
                     }
                   }
                 }
                 leaf minimum-receive-interval {
                   description "Minimum receive interval";
                   units "milliseconds";
                   type union {
                     type string {
                       pattern "<.*>|$.*";
                     }
                     type uint32 {
                       range "1 .. 255000";
                     }
                   }
                 }
                 leaf multiplier {
                   description "Detection time multiplier";
                   default "3";
                   type union {
                     type string {
                       pattern "<.*>|$.*";
                     }
                     type uint32 {
                       range "1 .. 255";
                     }
                   }
                 }
                 choice adaptation-choice {
                   case case_1 {
                     leaf no-adaptation {
                       description "Disable adaptation";
                       type empty;
                     }
                   }
                 }
                 container transmit-interval {
                   description "Transmit-interval options";
                   uses apply-advanced;
                   leaf minimum-interval {
                     description "Minimum transmit interval";
                     units "milliseconds";
                     type union {
                       type string {
                         pattern "<.*>|$.*";
                       }
                       type uint32 {
                         range "1 .. 255000";
                       }
                     }
                   }
                   leaf threshold {
                     description "High transmit interval triggering a trap";
                     units "milliseconds";
                     type union {
                       type uint32;
                       type string {
                         pattern "<.*>|$.*";
                       }
                     }
                   }
                 }
                 container detection-time {
                   description "Detection-time options";
                   uses apply-advanced;
                   leaf threshold {
                     description "High detection-time triggering a trap";
                     units "milliseconds";
                     type union {
                       type uint32;
                       type string {
                         pattern "<.*>|$.*";
                       }
                     }
                   }
                 }
                 container authentication {
                   description "Authentication options";
                   uses apply-advanced;
                   leaf key-chain {
                     description "Key chain name";
                     type string;
                   }
                   leaf algorithm {
                     description "Algorithm name";
                     type enumeration {
                       enum "simple-password" {
                         description "Simple password";
                       }
                       enum "keyed-md5" {
                         description "Keyed message Digest 5";
                       }
                       enum "meticulous-keyed-md5" {
                         description "Meticulous keyed message Digest 5";
                       }
                       enum "keyed-sha-1" {
                         description "Keyed secure hash algorithm (SHA1) ";
                       }
                       enum "meticulous-keyed-sha-1" {
                         description "Meticulous keyed secure hash algorithm (SHA1) ";
                       }
                     }
                   }
                   leaf loose-check {
                     description "Verify authentication only if authentication is negotiated";
                     type empty;
                   }
                 }
                 leaf full-neighbors-only {
                   description "Setup BFD sessions only to Full neighbors";
                   type empty;
                 }
               }
               leaf dynamic-neighbors {
                 description "Learn neighbors dynamically on a p2mp interface";
                 type empty;
               }
               leaf no-advertise-adjacency-segment {
                 description "Do not advertise an adjacency segment for this interface";
                 type empty;
               }
               list neighbor {
                 key name;
                 ordered-by user;
                 description "NBMA neighbor";
                 leaf name {
                   description "Address of neighbor";
                   type jt:ipaddr;
                 }
                 leaf eligible {
                   description "Eligible to be DR on an NBMA network";
                   type empty;
                 }
               }
               leaf poll-interval {
                 description "Poll interval for NBMA interfaces";
                 type union {
                   type string {
                     pattern "<.*>|$.*";
                   }
                   type uint32 {
                     range "1 .. 65535";
                   }
                 }
               }
               leaf no-interface-state-traps {
                 description "Do not send interface state change traps";
                 type empty;
               }
             }
             leaf no-source-packet-routing {
               description "Disable SPRING in this area";
               type empty;
             }
             leaf no-context-identifier-advertisement {
               description "Disable context identifier advertisments in this area";
               type empty;
             }
             list context-identifier {
               key name;
               ordered-by user;
               description "Configure context identifier in support of edge protection";
               leaf name {
                 description "Context identifier";
                 type jt:ipv4addr;
               }
               uses apply-advanced;
             }
             list label-switched-path {
               key name;
               ordered-by user;
               description "Configuration for advertisement of a label-switched path";
               leaf name {
                 description "Name of label-switched path to be advertised";
                 type string {
                   length "1 .. 64";
                 }
               }
               uses apply-advanced;
               choice enable-disable {
                 case case_1 {
                   leaf disable {
                     description "Disable OSPF on this label-switched path";
                     type empty;
                   }
                 }
               }
               leaf metric {
                 description "Interface metric";
                 type union {
                   type string {
                     pattern "<.*>|$.*";
                   }
                   type uint16 {
                     range "1 .. 65535";
                   }
                 }
               }
               list topology {
                 key name;
                 ordered-by user;
                 description "Topology specific attributes";
                 leaf name {
                   description "Topology name";
                   type string;
                 }
                 uses apply-advanced;
                 leaf disable {
                   description "Disable this topology";
                   type empty;
                 }
                 leaf metric {
                   description "Topology metric";
                   type union {
                     type string {
                       pattern "<.*>|$.*";
                     }
                     type uint16 {
                       range "1 .. 65535";
                     }
                   }
                 }
                 container bandwidth-based-metrics {
                   description "Configure bandwidth based metrics";
                   uses apply-advanced;
                   list bandwidth {
                     key name;
                     description "Bandwidth threshold";
                     leaf name {
                       type string;
                     }
                     leaf metric {
                       description "Metric associated with specified bandwidth";
                       type union {
                         type string {
                           pattern "<.*>|$.*";
                         }
                         type uint16 {
                           range "1 .. 65535";
                         }
                       }
                     }
                   }
                 }
               }
             }
             list peer-interface {
               key name;
               ordered-by user;
               description "Configuration for peer interface";
               leaf name {
                 description "Name of peer interface";
                 type string;
               }
               uses apply-advanced;
               choice enable-disable {
                 case case_1 {
                   leaf disable {
                     description "Disable OSPF on this control peer";
                     type empty;
                   }
                 }
               }
               leaf retransmit-interval {
                 description "Retransmission interval (seconds)";
                 type union {
                   type string {
                     pattern "<.*>|$.*";
                   }
                   type uint32 {
                     range "1 .. 65535";
                   }
                 }
               }
               leaf transit-delay {
                 description "Transit delay (seconds)";
                 type union {
                   type string {
                     pattern "<.*>|$.*";
                   }
                   type uint32 {
                     range "1 .. 65535";
                   }
                 }
               }
               leaf hello-interval {
                 description "Hello interval (seconds)";
                 type union {
                   type string {
                     pattern "<.*>|$.*";
                   }
                   type uint32 {
                     range "1 .. 255";
                   }
                 }
               }
               leaf dead-interval {
                 description "Dead interval (seconds)";
                 type union {
                   type string {
                     pattern "<.*>|$.*";
                   }
                   type uint32 {
                     range "1 .. 65535";
                   }
                 }
               }
               leaf mtu {
                 description "Maximum OSPF packet size";
                 type union {
                   type string {
                     pattern "<.*>|$.*";
                   }
                   type uint32 {
                     range "128 .. 65535";
                   }
                 }
               }
               choice auth {
                 case case_1 {
                   container authentication {
                     uses juniper-ospf-authentication;
                   }
                 }
                 case case_2 {
                   container authentication-key {
                     description "Authentication key";
                     status deprecated;
                     leaf keyname {
                       description "Authentication key value";
                       type jt:unreadable;
                     }
                     leaf key-id {
                       description "Key ID for MD5 authentication";
                       type union {
                         type string {
                           pattern "<.*>|$.*";
                         }
                         type uint32 {
                           range "0 .. 255";
                         }
                       }
                     }
                   }
                 }
               }
               leaf demand-circuit {
                 description "Interface functions as a demand circuit";
                 type empty;
               }
               leaf flood-reduction {
                 description "Enable flood reduction";
                 type empty;
               }
               leaf no-neighbor-down-notification {
                 description "Don't inform other protocols about neighbor down events";
                 type empty;
               }
             }
           }
         }
         uses apply-advanced;
         choice enable-disable {
           case case_1 {
             leaf disable {
               description "Disable OSPF";
               type empty;
             }
           }
         }
         container traceoptions {
           description "Trace options for OSPF";
           uses apply-advanced;
           container file {
             description "Trace file options";
             leaf filename {
               description "Name of file in which to write trace information";
               type string {
                 length "1 .. 1024";
               }
             }
             leaf replace {
               description "Replace trace file rather than appending to it";
               status deprecated;
               type empty;
             }
             leaf size {
               description "Maximum trace file size";
               type string;
             }
             leaf files {
               description "Maximum number of trace files";
               default "10";
               type union {
                 type string {
                   pattern "<.*>|$.*";
                 }
                 type uint32 {
                   range "2 .. 1000";
                 }
               }
             }
             leaf no-stamp {
               description "Do not timestamp trace file";
               status deprecated;
               type empty;
             }
             choice world-readable-choice {
               leaf world-readable {
                 description "Allow any user to read the log file";
                 type empty;
               }
               leaf no-world-readable {
                 description "Don't allow any user to read the log file";
                 type empty;
               }
             }
           }
           list flag {
             key name;
             ordered-by user;
             description "Tracing parameters";
             leaf name {
               type enumeration {
                 enum "spf" {
                   description "Trace SPF calculations";
                 }
                 enum "error" {
                   description "Trace errored packets";
                 }
                 enum "event" {
                   description "Trace OSPF state machine events";
                 }
                 enum "packet-dump" {
                   description "Dump the contents of selected packet types";
                 }
                 enum "flooding" {
                   description "Trace LSA flooding";
                 }
                 enum "lsa-analysis" {
                   description "Trace LSA analysis";
                 }
                 enum "packets" {
                   description "Trace all OSPF packets";
                 }
                 enum "hello" {
                   description "Trace hello packets";
                 }
                 enum "database-description" {
                   description "Trace database description packets";
                 }
                 enum "lsa-request" {
                   description "Trace LSA request packets";
                 }
                 enum "lsa-update" {
                   description "Trace LSA update packets";
                 }
                 enum "lsa-ack" {
                   description "Trace LSA acknowledgment packets";
                 }
                 enum "ldp-synchronization" {
                   description "Trace synchronization between OSPF and LDP";
                 }
                 enum "on-demand" {
                   description "Trace demand circuit extensions";
                 }
                 enum "nsr-synchronization" {
                   description "Trace NSR synchronization events";
                 }
                 enum "graceful-restart" {
                   description "Trace graceful restart";
                 }
                 enum "restart-signaling" {
                   description "Trace restart signaling";
                 }
                 enum "backup-spf" {
                   description "Trace backup SPF (LFA) specific events";
                 }
                 enum "source-packet-routing" {
                   description "Trace source packet routing (SPRING) events";
                 }
                 enum "post-convergence-lfa" {
                   description "Trace post-convergence-lfa related events";
                 }
                 enum "route" {
                   description "Trace routing information";
                 }
                 enum "normal" {
                   description "Trace normal events";
                 }
                 enum "general" {
                   description "Trace general events";
                 }
                 enum "state" {
                   description "Trace state transitions";
                 }
                 enum "policy" {
                   description "Trace policy processing";
                 }
                 enum "task" {
                   description "Trace routing protocol task processing";
                 }
                 enum "timer" {
                   description "Trace routing protocol timer processing";
                 }
                 enum "all" {
                   description "Trace everything";
                 }
               }
             }
             leaf send {
               description "Trace transmitted packets";
               type empty;
             }
             leaf receive {
               description "Trace received packets";
               type empty;
             }
             leaf detail {
               description "Trace detailed information";
               type empty;
             }
             leaf disable {
               description "Disable this trace flag";
               type empty;
             }
           }
         }
         list topology {
           key name;
           ordered-by user;
           description "Topology parameters";
           leaf name {
             description "Topology name";
             type string;
           }
           uses apply-advanced;
           leaf disable {
             description "Disable this topology";
             type empty;
           }
           leaf topology-id {
             description "Topology identifier";
             type union {
               type string {
                 pattern "<.*>|$.*";
               }
               type uint8 {
                 range "32 .. 127";
               }
             }
           }
           leaf overload {
             description "Set the overload mode (repel transit traffic)";
             type empty;
           }
           leaf rib-group {
             description "Routing table group for importing routes";
             type string;
           }
           container spf-options {
             description "Configure options for SPF";
             uses apply-advanced;
             leaf delay {
               description "Time to wait before running an SPF";
               units "milliseconds";
               type union {
                 type string {
                   pattern "<.*>|$.*";
                 }
                 type uint32 {
                   range "50 .. 8000";
                 }
               }
             }
             leaf holddown {
               description "Time to hold down before running an SPF";
               units "milliseconds";
               type union {
                 type string {
                   pattern "<.*>|$.*";
                 }
                 type uint32 {
                   range "2000 .. 20000";
                 }
               }
             }
             leaf rapid-runs {
               description "Number of maximum rapid SPF runs before holddown";
               type union {
                 type string {
                   pattern "<.*>|$.*";
                 }
                 type uint32 {
                   range "1 .. 10";
                 }
               }
             }
             leaf no-ignore-our-externals {
               description "Do not ignore self-generated external and NSSA LSAs";
               type empty;
             }
           }
           container backup-spf-options {
             description "Configure options for backup SPF";
             uses apply-advanced;
             leaf disable {
               description "Do not run backup SPF";
               type empty;
             }
             leaf no-install {
               description "Do not install backup nexthops into the RIB";
               type empty;
             }
             leaf downstream-paths-only {
               description "Use only downstream backup paths";
               type empty;
             }
             container remote-backup-calculation {
               presence "enable remote-backup-calculation";
               description "Calculate Remote LFA backup nexthops";
               uses apply-advanced;
               container pq-nodes-nearest-to-source {
                 description "PQ nodes selection based upon nearest to source";
                 uses apply-advanced;
                 leaf percent {
                   description "Selection percentage for nearest to source";
                   type union {
                     type string {
                       pattern "<.*>|$.*";
                     }
                     type uint32 {
                       range "10 .. 100";
                     }
                   }
                 }
               }
             }
             container use-post-convergence-lfa {
               presence "enable use-post-convergence-lfa";
               description "Calculate post-convergence backup paths";
               uses apply-advanced;
               leaf maximum-labels {
                 description "Maximum number of labels installed for post-convergence paths";
                 type union {
                   type string {
                     pattern "<.*>|$.*";
                   }
                   type uint32 {
                     range "2 .. 5";
                   }
                 }
               }
               leaf maximum-backup-paths {
                 description "Maximum number of equal-cost post-convergence paths installed";
                 type union {
                   type string {
                     pattern "<.*>|$.*";
                   }
                   type uint32 {
                     range "1 .. 8";
                   }
                 }
               }
             }
             container per-prefix-calculation {
               description "Calculate backup nexthops for non-best prefix originators";
               uses apply-advanced;
               leaf stubs {
                 description "Per prefix calculation for stubs only";
                 type empty;
               }
               leaf summary {
                 description "Per prefix calculation for summary originators only";
                 type empty;
               }
               leaf externals {
                 description "Per prefix calculation for externals";
                 type empty;
               }
               leaf all {
                 description "Per prefix calculation for all";
                 type empty;
               }
             }
             leaf node-link-degradation {
               description "Degrade to link protection when nodelink protection not available";
               type empty;
             }
             leaf use-source-packet-routing {
               description "Use spring backup paths for inet.0 routes";
               type empty;
             }
           }
           leaf prefix-export-limit {
             description "Maximum number of prefixes that can be exported";
             type union {
               type string {
                 pattern "<.*>|$.*";
               }
               type uint32 {
                 range "0 .. 4294967295";
               }
             }
           }
         }
         container spf-options {
           description "Configure options for SPF";
           uses apply-advanced;
           leaf delay {
             description "Time to wait before running an SPF";
             units "milliseconds";
             type union {
               type string {
                 pattern "<.*>|$.*";
               }
               type uint32 {
                 range "50 .. 8000";
               }
             }
           }
           leaf holddown {
             description "Time to hold down before running an SPF";
             units "milliseconds";
             type union {
               type string {
                 pattern "<.*>|$.*";
               }
               type uint32 {
                 range "2000 .. 20000";
               }
             }
           }
           leaf rapid-runs {
             description "Number of maximum rapid SPF runs before holddown";
             type union {
               type string {
                 pattern "<.*>|$.*";
               }
               type uint32 {
                 range "1 .. 10";
               }
             }
           }
           leaf no-ignore-our-externals {
             description "Do not ignore self-generated external and NSSA LSAs";
             type empty;
           }
         }
         container backup-spf-options {
           description "Configure options for backup SPF";
           uses apply-advanced;
           leaf disable {
             description "Do not run backup SPF";
             type empty;
           }
           leaf no-install {
             description "Do not install backup nexthops into the RIB";
             type empty;
           }
           leaf downstream-paths-only {
             description "Use only downstream backup paths";
             type empty;
           }
           container remote-backup-calculation {
             presence "enable remote-backup-calculation";
             description "Calculate Remote LFA backup nexthops";
             uses apply-advanced;
             container pq-nodes-nearest-to-source {
               description "PQ nodes selection based upon nearest to source";
               uses apply-advanced;
               leaf percent {
                 description "Selection percentage for nearest to source";
                 type union {
                   type string {
                     pattern "<.*>|$.*";
                   }
                   type uint32 {
                     range "10 .. 100";
                   }
                 }
               }
             }
           }
           container use-post-convergence-lfa {
             presence "enable use-post-convergence-lfa";
             description "Calculate post-convergence backup paths";
             uses apply-advanced;
             leaf maximum-labels {
               description "Maximum number of labels installed for post-convergence paths";
               type union {
                 type string {
                   pattern "<.*>|$.*";
                 }
                 type uint32 {
                   range "2 .. 5";
                 }
               }
             }
             leaf maximum-backup-paths {
               description "Maximum number of equal-cost post-convergence paths installed";
               type union {
                 type string {
                   pattern "<.*>|$.*";
                 }
                 type uint32 {
                   range "1 .. 8";
                 }
               }
             }
           }
           container per-prefix-calculation {
             description "Calculate backup nexthops for non-best prefix originators";
             uses apply-advanced;
             leaf stubs {
               description "Per prefix calculation for stubs only";
               type empty;
             }
             leaf summary {
               description "Per prefix calculation for summary originators only";
               type empty;
             }
             leaf externals {
               description "Per prefix calculation for externals";
               type empty;
             }
             leaf all {
               description "Per prefix calculation for all";
               type empty;
             }
           }
           leaf node-link-degradation {
             description "Degrade to link protection when nodelink protection not available";
             type empty;
           }
           leaf use-source-packet-routing {
             description "Use spring backup paths for inet.0 routes";
             type empty;
           }
         }
         leaf prefix-export-limit {
           description "Maximum number of prefixes that can be exported";
           type union {
             type string {
               pattern "<.*>|$.*";
             }
             type uint32 {
               range "0 .. 4294967295";
             }
           }
         }
         container rib-groups {
           description "Routing table groups for importing OSPF routes";
           uses apply-advanced;
           leaf inet {
             description "Name of the IPv4/v6 routing table group";
             type string;
           }
           leaf inet3 {
             description "Name of the IPv4/v6 inet.3 routing table group";
             type string;
           }
         }
         leaf job-stats {
           description "Collect job statistics";
           type empty;
         }
         container overload {
           presence "enable overload";
           description "Set the overload mode (repel transit traffic)";
           uses apply-advanced;
           leaf timeout {
             description "Time after which overload mode is reset";
             units "seconds";
             type union {
               type string {
                 pattern "<.*>|$.*";
               }
               type uint32 {
                 range "60 .. 1800";
               }
             }
           }
           leaf allow-route-leaking {
             description "Allow routes to be leaked when overload is configured";
             type empty;
           }
           leaf stub-network {
             description "Advertise Stub Network with maximum metric";
             type empty;
           }
           leaf intra-area-prefix {
             description "Advertise Intra Area Prefix with maximum metric";
             type empty;
           }
           leaf as-external {
             description "Advertise As External with maximum usable metric";
             type empty;
           }
         }
         container database-protection {
           presence "enable database-protection";
           description "Configure database protection attributes";
           uses apply-advanced;
           leaf maximum-lsa {
             description "Maximum allowed non self-generated LSAs";
             type union {
               type string {
                 pattern "<.*>|$.*";
               }
               type uint32 {
                 range "1 .. 1000000";
               }
             }
           }
           leaf warning-only {
             description "Emit only a warning when LSA maximum limit is exceeded";
             type empty;
           }
           leaf warning-threshold {
             description "Percentage of LSA maximum above which to trigger warning";
             units "percent";
             type union {
               type string {
                 pattern "<.*>|$.*";
               }
               type uint8 {
                 range "30 .. 100";
               }
             }
           }
           leaf ignore-count {
             description "Maximum number of times to go into ignore state";
             type union {
               type string {
                 pattern "<.*>|$.*";
               }
               type uint8 {
                 range "1 .. 32";
               }
             }
           }
           leaf ignore-time {
             description "Time to stay in ignore state and ignore all neighbors";
             units "seconds";
             type union {
               type string {
                 pattern "<.*>|$.*";
               }
               type uint16 {
                 range "30 .. 3600";
               }
             }
           }
           leaf reset-time {
             description "Time after which the ignore count gets reset to zero";
             units "seconds";
             type union {
               type string {
                 pattern "<.*>|$.*";
               }
               type uint32 {
                 range "60 .. 86400";
               }
             }
           }
         }
         container graceful-restart {
           description "Configure graceful restart attributes";
           uses apply-advanced;
           choice enable-disable {
             case case_1 {
               leaf disable {
                 description "Disable OSPF graceful restart capability";
                 type empty;
               }
             }
           }
           leaf restart-duration {
             description "Time for all neighbors to become full";
             units "seconds";
             type union {
               type string {
                 pattern "<.*>|$.*";
               }
               type uint32 {
                 range "1 .. 3600";
               }
             }
           }
           leaf notify-duration {
             description "Time to send all max-aged grace LSAs";
             units "seconds";
             type union {
               type string {
                 pattern "<.*>|$.*";
               }
               type uint32 {
                 range "1 .. 3600";
               }
             }
           }
           container helper-disable {
             presence "enable helper-disable";
             description "Disable graceful restart helper capability";
             uses apply-advanced;
             choice disable-choices {
               case case_1 {
                 leaf standard {
                   description "Disable helper-mode for rfc3623 based GR";
                   type empty;
                 }
               }
               case case_2 {
                 leaf restart-signaling {
                   description "Disable helper mode for restart-signaling ";
                   type empty;
                 }
               }
               case case_3 {
                 leaf both {
                   description "Disable helper mode for both the types of GR";
                   type empty;
                 }
               }
             }
           }
           leaf no-strict-lsa-checking {
             description "Do not abort graceful helper mode upon LSA changes";
             type empty;
           }
         }
         container traffic-engineering {
           presence "enable traffic-engineering";
           description "Configure traffic engineering attributes";
           uses apply-advanced;
           leaf no-topology {
             description "Disable dissemination of TE link-state topology information";
             type empty;
           }
           leaf multicast-rpf-routes {
             description "Install routes for multicast RPF checks into inet.2";
             type empty;
           }
           leaf igp-topology {
             description "Download IGP topology into TED";
             type empty;
           }
           leaf ignore-lsp-metrics {
             description "Ignore label-switched path metrics when doing shortcuts";
             type empty;
           }
           container shortcuts {
             presence "enable shortcuts";
             description "Use label-switched paths as next hops, if possible";
             uses apply-advanced;
             leaf ignore-lsp-metrics {
               description "Ignore label-switched path metrics when doing shortcuts";
               status deprecated;
               type empty;
             }
             leaf lsp-metric-into-summary {
               description "Advertise LSP metric into summary LSAs";
               type empty;
             }
             list family {
               key name;
               ordered-by user;
               description "Address family specific traffic-engineering attributes";
               leaf name {
                 type enumeration {
                   enum "inet" {
                     description "IPv4 family";
                   }
                   enum "inet-mpls" {
                     description "IPv4-MPLS family";
                   }
                 }
               }
               uses apply-advanced;
             }
           }
           leaf advertise-unnumbered-interfaces {
             description "Advertise unnumbered interfaces";
             type empty;
           }
           leaf credibility-protocol-preference {
             description "TED protocol credibility follows protocol preference";
             type empty;
           }
         }
         leaf route-type-community {
           description "Specify BGP extended community value to encode OSPF route type";
           type enumeration {
             enum "iana" {
               description "BGP extended community value used is 0x0306";
             }
             enum "vendor" {
               description "Vendor BGP extended community value used is 0x8000";
             }
           }
         }
         container domain-id {
           description "Configure domain ID";
           choice domain_id_or_disable {
             case case_1 {
               leaf domain-id {
                 description "Domain ID";
                 type string;
               }
             }
             case case_2 {
               leaf disable {
                 description "Disable domain ID";
                 type empty;
               }
             }
           }
         }
         choice domain_vpn_tag_or_disable {
           case case_1 {
             leaf domain-vpn-tag {
               description "Domain VPN tag for external LSA";
               type union {
                 type string {
                   pattern "<.*>|$.*";
                 }
                 type uint32 {
                   range "0 .. 4294967295";
                 }
               }
             }
           }
           case case_2 {
             leaf no-domain-vpn-tag {
               description "Disable domain VPN tag";
               type empty;
             }
           }
         }
         leaf preference {
           description "Preference of internal routes";
           type union {
             type uint32;
             type string {
               pattern "<.*>|$.*";
             }
           }
         }
         leaf external-preference {
           description "Preference of external routes";
           type union {
             type uint32;
             type string {
               pattern "<.*>|$.*";
             }
           }
         }
         leaf labeled-preference {
           description "Preference of labeled routes";
           type union {
             type uint32;
             type string {
               pattern "<.*>|$.*";
             }
           }
         }
         leaf-list export {
           ordered-by user;
           description "Export policy";
           type jt:policy-algebra;
         }
         leaf-list import {
           ordered-by user;
           description "Import policy (for external routes or setting priority)";
           type jt:policy-algebra;
         }
         leaf reference-bandwidth {
           description "Bandwidth for calculating metric defaults";
           type string;
         }
         leaf lsa-refresh-interval {
           description "LSA refresh interval (minutes)";
           default "50";
           type union {
             type string {
               pattern "<.*>|$.*";
             }
             type uint32 {
               range "25 .. 50";
             }
           }
         }
         leaf spf-delay {
           description "Time to wait before running an SPF";
           status deprecated;
           units "milliseconds";
           type union {
             type string {
               pattern "<.*>|$.*";
             }
             type uint32 {
               range "50 .. 8000";
             }
           }
         }
         leaf no-rfc-1583 {
           description "Disable RFC1583 compatibility";
           type empty;
         }
         container source-packet-routing {
           presence "enable source-packet-routing";
           description "Enable source packet routing (SPRING)";
           uses apply-advanced;
           container adjacency-segment {
             description "Attributes for adjacency segments in spring";
             uses apply-advanced;
             leaf hold-time {
               description "Retain time of Adjacency segment after isolating from an interface";
               type union {
                 type string {
                   pattern "<.*>|$.*";
                 }
                 type uint32 {
                   range "180000 .. 900000";
                 }
               }
             }
           }
           leaf-list prefix-segment {
             ordered-by user;
             description "Prefix Segment policy";
             type jt:policy-algebra;
           }
           leaf explicit-null {
             description "Set E and P bits in all Prefix SID advertisements";
             type empty;
           }
           container node-segment {
             presence "enable node-segment";
             description "Enable support for Node segments in SPRING";
             uses apply-advanced;
             leaf ipv4-index {
               description "Set ipv4 node segment index";
               type union {
                 type string {
                   pattern "<.*>|$.*";
                 }
                 type uint32 {
                   range "0 .. 16383";
                 }
               }
             }
             leaf index-range {
               description "Set range of node segment indices allowed";
               type union {
                 type string {
                   pattern "<.*>|$.*";
                 }
                 type uint32 {
                   range "32 .. 16384";
                 }
               }
             }
           }
           leaf mapping-server {
             description "Mapping server name";
             type string;
           }
           leaf install-prefix-sid-for-best-route {
             description "For best route install a exact prefix sid route";
             type empty;
           }
         }
         leaf forwarding-address-to-broadcast {
           description "Set forwarding address in Type 5 LSA in broadcast network";
           type empty;
         }
         choice nssa-abr-option {
           case case_1 {
             leaf no-nssa-abr {
               description "Disable full NSSA functionality at ABR";
               type empty;
             }
           }
         }
         container sham-link {
           presence "enable sham-link";
           description "Configure parameters for sham links";
           uses apply-advanced;
           leaf local {
             description "Local sham link endpoint address";
             type jt:ipaddr;
           }
           leaf no-advertise-local {
             description "Don't advertise local sham link endpoint as stub in router LSA";
             status deprecated;
             type empty;
           }
         }
         list area {
           key name;
           ordered-by user;
           description "Configure an OSPF area";
           leaf name {
             description "Area ID";
             type jt:areaid;
           }
           uses apply-advanced;
           choice stub-option {
             case case_1 {
               container stub {
                 presence "enable stub";
                 description "Configure a stub area";
                 leaf default-metric {
                   description "Metric for the default route in this stub area";
                   type union {
                     type string {
                       pattern "<.*>|$.*";
                     }
                     type uint32 {
                       range "1 .. 16777215";
                     }
                   }
                 }
                 choice summaries-choice {
                   leaf summaries {
                     description "Flood summary LSAs into this stub area";
                     type empty;
                   }
                   leaf no-summaries {
                     description "Don't flood summary LSAs into this stub area";
                     type empty;
                   }
                 }
               }
             }
             case case_2 {
               container nssa {
                 presence "enable nssa";
                 description "Configure a not-so-stubby area";
                 uses apply-advanced;
                 container default-lsa {
                   presence "enable default-lsa";
                   description "Configure a default LSA";
                   uses apply-advanced;
                   leaf default-metric {
                     description "Metric for the default route in this area";
                     type union {
                       type string {
                         pattern "<.*>|$.*";
                       }
                       type uint32 {
                         range "1 .. 16777215";
                       }
                     }
                   }
                   leaf metric-type {
                     description "External metric type for the default type 7 LSA";
                     type union {
                       type string {
                         pattern "<.*>|$.*";
                       }
                       type uint32 {
                         range "1 .. 2";
                       }
                     }
                   }
                   leaf type-7 {
                     description "Flood type 7 default LSA if no-summaries is configured";
                     type empty;
                   }
                 }
                 leaf default-metric {
                   description "Metric for the default route in this area";
                   status deprecated;
                   type union {
                     type string {
                       pattern "<.*>|$.*";
                     }
                     type uint32 {
                       range "1 .. 16777215";
                     }
                   }
                 }
                 leaf metric-type {
                   description "External metric type for the default type 7 LSA";
                   status deprecated;
                   type union {
                     type string {
                       pattern "<.*>|$.*";
                     }
                     type uint32 {
                       range "1 .. 2";
                     }
                   }
                 }
                 choice summaries-choice {
                   leaf summaries {
                     description "Flood summary LSAs into this NSSA area";
                     type empty;
                   }
                   leaf no-summaries {
                     description "Don't flood summary LSAs into this NSSA area";
                     type empty;
                   }
                 }
                 list area-range {
                   key name;
                   ordered-by user;
                   description "Configure NSSA area ranges";
                   leaf name {
                     description "Range to summarize NSSA routes in this area";
                     type jt:ipprefix;
                   }
                   uses apply-advanced;
                   leaf restrict {
                     description "Restrict advertisement of this area range";
                     type empty;
                   }
                   leaf exact {
                     description "Enforce exact match for advertisement of this area range";
                     type empty;
                   }
                   container override-metric {
                     presence "enable override-metric";
                     description "Override the dynamic metric for this area-range";
                     uses apply-advanced;
                     leaf metric {
                       description "Metric value";
                       type union {
                         type string {
                           pattern "<.*>|$.*";
                         }
                         type uint32 {
                           range "1 .. 16777215";
                         }
                       }
                     }
                     leaf metric-type {
                       description "Set the metric type for the override metric";
                       default "1";
                       type union {
                         type string {
                           pattern "<.*>|$.*";
                         }
                         type uint32 {
                           range "1 .. 2";
                         }
                       }
                     }
                   }
                 }
               }
             }
           }
           list area-range {
             key name;
             ordered-by user;
             description "Configure area ranges";
             leaf name {
               description "Range to summarize routes in this area";
               type jt:ipprefix;
             }
             uses apply-advanced;
             leaf restrict {
               description "Restrict advertisement of this area range";
               type empty;
             }
             leaf exact {
               description "Enforce exact match for advertisement of this area range";
               type empty;
             }
             leaf override-metric {
               description "Override the dynamic metric for this area-range";
               type union {
                 type string {
                   pattern "<.*>|$.*";
                 }
                 type uint32 {
                   range "1 .. 16777215";
                 }
               }
             }
           }
           leaf-list network-summary-export {
             ordered-by user;
             description "Export policy for Type 3 Summary LSAs";
             type jt:policy-algebra;
           }
           leaf-list network-summary-import {
             ordered-by user;
             description "Import policy for Type 3 Summary LSAs";
             type jt:policy-algebra;
           }
           leaf-list inter-area-prefix-export {
             ordered-by user;
             description "Export policy for Inter Area Prefix LSAs";
             type jt:policy-algebra;
           }
           leaf-list inter-area-prefix-import {
             ordered-by user;
             description "Import policy for Inter Area Prefix LSAs";
             type jt:policy-algebra;
           }
           leaf authentication-type {
             description "Authentication type";
             status deprecated;
             type enumeration {
               enum "none" {
                 description "No authentication";
                 status deprecated;
               }
               enum "simple" {
                 description "Simple password authentication";
                 status deprecated;
               }
               enum "md5" {
                 description "MD5 authentication";
                 status deprecated;
               }
             }
           }
           list virtual-link {
             key "neighbor-id transit-area";
             ordered-by user;
             description "Configure virtual links";
             leaf neighbor-id {
               description "Router ID of a virtual neighbor";
               type jt:ipv4addr;
             }
             leaf transit-area {
               description "Transit area in common with virtual neighbor";
               type jt:areaid;
             }
             uses apply-advanced;
             choice enable-disable {
               case case_1 {
                 leaf disable {
                   description "Disable this virtual link";
                   type empty;
                 }
               }
             }
             leaf retransmit-interval {
               description "Retransmission interval (seconds)";
               type union {
                 type string {
                   pattern "<.*>|$.*";
                 }
                 type uint32 {
                   range "1 .. 65535";
                 }
               }
             }
             leaf transit-delay {
               description "Transit delay (seconds)";
               type union {
                 type string {
                   pattern "<.*>|$.*";
                 }
                 type uint32 {
                   range "1 .. 65535";
                 }
               }
             }
             leaf hello-interval {
               description "Hello interval (seconds)";
               type union {
                 type string {
                   pattern "<.*>|$.*";
                 }
                 type uint32 {
                   range "1 .. 255";
                 }
               }
             }
             leaf dead-interval {
               description "Dead interval (seconds)";
               type union {
                 type string {
                   pattern "<.*>|$.*";
                 }
                 type uint32 {
                   range "1 .. 65535";
                 }
               }
             }
             leaf mtu {
               description "Maximum OSPF packet size";
               type union {
                 type string {
                   pattern "<.*>|$.*";
                 }
                 type uint32 {
                   range "128 .. 65535";
                 }
               }
             }
             choice auth {
               case case_1 {
                 container authentication {
                   uses juniper-ospf-authentication;
                 }
               }
               case case_2 {
                 container authentication-key {
                   description "Authentication key";
                   status deprecated;
                   leaf keyname {
                     description "Authentication key value";
                     type jt:unreadable;
                   }
                   leaf key-id {
                     description "Key ID for MD5 authentication";
                     type union {
                       type string {
                         pattern "<.*>|$.*";
                       }
                       type uint32 {
                         range "0 .. 255";
                       }
                     }
                   }
                 }
               }
             }
             leaf demand-circuit {
               description "Interface functions as a demand circuit";
               type empty;
             }
             leaf flood-reduction {
               description "Enable flood reduction";
               type empty;
             }
             leaf no-neighbor-down-notification {
               description "Don't inform other protocols about neighbor down events";
               type empty;
             }
             leaf ipsec-sa {
               description "IPSec security association name";
               type string {
                 length "1 .. 32";
               }
             }
             list topology {
               key name;
               ordered-by user;
               description "Topology specific attributes";
               leaf name {
                 description "Topology name";
                 type string;
               }
               uses apply-advanced;
               leaf disable {
                 description "Disable this topology";
                 type empty;
               }
               leaf metric {
                 description "Topology metric";
                 type union {
                   type string {
                     pattern "<.*>|$.*";
                   }
                   type uint16 {
                     range "1 .. 65535";
                   }
                 }
               }
               container bandwidth-based-metrics {
                 description "Configure bandwidth based metrics";
                 uses apply-advanced;
                 list bandwidth {
                   key name;
                   description "Bandwidth threshold";
                   leaf name {
                     type string;
                   }
                   leaf metric {
                     description "Metric associated with specified bandwidth";
                     type union {
                       type string {
                         pattern "<.*>|$.*";
                       }
                       type uint16 {
                         range "1 .. 65535";
                       }
                     }
                   }
                 }
               }
             }
           }
           list sham-link-remote {
             key name;
             ordered-by user;
             description "Configure parameters for remote sham link endpoint";
             leaf name {
               description "Remote sham link endpoint address";
               type jt:ipaddr;
             }
             uses apply-advanced;
             leaf metric {
               description "Sham link metric";
               type union {
                 type string {
                   pattern "<.*>|$.*";
                 }
                 type uint16 {
                   range "1 .. 65535";
                 }
               }
             }
             leaf ipsec-sa {
               description "IPSec security association name";
               type string {
                 length "1 .. 32";
               }
             }
             leaf demand-circuit {
               description "Interface functions as a demand circuit";
               type empty;
             }
             leaf flood-reduction {
               description "Enable flood reduction";
               type empty;
             }
             list topology {
               key name;
               ordered-by user;
               description "Topology specific attributes";
               leaf name {
                 description "Topology name";
                 type string;
               }
               uses apply-advanced;
               leaf disable {
                 description "Disable this topology";
                 type empty;
               }
               leaf metric {
                 description "Topology metric";
                 type union {
                   type string {
                     pattern "<.*>|$.*";
                   }
                   type uint16 {
                     range "1 .. 65535";
                   }
                 }
               }
               container bandwidth-based-metrics {
                 description "Configure bandwidth based metrics";
                 uses apply-advanced;
                 list bandwidth {
                   key name;
                   description "Bandwidth threshold";
                   leaf name {
                     type string;
                   }
                   leaf metric {
                     description "Metric associated with specified bandwidth";
                     type union {
                       type string {
                         pattern "<.*>|$.*";
                       }
                       type uint16 {
                         range "1 .. 65535";
                       }
                     }
                   }
                 }
               }
             }
           }
           list interface {
             key name;
             ordered-by user;
             description "Include an interface in this area";
             leaf name {
               description "Interface name";
               type union {
                 type jt:ipv4addr-or-interface;
                 type string {
                   pattern "<.*>|$.*";
                 }
               }
             }
             uses apply-advanced;
             choice enable-disable {
               case case_1 {
                 leaf disable {
                   description "Disable OSPF on this interface";
                   type empty;
                 }
               }
             }
             leaf interface-type {
               description "Type of interface";
               type enumeration {
                 enum "nbma" {
                   description "Nonbroadcast multiaccess";
                 }
                 enum "p2mp" {
                   description "Point-to-multipoint NBMA";
                 }
                 enum "p2p" {
                   description "Point-to-point";
                 }
                 enum "p2mp-over-lan" {
                   description "Point-to-multipoint over LAN mode";
                 }
               }
             }
             container post-convergence-lfa {
               presence "enable post-convergence-lfa";
               description "Protect interface using post-convergence backup path";
               uses apply-advanced;
               container node-protection {
                 presence "enable node-protection";
                 description "Compute backup path assuming node failure";
                 uses apply-advanced;
                 leaf cost {
                   description "Cost for node protection";
                   type union {
                     type string {
                       pattern "<.*>|$.*";
                     }
                     type uint16 {
                       range "1 .. 65535";
                     }
                   }
                 }
               }
             }
             choice protection-type {
               case case_1 {
                 leaf link-protection {
                   description "Protect interface from link faults only";
                   type empty;
                 }
               }
               case case_2 {
                 leaf node-link-protection {
                   description "Protect interface from both link and node faults";
                   type empty;
                 }
               }
             }
             leaf no-eligible-backup {
               description "Not eligible to backup traffic from protected interfaces";
               type empty;
             }
             leaf no-eligible-remote-backup {
               description "Not eligible for Remote-LFA backup traffic from protected interfaces";
               type empty;
             }
             container passive {
               presence "enable passive";
               description "Do not run OSPF, but advertise it";
               uses apply-advanced;
               container traffic-engineering {
                 description "Advertise TE link information";
                 uses apply-advanced;
                 leaf remote-node-id {
                   description "Remote address of the link";
                   type jt:ipaddr;
                 }
                 leaf remote-node-router-id {
                   description "TE Router-ID of the remote node";
                   type jt:ipv4addr;
                 }
               }
             }
             leaf secondary {
               description "Treat interface as secondary";
               type empty;
             }
             leaf own-router-lsa {
               description "Generate a separate router LSA for this interface";
               type empty;
             }
             container bandwidth-based-metrics {
               description "Configure bandwidth based metrics";
               uses apply-advanced;
               list bandwidth {
                 key name;
                 description "Bandwidth threshold";
                 leaf name {
                   type string;
                 }
                 leaf metric {
                   description "Metric associated with specified bandwidth";
                   type union {
                     type string {
                       pattern "<.*>|$.*";
                     }
                     type uint16 {
                       range "1 .. 65535";
                     }
                   }
                 }
               }
             }
             leaf metric {
               description "Interface metric";
               type union {
                 type string {
                   pattern "<.*>|$.*";
                 }
                 type uint16 {
                   range "1 .. 65535";
                 }
               }
             }
             leaf te-metric {
               description "Traffic engineering metric";
               type union {
                 type string {
                   pattern "<.*>|$.*";
                 }
                 type uint32 {
                   range "1 .. 4294967295";
                 }
               }
             }
             leaf priority {
               description "Designated router priority";
               type union {
                 type string {
                   pattern "<.*>|$.*";
                 }
                 type uint32 {
                   range "0 .. 255";
                 }
               }
             }
             container ldp-synchronization {
               description "Advertise maximum metric until LDP is operational";
               presence "enable ldp-synchronization";
               uses ldp-sync-obj;
             }
             leaf retransmit-interval {
               description "Retransmission interval (seconds)";
               type union {
                 type string {
                   pattern "<.*>|$.*";
                 }
                 type uint32 {
                   range "1 .. 65535";
                 }
               }
             }
             leaf transit-delay {
               description "Transit delay (seconds)";
               type union {
                 type string {
                   pattern "<.*>|$.*";
                 }
                 type uint32 {
                   range "1 .. 65535";
                 }
               }
             }
             leaf hello-interval {
               description "Hello interval (seconds)";
               type union {
                 type string {
                   pattern "<.*>|$.*";
                 }
                 type uint32 {
                   range "1 .. 255";
                 }
               }
             }
             leaf dead-interval {
               description "Dead interval (seconds)";
               type union {
                 type string {
                   pattern "<.*>|$.*";
                 }
                 type uint32 {
                   range "1 .. 65535";
                 }
               }
             }
             leaf mtu {
               description "Maximum OSPF packet size";
               type union {
                 type string {
                   pattern "<.*>|$.*";
                 }
                 type uint32 {
                   range "128 .. 65535";
                 }
               }
             }
             choice auth {
               case case_1 {
                 container authentication {
                   uses juniper-ospf-authentication;
                 }
               }
               case case_2 {
                 container authentication-key {
                   description "Authentication key";
                   status deprecated;
                   leaf keyname {
                     description "Authentication key value";
                     type jt:unreadable;
                   }
                   leaf key-id {
                     description "Key ID for MD5 authentication";
                     type union {
                       type string {
                         pattern "<.*>|$.*";
                       }
                       type uint32 {
                         range "0 .. 255";
                       }
                     }
                   }
                 }
               }
             }
             leaf demand-circuit {
               description "Interface functions as a demand circuit";
               type empty;
             }
             leaf flood-reduction {
               description "Enable flood reduction";
               type empty;
             }
             leaf no-neighbor-down-notification {
               description "Don't inform other protocols about neighbor down events";
               type empty;
             }
             leaf ipsec-sa {
               description "IPSec security association name";
               type string {
                 length "1 .. 32";
               }
             }
             list topology {
               key name;
               ordered-by user;
               description "Topology specific attributes";
               leaf name {
                 description "Topology name";
                 type string;
               }
               uses apply-advanced;
               leaf disable {
                 description "Disable this topology";
                 type empty;
               }
               leaf metric {
                 description "Topology metric";
                 type union {
                   type string {
                     pattern "<.*>|$.*";
                   }
                   type uint16 {
                     range "1 .. 65535";
                   }
                 }
               }
               container bandwidth-based-metrics {
                 description "Configure bandwidth based metrics";
                 uses apply-advanced;
                 list bandwidth {
                   key name;
                   description "Bandwidth threshold";
                   leaf name {
                     type string;
                   }
                   leaf metric {
                     description "Metric associated with specified bandwidth";
                     type union {
                       type string {
                         pattern "<.*>|$.*";
                       }
                       type uint16 {
                         range "1 .. 65535";
                       }
                     }
                   }
                 }
               }
             }
             leaf transmit-interval {
               description "OSPF packet transmit interval (milliseconds)";
               status deprecated;
               type union {
                 type string {
                   pattern "<.*>|$.*";
                 }
                 type uint32 {
                   range "1 .. 4294967295";
                 }
               }
             }
             container bfd-liveness-detection {
               description "Bidirectional Forwarding Detection options";
               uses apply-advanced;
               leaf version {
                 description "BFD protocol version number";
                 default "automatic";
                 type enumeration {
                   enum "0" {
                     description "BFD version 0 (deprecated)";
                   }
                   enum "1" {
                     description "BFD version 1";
                   }
                   enum "automatic" {
                     description "Choose BFD version automatically";
                   }
                 }
               }
               leaf minimum-interval {
                 description "Minimum transmit and receive interval";
                 units "milliseconds";
                 type union {
                   type string {
                     pattern "<.*>|$.*";
                   }
                   type uint32 {
                     range "1 .. 255000";
                   }
                 }
               }
               leaf minimum-transmit-interval {
                 description "Minimum transmit interval";
                 status deprecated;
                 units "milliseconds";
                 type union {
                   type string {
                     pattern "<.*>|$.*";
                   }
                   type uint32 {
                     range "1 .. 255000";
                   }
                 }
               }
               leaf minimum-receive-interval {
                 description "Minimum receive interval";
                 units "milliseconds";
                 type union {
                   type string {
                     pattern "<.*>|$.*";
                   }
                   type uint32 {
                     range "1 .. 255000";
                   }
                 }
               }
               leaf multiplier {
                 description "Detection time multiplier";
                 default "3";
                 type union {
                   type string {
                     pattern "<.*>|$.*";
                   }
                   type uint32 {
                     range "1 .. 255";
                   }
                 }
               }
               choice adaptation-choice {
                 case case_1 {
                   leaf no-adaptation {
                     description "Disable adaptation";
                     type empty;
                   }
                 }
               }
               container transmit-interval {
                 description "Transmit-interval options";
                 uses apply-advanced;
                 leaf minimum-interval {
                   description "Minimum transmit interval";
                   units "milliseconds";
                   type union {
                     type string {
                       pattern "<.*>|$.*";
                     }
                     type uint32 {
                       range "1 .. 255000";
                     }
                   }
                 }
                 leaf threshold {
                   description "High transmit interval triggering a trap";
                   units "milliseconds";
                   type union {
                     type uint32;
                     type string {
                       pattern "<.*>|$.*";
                     }
                   }
                 }
               }
               container detection-time {
                 description "Detection-time options";
                 uses apply-advanced;
                 leaf threshold {
                   description "High detection-time triggering a trap";
                   units "milliseconds";
                   type union {
                     type uint32;
                     type string {
                       pattern "<.*>|$.*";
                     }
                   }
                 }
               }
               container authentication {
                 description "Authentication options";
                 uses apply-advanced;
                 leaf key-chain {
                   description "Key chain name";
                   type string;
                 }
                 leaf algorithm {
                   description "Algorithm name";
                   type enumeration {
                     enum "simple-password" {
                       description "Simple password";
                     }
                     enum "keyed-md5" {
                       description "Keyed message Digest 5";
                     }
                     enum "meticulous-keyed-md5" {
                       description "Meticulous keyed message Digest 5";
                     }
                     enum "keyed-sha-1" {
                       description "Keyed secure hash algorithm (SHA1) ";
                     }
                     enum "meticulous-keyed-sha-1" {
                       description "Meticulous keyed secure hash algorithm (SHA1) ";
                     }
                   }
                 }
                 leaf loose-check {
                   description "Verify authentication only if authentication is negotiated";
                   type empty;
                 }
               }
               leaf full-neighbors-only {
                 description "Setup BFD sessions only to Full neighbors";
                 type empty;
               }
             }
             leaf dynamic-neighbors {
               description "Learn neighbors dynamically on a p2mp interface";
               type empty;
             }
             leaf no-advertise-adjacency-segment {
               description "Do not advertise an adjacency segment for this interface";
               type empty;
             }
             list neighbor {
               key name;
               ordered-by user;
               description "NBMA neighbor";
               leaf name {
                 description "Address of neighbor";
                 type jt:ipaddr;
               }
               leaf eligible {
                 description "Eligible to be DR on an NBMA network";
                 type empty;
               }
             }
             leaf poll-interval {
               description "Poll interval for NBMA interfaces";
               type union {
                 type string {
                   pattern "<.*>|$.*";
                 }
                 type uint32 {
                   range "1 .. 65535";
                 }
               }
             }
             leaf no-interface-state-traps {
               description "Do not send interface state change traps";
               type empty;
             }
           }
           leaf no-source-packet-routing {
             description "Disable SPRING in this area";
             type empty;
           }
           leaf no-context-identifier-advertisement {
             description "Disable context identifier advertisments in this area";
             type empty;
           }
           list context-identifier {
             key name;
             ordered-by user;
             description "Configure context identifier in support of edge protection";
             leaf name {
               description "Context identifier";
               type jt:ipv4addr;
             }
             uses apply-advanced;
           }
           list label-switched-path {
             key name;
             ordered-by user;
             description "Configuration for advertisement of a label-switched path";
             leaf name {
               description "Name of label-switched path to be advertised";
               type string {
                 length "1 .. 64";
               }
             }
             uses apply-advanced;
             choice enable-disable {
               case case_1 {
                 leaf disable {
                   description "Disable OSPF on this label-switched path";
                   type empty;
                 }
               }
             }
             leaf metric {
               description "Interface metric";
               type union {
                 type string {
                   pattern "<.*>|$.*";
                 }
                 type uint16 {
                   range "1 .. 65535";
                 }
               }
             }
             list topology {
               key name;
               ordered-by user;
               description "Topology specific attributes";
               leaf name {
                 description "Topology name";
                 type string;
               }
               uses apply-advanced;
               leaf disable {
                 description "Disable this topology";
                 type empty;
               }
               leaf metric {
                 description "Topology metric";
                 type union {
                   type string {
                     pattern "<.*>|$.*";
                   }
                   type uint16 {
                     range "1 .. 65535";
                   }
                 }
               }
               container bandwidth-based-metrics {
                 description "Configure bandwidth based metrics";
                 uses apply-advanced;
                 list bandwidth {
                   key name;
                   description "Bandwidth threshold";
                   leaf name {
                     type string;
                   }
                   leaf metric {
                     description "Metric associated with specified bandwidth";
                     type union {
                       type string {
                         pattern "<.*>|$.*";
                       }
                       type uint16 {
                         range "1 .. 65535";
                       }
                     }
                   }
                 }
               }
             }
           }
           list peer-interface {
             key name;
             ordered-by user;
             description "Configuration for peer interface";
             leaf name {
               description "Name of peer interface";
               type string;
             }
             uses apply-advanced;
             choice enable-disable {
               case case_1 {
                 leaf disable {
                   description "Disable OSPF on this control peer";
                   type empty;
                 }
               }
             }
             leaf retransmit-interval {
               description "Retransmission interval (seconds)";
               type union {
                 type string {
                   pattern "<.*>|$.*";
                 }
                 type uint32 {
                   range "1 .. 65535";
                 }
               }
             }
             leaf transit-delay {
               description "Transit delay (seconds)";
               type union {
                 type string {
                   pattern "<.*>|$.*";
                 }
                 type uint32 {
                   range "1 .. 65535";
                 }
               }
             }
             leaf hello-interval {
               description "Hello interval (seconds)";
               type union {
                 type string {
                   pattern "<.*>|$.*";
                 }
                 type uint32 {
                   range "1 .. 255";
                 }
               }
             }
             leaf dead-interval {
               description "Dead interval (seconds)";
               type union {
                 type string {
                   pattern "<.*>|$.*";
                 }
                 type uint32 {
                   range "1 .. 65535";
                 }
               }
             }
             leaf mtu {
               description "Maximum OSPF packet size";
               type union {
                 type string {
                   pattern "<.*>|$.*";
                 }
                 type uint32 {
                   range "128 .. 65535";
                 }
               }
             }
             choice auth {
               case case_1 {
                 container authentication {
                   uses juniper-ospf-authentication;
                 }
               }
               case case_2 {
                 container authentication-key {
                   description "Authentication key";
                   status deprecated;
                   leaf keyname {
                     description "Authentication key value";
                     type jt:unreadable;
                   }
                   leaf key-id {
                     description "Key ID for MD5 authentication";
                     type union {
                       type string {
                         pattern "<.*>|$.*";
                       }
                       type uint32 {
                         range "0 .. 255";
                       }
                     }
                   }
                 }
               }
             }
             leaf demand-circuit {
               description "Interface functions as a demand circuit";
               type empty;
             }
             leaf flood-reduction {
               description "Enable flood reduction";
               type empty;
             }
             leaf no-neighbor-down-notification {
               description "Don't inform other protocols about neighbor down events";
               type empty;
             }
           }
         }
       }
       container rip {
         description "RIP options";
         uses juniper-protocols-rip;
       }
       container ripng {
         description "RIPng options";
         uses juniper-protocols-ripng;
       }
       container isis {
         description "IS-IS configuration";
         uses juniper-protocols-isis;
       }
       container esis {
         description "ES-IS configuration";
         uses juniper-protocols-esis;
       }
       container l2vpn {
         description "Layer 2 VPN configuration";
         uses juniper-protocols-l2vpn;
       }
       container vpls {
         description "VPLS configuration";
         presence "enable vpls";
         uses juniper-protocols-l2vpn;
       }
       container pim {
         description "PIM configuration";
         uses juniper-protocols-pim;
       }
       container amt {
         description "AMT relay configuration";
         uses juniper-protocols-amt;
       }
       container ldp {
         description "LDP configuration";
         uses juniper-protocols-ldp;
       }
       container router-discovery {
         description "ICMP router discovery options";
         uses juniper-protocols-router-discovery;
       }
       container msdp {
         description "MSDP configuration";
         uses juniper-protocols-msdp;
       }
       container mvpn {
         description "BGP-MVPN configuration";
         presence "enable mvpn";
         uses juniper-protocols-mvpn;
       }
       container igmp-snooping {
         description "IGMP snooping configuration";
         presence "enable igmp-snooping";
         uses juniper-ri-protocols-igmp-snooping;
       }
       container mld-snooping {
         description "MLD snooping configuration";
         presence "enable mld-snooping";
         uses juniper-ri-protocols-mld-snooping;
       }
       container pim-snooping {
         description "PIM snooping configuration";
         presence "enable pim-snooping";
         uses juniper-protocols-pim-snooping;
       }
       container mvrp {
         description "MVRP configuration";
         uses juniper-protocols-mvrp;
       }
       container rstp {
         description "RSTP configuration";
         uses juniper-protocols-stp;
       }
       container mstp {
         description "MSTP configuration";
         uses juniper-protocols-mstp;
       }
       container vstp {
         description "VSTP configuration";
         uses juniper-protocols-vstp;
       }
     }
     container bridge-domains {
       description "Bridge domain configuration";
       uses apply-advanced;
       list domain {
         key name;
         uses juniper-bridge-domains;
       }
     }
     container switch-options {
       description "L2 options for routing-instance of type virtual-switch";
       uses juniper-routing-instance-switch-options;
     }
     container pbb-options {
       description "Provider backbone bridging options for routing-instance";
       uses juniper-routing-instance-pbb-options;
     }
     list service-groups {
       key name;
       description "Service group configuration for routing-instance";
       uses juniper-routing-instance-service-groups;
     }
   }
   grouping juniper-forwarding-options {
     uses apply-advanced;
     list storm-control-profiles {
       key name;
       description "Storm control profile for this instance";
       leaf name {
         description "Storm control profile name";
         type string {
           length "1 .. 127";
         }
       }
       uses apply-advanced;
       container all {
         presence "enable all";
         description "For all BUM traffic";
         uses apply-advanced;
         choice bandwidth {
           case case_1 {
             leaf bandwidth-percentage {
               description "Percentage of link bandwidth";
               type union {
                 type string {
                   pattern "<.*>|$.*";
                 }
                 type uint32 {
                   range "1 .. 100";
                 }
               }
             }
           }
           case case_2 {
             leaf bandwidth-level {
               description "Link bandwidth";
               units "kbps";
               type union {
                 type string {
                   pattern "<.*>|$.*";
                 }
                 type uint32;
               }
             }
           }
         }
         leaf burst-size {
           description "Burst size";
           units "bytes";
           type union {
             type string {
               pattern "<.*>|$.*";
             }
             type uint32 {
               range "1500 .. 100000000";
             }
           }
         }
         leaf no-broadcast {
           description "Disable broadcast storm control";
           type empty;
         }
         leaf no-unknown-unicast {
           description "Disable unknown unicast storm control";
           type empty;
         }
         choice no-multicast-choices {
           case case_1 {
             leaf no-multicast {
               description "Disable multicast storm control";
               type empty;
             }
           }
           case case_2 {
             leaf no-registered-multicast {
               description "Disable registered multicast storm control";
               type empty;
             }
           }
           case case_3 {
             leaf no-unregistered-multicast {
               description "Disable unregistered multicast storm control";
               type empty;
             }
           }
         }
       }
       leaf action-shutdown {
         description "Disable port for excessive storm control errors";
         type empty;
       }
     }
     choice sampling-or-packet-capture {
       case case_1 {
         container sampling {
           description "Statistical traffic sampling options";
           uses juniper-sampling-options;
         }
       }
       case case_2 {
         container packet-capture {
           description "Packet capture options";
           uses juniper-packet-capture-options;
         }
       }
     }
     list accounting {
       key name;
       description "Configure accounting of traffic";
       uses juniper-packet-accounting-options;
     }
     container port-mirroring {
       description "Configure port mirroring of traffic";
       uses juniper-port-mirror-options;
     }
     container multicast-replication {
       description "Set mode of multicast replication";
       uses apply-advanced;
       container evpn {
         description "EVPN IRB multicast related options";
         uses apply-advanced;
         leaf irb {
           type enumeration {
             enum "local-only" {
               description "Multicast forward in local-only mode";
             }
             enum "local-remote" {
               description "Multicast forward in local-remote mode";
             }
           }
         }
         leaf smet-nexthop-limit {
           description "Flood traffic to all egress when count goes above limit";
           type union {
             type string {
               pattern "<.*>|$.*";
             }
             type uint32 {
               range "10000 .. 40000";
             }
           }
         }
       }
     }
     container load-balance {
       description "Configure load-balancing attributes on the forwarding path";
       uses apply-advanced;
       container indexed-load-balance {
         presence "enable indexed-load-balance";
         description "Use indexed permuted next hop lists for unilist and aggregate next hops";
         uses apply-advanced;
       }
       container per-flow {
         uses apply-advanced;
       }
       container per-prefix {
         presence "enable per-prefix";
         uses apply-advanced;
         leaf hash-seed {
           description "Specifies per-router input value for per-prefix load-balancing hash function";
           default "0";
           type union {
             type string {
               pattern "<.*>|$.*";
             }
             type uint16 {
               range "0 .. 65534";
             }
           }
         }
       }
     }
     container hash-key {
       description "Select data used in the hash key";
       uses junos_hash_key;
     }
     container enhanced-hash-key {
       description "Select data used in the hash key for Enhanced IP Forwarding Engines";
       uses apply-advanced;
       container hash-parameters {
         description "Set traffic hashing parameters";
         uses apply-advanced;
         container ecmp {
           description "Configure hashing parameters for ECMP Traffic";
           uses apply-advanced;
           leaf offset {
             description "Set hashing offset for ECMP Traffic";
             type union {
               type string {
                 pattern "<.*>|$.*";
               }
               type uint32 {
                 range "0 .. 199";
               }
             }
           }
           leaf preprocess {
             description "Enable/Disable the preprocess parameter for ECMP traffic";
             type empty;
           }
           container function {
             description "Configure hash functions for ECMP traffic";
             uses apply-advanced;
             choice instance {
               case case_1 {
                 leaf crc16-bisync {
                   description "Use CRC16-BISYNC function for ECMP traffic rcvd on xe";
                   type empty;
                 }
               }
               case case_2 {
                 leaf crc16-ccitt {
                   description "Use CRC16-CCITT function for ECMP traffic rcvd on xe";
                   type empty;
                 }
               }
               case case_3 {
                 leaf crc32-hi {
                   description "Use CRC32-HI function for ECMP traffic rcvd on xe";
                   type empty;
                 }
               }
               case case_4 {
                 leaf crc32-lo {
                   description "Use CRC32-LO function for ECMP traffic rcvd on xe";
                   type empty;
                 }
               }
             }
           }
         }
         container lag {
           description "Configure hashing parameters for LAG Traffic";
           uses apply-advanced;
           leaf offset {
             description "Set hashing offset for LAG Traffic";
             type union {
               type string {
                 pattern "<.*>|$.*";
               }
               type uint32 {
                 range "0 .. 4294967295";
               }
             }
           }
           leaf preprocess {
             description "Enable/Disable the preprocess parameter for LAG traffic";
             type empty;
           }
           container function {
             description "Configure hash functions for LAG traffic";
             uses apply-advanced;
             choice instance {
               case case_1 {
                 leaf crc16-bisync {
                   description "Use CRC16-BISYNC function for LAG traffic rcvd on xe";
                   type empty;
                 }
               }
               case case_2 {
                 leaf crc16-ccitt {
                   description "Use CRC16-CCITT function for LAG traffic rcvd on xe";
                   type empty;
                 }
               }
               case case_3 {
                 leaf crc32-hi {
                   description "Use CRC32-HI function for LAG traffic rcvd on xe";
                   type empty;
                 }
               }
               case case_4 {
                 leaf crc32-lo {
                   description "Use CRC32-LO function for LAG traffic rcvd on xe";
                   type empty;
                 }
               }
             }
           }
         }
       }
       container hash-seed {
         presence "enable hash-seed";
         description "Hash seed";
         uses apply-advanced;
       }
       container mpls {
         description "Configure mpls fields";
         uses apply-advanced;
         leaf no-incoming-port {
           description "Exclude incoming port from the hash key";
           type empty;
         }
         leaf no-incoming-device {
           description "Exclude incoming device from the hash key";
           type empty;
         }
       }
       container services-loadbalancing {
         description "Select key to load balance across service PICs";
         uses apply-advanced;
         container family {
           description "Protocol family";
           container inet {
             description "IPv4 protocol family";
             uses apply-advanced;
             container layer-3-services {
               description "Include Layer 3 (IP) data in the hash key";
               uses apply-advanced;
               leaf source-address {
                 description "Include IP source address in the hash key";
                 type empty;
               }
               leaf destination-address {
                 description "Include IP destination address in the hash key";
                 type empty;
               }
               leaf incoming-interface-index {
                 description "Include incoming interface index in the hash key";
                 type empty;
               }
             }
           }
           container inet6 {
             description "IPv6 protocol family";
             uses apply-advanced;
             container layer-3-services {
               description "Include Layer 3 (IP) data in the hash key";
               uses apply-advanced;
               leaf source-address {
                 description "Include IP source address in the hash key";
                 type empty;
               }
               leaf destination-address {
                 description "Include IP destination address in the hash key";
                 type empty;
               }
               leaf incoming-interface-index {
                 description "Include incoming interface index in the hash key";
                 type empty;
               }
               leaf src-prefix-len {
                 description "Enhanced hash key inet6 source prefix length";
                 default "127";
                 units "bits";
                 type union {
                   type string {
                     pattern "<.*>|$.*";
                   }
                   type uint32 {
                     range "56 .. 127";
                   }
                 }
               }
             }
           }
         }
       }
       container family {
         description "Protocol family";
         container inet {
           description "IPv4 protocol family";
           uses apply-advanced;
           leaf incoming-interface-index {
             description "Include incoming interface index in the hash key";
             type empty;
           }
           leaf no-destination-port {
             description "Omit IP destination port in the hash key";
             type empty;
           }
           leaf no-source-port {
             description "Omit IP source port in the hash key";
             type empty;
           }
           leaf type-of-service {
             description "Include TOS byte in the hash key";
             type empty;
           }
           leaf gtp-tunnel-endpoint-identifier {
             description "Include TEID in the hash key for GTP-U packets";
             type empty;
           }
           leaf l2tp-tunnel-session-identifier {
             description "Include TID SID in the hash key for L2TP packets";
             type empty;
           }
           leaf session-id {
             description "Include session ID in the enhanced hash key";
             type empty;
           }
         }
         container inet6 {
           description "IPv6 protocol family";
           uses apply-advanced;
           leaf incoming-interface-index {
             description "Include incoming interface index in the hash key";
             type empty;
           }
           leaf traffic-class {
             description "Include Traffic Class byte in the hash key";
             type empty;
           }
           leaf no-destination-port {
             description "Omit IP destination port in the hash key";
             type empty;
           }
           leaf no-source-port {
             description "Omit IP source port in the hash key";
             type empty;
           }
           leaf gtp-tunnel-endpoint-identifier {
             description "Include TEID in the hash key for GTP-U packets";
             type empty;
           }
           leaf session-id {
             description "Include session ID in the enhanced hash key";
             type empty;
           }
           leaf no-flow-label {
             description "Omit Flow label in the hash key";
             type empty;
           }
         }
         container mpls {
           description "MPLS protocol family";
           uses apply-advanced;
           leaf label-1-exp {
             description "Include EXP of first MPLS label from the hash key";
             type empty;
           }
           leaf incoming-interface-index {
             description "Include incoming interface index in the hash key";
             type empty;
           }
           choice pseudowire_option {
             case case_1 {
               leaf no-ether-pseudowire {
                 description "Omit IP payload over ethernet PW from the hash-key";
                 type empty;
               }
             }
             case case_2 {
             }
           }
           leaf no-payload {
             description "Omit MPLS payload data from the hash key";
             type empty;
           }
         }
         container multiservice {
           description "Multiservice protocol (bridged/CCC/VPLS) family";
           uses apply-advanced;
           leaf incoming-interface-index {
             description "Include incoming interface index in hash key";
             type empty;
           }
           leaf outer-priority {
             description "Include Outer 802.1 Priority bits in the hash key";
             type empty;
           }
           leaf no-payload {
             description "Omit payload data from the hash key";
             type empty;
           }
           leaf no-mac-addresses {
             description "Omit source and destination MAC addresses from the hash key";
             type empty;
           }
         }
       }
     }
     container next-hop {
       description "Next hop throttle";
       uses apply-advanced;
       leaf arp-throttle {
         description "Change the arp throttling time(seconds)";
         type union {
           type string {
             pattern "<.*>|$.*";
           }
           type uint16 {
             range "10 .. 100";
           }
         }
       }
       leaf arp-detect {
         description "Change the arp throttling detect time(milliseconds)";
         type union {
           type string {
             pattern "<.*>|$.*";
           }
           type uint32 {
             range "1 .. 100000";
           }
         }
       }
     }
     container multicast {
       description "Multicast resolve and mismatch rate";
       uses apply-advanced;
       leaf resolve-rate {
         description "Multicast resolve rate";
         units "per second";
         type union {
           type string {
             pattern "<.*>|$.*";
           }
           type uint32 {
             range "100 .. 1000";
           }
         }
       }
       leaf mismatch-rate {
         description "Multicast interface mismatch rate";
         units "per second";
         type union {
           type string {
             pattern "<.*>|$.*";
           }
           type uint32 {
             range "50 .. 1000";
           }
         }
       }
     }
     container explicit-null-cos {
       presence "enable explicit-null-cos";
       description "Configure to use MPLS explicit null exp for COS classification";
       uses apply-advanced;
       leaf inet {
         description "Include family inet";
         type empty;
       }
       leaf inet6 {
         description "Include family inet6";
         type empty;
       }
     }
     container helpers {
       description "Port forwarding configuration";
       uses apply-advanced;
       container traceoptions {
         description "Trace options for helper";
         uses apply-advanced;
         leaf no-remote-trace {
           description "Disable remote tracing";
           type empty;
         }
         container file {
           description "Trace file information";
           leaf filename {
             description "Name of file in which to write trace information";
             type string {
               length "1 .. 1024";
             }
           }
           leaf size {
             description "Maximum trace file size";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         leaf level {
           description "Level of debugging output";
           default "error";
           type enumeration {
             enum "error" {
               description "Match error conditions";
             }
             enum "warning" {
               description "Match warning messages";
             }
             enum "notice" {
               description "Match conditions that should be handled specially";
             }
             enum "info" {
               description "Match informational messages";
             }
             enum "verbose" {
               description "Match verbose messages";
             }
             enum "all" {
               description "Match all levels";
             }
           }
         }
         list flag {
           key name;
           ordered-by user;
           description "Area of UDP forwarding helper process on which to enable debugging output";
           leaf name {
             type enumeration {
               enum "trace" {
                 description "Trace tracing code";
               }
               enum "address" {
                 description "Trace address management code";
               }
               enum "main" {
                 description "Trace main loop code";
               }
               enum "config" {
                 description "Trace configuration code";
               }
               enum "ifdb" {
                 description "Trace interface database code";
               }
               enum "io" {
                 description "Trace I/O code";
               }
               enum "rtsock" {
                 description "Trace routing socket code";
               }
               enum "ui" {
                 description "Trace user interface code";
               }
               enum "util" {
                 description "Trace miscellaneous utility code";
               }
               enum "gencfg" {
                 description "Trace fud gencfg message";
               }
               enum "domain" {
                 description "Trace DNS service-specific code";
               }
               enum "tftp" {
                 description "Trace TFTP service-specific code";
               }
               enum "bootp" {
                 description "Trace BOOTP/DHCP service-specific code";
               }
               enum "port" {
                 description "Trace arbitrary protocol code";
               }
               enum "if-rtsdb" {
                 description "Trace interface hierarchy rtsdb";
               }
               enum "all" {
                 description "Trace all areas of code";
               }
             }
           }
         }
       }
       container rtsdb-client-traceoptions {
         presence "enable rtsdb-client-traceoptions";
         description "SHM rtsock database client library trace options";
         status deprecated;
         uses apply-advanced;
         container if-rtsdb {
           presence "enable if-rtsdb";
           description "Trace interface hierarchy rtsdb";
           uses apply-advanced;
           list flag {
             key name;
             ordered-by user;
             description "Tracing parameters";
             leaf name {
               type enumeration {
                 enum "init" {
                   description "Trace initialization";
                 }
                 enum "routing-socket" {
                   description "Trace routing socket messages";
                 }
                 enum "map" {
                   description "Trace shared memory mapping";
                 }
                 enum "all" {
                   description "Trace all";
                 }
               }
             }
             leaf disable {
               description "Disable this trace flag";
               type empty;
             }
           }
         }
       }
       container domain {
         description "Incoming DNS request forwarding configuration";
         uses apply-advanced;
         leaf description {
           description "Text description of server";
           type string;
         }
         container server {
           description "Server information";
           leaf address {
             description "Name or address of server to which to forward";
             type jt:ipv4addr;
           }
           choice instance {
             case case_1 {
               container logical-system {
                 description "Logical system of server to which to forward";
                 leaf logical-system-name {
                   description "Name of logical system";
                   type string {
                   }
                 }
                 leaf routing-instance {
                   description "Routing instance of server to which to forward";
                   type union {
                     type string {
                       pattern "default";
                     }
                     type string {
                     }
                   }
                 }
               }
             }
             case case_2 {
               leaf routing-instance {
                 description "Routing instance of server to which to forward";
                 type union {
                   type string {
                     pattern "default";
                   }
                   type string {
                   }
                 }
               }
             }
           }
         }
         list interface {
           key name;
           ordered-by user;
           description "Incoming DNS request forwarding interface configuration";
           leaf name {
             description "Name of interface or group of interfaces";
             type union {
               type jt:interface-wildcard;
               type string {
                 pattern "<.*>|$.*";
               }
             }
           }
           uses apply-advanced;
           leaf no-listen {
             description "Do not listen on this interface";
             type empty;
           }
           leaf broadcast {
             description "If the layer 2 interface is unknown then broadcast";
             type empty;
           }
           leaf description {
             description "Text description of server";
             type string;
           }
           container server {
             description "Server information";
             leaf address {
               description "Name or address of server to which to forward";
               type jt:ipv4addr;
             }
             choice instance {
               case case_1 {
                 container logical-system {
                   description "Logical system of server to which to forward";
                   leaf logical-system-name {
                     description "Name of logical system";
                     type string {
                     }
                   }
                   leaf routing-instance {
                     description "Routing instance of server to which to forward";
                     type union {
                       type string {
                         pattern "default";
                       }
                       type string {
                       }
                     }
                   }
                 }
               }
               case case_2 {
                 leaf routing-instance {
                   description "Routing instance of server to which to forward";
                   type union {
                     type string {
                       pattern "default";
                     }
                     type string {
                     }
                   }
                 }
               }
             }
           }
         }
       }
       container tftp {
         description "Incoming TFTP request forwarding configuration";
         uses apply-advanced;
         leaf description {
           description "Text description of server";
           type string;
         }
         container server {
           description "Server information";
           leaf address {
             description "Name or address of server to which to forward";
             type jt:ipv4addr;
           }
           choice instance {
             case case_1 {
               container logical-system {
                 description "Logical system of server to which to forward";
                 leaf logical-system-name {
                   description "Name of logical system";
                   type string {
                   }
                 }
                 leaf routing-instance {
                   description "Routing instance of server to which to forward";
                   type union {
                     type string {
                       pattern "default";
                     }
                     type string {
                     }
                   }
                 }
               }
             }
             case case_2 {
               leaf routing-instance {
                 description "Routing instance of server to which to forward";
                 type union {
                   type string {
                     pattern "default";
                   }
                   type string {
                   }
                 }
               }
             }
           }
         }
         list interface {
           key name;
           ordered-by user;
           description "Incoming TFTP request forwarding interface configuration";
           leaf name {
             description "Name of interface or group of interfaces";
             type union {
               type jt:interface-wildcard;
               type string {
                 pattern "<.*>|$.*";
               }
             }
           }
           uses apply-advanced;
           leaf no-listen {
             description "Do not listen on this interface";
             type empty;
           }
           leaf broadcast {
             description "If the layer 2 interface is unknown then broadcast";
             type empty;
           }
           leaf description {
             description "Text description of server";
             type string;
           }
           container server {
             description "Server information";
             leaf address {
               description "Name or address of server to which to forward";
               type jt:ipv4addr;
             }
             choice instance {
               case case_1 {
                 container logical-system {
                   description "Logical system of server to which to forward";
                   leaf logical-system-name {
                     description "Name of logical system";
                     type string {
                     }
                   }
                   leaf routing-instance {
                     description "Routing instance of server to which to forward";
                     type union {
                       type string {
                         pattern "default";
                       }
                       type string {
                       }
                     }
                   }
                 }
               }
               case case_2 {
                 leaf routing-instance {
                   description "Routing instance of server to which to forward";
                   type union {
                     type string {
                       pattern "default";
                     }
                     type string {
                     }
                   }
                 }
               }
             }
           }
         }
       }
       container bootp {
         description "Incoming BOOTP/DHCP request forwarding configuration";
         uses apply-advanced;
         leaf relay-agent-option {
           description "Use DHCP Relay Agent option in relayed BOOTP/DHCP messages";
           type empty;
         }
         leaf description {
           description "Text description of servers";
           type string;
         }
         list server {
           key name;
           ordered-by user;
           description "Server information";
           leaf name {
             description "Name or address of servers to which to forward";
             type jt:ipv4addr;
           }
           uses apply-advanced;
           list logical-system {
             key name;
             ordered-by user;
             description "Logical system of server to which to forward";
             leaf name {
               description "Name of logical system";
               type string {
               }
             }
             leaf-list routing-instance {
               ordered-by user;
               description "Routing instance of server to which to forward";
               type string;
             }
           }
           leaf-list routing-instance {
             ordered-by user;
             description "Routing instance of server to which to forward";
             type string;
           }
         }
         leaf maximum-hop-count {
           description "Maximum number of hops per packet";
           default "4";
           type union {
             type string {
               pattern "<.*>|$.*";
             }
             type uint32 {
               range "1 .. 16";
             }
           }
         }
         leaf minimum-wait-time {
           description "Minimum number of seconds before requests are forwarded";
           default "0";
           type union {
             type string {
               pattern "<.*>|$.*";
             }
             type uint32 {
               range "0 .. 30000";
             }
           }
         }
         leaf client-response-ttl {
           description "IP time-to-live value to set in responses to client";
           type union {
             type string {
               pattern "<.*>|$.*";
             }
             type uint32 {
               range "1 .. 255";
             }
           }
         }
         leaf vpn {
           description "Enable vpn encryption ";
           type empty;
         }
         leaf apply-secondary-as-giaddr {
           description "Enable DHCP relay to use secondary gateway ip on all interfaces";
           type empty;
         }
         list interface {
           key name;
           ordered-by user;
           description "Incoming BOOTP/DHCP request forwarding interface configuration";
           leaf name {
             description "Name of interface or group of interfaces";
             type union {
               type jt:interface-wildcard;
               type string {
                 pattern "<.*>|$.*";
               }
             }
           }
           uses apply-advanced;
           leaf no-listen {
             description "Do not listen on this interface";
             type empty;
           }
           leaf broadcast {
             description "If the layer 2 interface is unknown then broadcast";
             type empty;
           }
           leaf description {
             description "Text description of servers";
             type string;
           }
           list server {
             key name;
             ordered-by user;
             description "Server information";
             leaf name {
               description "Name or address of servers to which to forward";
               type jt:ipv4addr;
             }
             uses apply-advanced;
             list logical-system {
               key name;
               ordered-by user;
               description "Logical system of server to which to forward";
               leaf name {
                 description "Name of logical system";
                 type string {
                 }
               }
               leaf-list routing-instance {
                 ordered-by user;
                 description "Routing instance of server to which to forward";
                 type string;
               }
             }
             leaf-list routing-instance {
               ordered-by user;
               description "Routing instance of server to which to forward";
               type string;
             }
           }
           leaf maximum-hop-count {
             description "Maximum number of hops per packet";
             default "4";
             type union {
               type string {
                 pattern "<.*>|$.*";
               }
               type uint32 {
                 range "1 .. 16";
               }
             }
           }
           leaf minimum-wait-time {
             description "Minimum number of seconds before requests are forwarded";
             default "0";
             type union {
               type string {
                 pattern "<.*>|$.*";
               }
               type uint32 {
                 range "0 .. 30000";
               }
             }
           }
           leaf client-response-ttl {
             description "IP time-to-live value to set in responses to client";
             type union {
               type string {
                 pattern "<.*>|$.*";
               }
               type uint32 {
                 range "1 .. 255";
               }
             }
           }
           leaf vpn {
             description "Enable vpn encryption ";
             type empty;
           }
           leaf apply-secondary-as-giaddr {
             description "Enable DHCP relay to use secondary gateway ip on this interface";
             type empty;
           }
         }
       }
       list port {
         key name;
         ordered-by user;
         description "Incoming arbitrary protocol request forwarding configuration";
         leaf name {
           description "Port number of the protocol to listen";
           type union {
             type string {
               pattern "<.*>|$.*";
             }
             type uint32 {
               range "1 .. 65535";
             }
           }
         }
         uses apply-advanced;
         leaf description {
           description "Text description of server";
           type string;
         }
         list server {
           key name;
           ordered-by user;
           description "Server information";
           leaf name {
             description "Name or address of server to which to forward";
             type jt:ipv4addr;
           }
           uses apply-advanced;
           choice instance {
             case case_1 {
               container logical-system {
                 description "Logical system of server to which to forward";
                 leaf logical-system-name {
                   description "Name of logical system";
                   type string {
                   }
                 }
                 leaf routing-instance {
                   description "Routing instance of server to which to forward";
                   type union {
                     type string {
                       pattern "default";
                     }
                     type string {
                     }
                   }
                 }
               }
             }
             case case_2 {
               leaf routing-instance {
                 description "Routing instance of server to which to forward";
                 type union {
                   type string {
                     pattern "default";
                   }
                   type string {
                   }
                 }
               }
             }
           }
         }
         list interface {
           key name;
           ordered-by user;
           description "Incoming request forwarding interface configuration";
           leaf name {
             description "Name of interface or group of interfaces";
             type union {
               type jt:interface-wildcard;
               type string {
                 pattern "<.*>|$.*";
               }
             }
           }
           uses apply-advanced;
           leaf no-listen {
             description "Do not listen on this interface";
             type empty;
           }
           leaf broadcast {
             description "If the layer 2 interface is unknown then broadcast";
             type empty;
           }
           leaf description {
             description "Text description of server";
             type string;
           }
           list server {
             key name;
             ordered-by user;
             description "Server information";
             leaf name {
               description "Name or address of server to which to forward";
               type jt:ipv4addr;
             }
             uses apply-advanced;
             choice instance {
               case case_1 {
                 container logical-system {
                   description "Logical system of server to which to forward";
                   leaf logical-system-name {
                     description "Name of logical system";
                     type string {
                     }
                   }
                   leaf routing-instance {
                     description "Routing instance of server to which to forward";
                     type union {
                       type string {
                         pattern "default";
                       }
                       type string {
                       }
                     }
                   }
                 }
               }
               case case_2 {
                 leaf routing-instance {
                   description "Routing instance of server to which to forward";
                   type union {
                     type string {
                       pattern "default";
                     }
                     type string {
                     }
                   }
                 }
               }
             }
           }
         }
       }
     }
     container family {
       description "Protocol family";
       container inet {
         description "IPv4 parameters";
         uses apply-advanced;
         container filter {
           description "Filtering for forwarding table";
           uses apply-advanced;
           leaf input {
             description "Name of input filter to apply for forwarded packets";
             type string;
           }
           leaf output {
             description "Name of output filter to apply for forwarded packets";
             type string;
           }
         }
       }
       container inet6 {
         description "IPv6 parameters";
         uses apply-advanced;
         container filter {
           description "Filtering for forwarding table";
           uses apply-advanced;
           leaf input {
             description "Name of input filter to apply for forwarded packets";
             type string;
           }
           leaf output {
             description "Name of output filter to apply for forwarded packets";
             type string;
           }
         }
         leaf source-checking {
           description "Discard IPv6 packet when source address type is unspecified, loopback, multicast or link-local ";
           type empty;
         }
       }
       container mpls {
         description "MPLS parameters";
         uses apply-advanced;
         container filter {
           description "Filtering for forwarding table";
           uses apply-advanced;
           leaf input {
             description "Name of input filter to apply for forwarded packets";
             type string;
           }
           leaf output {
             description "Name of output filter to apply for forwarded packets";
             type string;
           }
         }
       }
       container vpls {
         description "VPLS parameters";
         uses apply-advanced;
         container filter {
           description "Filtering for VPLS DMAC forwarding table";
           uses apply-advanced;
           leaf input {
             description "Name of input filter to apply for forwarded packets";
             type string;
           }
         }
         container flood {
           description "Filtering for VPLS flood table";
           uses apply-advanced;
           leaf input {
             description "Name of input filter to apply for VPLS flood packets";
             type string;
           }
         }
       }
       container evpn {
         description "EVPN parameters";
         uses apply-advanced;
         container filter {
           description "Filtering for EVPN DMAC forwarding table";
           uses apply-advanced;
           leaf input {
             description "Name of input filter to apply for forwarded packets";
             type string;
           }
         }
         container flood {
           description "Filtering for EVPN flood table";
           uses apply-advanced;
           leaf input {
             description "Name of input filter to apply for EVPN flood packets";
             type string;
           }
         }
       }
     }
     list next-hop-group {
       key name;
       description "Next hop group forwarding option";
       uses juniper-next-hop-group-options;
     }
     container dhcp-relay {
       description "Dynamic Host Configuration Protocol relay configuration";
       uses jdhcp-relay-type;
     }
     choice load-balance-label-capability-choice {
       leaf load-balance-label-capability {
         description "Load balance label capability";
         type empty;
       }
       leaf no-load-balance-label-capability {
         description "Don't load balance label capability";
         type empty;
       }
     }
     list ip-options-protocol-queue {
       key name;
       ordered-by user;
       description "IP Options protocol logical queue parameters";
       leaf name {
         description "Protocol name";
         type string;
       }
       uses apply-advanced;
       leaf protocol-id {
         description "Protocol Identifier";
         type union {
           type string {
             pattern "<.*>|$.*";
           }
           type uint8 {
             range "1 .. 254";
           }
         }
       }
       leaf queue-depth {
         description "Size of the protocol logical options queue";
         type union {
           type string {
             pattern "<.*>|$.*";
           }
           type uint32 {
             range "1 .. 807";
           }
         }
       }
     }
     container access-security {
       description "Access security configuration";
       uses jdhcp-access-security-type;
     }
   }
   grouping jdhcp-access-security-type {
     description "Access security configuration";
     uses apply-advanced;
     container router-advertisement-guard {
       presence "enable router-advertisement-guard";
       description "Router Advertisement Guard Configuration";
       uses apply-advanced;
       list policy {
         key name;
         ordered-by user;
         description "Router Advertisement Guard policy";
         leaf name {
           description "Router Advertisement Guard policy name";
           type string {
             length "1 .. 64";
           }
         }
         uses apply-advanced;
         container discard {
           description "Discard parameters";
           uses apply-advanced;
           leaf source-ip-address-list {
             description "IPv6 Source address list name";
             type string;
           }
           leaf source-mac-address-list {
             description "Source mac address list name";
             type string;
           }
           leaf prefix-list-name {
             description "Prefix-list Name";
             type string;
           }
         }
         container accept {
           description "Accept parameters";
           uses apply-advanced;
           container match-list {
             description "List of parameters to check";
             uses apply-advanced;
             leaf source-ip-address-list {
               description "IPv6 Source address list name";
               type string;
             }
             leaf source-mac-address-list {
               description "Source mac address list name";
               type string;
             }
             leaf prefix-list-name {
               description "Prefix-list Name";
               type string;
             }
             leaf match-criteria {
               description "Match Criteria";
               type enumeration {
                 enum "match-all" {
                   description "A match from every list";
                 }
                 enum "match-any" {
                   description "A match from any list";
                 }
               }
             }
           }
           container match-options {
             presence "enable match-options";
             description "List of Options to check";
             uses apply-advanced;
             container hop-limit {
               description "Hop limit";
               uses apply-advanced;
               leaf maximum {
                 description "Maximum hop limit";
                 type union {
                   type string {
                     pattern "<.*>|$.*";
                   }
                   type uint32 {
                     range "1 .. 255";
                   }
                 }
               }
               leaf minimum {
                 description "Minimum hop limit";
                 type union {
                   type string {
                     pattern "<.*>|$.*";
                   }
                   type uint32 {
                     range "1 .. 255";
                   }
                 }
               }
             }
             container route-preference {
               description "Accept route preference";
               uses apply-advanced;
               leaf maximum {
                 description "Maximum route preference";
                 type enumeration {
                   enum "low" {
                     description "Route preference low";
                   }
                   enum "medium" {
                     description "Route preference medium";
                   }
                   enum "high" {
                     description "Route preference high";
                   }
                 }
               }
             }
             leaf managed-config-flag {
               description "Check Managed config flag";
               type empty;
             }
             leaf other-config-flag {
               description "Check Other config flag";
               type empty;
             }
           }
         }
       }
       container interface {
         description "RA Guard config on Interface";
         uses apply-advanced;
         list intf-config {
           key name;
           description "Interface Configuration";
           uses interface-policy;
         }
       }
       container vlans {
         description "RA Guard config on Vlan";
         uses apply-advanced;
         list vlan-config {
           key name;
           description "Virtual LAN Configuration";
           uses vlan-policy;
         }
       }
     }
   }
   grouping interface-policy {
     description "Interface Name";
     leaf name {
       description "Interface Name";
       type union {
         type jt:interface-name;
         type string {
           pattern "<.*>|$.*";
         }
       }
     }
     uses apply-advanced;
     container policy {
       description "Attach policy";
       uses apply-advanced;
       leaf policy-name {
         description "Router Advertisement Guard policy name";
         type string;
       }
       choice policy-type {
         case case_1 {
           leaf stateful {
             description "Stateful router advertisement guard";
             type empty;
           }
         }
         case case_2 {
           leaf stateless {
             description "Stateless router advertisement guard";
             type empty;
           }
         }
       }
     }
     container mark-interface {
       description "Mark interface";
       uses apply-advanced;
       choice mark-intf-type {
         case case_1 {
           leaf trusted {
             description "Mark interface trusted";
             type empty;
           }
         }
         case case_2 {
           leaf block {
             description "Block router-advertisement";
             type empty;
           }
         }
       }
     }
   }
   grouping juniper-igmp-snooping-options {
     uses apply-advanced;
     leaf use-p2mp-lsp {
       description "P2MP will be used to forward traffic instead of PW";
       type empty;
     }
     container snoop-pseudowires {
       presence "enable snoop-pseudowires";
       description "VPLS PE would send traffic selectively to PE's having interest";
       uses apply-advanced;
     }
   }
   grouping juniper-mld-snooping-options {
     uses apply-advanced;
     leaf use-p2mp-lsp {
       description "P2MP will be used to forward traffic instead of PW";
       type empty;
     }
     container snoop-pseudowires {
       presence "enable snoop-pseudowires";
       description "VPLS PE would send traffic selectively to PE's having interest";
       uses apply-advanced;
     }
   }
   grouping juniper-next-hop-group-options {
     leaf name {
       description "Next hop group name";
       type string;
     }
     uses apply-advanced;
     leaf group-type {
       description "Next hop group type";
       default "inet";
       type enumeration {
         enum "inet" {
           description "Group of family inet next-hops";
         }
         enum "layer-2" {
           description "Layer-2 next-hop group";
         }
         enum "inet6" {
           description "Group of family inet6 next-hops";
         }
       }
     }
     list interface {
       key name;
       description "Interfaces through which to send sampled traffic";
       uses next_hop_group_intf_type;
     }
     list next-hop-subgroup {
       key name;
       description "Group of interfaces through which to send sampled traffic";
       uses juniper-next-hop-subgroup-options;
     }
   }
   grouping juniper-next-hop-subgroup-options {
     leaf name {
       description "Next-hop sub-group name";
       type string;
     }
     uses apply-advanced;
     list interface {
       key name;
       description "Interface through which to send the sampled traffic";
       max-elements 16;
       uses next_hop_subgroup_intf_type;
     }
   }
   grouping juniper-packet-accounting-options {
     leaf name {
       description "Name for accounting group";
       type string;
     }
     uses apply-advanced;
     container output {
       description "Accounting data disposition";
       uses packet_accounting_output_type;
     }
   }
   grouping juniper-packet-capture-options {
     description "Packet capture options";
     uses apply-advanced;
     choice enable-disable {
       case case_1 {
         leaf disable {
           description "Disable packet-capture";
           type empty;
         }
       }
     }
     container file {
       description "Parameters for file that contains captured packets";
       leaf filename {
         description "Name of file";
         type string {
           length "1 .. 900";
         }
       }
       leaf files {
         description "Maximum number of files";
         default "10";
         type union {
           type string {
             pattern "<.*>|$.*";
           }
           type uint32 {
             range "2 .. 10000";
           }
         }
       }
       leaf size {
         description "Maximum file size";
         type string;
       }
       choice world-readable-choice {
         leaf world-readable {
           description "Allow any user to read packet-capture files";
           type empty;
         }
         leaf no-world-readable {
           description "Don't allow any user to read packet-capture files";
           type empty;
         }
       }
     }
     leaf maximum-capture-size {
       description "Maximum packet size to capture";
       default "68";
       units "bytes";
       type union {
         type string {
           pattern "<.*>|$.*";
         }
         type uint32 {
           range "68 .. 1520";
         }
       }
     }
   }
   grouping juniper-port-mirror-options {
     uses apply-advanced;
     container traceoptions {
       description "Port-mirroring trace options";
       uses sampling_traceoptions_type;
     }
     leaf disable {
       description "Disable the global port-mirroring instance";
       type empty;
     }
     leaf disable-all-instances {
       description "Disable the all port-mirroring instances";
       type empty;
     }
     container input {
       description "Settings for sampling of input packets";
       uses pm_family_input_type;
     }
     container family {
       description "Address family of packets to mirror";
       container inet {
         description "Mirror IPv4 packets";
         uses apply-advanced;
         container input {
           description "Settings for sampling of input packets";
           status deprecated;
           uses pm_family_input_type;
         }
         container output {
           description "One or more next hops for port-mirrored packets";
           uses inet_pm_family_output_type;
         }
       }
       container mpls {
         description "Mirror MPLS packets";
         uses apply-advanced;
         container input {
           description "Settings for sampling of input packets";
           status deprecated;
           uses pm_family_input_type;
         }
         container output {
           description "One or more next hops for port-mirrored packets";
           uses mpls_pm_family_output_type;
         }
       }
       container any {
         description "Mirror any packets";
         uses apply-advanced;
         container output {
           description "One or more next hops for port-mirrored packets";
           uses any_pm_family_output_type;
         }
       }
       container vpls {
         description "Mirror Layer-2 bridged/vpls packets";
         uses apply-advanced;
         container input {
           description "Settings for sampling of input packets";
           status deprecated;
           uses pm_family_input_type;
         }
         container output {
           description "Destination for port-mirrored packets";
           uses layer2_pm_family_output_type;
         }
       }
       container ccc {
         description "Mirror layer-2 ccc packets";
         uses apply-advanced;
         container input {
           description "Settings for sampling of input packets";
           status deprecated;
           uses pm_family_input_type;
         }
         container output {
           description "Destination for port-mirrored packets";
           uses layer2_pm_family_output_type;
         }
       }
     }
     list instance {
       key name;
       ordered-by user;
       description "Instance of port-mirroring parameters";
       leaf name {
         description "Name for port-mirroring instance";
         type string {
           length "1 .. 63";
         }
       }
       uses apply-advanced;
       leaf disable {
         description "Disable the this port-mirroring instance";
         type empty;
       }
       choice input_params_or_instance {
         case case_1 {
           container input {
             description "Settings for sampling of input packets";
             uses pm_family_input_type;
           }
         }
         case case_2 {
           leaf input-parameters-instance {
             description "Name of port-mirroring instance to use for input parameters";
             type string;
           }
         }
       }
       container family {
         description "Address family of packets to mirror";
         container inet {
           description "Mirror IPv4 packets";
           uses apply-advanced;
           container input {
             description "Settings for sampling of input packets";
             status deprecated;
             uses pm_family_input_type;
           }
           container output {
             description "One or more next hops for port-mirrored packets";
             uses inet_pm_family_output_type;
           }
         }
         container mpls {
           description "Mirror MPLS packets";
           uses apply-advanced;
           container input {
             description "Settings for sampling of input packets";
             status deprecated;
             uses pm_family_input_type;
           }
           container output {
             description "One or more next hops for port-mirrored packets";
             uses mpls_pm_family_output_type;
           }
         }
         container any {
           description "Mirror any packets";
           uses apply-advanced;
           container output {
             description "One or more next hops for port-mirrored packets";
             uses any_pm_family_output_type;
           }
         }
         container vpls {
           description "Mirror Layer-2 bridged/vpls packets";
           uses apply-advanced;
           container input {
             description "Settings for sampling of input packets";
             status deprecated;
             uses pm_family_input_type;
           }
           container output {
             description "Destination for port-mirrored packets";
             uses layer2_pm_family_output_type;
           }
         }
         container ccc {
           description "Mirror layer-2 ccc packets";
           uses apply-advanced;
           container input {
             description "Settings for sampling of input packets";
             status deprecated;
             uses pm_family_input_type;
           }
           container output {
             description "Destination for port-mirrored packets";
             uses layer2_pm_family_output_type;
           }
         }
       }
     }
   }
   grouping any_pm_family_output_type {
     uses apply-advanced;
     choice interface-or-next-hop-index {
       case case_1 {
         list interface {
           key name;
           description "Interfaces through which to send sampled traffic";
           uses any_pm_intf_type;
         }
       }
       case case_2 {
       }
     }
     container hosted-service {
       description "Configure Hosted Service";
       uses apply-advanced;
       leaf server-profile {
         description "Server profile name";
         type string {
           length "3 .. 32";
         }
       }
     }
   }
   grouping any_pm_intf_type {
     leaf name {
       description "Interface through which to send sampled traffic";
       type union {
         type jt:interface-name;
         type string {
           pattern "<.*>|$.*";
         }
       }
     }
     uses apply-advanced;
     list next-hop {
       key name;
       ordered-by user;
       description "Address of next hop through which to send sampled traffic";
       uses inet_next_hop_type;
     }
   }
   grouping inet_next_hop_type {
     description "Address of next hop through which to send sampled traffic";
     leaf name {
       type jt:ipv4addr;
     }
     uses apply-advanced;
   }
   grouping inet_pm_family_output_type {
     uses apply-advanced;
     choice interface-or-next-hop-index {
       case case_1 {
         list interface {
           key name;
           description "Interfaces through which to send sampled traffic";
           uses inet_pm_intf_type;
         }
       }
       case case_2 {
       }
     }
     leaf no-filter-check {
       description "Do not check for filters on port-mirroring interface";
       type empty;
     }
     leaf ip-address {
       description "ERSPAN Destination IP Address";
       type jt:ipv4addr;
     }
   }
   grouping inet_pm_intf_type {
     leaf name {
       description "Interface through which to send sampled traffic";
       type union {
         type jt:interface-name;
         type string {
           pattern "<.*>|$.*";
         }
       }
     }
     uses apply-advanced;
     list next-hop {
       key name;
       ordered-by user;
       description "Address of next hop through which to send sampled traffic";
       uses inet_next_hop_type;
     }
   }
   grouping juniper-protocols-l2vpn {
     description "Layer 2 VPN, VPLS or EVPN configuration";
     uses apply-advanced;
     container traceoptions {
       description "Trace options for Layer 2 VPNs";
       uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "error" {
               description "Trace errors";
             }
             enum "topology" {
               description "Trace Layer 2 VPN, VPLS and EVPN topology changes";
             }
             enum "nlri" {
               description "Trace Layer 2 VPN, VPLS and EVPN remote site advertisements";
             }
             enum "connections" {
               description "Trace Layer 2 VPN and VPLS connections";
             }
             enum "automatic-site" {
               description "Trace VPLS automatic site state";
             }
             enum "oam" {
               description "Trace OAM messages";
             }
             enum "mac-database" {
               description "Trace MAC route database in a EVPN instance";
             }
             enum "nsr" {
               description "Trace NSR in a EVPN instance";
             }
             enum "egress-protection" {
               description "Trace Edge Protection messages";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     leaf encapsulation-type {
       description "Encapsulation type for VPN";
       type enumeration {
         enum "atm-aal5" {
           description "ATM AAL/5 encapsulation";
         }
         enum "atm-cell" {
           description "ATM port promiscuous mode cell encapsulation";
         }
         enum "atm-cell-port-mode" {
           description "ATM port promiscuous mode cell encapsulation";
         }
         enum "atm-cell-vp-mode" {
           description "ATM VP promiscuous mode cell encapsulation";
         }
         enum "atm-cell-vc-mode" {
           description "ATM non-promiscuous cell encapsulation";
         }
         enum "frame-relay" {
           description "Frame Relay encapsulation";
         }
         enum "ppp" {
           description "PPP encapsulation";
         }
         enum "cisco-hdlc" {
           description "Cisco-compatible HDLC encapsulation";
         }
         enum "ethernet-vlan" {
           description "Ethernet VLAN encapsulation";
         }
         enum "ethernet" {
           description "Ethernet encapsulation";
         }
         enum "interworking" {
           description "Layer 2.5 interworking VPN";
         }
         enum "frame-relay-port-mode" {
           description "Frame Relay port mode encapsulation";
         }
         enum "satop-t1" {
           description "SATOP-T1 based Layer 2 VPN";
         }
         enum "satop-e1" {
           description "SATOP-E1 based Layer 2 VPN";
         }
         enum "satop-t3" {
           description "SATOP-T3 based Layer 2 VPN";
         }
         enum "satop-e3" {
           description "SATOP-E3 based Layer 2 VPN";
         }
         enum "cesop" {
           description "CESOP based Layer 2 VPN";
         }
       }
     }
     choice cword {
       case case_1 {
         leaf control-word {
           description "Add control word to the Layer 2 encapsulation";
           type empty;
         }
       }
       case case_2 {
         leaf no-control-word {
           description "Disables control word on the Layer 2 encapsulation";
           type empty;
         }
       }
     }
     leaf site-range {
       description "Maximum site identifier in this VPLS domain";
       type union {
         type string {
           pattern "<.*>|$.*";
         }
         type uint32 {
           range "1 .. 65534";
         }
       }
     }
     leaf bum-hashing {
       description "Enable BUM hashing feature in the instance";
       type empty;
     }
     leaf mac-pinning {
       description "Enable MAC pinning";
       type empty;
     }
     leaf label-block-size {
       description "Label block size for this VPLS instance";
       type enumeration {
         enum "2" {
           description "Label block size of 2";
         }
         enum "4" {
           description "Label block size of 4";
         }
         enum "8" {
           description "Label block size of 8";
         }
         enum "16" {
           description "Label block size of 16";
         }
       }
     }
     container mac-table-size {
       description "Size of MAC address forwarding table";
       uses apply-advanced;
       leaf limit {
         description "Maximum number of MAC addresses";
         type union {
           type string {
             pattern "<.*>|$.*";
           }
           type uint32;
         }
       }
       leaf packet-action {
         description "Action when MAC limit is reached";
         type enumeration {
           enum "none" {
             description "Forward the packet";
           }
           enum "drop" {
             description "Drop packets and do not learn. Default is forward";
           }
         }
       }
     }
     container mac-ip-table-size {
       description "Size of MAC+IP bindings table";
       uses apply-advanced;
       leaf limit {
         description "Maximum number of MAC+IP bindings";
         type union {
           type string {
             pattern "<.*>|$.*";
           }
           type uint32;
         }
       }
     }
     container interface-mac-limit {
       description "Maximum MAC address learned per interface";
       uses apply-advanced;
       leaf limit {
         description "Maximum number of MAC addresses per interface";
         type union {
           type string {
             pattern "<.*>|$.*";
           }
           type uint32;
         }
       }
       leaf packet-action {
         description "Action when MAC limit is reached";
         type enumeration {
           enum "none" {
             description "Forward the packet";
           }
           enum "drop" {
             description "Drop packets and do not learn. Default is forward";
           }
           enum "log" {
             description "Do not drop the packet but generate an alarm, an SNMP trap or a system log entry";
           }
           enum "shutdown" {
             description "Disable the interface and generate an alarm, an SNMP trap or a system log entry";
           }
           enum "drop-and-log" {
             description "Drop the packet and generate an alarm, an SNMP trap or a system log entry";
           }
         }
       }
     }
     container interface-mac-ip-limit {
       description "Maximum MAC+IP bindings learned per interface";
       uses apply-advanced;
       leaf limit {
         description "Maximum number of MAC+IP bindings per interface";
         type union {
           type string {
             pattern "<.*>|$.*";
           }
           type uint32;
         }
       }
     }
     container mac-notification {
       presence "enable mac-notification";
       description "MAC notification options";
       uses apply-advanced;
       leaf notification-interval {
         description "Interval for sending MAC notifications";
         default "30";
         units "seconds";
         type union {
           type string {
             pattern "<.*>|$.*";
           }
           type uint32 {
             range "1 .. 60";
           }
         }
       }
     }
     leaf mac-table-aging-time {
       description "Delay for discarding MAC address if no updates are received";
       units "seconds";
       type union {
         type string {
           pattern "<.*>|$.*";
         }
         type uint32;
       }
     }
     leaf no-mac-learning {
       description "Disable dynamic MAC address learning";
       type empty;
     }
     leaf no-normalization {
       description "Disable vlan id normalization for interfaces";
       type empty;
     }
     leaf mac-statistics {
       description "Enable MAC address statistics";
       type empty;
     }
     container mib {
       presence "enable mib";
       description "Snmp mib options";
       uses apply-advanced;
       container dot1q-mib {
         presence "enable dot1q-mib";
         description "Dot1q MIB configuration options";
         uses apply-advanced;
         leaf port-list {
           description "Port list for staticegressports and staticuntaggedports MIB";
           type enumeration {
             enum "bit-map" {
               description "Port list is represented in bit-map format";
             }
             enum "string" {
               description "Port list is represented in string format";
             }
           }
         }
       }
     }
     container static-rvtep-mac {
       description "Configure Static MAC and remote VxLAN tunnel endpoint entries";
       uses apply-advanced;
       list mac {
         key "mac_addr remote-vtep";
         description "Unicast MAC address";
         leaf mac_addr {
           type jt:mac-unicast;
         }
         leaf remote-vtep {
           description "Configure static remote VXLAN tunnel endpoints";
           type jt:ipaddr;
         }
       }
     }
     list interface {
       key name;
       ordered-by user;
       description "Interface that connect this site to the VPN";
       leaf name {
         description "Interface name";
         type union {
           type jt:interface-name;
           type string {
             pattern "<.*>|$.*";
           }
         }
       }
       uses apply-advanced;
       container interface-mac-limit {
         description "Maximum number of MAC addresses learned on the interface";
         uses apply-advanced;
         leaf limit {
           description "Maximum number of MAC addresses per interface";
           type union {
             type string {
               pattern "<.*>|$.*";
             }
             type uint32;
           }
         }
         leaf disable {
           description "Disable interface for interface-mac-limit";
           type empty;
         }
         leaf packet-action {
           description "Action when MAC limit is reached";
           type enumeration {
             enum "none" {
               description "Forward the packet";
             }
             enum "drop" {
               description "Drop packets and do not learn. Default is forward";
             }
             enum "log" {
               description "Do not drop the packet but generate an alarm, an SNMP trap or a system log entry";
             }
             enum "shutdown" {
               description "Disable the interface and generate an alarm, an SNMP trap or a system log entry";
             }
             enum "drop-and-log" {
               description "Drop the packet and generate an alarm, an SNMP trap or a system log entry";
             }
           }
         }
       }
       container vpws-service-id {
         presence "enable vpws-service-id";
         description "Service-id for EVPN VPWS routing instance";
         uses apply-advanced;
         leaf local {
           description "Local EVPN VPWS service id";
           type union {
             type string {
               pattern "<.*>|$.*";
             }
             type uint32 {
               range "1 .. 16777215";
             }
           }
         }
         leaf remote {
           description "Remote EVPN VPWS service id";
           type union {
             type string {
               pattern "<.*>|$.*";
             }
             type uint32 {
               range "1 .. 16777215";
             }
           }
         }
       }
       leaf protect-interface {
         description "Name of protect interface";
         type union {
           type jt:interface-name;
           type string {
             pattern "<.*>|$.*";
           }
         }
       }
       leaf action-priority {
         description "Blocking priority of this interface on mac move detection";
         type union {
           type string {
             pattern "<.*>|$.*";
           }
           type uint32 {
             range "0 .. 8";
           }
         }
       }
       leaf remote-site-id {
         description "Site identifier associated with this interface";
         type union {
           type string {
             pattern "<.*>|$.*";
           }
           type uint32 {
             range "1 .. 65534";
           }
         }
       }
       leaf target-attachment-identifier {
         description "FEC 129 VPWS target attachment identifier";
         type string {
         }
       }
       leaf flow-label-transmit {
         description "Advertise capability to push Flow Label in transmit direction to remote PE";
         type empty;
       }
       leaf flow-label-receive {
         description "Advertise capability to push Flow Label in receive direction to remote PE";
         type empty;
       }
       leaf encapsulation-type {
         description "Encapsulation type for VPN";
         type enumeration {
           enum "atm-aal5" {
             description "ATM AAL/5 encapsulation";
           }
           enum "atm-cell" {
             description "ATM port promiscuous mode cell encapsulation";
           }
           enum "atm-cell-port-mode" {
             description "ATM port promiscuous mode cell encapsulation";
           }
           enum "atm-cell-vp-mode" {
             description "ATM VP promiscuous mode cell encapsulation";
           }
           enum "atm-cell-vc-mode" {
             description "ATM non-promiscuous cell encapsulation";
           }
           enum "frame-relay" {
             description "Frame Relay encapsulation";
           }
           enum "ppp" {
             description "PPP encapsulation";
           }
           enum "cisco-hdlc" {
             description "Cisco-compatible HDLC encapsulation";
           }
           enum "ethernet-vlan" {
             description "Ethernet VLAN encapsulation";
           }
           enum "ethernet" {
             description "Ethernet encapsulation";
           }
           enum "interworking" {
             description "Layer 2.5 interworking VPN";
           }
           enum "frame-relay-port-mode" {
             description "Frame Relay port mode encapsulation";
           }
           enum "satop-t1" {
             description "SATOP-T1 based Layer 2 VPN";
           }
           enum "satop-e1" {
             description "SATOP-E1 based Layer 2 VPN";
           }
           enum "satop-t3" {
             description "SATOP-T3 based Layer 2 VPN";
           }
           enum "satop-e3" {
             description "SATOP-E3 based Layer 2 VPN";
           }
           enum "cesop" {
             description "CESOP based Layer 2 VPN";
           }
         }
       }
       leaf ignore-encapsulation-mismatch {
         description "Allow different encapsulation types on local and remote end";
         type empty;
       }
       leaf mtu {
         description "MTU to be advertised to the remote end";
         type union {
           type string {
             pattern "<.*>|$.*";
           }
           type uint16 {
             range "512 .. 65535";
           }
         }
       }
       leaf ignore-mtu-mismatch {
         description "Allow different MTU values on local and remote end";
         type empty;
       }
       choice cword {
         case case_1 {
           leaf control-word {
             description "Adds control-word to the Layer 2 encapsulation";
             type empty;
           }
         }
         case case_2 {
           leaf no-control-word {
             description "Disables control-word to the Layer 2 encapsulation";
             type empty;
           }
         }
       }
       leaf pseudowire-status-tlv {
         description "Send pseudowire status TLV";
         type empty;
       }
       container oam {
         description "OAM Configuration for VPN";
         uses apply-advanced;
         leaf ping-interval {
           description "Time interval between ping messages";
           default "60";
           units "seconds";
           type union {
             type string {
               pattern "<.*>|$.*";
             }
             type uint16 {
               range "30 .. 3600";
             }
           }
         }
         leaf ping-multiplier {
           description "Number of ping reply missed before declaring BFD down";
           type union {
             type string {
               pattern "<.*>|$.*";
             }
             type uint8 {
               range "1 .. 5";
             }
           }
         }
         container bfd-liveness-detection {
           description "Bidirectional Forwarding Detection (BFD) options";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
         }
       }
       leaf community {
         description "Community associated with this interface";
         type string;
       }
       list static-mac {
         key name;
         ordered-by user;
         description "Static MAC addresses assigned to this interface";
         leaf name {
           description "MAC address";
           type jt:mac-addr;
         }
         uses apply-advanced;
         list vlan-id {
           key name;
           ordered-by user;
           description "VLAN ID of learning VLAN";
           leaf name {
             description "Learning VLAN";
             type union {
               type string {
                 pattern "<.*>|$.*";
               }
               type uint32 {
                 range "0 .. 4094";
               }
             }
           }
           uses apply-advanced;
         }
       }
       container interface-mac-ip-limit {
         description "Maximum number of MAC+IP bindings learned on the interface";
         uses apply-advanced;
         leaf limit {
           description "Maximum number of MAC+IP bindings per interface";
           type union {
             type string {
               pattern "<.*>|$.*";
             }
             type uint32;
           }
         }
       }
       leaf no-mac-learning {
         description "Disable dynamic MAC address learning";
         type empty;
       }
       leaf mac-pinning {
         description "Enable MAC pinning";
         type empty;
       }
       leaf description {
         description "Text description";
         type string;
       }
       leaf persistent-learning {
         description "Enable persistent MAC learning on this interface";
         type empty;
       }
     }
     choice tunnel-services-choice {
       case case_1 {
         container tunnel-services {
           description "Use tunnel services for this VPLS instance";
           uses apply-advanced;
           leaf-list devices {
             ordered-by user;
             description "Tunnel services devices to use for this VPLS instance";
             type union {
               type jt:interface-device;
               type string {
                 pattern "<.*>|$.*";
               }
             }
           }
           leaf primary {
             description "Primary tunnel services device to use for VPLS instance";
             type union {
               type jt:interface-device;
               type string {
                 pattern "<.*>|$.*";
               }
             }
           }
         }
       }
       case case_2 {
         leaf no-tunnel-services {
           description "Do not use tunnel services for this VPLS instance";
           type empty;
         }
       }
     }
     list site {
       key name;
       ordered-by user;
       description "Sites connected to this provider equipment";
       leaf name {
         description "Name of Layer 2 VPN or VPLS site";
         type string;
       }
       uses apply-advanced;
       choice site-identifier-mode {
         case case_1 {
           leaf site-identifier {
             description "Layer 2 VPN or VPLS site identifier (unique in the VPN)";
             type union {
               type string {
                 pattern "<.*>|$.*";
               }
               type uint32 {
                 range "1 .. 65534";
               }
             }
           }
         }
         case case_2 {
           container automatic-site-id {
             presence "enable automatic-site-id";
             description "Enable automatic assignment of site identifier";
             uses apply-advanced;
             leaf startup-wait-time {
               description "Time to wait at startup before claming a site identifier (seconds)";
               units "seconds";
               type union {
                 type string {
                   pattern "<.*>|$.*";
                 }
                 type uint32 {
                   range "1 .. 3600";
                 }
               }
             }
             leaf new-site-wait-time {
               description "Time to wait before claiming a site identifier";
               units "seconds";
               type union {
                 type string {
                   pattern "<.*>|$.*";
                 }
                 type uint32 {
                   range "1 .. 3600";
                 }
               }
             }
             leaf collision-detect-time {
               description "Time to wait for detecting a collision";
               units "seconds";
               type union {
                 type string {
                   pattern "<.*>|$.*";
                 }
                 type uint32 {
                   range "1 .. 3600";
                 }
               }
             }
             container reclaim-wait-time {
               presence "enable reclaim-wait-time";
               description "Time to wait for reclaiming a site identifier";
               leaf minimum {
                 description "Minimum wait time";
                 units "milliseconds";
                 type union {
                   type uint32;
                   type string {
                     pattern "<.*>|$.*";
                   }
                 }
               }
               leaf maximum {
                 description "Maximum wait time";
                 units "milliseconds";
                 type union {
                   type uint32;
                   type string {
                     pattern "<.*>|$.*";
                   }
                 }
               }
             }
           }
         }
       }
       leaf source-attachment-identifier {
         description "FEC 129 VPWS source attachment identifier";
         type string {
         }
       }
       leaf flow-label-transmit {
         description "Advertise capability to push Flow Label in transmit direction to remote PE";
         type empty;
       }
       leaf flow-label-receive {
         description "Advertise capability to push Flow Label in receive direction to remote PE";
         type empty;
       }
       leaf encapsulation-type {
         description "Encapsulation type for VPN";
         type enumeration {
           enum "atm-aal5" {
             description "ATM AAL/5 encapsulation";
           }
           enum "atm-cell" {
             description "ATM port promiscuous mode cell encapsulation";
           }
           enum "atm-cell-port-mode" {
             description "ATM port promiscuous mode cell encapsulation";
           }
           enum "atm-cell-vp-mode" {
             description "ATM VP promiscuous mode cell encapsulation";
           }
           enum "atm-cell-vc-mode" {
             description "ATM non-promiscuous cell encapsulation";
           }
           enum "frame-relay" {
             description "Frame Relay encapsulation";
           }
           enum "ppp" {
             description "PPP encapsulation";
           }
           enum "cisco-hdlc" {
             description "Cisco-compatible HDLC encapsulation";
           }
           enum "ethernet-vlan" {
             description "Ethernet VLAN encapsulation";
           }
           enum "ethernet" {
             description "Ethernet encapsulation";
           }
           enum "interworking" {
             description "Layer 2.5 interworking VPN";
           }
           enum "frame-relay-port-mode" {
             description "Frame Relay port mode encapsulation";
           }
           enum "satop-t1" {
             description "SATOP-T1 based Layer 2 VPN";
           }
           enum "satop-e1" {
             description "SATOP-E1 based Layer 2 VPN";
           }
           enum "satop-t3" {
             description "SATOP-T3 based Layer 2 VPN";
           }
           enum "satop-e3" {
             description "SATOP-E3 based Layer 2 VPN";
           }
           enum "cesop" {
             description "CESOP based Layer 2 VPN";
           }
         }
       }
       leaf ignore-encapsulation-mismatch {
         description "Allow different encapsulation types on local and remote end";
         type empty;
       }
       choice cword {
         case case_1 {
           leaf control-word {
             description "Adds control-word to the Layer 2 encapsulation";
             type empty;
           }
         }
         case case_2 {
           leaf no-control-word {
             description "Disables control-word to the Layer 2 encapsulation";
             type empty;
           }
         }
       }
       leaf pseudowire-status-tlv {
         description "Send pseudowire status TLV";
         type empty;
       }
       container oam {
         description "OAM Configuration for VPN";
         uses apply-advanced;
         leaf ping-interval {
           description "Time interval between ping messages";
           default "60";
           units "seconds";
           type union {
             type string {
               pattern "<.*>|$.*";
             }
             type uint16 {
               range "30 .. 3600";
             }
           }
         }
         leaf ping-multiplier {
           description "Number of ping reply missed before declaring BFD down";
           type union {
             type string {
               pattern "<.*>|$.*";
             }
             type uint8 {
               range "1 .. 5";
             }
           }
         }
         container bfd-liveness-detection {
           description "Bidirectional Forwarding Detection (BFD) options";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
         }
       }
       leaf community {
         description "Community associated with this site";
         type string;
       }
       container multi-homing {
         presence "enable multi-homing";
         description "Enable multi-homing functionality for this site";
         uses apply-advanced;
         leaf hold-time {
           description "Enable multi-homing non-designated forwarder hold time (seconds)";
           units "seconds";
           type union {
             type string {
               pattern "<.*>|$.*";
             }
             type uint32 {
               range "1 .. 18000";
             }
           }
         }
       }
       leaf mac-pinning {
         description "Enable MAC pinning";
         type empty;
       }
       leaf site-preference {
         description "Layer 2 VPN or VPLS site preference";
         type string;
       }
       leaf hot-standby {
         description "Keep backup pseudowire in continuous standby mode and ready for traffic forwarding";
         type empty;
       }
       leaf mtu {
         description "MTU to be advertised to the remote end";
         type union {
           type string {
             pattern "<.*>|$.*";
           }
           type uint16 {
             range "512 .. 65535";
           }
         }
       }
       leaf ignore-mtu-mismatch {
         description "Allow different MTU values on local and remote end";
         type empty;
       }
       list mesh-group {
         key name;
         ordered-by user;
         description "Mesh-groups that are part of this site";
         leaf name {
           description "Mesh-group name";
           type string;
         }
         uses apply-advanced;
       }
       container active-interface {
         description "Configure interface to designate as active";
         choice interface_name {
           case case_1 {
             leaf any {
               description "One configured interface is designated active at random";
               type empty;
             }
           }
           case case_2 {
             leaf primary {
               description "Interface to designate as active if it is operational";
               type union {
                 type jt:interface-name;
                 type string {
                   pattern "<.*>|$.*";
                 }
               }
             }
           }
         }
       }
       leaf best-site {
         description "Activates best-site functionality for this instance";
         type empty;
       }
       list interface {
         key name;
         ordered-by user;
         description "Interface that connect this site to the VPN";
         leaf name {
           description "Interface name";
           type union {
             type jt:interface-name;
             type string {
               pattern "<.*>|$.*";
             }
           }
         }
         uses apply-advanced;
         container interface-mac-limit {
           description "Maximum number of MAC addresses learned on the interface";
           uses apply-advanced;
           leaf limit {
             description "Maximum number of MAC addresses per interface";
             type union {
               type string {
                 pattern "<.*>|$.*";
               }
               type uint32;
             }
           }
           leaf disable {
             description "Disable interface for interface-mac-limit";
             type empty;
           }
           leaf packet-action {
             description "Action when MAC limit is reached";
             type enumeration {
               enum "none" {
                 description "Forward the packet";
               }
               enum "drop" {
                 description "Drop packets and do not learn. Default is forward";
               }
               enum "log" {
                 description "Do not drop the packet but generate an alarm, an SNMP trap or a system log entry";
               }
               enum "shutdown" {
                 description "Disable the interface and generate an alarm, an SNMP trap or a system log entry";
               }
               enum "drop-and-log" {
                 description "Drop the packet and generate an alarm, an SNMP trap or a system log entry";
               }
             }
           }
         }
         container vpws-service-id {
           presence "enable vpws-service-id";
           description "Service-id for EVPN VPWS routing instance";
           uses apply-advanced;
           leaf local {
             description "Local EVPN VPWS service id";
             type union {
               type string {
                 pattern "<.*>|$.*";
               }
               type uint32 {
                 range "1 .. 16777215";
               }
             }
           }
           leaf remote {
             description "Remote EVPN VPWS service id";
             type union {
               type string {
                 pattern "<.*>|$.*";
               }
               type uint32 {
                 range "1 .. 16777215";
               }
             }
           }
         }
         leaf protect-interface {
           description "Name of protect interface";
           type union {
             type jt:interface-name;
             type string {
               pattern "<.*>|$.*";
             }
           }
         }
         leaf action-priority {
           description "Blocking priority of this interface on mac move detection";
           type union {
             type string {
               pattern "<.*>|$.*";
             }
             type uint32 {
               range "0 .. 8";
             }
           }
         }
         leaf remote-site-id {
           description "Site identifier associated with this interface";
           type union {
             type string {
               pattern "<.*>|$.*";
             }
             type uint32 {
               range "1 .. 65534";
             }
           }
         }
         leaf target-attachment-identifier {
           description "FEC 129 VPWS target attachment identifier";
           type string {
           }
         }
         leaf flow-label-transmit {
           description "Advertise capability to push Flow Label in transmit direction to remote PE";
           type empty;
         }
         leaf flow-label-receive {
           description "Advertise capability to push Flow Label in receive direction to remote PE";
           type empty;
         }
         leaf encapsulation-type {
           description "Encapsulation type for VPN";
           type enumeration {
             enum "atm-aal5" {
               description "ATM AAL/5 encapsulation";
             }
             enum "atm-cell" {
               description "ATM port promiscuous mode cell encapsulation";
             }
             enum "atm-cell-port-mode" {
               description "ATM port promiscuous mode cell encapsulation";
             }
             enum "atm-cell-vp-mode" {
               description "ATM VP promiscuous mode cell encapsulation";
             }
             enum "atm-cell-vc-mode" {
               description "ATM non-promiscuous cell encapsulation";
             }
             enum "frame-relay" {
               description "Frame Relay encapsulation";
             }
             enum "ppp" {
               description "PPP encapsulation";
             }
             enum "cisco-hdlc" {
               description "Cisco-compatible HDLC encapsulation";
             }
             enum "ethernet-vlan" {
               description "Ethernet VLAN encapsulation";
             }
             enum "ethernet" {
               description "Ethernet encapsulation";
             }
             enum "interworking" {
               description "Layer 2.5 interworking VPN";
             }
             enum "frame-relay-port-mode" {
               description "Frame Relay port mode encapsulation";
             }
             enum "satop-t1" {
               description "SATOP-T1 based Layer 2 VPN";
             }
             enum "satop-e1" {
               description "SATOP-E1 based Layer 2 VPN";
             }
             enum "satop-t3" {
               description "SATOP-T3 based Layer 2 VPN";
             }
             enum "satop-e3" {
               description "SATOP-E3 based Layer 2 VPN";
             }
             enum "cesop" {
               description "CESOP based Layer 2 VPN";
             }
           }
         }
         leaf ignore-encapsulation-mismatch {
           description "Allow different encapsulation types on local and remote end";
           type empty;
         }
         leaf mtu {
           description "MTU to be advertised to the remote end";
           type union {
             type string {
               pattern "<.*>|$.*";
             }
             type uint16 {
               range "512 .. 65535";
             }
           }
         }
         leaf ignore-mtu-mismatch {
           description "Allow different MTU values on local and remote end";
           type empty;
         }
         choice cword {
           case case_1 {
             leaf control-word {
               description "Adds control-word to the Layer 2 encapsulation";
               type empty;
             }
           }
           case case_2 {
             leaf no-control-word {
               description "Disables control-word to the Layer 2 encapsulation";
               type empty;
             }
           }
         }
         leaf pseudowire-status-tlv {
           description "Send pseudowire status TLV";
           type empty;
         }
         container oam {
           description "OAM Configuration for VPN";
           uses apply-advanced;
           leaf ping-interval {
             description "Time interval between ping messages";
             default "60";
             units "seconds";
             type union {
               type string {
                 pattern "<.*>|$.*";
               }
               type uint16 {
                 range "30 .. 3600";
               }
             }
           }
           leaf ping-multiplier {
             description "Number of ping reply missed before declaring BFD down";
             type union {
               type string {
                 pattern "<.*>|$.*";
               }
               type uint8 {
                 range "1 .. 5";
               }
             }
           }
           container bfd-liveness-detection {
             description "Bidirectional Forwarding Detection (BFD) options";
             uses apply-advanced;
             leaf version {
               description "BFD protocol version number";
               default "automatic";
               type enumeration {
                 enum "0" {
                   description "BFD version 0 (deprecated)";
                 }
                 enum "1" {
                   description "BFD version 1";
                 }
                 enum "automatic" {
                   description "Choose BFD version automatically";
                 }
               }
             }
             leaf minimum-interval {
               description "Minimum transmit and receive interval";
               units "milliseconds";
               type union {
                 type string {
                   pattern "<.*>|$.*";
                 }
                 type uint32 {
                   range "1 .. 255000";
                 }
               }
             }
             leaf minimum-transmit-interval {
               description "Minimum transmit interval";
               status deprecated;
               units "milliseconds";
               type union {
                 type string {
                   pattern "<.*>|$.*";
                 }
                 type uint32 {
                   range "1 .. 255000";
                 }
               }
             }
             leaf minimum-receive-interval {
               description "Minimum receive interval";
               units "milliseconds";
               type union {
                 type string {
                   pattern "<.*>|$.*";
                 }
                 type uint32 {
                   range "1 .. 255000";
                 }
               }
             }
             leaf multiplier {
               description "Detection time multiplier";
               default "3";
               type union {
                 type string {
                   pattern "<.*>|$.*";
                 }
                 type uint32 {
                   range "1 .. 255";
                 }
               }
             }
             choice adaptation-choice {
               case case_1 {
                 leaf no-adaptation {
                   description "Disable adaptation";
                   type empty;
                 }
               }
             }
             container transmit-interval {
               description "Transmit-interval options";
               uses apply-advanced;
               leaf minimum-interval {
                 description "Minimum transmit interval";
                 units "milliseconds";
                 type union {
                   type string {
                     pattern "<.*>|$.*";
                   }
                   type uint32 {
                     range "1 .. 255000";
                   }
                 }
               }
               leaf threshold {
                 description "High transmit interval triggering a trap";
                 units "milliseconds";
                 type union {
                   type uint32;
                   type string {
                     pattern "<.*>|$.*";
                   }
                 }
               }
             }
             container detection-time {
               description "Detection-time options";
               uses apply-advanced;
               leaf threshold {
                 description "High detection-time triggering a trap";
                 units "milliseconds";
                 type union {
                   type uint32;
                   type string {
                     pattern "<.*>|$.*";
                   }
                 }
               }
             }
           }
         }
         leaf community {
           description "Community associated with this interface";
           type string;
         }
         list static-mac {
           key name;
           ordered-by user;
           description "Static MAC addresses assigned to this interface";
           leaf name {
             description "MAC address";
             type jt:mac-addr;
           }
           uses apply-advanced;
           list vlan-id {
             key name;
             ordered-by user;
             description "VLAN ID of learning VLAN";
             leaf name {
               description "Learning VLAN";
               type union {
                 type string {
                   pattern "<.*>|$.*";
                 }
                 type uint32 {
                   range "0 .. 4094";
                 }
               }
             }
             uses apply-advanced;
           }
         }
         container interface-mac-ip-limit {
           description "Maximum number of MAC+IP bindings learned on the interface";
           uses apply-advanced;
           leaf limit {
             description "Maximum number of MAC+IP bindings per interface";
             type union {
               type string {
                 pattern "<.*>|$.*";
               }
               type uint32;
             }
           }
         }
         leaf no-mac-learning {
           description "Disable dynamic MAC address learning";
           type empty;
         }
         leaf mac-pinning {
           description "Enable MAC pinning";
           type empty;
         }
         leaf description {
           description "Text description";
           type string;
         }
         leaf persistent-learning {
           description "Enable persistent MAC learning on this interface";
           type empty;
         }
       }
     }
     leaf community {
       description "Community associated with this VPLS instance";
       type string;
     }
     leaf vpls-id {
       description "Identifier for this VPLS instance";
       type string;
     }
     leaf mtu {
       description "MTU to be advertised to the remote end";
       type union {
         type string {
           pattern "<.*>|$.*";
         }
         type uint16 {
           range "512 .. 65535";
         }
       }
     }
     leaf ignore-mtu-mismatch {
       description "Allow different MTU values on local and remote end";
       type empty;
     }
     container mac-flush {
       presence "enable mac-flush";
       description "Enables mac-flush processing";
       uses apply-advanced;
       leaf any-interface {
         description "Send mac-flush when any AC interface goes down";
         type empty;
       }
       leaf any-spoke {
         description "Send mac-flush when any spoke pseudo wire goes down";
         type empty;
       }
       leaf propagate {
         description "Propagate mac-flush to the core";
         type empty;
       }
     }
     leaf ignore-encapsulation-mismatch {
       description "Allow different encapsulation types on local and remote end";
       type empty;
     }
     leaf pseudowire-status-tlv {
       description "Send pseudowire status TLV";
       type empty;
     }
     list neighbor {
       key name;
       ordered-by user;
       description "Neighbor for this VPLS instance";
       leaf name {
         description "Neighbor ID";
         type jt:ipv4addr;
       }
       uses apply-advanced;
       container static {
         presence "enable static";
         description "Configuration of static vpls";
         uses apply-advanced;
         leaf incoming-label {
           description "VPLS incoming static label [1000000 - 1048575] or [29696 - 41983]";
           type union {
             type uint32;
             type string {
               pattern "<.*>|$.*";
             }
           }
         }
         leaf outgoing-label {
           description "VPLS outgoing static label";
           type union {
             type string {
               pattern "<.*>|$.*";
             }
             type uint32 {
               range "16 .. 1048575";
             }
           }
         }
       }
       container associate-profile {
         description "Associate profile options for dynamic IFL";
         uses apply-advanced;
         leaf profile-name {
           description "Associated profile name";
           type string {
             length "1 .. 81";
           }
         }
         leaf profile-variable-set {
           description "Associate dynamic variable set with the profile";
           type string {
             length "1 .. 81";
           }
         }
       }
       leaf psn-tunnel-endpoint {
         description "Endpoint of the transport tunnel on the remote PE";
         type jt:ipv4addr;
       }
       leaf community {
         description "Community associated with this neighbor";
         type string;
       }
       leaf mac-pinning {
         description "Enable MAC pinning";
         type empty;
       }
       leaf encapsulation-type {
         description "Encapsulation type for VPN";
         type enumeration {
           enum "ethernet-vlan" {
             description "Ethernet VLAN encapsulation";
           }
           enum "ethernet" {
             description "Ethernet encapsulation";
           }
         }
       }
       leaf ignore-encapsulation-mismatch {
         description "Allow different encapsulation types on local and remote end";
         type empty;
       }
       container pseudowire-status-tlv {
         presence "enable pseudowire-status-tlv";
         description "Send pseudowire status TLV";
         uses apply-advanced;
         leaf hot-standby-vc-on {
           description "Activate pseudowire upon arrival of 'hot-standby' status TLV message";
           type empty;
         }
       }
       leaf switchover-delay {
         description "Pseudowire switchover delay ";
         default "10000";
         units "milliseconds";
         type union {
           type string {
             pattern "<.*>|$.*";
           }
           type uint32 {
             range "0 .. 180000";
           }
         }
       }
       container revert-time {
         presence "enable revert-time";
         description "Enable pseudowire redundancy reversion (seconds)";
         leaf delay {
           description "Reversion timer (seconds)";
           units "seconds";
           type union {
             type string {
               pattern "<.*>|$.*";
             }
             type uint32 {
               range "0 .. 600";
             }
           }
         }
         leaf maximum {
           description "Maximum reversion interval to add over revert-time delay";
           units "seconds";
           type union {
             type string {
               pattern "<.*>|$.*";
             }
             type uint32 {
               range "0 .. 1200";
             }
           }
         }
       }
       leaf connection-protection {
         description "End-2-end protection via OAM failure detection";
         type empty;
       }
       list backup-neighbor {
         key name;
         ordered-by user;
         description "Configuration of redundant l2circuit";
         leaf name {
           description "Neighbor ID";
           type jt:ipv4addr;
         }
         uses apply-advanced;
         container static {
           presence "enable static";
           description "Configuration of static vpls";
           uses apply-advanced;
           leaf incoming-label {
             description "VPLS incoming static label [1000000 - 1048575] or [29696 - 41983]";
             type union {
               type uint32;
               type string {
                 pattern "<.*>|$.*";
               }
             }
           }
           leaf outgoing-label {
             description "VPLS outgoing static label";
             type union {
               type string {
                 pattern "<.*>|$.*";
               }
               type uint32 {
                 range "16 .. 1048575";
               }
             }
           }
         }
         leaf community {
           description "Community associated with this Layer 2 circuit";
           type string;
         }
         leaf psn-tunnel-endpoint {
           description "Endpoint of the transport tunnel on the remote PE";
           type jt:ipv4addr;
         }
         leaf standby {
           description "Keep backup pseudowire in continuous standby";
           type empty;
         }
         leaf hot-standby {
           description "Keep backup pseudowire in continuous standby mode and ready for traffic forwarding";
           type empty;
         }
       }
     }
     leaf flow-label-transmit {
       description "Advertise capability to push Flow Label in transmit direction to remote PE";
       type empty;
     }
     leaf flow-label-receive {
       description "Advertise capability to pop Flow Label in receive direction to remote PE";
       type empty;
     }
     leaf flow-label-transmit-static {
       description "Push Flow Label on PW packets sent to remote PE";
       type empty;
     }
     leaf flow-label-receive-static {
       description "Pop Flow Label from PW packets received from remote PE";
       type empty;
     }
     container associate-profile {
       description "Associate profile options for dynamic IFL";
       uses apply-advanced;
       leaf profile-name {
         description "Associated profile name";
         type string {
           length "1 .. 81";
         }
       }
       leaf profile-variable-set {
         description "Associate dynamic variable set with the profile";
         type string {
           length "1 .. 81";
         }
       }
     }
     list mesh-group {
       key name;
       description "Mesh-group under this VPLS instance";
       leaf name {
         description "Mesh-group name";
         type string {
         }
       }
       uses apply-advanced;
       container associate-profile {
         description "Associate profile options for dynamic IFL";
         uses apply-advanced;
         leaf profile-name {
           description "Associated profile name";
           type string {
             length "1 .. 81";
           }
         }
         leaf profile-variable-set {
           description "Associate dynamic variable set with the profile";
           type string {
             length "1 .. 81";
           }
         }
       }
       choice peer-as-choice {
         case case_1 {
           container peer-as {
             description "Autonomous system of the peer";
             uses apply-advanced;
             leaf all {
               description "Include peers from all autonomous systems";
               type empty;
             }
           }
         }
       }
       leaf vpls-id {
         description "LDP VPLS Identifier for this mesh-group";
         type string;
       }
       container mac-flush {
         presence "enable mac-flush";
         description "Enables mac-flush processing";
         uses apply-advanced;
         leaf any-interface {
           description "Send mac-flush when any AC interface goes down";
           type empty;
         }
         leaf any-spoke {
           description "Send mac-flush when any spoke pseudo wire goes down";
           type empty;
         }
         leaf propagate {
           description "Propagate mac-flush to the core";
           type empty;
         }
       }
       leaf local-switching {
         description "Allow local-switching within interfaces in this mesh-group";
         type empty;
       }
       list neighbor {
         key name;
         ordered-by user;
         description "Neighbor belonging to this mesh-group";
         leaf name {
           description "Neighbor ID";
           type jt:ipv4addr;
         }
         uses apply-advanced;
         container static {
           presence "enable static";
           description "Configuration of static vpls";
           uses apply-advanced;
           leaf incoming-label {
             description "VPLS incoming static label [1000000 - 1048575] or [29696 - 41983]";
             type union {
               type uint32;
               type string {
                 pattern "<.*>|$.*";
               }
             }
           }
           leaf outgoing-label {
             description "VPLS outgoing static label";
             type union {
               type string {
                 pattern "<.*>|$.*";
               }
               type uint32 {
                 range "16 .. 1048575";
               }
             }
           }
         }
         container associate-profile {
           description "Associate profile options for dynamic IFL";
           uses apply-advanced;
           leaf profile-name {
             description "Associated profile name";
             type string {
               length "1 .. 81";
             }
           }
           leaf profile-variable-set {
             description "Associate dynamic variable set with the profile";
             type string {
               length "1 .. 81";
             }
           }
         }
         leaf psn-tunnel-endpoint {
           description "Endpoint of the transport tunnel on the remote PE";
           type jt:ipv4addr;
         }
         leaf community {
           description "Community associated with this neighbor";
           type string;
         }
         leaf mac-pinning {
           description "Enable MAC pinning";
           type empty;
         }
         leaf encapsulation-type {
           description "Encapsulation type for VPN";
           type enumeration {
             enum "ethernet-vlan" {
               description "Ethernet VLAN encapsulation";
             }
             enum "ethernet" {
               description "Ethernet encapsulation";
             }
           }
         }
         leaf ignore-encapsulation-mismatch {
           description "Allow different encapsulation types on local and remote end";
           type empty;
         }
         container pseudowire-status-tlv {
           presence "enable pseudowire-status-tlv";
           description "Send pseudowire status TLV";
           uses apply-advanced;
           leaf hot-standby-vc-on {
             description "Activate pseudowire upon arrival of 'hot-standby' status TLV message";
             type empty;
           }
         }
         leaf switchover-delay {
           description "Pseudowire switchover delay ";
           default "10000";
           units "milliseconds";
           type union {
             type string {
               pattern "<.*>|$.*";
             }
             type uint32 {
               range "0 .. 180000";
             }
           }
         }
         container revert-time {
           presence "enable revert-time";
           description "Enable pseudowire redundancy reversion (seconds)";
           leaf delay {
             description "Reversion timer (seconds)";
             units "seconds";
             type union {
               type string {
                 pattern "<.*>|$.*";
               }
               type uint32 {
                 range "0 .. 600";
               }
             }
           }
           leaf maximum {
             description "Maximum reversion interval to add over revert-time delay";
             units "seconds";
             type union {
               type string {
                 pattern "<.*>|$.*";
               }
               type uint32 {
                 range "0 .. 1200";
               }
             }
           }
         }
         leaf connection-protection {
           description "End-2-end protection via OAM failure detection";
           type empty;
         }
         list backup-neighbor {
           key name;
           ordered-by user;
           description "Configuration of redundant l2circuit";
           leaf name {
             description "Neighbor ID";
             type jt:ipv4addr;
           }
           uses apply-advanced;
           container static {
             presence "enable static";
             description "Configuration of static vpls";
             uses apply-advanced;
             leaf incoming-label {
               description "VPLS incoming static label [1000000 - 1048575] or [29696 - 41983]";
               type union {
                 type uint32;
                 type string {
                   pattern "<.*>|$.*";
                 }
               }
             }
             leaf outgoing-label {
               description "VPLS outgoing static label";
               type union {
                 type string {
                   pattern "<.*>|$.*";
                 }
                 type uint32 {
                   range "16 .. 1048575";
                 }
               }
             }
           }
           leaf community {
             description "Community associated with this Layer 2 circuit";
             type string;
           }
           leaf psn-tunnel-endpoint {
             description "Endpoint of the transport tunnel on the remote PE";
             type jt:ipv4addr;
           }
           leaf standby {
             description "Keep backup pseudowire in continuous standby";
             type empty;
           }
           leaf hot-standby {
             description "Keep backup pseudowire in continuous standby mode and ready for traffic forwarding";
             type empty;
           }
         }
         leaf-list vpls-id-list {
           ordered-by user;
           description "LDP VPLS Identifier list for this neighbor";
           type union {
             type string {
               pattern "<.*>|$.*";
             }
             type uint32 {
               range "1 .. 4294967295";
             }
           }
         }
       }
       list interface {
         key name;
         description "Interfaces belonging to this flood group";
         leaf name {
           description "Interface name";
           type union {
             type jt:interface-name;
             type string {
               pattern "<.*>|$.*";
             }
           }
         }
         uses apply-advanced;
       }
       container route-distinguisher {
         description "Route distinguisher for this mesh-group";
         leaf rd-type {
           description "Number in (16 bit:32 bit) or (32 bit 'L':16 bit) or (IP address:16 bit) format";
           type string {
           }
         }
       }
     }
     leaf connectivity-type {
       description "Specify type of interface sufficient to bring vpls connection up";
       type enumeration {
         enum "ce" {
           description "CE interface is required";
         }
         enum "irb" {
           description "IRB interface is sufficient";
         }
         enum "permanent" {
           description "Pseudowire permanently up";
         }
       }
     }
     list import-labeled-routes {
       key name;
       ordered-by user;
       description "Import ingress label route to instance.mpls.0 from mpls.0";
       leaf name {
         description "Routing instance name where label route has to be imported";
         type string;
       }
     }
     container multi-homing {
       description "Multi-homing configuration for FEC129 VPLS";
       uses apply-advanced;
       leaf peer-active {
         description "Keep CE interfaces in up state when all BGP peers go down";
         type empty;
       }
       list site {
         key name;
         description "Sites connected to this provider equipment";
         leaf name {
           description "Name of Layer 2 VPN or VPLS site";
           type string;
         }
         uses apply-advanced;
         leaf identifier {
           description "Layer 2 VPN or VPLS multi-homing identifier";
           type union {
             type string {
               pattern "<.*>|$.*";
             }
             type uint16 {
               range "1 .. 65534";
             }
           }
         }
         leaf preference {
           description "Layer 2 VPN or VPLS multi-homing preference";
           type string;
         }
         container active-interface {
           description "Configure interface to designate as active";
           uses apply-advanced;
           choice interface_name {
             case case_1 {
               leaf any {
                 description "One configured interface is designated active at random";
                 type empty;
               }
             }
             case case_2 {
               leaf primary {
                 description "Interface to designate as active if it is operational";
                 type union {
                   type jt:interface-name;
                   type string {
                     pattern "<.*>|$.*";
                   }
                 }
               }
             }
           }
         }
         list interface {
           key name;
           ordered-by user;
           description "Interface that connects this site to the VPN";
           leaf name {
             description "Interface name";
             type union {
               type jt:interface-name;
               type string {
                 pattern "<.*>|$.*";
               }
             }
           }
           uses apply-advanced;
           leaf preference {
             description "Layer 2 VPN or VPLS multi-homing preference for the interface";
             type union {
               type string {
                 pattern "<.*>|$.*";
               }
               type uint16 {
                 range "1 .. 65535";
               }
             }
           }
         }
         leaf peer-active {
           description "Keep CE interfaces in up state when all BGP peers go down";
           type empty;
         }
       }
     }
     container evi-options {
       description "EVI options";
       uses juniper-protocols-evi-options;
     }
     leaf p2mp-bud-support {
       description "Enable EVPN to act as P2MP transit and egress PE (bud)";
       type empty;
     }
     container remote-ip-host-routes {
       presence "enable remote-ip-host-routes";
       description "Virtual machine traffic optimization(VMTO) for EVPN";
       uses apply-advanced;
       leaf-list import {
         ordered-by user;
         description "Policy to control the creation of remote IP host routes";
         type jt:policy-algebra;
       }
     }
     leaf pbb-evpn-core {
       description "Configure PBB EVPN core";
       type empty;
     }
     leaf label-allocation {
       description "Label allocation policy";
       type enumeration {
         enum "per-instance" {
           description "Allocate one label for the entire instance";
         }
       }
     }
     container proxy-mac {
       description "Proxy MAC settings";
       uses apply-advanced;
       leaf irb {
         description "Reply with virtual-gateway MAC or IRB MAC";
         type empty;
       }
       leaf proxy-mac-address {
         description "Reply with configured MAC for all requests";
         type jt:mac-unicast;
       }
     }
     leaf designated-forwarder-election-hold-time {
       description "Time to wait before electing a DF(seconds)";
       units "seconds";
       type union {
         type string {
           pattern "<.*>|$.*";
         }
         type uint32 {
           range "1 .. 1800";
         }
       }
     }
     leaf evpn-etree {
       description "Evpn etree mode";
       type empty;
     }
     leaf igmp-id {
       description "EVPN IGMP Identifier value";
       type union {
         type string {
           pattern "<.*>|$.*";
         }
         type uint32 {
           range "1 .. 65535";
         }
       }
     }
     leaf designated-forwarder-preference-least {
       description "Use least preference in DF election";
       type empty;
     }
     container assisted-replication {
       description "Option to enable Assisted Replication";
       uses apply-advanced;
       choice AR {
         case case_1 {
           container leaf {
             presence "enable leaf";
             description "Assisted Replicator Leaf";
             uses apply-advanced;
             leaf replicator-activation-delay {
               description "Dealy interval in starting replication";
               default "10";
               units "seconds";
               type union {
                 type string {
                   pattern "<.*>|$.*";
                 }
                 type uint32 {
                   range "0 .. 180";
                 }
               }
             }
           }
         }
         case case_2 {
         }
       }
     }
     leaf encapsulation {
       description "Encapsulation type for EVPN";
       default "mpls";
       type enumeration {
         enum "mpls" {
           description "MPLS encapsulation";
         }
         enum "vxlan" {
           description "VXLAN encapsulation";
         }
       }
     }
     choice extended-attributes {
       case case_1 {
         leaf-list extended-vlan-list {
           description "List of VLAN identifiers that are to be EVPN extended";
           type jt:vlan-range;
         }
       }
       case case_2 {
         leaf-list extended-vni-list {
           description "List of VNI identifiers (1..16777214) or all, that are to be EVPN extended";
           type string;
         }
       }
       case case_3 {
         leaf-list extended-isid-list {
           description "Configure list of isids or all for extending to PBB EVPN";
           type string;
         }
       }
     }
     container vni-options {
       description "VNI options";
       uses apply-advanced;
       list vni {
         key name;
         description "Per-vni options";
         leaf name {
           type union {
             type string {
               pattern "<.*>|$.*";
             }
             type int32 {
               range "1 .. 16777214";
             }
           }
         }
         uses apply-advanced;
         container vrf-target {
           description "VRF target community configuration";
           uses apply-advanced;
           leaf export {
             description "Target community to use when marking routes on export";
             status deprecated;
             type string {
             }
           }
           leaf community {
             description "Target community";
             type string {
             }
           }
         }
       }
     }
     container ip-prefix-routes {
       presence "enable ip-prefix-routes";
       description "Advertise IP prefixes through EVPN";
       uses apply-advanced;
       leaf advertise {
         description "Advertisement attributes for IP prefixes";
         type enumeration {
           enum "gateway-address" {
             description "Advertise a gateway address in exported IP prefix routes";
           }
           enum "direct-nexthop" {
             description "Advertise a direct nexthop in exported IP prefix routes";
           }
         }
       }
       leaf gateway-interface {
         description "Gateway interface used when gateway address is advertised";
         type union {
           type jt:interface-unit;
           type string {
             pattern "<.*>|$.*";
           }
         }
       }
       leaf encapsulation {
         description "Encapsulation used for IP prefixes";
         type enumeration {
           enum "mpls" {
             description "MPLS encapsulation";
           }
           enum "vxlan" {
             description "VXLAN encapsulation";
           }
         }
       }
       leaf vni {
         description "VXLAN network identifier used for IP prefixes";
         type union {
           type string {
             pattern "<.*>|$.*";
           }
           type uint32 {
             range "1 .. 16777214";
           }
         }
       }
       leaf-list import {
         ordered-by user;
         description "Policy to control import of IP prefixes from EVPN";
         type jt:policy-algebra;
       }
       leaf-list export {
         ordered-by user;
         description "Policy to control export of IP prefixes through EVPN";
         type jt:policy-algebra;
       }
     }
     leaf multicast-mode {
       description "Multicast mode for EVPN";
       default "ingress-replication";
       type enumeration {
         enum "ingress-replication" {
           description "Ingress Replication";
         }
       }
     }
     container vrf-target {
       description "VRF target community configuration";
       uses apply-advanced;
       leaf community {
         description "Target community to use in import and export";
         type string {
         }
       }
     }
     leaf default-gateway {
       description "Default gateway mode";
       type enumeration {
         enum "advertise" {
           description "Advertise IRB MACs with default gateway community";
         }
         enum "no-gateway-community" {
           description "Advertise IRB MACs without default gateway community";
         }
         enum "do-not-advertise" {
           description "Do not advertise IRB MACs";
         }
       }
     }
     leaf no-arp-suppression {
       description "Disable suppression of ARP/NDP for EVPN";
       type empty;
     }
     container duplicate-mac-detection {
       description "Duplicate MAC detection settings";
       uses apply-advanced;
       leaf detection-threshold {
         description "Number of moves to trigger duplicate MAC detection";
         type union {
           type string {
             pattern "<.*>|$.*";
           }
           type uint32 {
             range "2 .. 20";
           }
         }
       }
       leaf detection-window {
         description "Time window for detection of duplicate MACs";
         units "seconds";
         type union {
           type string {
             pattern "<.*>|$.*";
           }
           type uint32 {
             range "5 .. 600";
           }
         }
       }
       leaf auto-recovery-time {
         description "Automatically unblock duplicate MACs after a time delay";
         units "minutes";
         type union {
           type string {
             pattern "<.*>|$.*";
           }
           type uint32 {
             range "5 .. 360";
           }
         }
       }
     }
     choice flexible-cross-connect-type {
       case case_1 {
         leaf flexible-cross-connect-vlan-aware {
           description "Enable EVPN flexible cross-connect VLAN aware Service";
           type empty;
         }
       }
       case case_2 {
         leaf flexible-cross-connect-vlan-unaware {
           description "Enable EVPN flexible cross-connect VLAN unaware Service";
           type empty;
         }
       }
     }
     leaf auto-service-id {
       description "Enable auto-derivation of VPWS service instance identifier";
       type empty;
     }
     leaf hot-standby-on {
       description "Activate evpn vpws upon becoming DF";
       type empty;
     }
     list group {
       key name;
       ordered-by user;
       description "Enable EVPN flexible cross-connect VLAN unaware Service";
       leaf name {
         description "Group name to group vlan unaware cross connects";
         type string;
       }
       uses apply-advanced;
       container esi {
         presence "enable esi";
         description "ESI configuration to group vlan unaware cross connects";
         uses apply-advanced;
         leaf identifier {
           description "ESI value for grouping of vlan unaware cross connects";
           type jt:esi;
         }
       }
       list interface {
         key name;
         ordered-by user;
         description "Name of the  interface part of vlan unaware fxc";
         leaf name {
           description "Interface name";
           type union {
             type jt:interface-name;
             type string {
               pattern "<.*>|$.*";
             }
           }
         }
         uses apply-advanced;
       }
       container service-id {
         presence "enable service-id";
         description "Service-id for vlan unaware cross connects for  EVPN VPWS";
         uses apply-advanced;
         leaf local {
           description "Local service id for vlan unaware service";
           type union {
             type string {
               pattern "<.*>|$.*";
             }
             type uint32 {
               range "1 .. 16777215";
             }
           }
         }
         leaf remote {
           description "Remote service id for vlan unaware service";
           type union {
             type string {
               pattern "<.*>|$.*";
             }
             type uint32 {
               range "1 .. 16777215";
             }
           }
         }
       }
     }
   }
   grouping juniper-protocols-evi-options {
     uses apply-advanced;
     list isid {
       key name;
       description "Per-evi options";
       leaf name {
         type union {
           type string {
             pattern "<.*>|$.*";
           }
           type int32 {
             range "256 .. 16777214";
           }
         }
       }
       uses apply-advanced;
       container vrf-target {
         description "VRF target community configuration";
         uses apply-advanced;
         leaf community {
           description "Target community";
           type string {
           }
         }
       }
     }
   }
   grouping juniper-protocols-pim-snooping {
     description "PIM snooping options";
     uses apply-advanced;
     container traceoptions {
       description "Trace options for PIM Snooping";
       uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "packets" {
               description "Trace all PIM packets";
             }
             enum "hello" {
               description "Trace hello packets";
             }
             enum "join" {
               description "Trace join messages";
             }
             enum "prune" {
               description "Trace prune messages";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     leaf no-dr-flood {
       description "Disable default flooding of multicast data on the PIM designated router port";
       type empty;
     }
     list vlan {
       key name;
       ordered-by user;
       description "Vlan options";
       leaf name {
         description "Vlan_id of the learning-domain";
         type union {
           type string {
             pattern "<.*>|$.*";
           }
           type uint32 {
             range "0 .. 1023";
           }
         }
       }
       uses apply-advanced;
       leaf no-dr-flood {
         description "Disable default flooding of multicast data on the PIM DR port";
         type empty;
       }
     }
   }
   grouping juniper-ri-protocols-igmp-snooping {
     description "IGMP snooping options";
     uses apply-advanced;
     container traceoptions {
       description "Trace options for IGMP Snooping";
       uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "packets" {
               description "Trace all IGMP packets";
             }
             enum "query" {
               description "Trace IGMP membership query messages";
             }
             enum "report" {
               description "Trace membership report messages";
             }
             enum "leave" {
               description "Trace leave group messages (IGMPv2 only)";
             }
             enum "group" {
               description "Trace group operations";
             }
             enum "client-notification" {
               description "Trace notifications";
             }
             enum "host-notification" {
               description "Trace host notifications";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     leaf query-interval {
       description "When to send host query messages";
       default "125";
       units "seconds";
       type union {
         type string {
           pattern "<.*>|$.*";
         }
         type uint32 {
           range "1 .. 1024";
         }
       }
     }
     container l2-querier {
       description "Enable L2 querier mode";
       uses apply-advanced;
       leaf source-address {
         description "Source IP address to use for L2 querier";
         type jt:ipv4addr;
       }
     }
     leaf query-response-interval {
       description "How long to wait for a host query response";
       default "10";
       units "seconds";
       type string {
       }
     }
     leaf query-last-member-interval {
       description "When to send group query messages";
       default "1";
       units "seconds";
       type string {
       }
     }
     leaf robust-count {
       description "Expected packet loss on a subnet";
       default "2";
       type union {
         type string {
           pattern "<.*>|$.*";
         }
         type uint32 {
           range "2 .. 10";
         }
       }
     }
     leaf learn-pim-router {
       description "Learn PIM router interfaces from PIM hellos";
       type empty;
     }
     leaf immediate-leave {
       description "Enable immediate group leave on interfaces";
       type empty;
     }
     container proxy {
       presence "enable proxy";
       description "Enable proxy mode";
       uses apply-advanced;
       leaf source-address {
         description "Source IP address to use for proxy";
         type jt:ipv4addr;
       }
       leaf irb {
         description "Proxy IGMP reports to IRB";
         type empty;
       }
     }
     list interface {
       key name;
       ordered-by user;
       description "Interface options for IGMP";
       leaf name {
         description "Interface name";
         type union {
           type jt:interface-name;
           type string {
             pattern "<.*>|$.*";
           }
         }
       }
       uses apply-advanced;
       leaf multicast-router-interface {
         description "Enabling multicast-router-interface on the interface";
         type empty;
       }
       leaf immediate-leave {
         description "Enable immediate group leave on interfaces";
         type empty;
       }
       leaf host-only-interface {
         description "Enable interfaces to be treated as host-side interfaces";
         type empty;
       }
       leaf group-limit {
         description "Maximum number of (source,group) per interface";
         type union {
           type string {
             pattern "<.*>|$.*";
           }
           type uint16 {
             range "1 .. 65535";
           }
         }
       }
       container static {
         description "Static group or source membership";
         uses apply-advanced;
         list group {
           key name;
           ordered-by user;
           description "IP multicast group address";
           leaf name {
             description "IP multicast group address";
             type jt:ipv4addr;
           }
           uses apply-advanced;
           list source {
             key name;
             ordered-by user;
             description "IP multicast source address";
             leaf name {
               description "Source address of IP multicast data";
               type jt:ipv4addr;
             }
             uses apply-advanced;
           }
         }
       }
     }
     list pseudowire-remote-address {
       key name;
       ordered-by user;
       description "Pseudowire interface options for IGMP";
       leaf name {
         description "Pseudowire endpoint address";
         type jt:ipv4addr;
       }
       uses apply-advanced;
       leaf multicast-router-interface {
         description "Enabling multicast-router-interface on the interface";
         type empty;
       }
       leaf immediate-leave {
         description "Enable immediate group leave on interfaces";
         type empty;
       }
     }
     list qualified-vlan {
       key name;
       ordered-by user;
       description "VLAN options for qualified-learning";
       leaf name {
         description "VLAN ID of the learning-domain";
         type union {
           type string {
             pattern "<.*>|$.*";
           }
           type uint32 {
             range "0 .. 1023";
           }
         }
       }
       uses apply-advanced;
       leaf query-interval {
         description "When to send host query messages";
         units "seconds";
         type union {
           type string {
             pattern "<.*>|$.*";
           }
           type uint32 {
             range "1 .. 1024";
           }
         }
       }
       leaf query-response-interval {
         description "How long to wait for a host query response";
         units "seconds";
         type string {
         }
       }
       leaf query-last-member-interval {
         description "When to send group query messages";
         units "seconds";
         type string {
         }
       }
       leaf robust-count {
         description "Expected packet loss on a subnet";
         type union {
           type string {
             pattern "<.*>|$.*";
           }
           type uint32 {
             range "2 .. 10";
           }
         }
       }
       leaf immediate-leave {
         description "Enable immediate group leave on interfaces";
         type empty;
       }
       container proxy {
         presence "enable proxy";
         description "Enable proxy mode";
         uses apply-advanced;
         leaf source-address {
           description "Source IP address to use for proxy";
           type jt:ipv4addr;
         }
       }
       list interface {
         key name;
         ordered-by user;
         description "Interface options for IGMP";
         leaf name {
           description "Interface name";
           type union {
             type jt:interface-name;
             type string {
               pattern "<.*>|$.*";
             }
           }
         }
         uses apply-advanced;
         leaf multicast-router-interface {
           description "Enabling multicast-router-interface on the interface";
           type empty;
         }
         leaf immediate-leave {
           description "Enable immediate group leave on interfaces";
           type empty;
         }
         leaf host-only-interface {
           description "Enable interfaces to be treated as host-side interfaces";
           type empty;
         }
         leaf group-limit {
           description "Maximum number of (source,group) per interface";
           type union {
             type string {
               pattern "<.*>|$.*";
             }
             type uint16 {
               range "1 .. 65535";
             }
           }
         }
         container static {
           description "Static group or source membership";
           uses apply-advanced;
           list group {
             key name;
             ordered-by user;
             description "IP multicast group address";
             leaf name {
               description "IP multicast group address";
               type jt:ipv4addr;
             }
             uses apply-advanced;
             list source {
               key name;
               ordered-by user;
               description "IP multicast source address";
               leaf name {
                 description "Source address of IP multicast data";
                 type jt:ipv4addr;
               }
               uses apply-advanced;
             }
           }
         }
       }
       list pseudowire-remote-address {
         key name;
         ordered-by user;
         description "Pseudowire interface options for IGMP";
         leaf name {
           description "Pseudowire endpoint address";
           type jt:ipv4addr;
         }
         uses apply-advanced;
         leaf multicast-router-interface {
           description "Enabling multicast-router-interface on the interface";
           type empty;
         }
         leaf immediate-leave {
           description "Enable immediate group leave on interfaces";
           type empty;
         }
       }
     }
     list vlan {
       key name;
       ordered-by user;
       description "Vlan options";
       leaf name {
         description "VLAN name";
         type string {
           length "1 .. 64";
         }
       }
       uses apply-advanced;
       leaf query-interval {
         description "When to send host query messages";
         units "seconds";
         type union {
           type string {
             pattern "<.*>|$.*";
           }
           type uint32 {
             range "1 .. 1024";
           }
         }
       }
       leaf query-response-interval {
         description "How long to wait for a host query response";
         units "seconds";
         type string {
         }
       }
       leaf query-last-member-interval {
         description "When to send group query messages";
         units "seconds";
         type string {
         }
       }
       leaf robust-count {
         description "Expected packet loss on a subnet";
         type union {
           type string {
             pattern "<.*>|$.*";
           }
           type uint32 {
             range "2 .. 10";
           }
         }
       }
       leaf immediate-leave {
         description "Enable immediate group leave on interfaces";
         type empty;
       }
       container proxy {
         presence "enable proxy";
         description "Enable proxy mode";
         uses apply-advanced;
         leaf source-address {
           description "Source IP address to use for proxy";
           type jt:ipv4addr;
         }
       }
       list interface {
         key name;
         ordered-by user;
         description "Interface options for IGMP";
         leaf name {
           description "Interface name";
           type union {
             type jt:interface-name;
             type string {
               pattern "<.*>|$.*";
             }
           }
         }
         uses apply-advanced;
         leaf multicast-router-interface {
           description "Enabling multicast-router-interface on the interface";
           type empty;
         }
         leaf immediate-leave {
           description "Enable immediate group leave on interfaces";
           type empty;
         }
         leaf host-only-interface {
           description "Enable interfaces to be treated as host-side interfaces";
           type empty;
         }
         leaf group-limit {
           description "Maximum number of (source,group) per interface";
           type union {
             type string {
               pattern "<.*>|$.*";
             }
             type uint16 {
               range "1 .. 65535";
             }
           }
         }
         container static {
           description "Static group or source membership";
           uses apply-advanced;
           list group {
             key name;
             ordered-by user;
             description "IP multicast group address";
             leaf name {
               description "IP multicast group address";
               type jt:ipv4addr;
             }
             uses apply-advanced;
             list source {
               key name;
               ordered-by user;
               description "IP multicast source address";
               leaf name {
                 description "Source address of IP multicast data";
                 type jt:ipv4addr;
               }
               uses apply-advanced;
             }
           }
         }
       }
       list pseudowire-remote-address {
         key name;
         ordered-by user;
         description "Pseudowire interface options for IGMP";
         leaf name {
           description "Pseudowire endpoint address";
           type jt:ipv4addr;
         }
         uses apply-advanced;
         leaf multicast-router-interface {
           description "Enabling multicast-router-interface on the interface";
           type empty;
         }
         leaf immediate-leave {
           description "Enable immediate group leave on interfaces";
           type empty;
         }
       }
       list qualified-vlan {
         key name;
         ordered-by user;
         description "VLAN options for qualified-learning";
         leaf name {
           description "VLAN ID of the learning-domain";
           type union {
             type string {
               pattern "<.*>|$.*";
             }
             type uint32 {
               range "0 .. 1023";
             }
           }
         }
         uses apply-advanced;
         leaf query-interval {
           description "When to send host query messages";
           units "seconds";
           type union {
             type string {
               pattern "<.*>|$.*";
             }
             type uint32 {
               range "1 .. 1024";
             }
           }
         }
         leaf query-response-interval {
           description "How long to wait for a host query response";
           units "seconds";
           type string {
           }
         }
         leaf query-last-member-interval {
           description "When to send group query messages";
           units "seconds";
           type string {
           }
         }
         leaf robust-count {
           description "Expected packet loss on a subnet";
           type union {
             type string {
               pattern "<.*>|$.*";
             }
             type uint32 {
               range "2 .. 10";
             }
           }
         }
         leaf immediate-leave {
           description "Enable immediate group leave on interfaces";
           type empty;
         }
         container proxy {
           presence "enable proxy";
           description "Enable proxy mode";
           uses apply-advanced;
           leaf source-address {
             description "Source IP address to use for proxy";
             type jt:ipv4addr;
           }
         }
         list interface {
           key name;
           ordered-by user;
           description "Interface options for IGMP";
           leaf name {
             description "Interface name";
             type union {
               type jt:interface-name;
               type string {
                 pattern "<.*>|$.*";
               }
             }
           }
           uses apply-advanced;
           leaf multicast-router-interface {
             description "Enabling multicast-router-interface on the interface";
             type empty;
           }
           leaf immediate-leave {
             description "Enable immediate group leave on interfaces";
             type empty;
           }
           leaf host-only-interface {
             description "Enable interfaces to be treated as host-side interfaces";
             type empty;
           }
           leaf group-limit {
             description "Maximum number of (source,group) per interface";
             type union {
               type string {
                 pattern "<.*>|$.*";
               }
               type uint16 {
                 range "1 .. 65535";
               }
             }
           }
           container static {
             description "Static group or source membership";
             uses apply-advanced;
             list group {
               key name;
               ordered-by user;
               description "IP multicast group address";
               leaf name {
                 description "IP multicast group address";
                 type jt:ipv4addr;
               }
               uses apply-advanced;
               list source {
                 key name;
                 ordered-by user;
                 description "IP multicast source address";
                 leaf name {
                   description "Source address of IP multicast data";
                   type jt:ipv4addr;
                 }
                 uses apply-advanced;
               }
             }
           }
         }
         list pseudowire-remote-address {
           key name;
           ordered-by user;
           description "Pseudowire interface options for IGMP";
           leaf name {
             description "Pseudowire endpoint address";
             type jt:ipv4addr;
           }
           uses apply-advanced;
           leaf multicast-router-interface {
             description "Enabling multicast-router-interface on the interface";
             type empty;
           }
           leaf immediate-leave {
             description "Enable immediate group leave on interfaces";
             type empty;
           }
         }
       }
     }
   }
   grouping juniper-ri-protocols-mld-snooping {
     description "MLD snooping options";
     uses apply-advanced;
     container traceoptions {
       description "Trace options for MLD Snooping";
       uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "packets" {
               description "Trace all MLD packets";
             }
             enum "query" {
               description "Trace MLD membership query messages";
             }
             enum "report" {
               description "Trace membership report messages";
             }
             enum "leave" {
               description "Trace leave group messages (MLDv2 only)";
             }
             enum "group" {
               description "Trace group operations";
             }
             enum "client-notification" {
               description "Trace notifications";
             }
             enum "host-notification" {
               description "Trace host notifications";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     leaf query-interval {
       description "When to send host query messages";
       default "125";
       units "seconds";
       type union {
         type string {
           pattern "<.*>|$.*";
         }
         type uint32 {
           range "1 .. 1024";
         }
       }
     }
     container l2-querier {
       description "Enable L2 querier mode";
       uses apply-advanced;
       leaf source-address {
         description "Source IP address to use for L2 querier";
         type jt:ipv6addr;
       }
     }
     leaf query-response-interval {
       description "How long to wait for a host query response";
       default "10";
       units "seconds";
       type string {
       }
     }
     leaf query-last-member-interval {
       description "When to send group query messages";
       default "1";
       units "seconds";
       type string {
       }
     }
     leaf robust-count {
       description "Expected packet loss on a subnet";
       default "2";
       type union {
         type string {
           pattern "<.*>|$.*";
         }
         type uint32 {
           range "2 .. 10";
         }
       }
     }
     leaf immediate-leave {
       description "Enable immediate group leave on interfaces";
       type empty;
     }
     container proxy {
       presence "enable proxy";
       description "Enable proxy mode";
       uses apply-advanced;
       leaf source-address {
         description "Source IP address to use for proxy";
         type jt:ipv6addr;
       }
       leaf irb {
         description "Proxy IGMP reports to IRB";
         type empty;
       }
     }
     leaf evpn-ssm-reports-only {
       description "Accept and process only <s,g> reports of SSM groups";
       type empty;
     }
     list interface {
       key name;
       ordered-by user;
       description "Interface options for MLD";
       leaf name {
         description "Interface name";
         type union {
           type jt:interface-name;
           type string {
             pattern "<.*>|$.*";
           }
         }
       }
       uses apply-advanced;
       leaf multicast-router-interface {
         description "Enabling multicast-router-interface on the interface";
         type empty;
       }
       leaf immediate-leave {
         description "Enable immediate group leave on interfaces";
         type empty;
       }
       leaf host-only-interface {
         description "Enable interfaces to be treated as host-side interfaces";
         type empty;
       }
       leaf group-limit {
         description "Maximum number of (source,group) per interface";
         type union {
           type string {
             pattern "<.*>|$.*";
           }
           type uint16 {
             range "1 .. 65535";
           }
         }
       }
       container static {
         description "Static group or source membership";
         uses apply-advanced;
         list group {
           key name;
           ordered-by user;
           description "IP multicast group address";
           leaf name {
             description "IP multicast group address";
             type jt:ipv6addr;
           }
           uses apply-advanced;
           list source {
             key name;
             ordered-by user;
             description "IP multicast source address";
             leaf name {
               description "Source address of IP multicast data";
               type jt:ipv6addr;
             }
             uses apply-advanced;
           }
         }
       }
     }
     list pseudowire-remote-address {
       key name;
       ordered-by user;
       description "Pseudowire interface options for MLD";
       leaf name {
         description "Pseudowire endpoint address";
         type jt:ipv4addr;
       }
       uses apply-advanced;
       leaf multicast-router-interface {
         description "Enabling multicast-router-interface on the interface";
         type empty;
       }
       leaf immediate-leave {
         description "Enable immediate group leave on interfaces";
         type empty;
       }
     }
     list qualified-vlan {
       key name;
       ordered-by user;
       description "VLAN options for qualified-learning";
       leaf name {
         description "VLAN ID of the learning-domain";
         type union {
           type string {
             pattern "<.*>|$.*";
           }
           type uint32 {
             range "0 .. 1023";
           }
         }
       }
       uses apply-advanced;
       leaf query-interval {
         description "When to send host query messages";
         units "seconds";
         type union {
           type string {
             pattern "<.*>|$.*";
           }
           type uint32 {
             range "1 .. 1024";
           }
         }
       }
       leaf query-response-interval {
         description "How long to wait for a host query response";
         units "seconds";
         type string {
         }
       }
       leaf query-last-member-interval {
         description "When to send group query messages";
         units "seconds";
         type string {
         }
       }
       leaf robust-count {
         description "Expected packet loss on a subnet";
         type union {
           type string {
             pattern "<.*>|$.*";
           }
           type uint32 {
             range "2 .. 10";
           }
         }
       }
       leaf immediate-leave {
         description "Enable immediate group leave on interfaces";
         type empty;
       }
       container proxy {
         presence "enable proxy";
         description "Enable proxy mode";
         uses apply-advanced;
         leaf source-address {
           description "Source IP address to use for proxy";
           type jt:ipv6addr;
         }
       }
       leaf evpn-ssm-reports-only {
         description "Accept and process only <s,g> reports of SSM groups";
         type empty;
       }
       list interface {
         key name;
         ordered-by user;
         description "Interface options for MLD";
         leaf name {
           description "Interface name";
           type union {
             type jt:interface-name;
             type string {
               pattern "<.*>|$.*";
             }
           }
         }
         uses apply-advanced;
         leaf multicast-router-interface {
           description "Enabling multicast-router-interface on the interface";
           type empty;
         }
         leaf immediate-leave {
           description "Enable immediate group leave on interfaces";
           type empty;
         }
         leaf host-only-interface {
           description "Enable interfaces to be treated as host-side interfaces";
           type empty;
         }
         leaf group-limit {
           description "Maximum number of (source,group) per interface";
           type union {
             type string {
               pattern "<.*>|$.*";
             }
             type uint16 {
               range "1 .. 65535";
             }
           }
         }
         container static {
           description "Static group or source membership";
           uses apply-advanced;
           list group {
             key name;
             ordered-by user;
             description "IP multicast group address";
             leaf name {
               description "IP multicast group address";
               type jt:ipv6addr;
             }
             uses apply-advanced;
             list source {
               key name;
               ordered-by user;
               description "IP multicast source address";
               leaf name {
                 description "Source address of IP multicast data";
                 type jt:ipv6addr;
               }
               uses apply-advanced;
             }
           }
         }
       }
       list pseudowire-remote-address {
         key name;
         ordered-by user;
         description "Pseudowire interface options for MLD";
         leaf name {
           description "Pseudowire endpoint address";
           type jt:ipv4addr;
         }
         uses apply-advanced;
         leaf multicast-router-interface {
           description "Enabling multicast-router-interface on the interface";
           type empty;
         }
         leaf immediate-leave {
           description "Enable immediate group leave on interfaces";
           type empty;
         }
       }
     }
     list vlan {
       key name;
       ordered-by user;
       description "Vlan options";
       leaf name {
         description "Vlan of the bridge-domain";
         type string {
           length "1 .. 64";
         }
       }
       uses apply-advanced;
       leaf query-interval {
         description "When to send host query messages";
         units "seconds";
         type union {
           type string {
             pattern "<.*>|$.*";
           }
           type uint32 {
             range "1 .. 1024";
           }
         }
       }
       leaf query-response-interval {
         description "How long to wait for a host query response";
         units "seconds";
         type string {
         }
       }
       leaf query-last-member-interval {
         description "When to send group query messages";
         units "seconds";
         type string {
         }
       }
       leaf robust-count {
         description "Expected packet loss on a subnet";
         type union {
           type string {
             pattern "<.*>|$.*";
           }
           type uint32 {
             range "2 .. 10";
           }
         }
       }
       leaf immediate-leave {
         description "Enable immediate group leave on interfaces";
         type empty;
       }
       container proxy {
         presence "enable proxy";
         description "Enable proxy mode";
         uses apply-advanced;
         leaf source-address {
           description "Source IP address to use for proxy";
           type jt:ipv6addr;
         }
       }
       leaf evpn-ssm-reports-only {
         description "Accept and process only <s,g> reports of SSM groups";
         type empty;
       }
       list interface {
         key name;
         ordered-by user;
         description "Interface options for MLD";
         leaf name {
           description "Interface name";
           type union {
             type jt:interface-name;
             type string {
               pattern "<.*>|$.*";
             }
           }
         }
         uses apply-advanced;
         leaf multicast-router-interface {
           description "Enabling multicast-router-interface on the interface";
           type empty;
         }
         leaf immediate-leave {
           description "Enable immediate group leave on interfaces";
           type empty;
         }
         leaf host-only-interface {
           description "Enable interfaces to be treated as host-side interfaces";
           type empty;
         }
         leaf group-limit {
           description "Maximum number of (source,group) per interface";
           type union {
             type string {
               pattern "<.*>|$.*";
             }
             type uint16 {
               range "1 .. 65535";
             }
           }
         }
         container static {
           description "Static group or source membership";
           uses apply-advanced;
           list group {
             key name;
             ordered-by user;
             description "IP multicast group address";
             leaf name {
               description "IP multicast group address";
               type jt:ipv6addr;
             }
             uses apply-advanced;
             list source {
               key name;
               ordered-by user;
               description "IP multicast source address";
               leaf name {
                 description "Source address of IP multicast data";
                 type jt:ipv6addr;
               }
               uses apply-advanced;
             }
           }
         }
       }
       list pseudowire-remote-address {
         key name;
         ordered-by user;
         description "Pseudowire interface options for MLD";
         leaf name {
           description "Pseudowire endpoint address";
           type jt:ipv4addr;
         }
         uses apply-advanced;
         leaf multicast-router-interface {
           description "Enabling multicast-router-interface on the interface";
           type empty;
         }
         leaf immediate-leave {
           description "Enable immediate group leave on interfaces";
           type empty;
         }
       }
       list qualified-vlan {
         key name;
         ordered-by user;
         description "VLAN options for qualified-learning";
         leaf name {
           description "VLAN ID of the learning-domain";
           type union {
             type string {
               pattern "<.*>|$.*";
             }
             type uint32 {
               range "0 .. 1023";
             }
           }
         }
         uses apply-advanced;
         leaf query-interval {
           description "When to send host query messages";
           units "seconds";
           type union {
             type string {
               pattern "<.*>|$.*";
             }
             type uint32 {
               range "1 .. 1024";
             }
           }
         }
         leaf query-response-interval {
           description "How long to wait for a host query response";
           units "seconds";
           type string {
           }
         }
         leaf query-last-member-interval {
           description "When to send group query messages";
           units "seconds";
           type string {
           }
         }
         leaf robust-count {
           description "Expected packet loss on a subnet";
           type union {
             type string {
               pattern "<.*>|$.*";
             }
             type uint32 {
               range "2 .. 10";
             }
           }
         }
         leaf immediate-leave {
           description "Enable immediate group leave on interfaces";
           type empty;
         }
         container proxy {
           presence "enable proxy";
           description "Enable proxy mode";
           uses apply-advanced;
           leaf source-address {
             description "Source IP address to use for proxy";
             type jt:ipv6addr;
           }
         }
         leaf evpn-ssm-reports-only {
           description "Accept and process only <s,g> reports of SSM groups";
           type empty;
         }
         list interface {
           key name;
           ordered-by user;
           description "Interface options for MLD";
           leaf name {
             description "Interface name";
             type union {
               type jt:interface-name;
               type string {
                 pattern "<.*>|$.*";
               }
             }
           }
           uses apply-advanced;
           leaf multicast-router-interface {
             description "Enabling multicast-router-interface on the interface";
             type empty;
           }
           leaf immediate-leave {
             description "Enable immediate group leave on interfaces";
             type empty;
           }
           leaf host-only-interface {
             description "Enable interfaces to be treated as host-side interfaces";
             type empty;
           }
           leaf group-limit {
             description "Maximum number of (source,group) per interface";
             type union {
               type string {
                 pattern "<.*>|$.*";
               }
               type uint16 {
                 range "1 .. 65535";
               }
             }
           }
           container static {
             description "Static group or source membership";
             uses apply-advanced;
             list group {
               key name;
               ordered-by user;
               description "IP multicast group address";
               leaf name {
                 description "IP multicast group address";
                 type jt:ipv6addr;
               }
               uses apply-advanced;
               list source {
                 key name;
                 ordered-by user;
                 description "IP multicast source address";
                 leaf name {
                   description "Source address of IP multicast data";
                   type jt:ipv6addr;
                 }
                 uses apply-advanced;
               }
             }
           }
         }
         list pseudowire-remote-address {
           key name;
           ordered-by user;
           description "Pseudowire interface options for MLD";
           leaf name {
             description "Pseudowire endpoint address";
             type jt:ipv4addr;
           }
           uses apply-advanced;
           leaf multicast-router-interface {
             description "Enabling multicast-router-interface on the interface";
             type empty;
           }
           leaf immediate-leave {
             description "Enable immediate group leave on interfaces";
             type empty;
           }
         }
       }
     }
   }
   grouping juniper-routing-instance-pbb-options {
     description "PBB options for the routing instance";
     uses apply-advanced;
     leaf peer-instance {
       description "Set the peer-pbbn routing instance";
       type string;
     }
     list vlan-id {
       key name;
       ordered-by user;
       description "Set B-VLAN to ISID mapping";
       leaf name {
         description "Configure B-Vlan";
         type union {
           type string {
             pattern "<.*>|$.*";
           }
           type uint32 {
             range "1 .. 4094";
           }
         }
       }
       leaf-list isid-list {
         ordered-by user;
         description "Configure ISID(Valid Range:256..16777214) for the B-VLAN";
         type string;
       }
     }
     leaf default-bvlan {
       description "Default B-VLAN for all un-mapped ISIDs";
       type union {
         type string {
           pattern "<.*>|$.*";
         }
         type uint32 {
           range "1 .. 4094";
         }
       }
     }
   }
   grouping juniper-routing-instance-service-groups {
     description "Service-groups configuration";
     leaf name {
       description "Service-group name";
       type string;
     }
     uses apply-advanced;
     leaf service-type {
       description "Service type as ethernet LAN or point-to-point";
       type enumeration {
         enum "eline" {
           description "Ethernet point-to-point";
         }
         enum "elan" {
           description "Ethernet LAN service";
         }
       }
     }
     container pbb-service-options {
       presence "enable pbb-service-options";
       description "Provider backbone instance service options";
       uses apply-advanced;
       list isid {
         key name;
         ordered-by user;
         description "ISID to S-VLAN configuration";
         leaf name {
           description "Configure ISID";
           type union {
             type string {
               pattern "<.*>|$.*";
             }
             type uint32 {
               range "256 .. 16777214";
             }
           }
         }
         choice service-data {
           case case_1 {
             leaf-list vlan-id-list {
               description "List of S-VLANs";
               type jt:vlan-range;
             }
           }
           case case_2 {
             leaf interface {
               description "Point to point interface name";
               type union {
                 type jt:interface-name;
                 type string {
                   pattern "<.*>|$.*";
                 }
               }
             }
           }
         }
       }
       leaf default-isid {
         description "Default ISID for all un-mapped S-VLANs";
         type union {
           type string {
             pattern "<.*>|$.*";
           }
           type uint32 {
             range "256 .. 16777214";
           }
         }
       }
       leaf mac-address {
         description "Unicast or multicast mac address";
         type jt:mac-addr;
       }
       leaf source-bmac {
         description "Unicast Source B Mac address";
         type jt:mac-addr;
       }
     }
   }
   grouping juniper-routing-instance-switch-options {
     description "Bridge options for the routing instance";
     uses apply-advanced;
     container mac-table-size {
       description "Size of MAC address forwarding table";
       uses apply-advanced;
       leaf limit {
         description "Maximum number of MAC addresses";
         type union {
           type string {
             pattern "<.*>|$.*";
           }
           type uint32;
         }
       }
       leaf packet-action {
         description "Action when MAC limit is reached";
         type enumeration {
           enum "none" {
             description "Forward the packet";
           }
           enum "drop" {
             description "Drop packets and do not learn. Default is forward";
           }
         }
       }
     }
     container mac-ip-table-size {
       description "Size of MAC+IP bindings table";
       uses apply-advanced;
       leaf limit {
         description "Maximum number of MAC+IP bindings";
         type union {
           type string {
             pattern "<.*>|$.*";
           }
           type uint32;
         }
       }
     }
     container interface-mac-limit {
       description "Maximum MAC address learned per interface";
       uses apply-advanced;
       leaf limit {
         description "Maximum number of MAC addresses per interface";
         type union {
           type string {
             pattern "<.*>|$.*";
           }
           type uint32;
         }
       }
       leaf packet-action {
         description "Action when MAC limit is reached";
         type enumeration {
           enum "none" {
             description "Forward the packet";
           }
           enum "drop" {
             description "Drop packets and do not learn. Default is forward";
           }
           enum "log" {
             description "Do not drop the packet but generate an alarm, an SNMP trap or a system log entry";
           }
           enum "shutdown" {
             description "Disable the interface and generate an alarm, an SNMP trap or a system log entry";
           }
           enum "drop-and-log" {
             description "Drop the packet and generate an alarm, an SNMP trap or a system log entry";
           }
         }
       }
     }
     container interface-mac-ip-limit {
       description "Maximum MAC+IP bindings learned per interface";
       uses apply-advanced;
       leaf limit {
         description "Maximum number of MAC+IP bindings per interface";
         type union {
           type string {
             pattern "<.*>|$.*";
           }
           type uint32;
         }
       }
     }
     container mac-notification {
       presence "enable mac-notification";
       description "MAC notification options";
       uses apply-advanced;
       leaf notification-interval {
         description "Interval for sending MAC notifications";
         default "30";
         units "seconds";
         type union {
           type string {
             pattern "<.*>|$.*";
           }
           type uint32 {
             range "1 .. 60";
           }
         }
       }
     }
     leaf mac-table-aging-time {
       description "Delay for discarding MAC address if no updates are received";
       units "seconds";
       type union {
         type string {
           pattern "<.*>|$.*";
         }
         type uint32;
       }
     }
     leaf no-mac-learning {
       description "Disable dynamic MAC address learning";
       type empty;
     }
     leaf no-normalization {
       description "Disable vlan id normalization for interfaces";
       type empty;
     }
     leaf mac-statistics {
       description "Enable MAC address statistics";
       type empty;
     }
     container mib {
       presence "enable mib";
       description "Snmp mib options";
       uses apply-advanced;
       container dot1q-mib {
         presence "enable dot1q-mib";
         description "Dot1q MIB configuration options";
         uses apply-advanced;
         leaf port-list {
           description "Port list for staticegressports and staticuntaggedports MIB";
           type enumeration {
             enum "bit-map" {
               description "Port list is represented in bit-map format";
             }
             enum "string" {
               description "Port list is represented in string format";
             }
           }
         }
       }
     }
     container static-rvtep-mac {
       description "Configure Static MAC and remote VxLAN tunnel endpoint entries";
       uses apply-advanced;
       list mac {
         key "mac_addr remote-vtep";
         description "Unicast MAC address";
         leaf mac_addr {
           type jt:mac-unicast;
         }
         leaf remote-vtep {
           description "Configure static remote VXLAN tunnel endpoints";
           type jt:ipaddr;
         }
       }
     }
     leaf service-id {
       description "Service ID required if multi-chassis AE is part of a bridge-domain";
       type union {
         type string {
           pattern "<.*>|$.*";
         }
         type uint32 {
           range "1 .. 65535";
         }
       }
     }
     leaf ovsdb-managed {
       description "All vxlan bridge domains in routing instance are remote managed";
       type empty;
     }
     list interface {
       key name;
       ordered-by user;
       description "Interface that connect this site to the VPN";
       leaf name {
         description "Interface name";
         type union {
           type jt:interface-name;
           type string {
             pattern "<.*>|$.*";
           }
         }
       }
       uses apply-advanced;
       container interface-mac-limit {
         description "Maximum number of MAC addresses learned on the interface";
         uses apply-advanced;
         leaf limit {
           description "Maximum number of MAC addresses per interface";
           type union {
             type string {
               pattern "<.*>|$.*";
             }
             type uint32;
           }
         }
         leaf disable {
           description "Disable interface for interface-mac-limit";
           type empty;
         }
         leaf packet-action {
           description "Action when MAC limit is reached";
           type enumeration {
             enum "none" {
               description "Forward the packet";
             }
             enum "drop" {
               description "Drop packets and do not learn. Default is forward";
             }
             enum "log" {
               description "Do not drop the packet but generate an alarm, an SNMP trap or a system log entry";
             }
             enum "shutdown" {
               description "Disable the interface and generate an alarm, an SNMP trap or a system log entry";
             }
             enum "drop-and-log" {
               description "Drop the packet and generate an alarm, an SNMP trap or a system log entry";
             }
           }
         }
       }
       container vpws-service-id {
         presence "enable vpws-service-id";
         description "Service-id for EVPN VPWS routing instance";
         uses apply-advanced;
         leaf local {
           description "Local EVPN VPWS service id";
           type union {
             type string {
               pattern "<.*>|$.*";
             }
             type uint32 {
               range "1 .. 16777215";
             }
           }
         }
         leaf remote {
           description "Remote EVPN VPWS service id";
           type union {
             type string {
               pattern "<.*>|$.*";
             }
             type uint32 {
               range "1 .. 16777215";
             }
           }
         }
       }
       leaf protect-interface {
         description "Name of protect interface";
         type union {
           type jt:interface-name;
           type string {
             pattern "<.*>|$.*";
           }
         }
       }
       leaf action-priority {
         description "Blocking priority of this interface on mac move detection";
         type union {
           type string {
             pattern "<.*>|$.*";
           }
           type uint32 {
             range "0 .. 8";
           }
         }
       }
       leaf remote-site-id {
         description "Site identifier associated with this interface";
         type union {
           type string {
             pattern "<.*>|$.*";
           }
           type uint32 {
             range "1 .. 65534";
           }
         }
       }
       leaf target-attachment-identifier {
         description "FEC 129 VPWS target attachment identifier";
         type string {
         }
       }
       leaf flow-label-transmit {
         description "Advertise capability to push Flow Label in transmit direction to remote PE";
         type empty;
       }
       leaf flow-label-receive {
         description "Advertise capability to push Flow Label in receive direction to remote PE";
         type empty;
       }
       leaf encapsulation-type {
         description "Encapsulation type for VPN";
         type enumeration {
           enum "atm-aal5" {
             description "ATM AAL/5 encapsulation";
           }
           enum "atm-cell" {
             description "ATM port promiscuous mode cell encapsulation";
           }
           enum "atm-cell-port-mode" {
             description "ATM port promiscuous mode cell encapsulation";
           }
           enum "atm-cell-vp-mode" {
             description "ATM VP promiscuous mode cell encapsulation";
           }
           enum "atm-cell-vc-mode" {
             description "ATM non-promiscuous cell encapsulation";
           }
           enum "frame-relay" {
             description "Frame Relay encapsulation";
           }
           enum "ppp" {
             description "PPP encapsulation";
           }
           enum "cisco-hdlc" {
             description "Cisco-compatible HDLC encapsulation";
           }
           enum "ethernet-vlan" {
             description "Ethernet VLAN encapsulation";
           }
           enum "ethernet" {
             description "Ethernet encapsulation";
           }
           enum "interworking" {
             description "Layer 2.5 interworking VPN";
           }
           enum "frame-relay-port-mode" {
             description "Frame Relay port mode encapsulation";
           }
           enum "satop-t1" {
             description "SATOP-T1 based Layer 2 VPN";
           }
           enum "satop-e1" {
             description "SATOP-E1 based Layer 2 VPN";
           }
           enum "satop-t3" {
             description "SATOP-T3 based Layer 2 VPN";
           }
           enum "satop-e3" {
             description "SATOP-E3 based Layer 2 VPN";
           }
           enum "cesop" {
             description "CESOP based Layer 2 VPN";
           }
         }
       }
       leaf ignore-encapsulation-mismatch {
         description "Allow different encapsulation types on local and remote end";
         type empty;
       }
       leaf mtu {
         description "MTU to be advertised to the remote end";
         type union {
           type string {
             pattern "<.*>|$.*";
           }
           type uint16 {
             range "512 .. 65535";
           }
         }
       }
       leaf ignore-mtu-mismatch {
         description "Allow different MTU values on local and remote end";
         type empty;
       }
       choice cword {
         case case_1 {
           leaf control-word {
             description "Adds control-word to the Layer 2 encapsulation";
             type empty;
           }
         }
         case case_2 {
           leaf no-control-word {
             description "Disables control-word to the Layer 2 encapsulation";
             type empty;
           }
         }
       }
       leaf pseudowire-status-tlv {
         description "Send pseudowire status TLV";
         type empty;
       }
       container oam {
         description "OAM Configuration for VPN";
         uses apply-advanced;
         leaf ping-interval {
           description "Time interval between ping messages";
           default "60";
           units "seconds";
           type union {
             type string {
               pattern "<.*>|$.*";
             }
             type uint16 {
               range "30 .. 3600";
             }
           }
         }
         leaf ping-multiplier {
           description "Number of ping reply missed before declaring BFD down";
           type union {
             type string {
               pattern "<.*>|$.*";
             }
             type uint8 {
               range "1 .. 5";
             }
           }
         }
         container bfd-liveness-detection {
           description "Bidirectional Forwarding Detection (BFD) options";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
         }
       }
       leaf community {
         description "Community associated with this interface";
         type string;
       }
       list static-mac {
         key name;
         ordered-by user;
         description "Static MAC addresses assigned to this interface";
         leaf name {
           description "MAC address";
           type jt:mac-addr;
         }
         uses apply-advanced;
         list vlan-id {
           key name;
           ordered-by user;
           description "VLAN ID of learning VLAN";
           leaf name {
             description "Learning VLAN";
             type union {
               type string {
                 pattern "<.*>|$.*";
               }
               type uint32 {
                 range "0 .. 4094";
               }
             }
           }
           uses apply-advanced;
         }
       }
       container interface-mac-ip-limit {
         description "Maximum number of MAC+IP bindings learned on the interface";
         uses apply-advanced;
         leaf limit {
           description "Maximum number of MAC+IP bindings per interface";
           type union {
             type string {
               pattern "<.*>|$.*";
             }
             type uint32;
           }
         }
       }
       leaf no-mac-learning {
         description "Disable dynamic MAC address learning";
         type empty;
       }
       leaf mac-pinning {
         description "Enable MAC pinning";
         type empty;
       }
       leaf description {
         description "Text description";
         type string;
       }
       leaf persistent-learning {
         description "Enable persistent MAC learning on this interface";
         type empty;
       }
     }
     container voip {
       description "Voice-over-IP configuration";
       uses apply-advanced;
       list interface {
         key name;
         ordered-by user;
         description "Enable voice over IP on this port";
         leaf name {
           type string;
         }
         uses apply-advanced;
         leaf vlan {
           description "VLAN for voice over IP";
           type string {
           }
         }
         leaf forwarding-class {
           description "Forwarding class";
           type string {
           }
         }
       }
     }
     container unknown-unicast-forwarding {
       description "Set interface for forwarding of unknown unicast packets";
       uses apply-advanced;
       list vlan {
         key name;
         description "VLAN for the unknown unicast packets";
         leaf name {
           description "VLAN name or VLAN Tag (1..4095)";
           type string {
           }
         }
         uses apply-advanced;
         leaf interface {
           description "Interface to send unknown unicast packets for the VLAN";
           type union {
             type jt:interface-name;
             type string {
               pattern "<.*>|$.*";
             }
           }
         }
       }
     }
     container traceoptions {
       description "Layer 2 trace options for this routing instance";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       leaf level {
         description "Level of debugging output";
         default "error";
         type enumeration {
           enum "error" {
             description "Match error conditions";
           }
           enum "warning" {
             description "Match warning messages";
           }
           enum "notice" {
             description "Match conditions that should be handled specially";
           }
           enum "info" {
             description "Match informational messages";
           }
           enum "verbose" {
             description "Match verbose messages";
           }
           enum "all" {
             description "Match all levels";
           }
         }
       }
       list flag {
         key name;
         ordered-by user;
         description "Type of operation or event to include in trace";
         leaf name {
           type enumeration {
             enum "configuration" {
               description "Configuration operations";
             }
             enum "routing-socket" {
               description "Routing socket operations";
             }
             enum "interface-device" {
               description "Interface device operations";
             }
             enum "interface-logical" {
               description "Logical interface operations";
             }
             enum "interface-family" {
               description "Interface family operations";
             }
             enum "bridging-domain" {
               description "Bridging domain operations";
             }
             enum "bridge-interface" {
               description "Interface bridge operations";
             }
             enum "learning-domain" {
               description "Learning domain operations";
             }
             enum "ipc" {
               description "Inter-process communications operations";
             }
             enum "mac-learning" {
               description "MAC address learning operations";
             }
             enum "initialization" {
               description "Initialization operations";
             }
             enum "flood-next-hop" {
               description "Flood next hop operations";
             }
             enum "irb" {
               description "Integrated routing and bridging operations";
             }
             enum "vpls-ping" {
               description "VPLS ping operations";
             }
             enum "vpls-loop-prev" {
               description "VPLS loop prevention";
             }
             enum "storm-control" {
               description "Storm-control";
             }
             enum "unknown-unicast-forwarding" {
               description "Trace unknown unicast forwarding events";
             }
             enum "vxlan" {
               description "VXLAN";
             }
             enum "all" {
               description "All operations";
             }
           }
         }
       }
     }
   }
   grouping juniper-routing-options {
     uses apply-advanced;
     leaf no-soft-core {
       description "Disable soft assert to generate core and just log the event";
       type empty;
     }
     leaf med-igp-update-interval {
       description "Delay (in minutes) in updating MED IGP for bgp groups with 'delay-med-update' ";
       type union {
         type string {
           pattern "<.*>|$.*";
         }
         type uint32 {
           range "10 .. 600";
         }
       }
     }
     container bmp {
       presence "enable bmp";
       description "BGP Monitoring Protocol (BMP) configuration";
       uses apply-advanced;
       leaf authentication-key {
         description "MD5 authentication key";
         type string {
           length "1 .. 126";
         }
       }
       leaf authentication-algorithm {
         description "Authentication algorithm name";
         default "hmac-sha-1-96";
         type enumeration {
           enum "md5" {
             description "Message Digest 5";
           }
           enum "hmac-sha-1-96" {
             description "Hash-based Message Authentication Code (SHA1) (96 bits)";
           }
           enum "aes-128-cmac-96" {
             description "Cipher-based Message Authentication Code (AES128) (96 bits)";
           }
         }
       }
       leaf authentication-key-chain {
         description "Key chain name";
         type string {
           length "1 .. 128";
         }
       }
       container hold-down {
         presence "enable hold-down";
         leaf hold-down-time {
           description "Prevent re-establishment for this time";
           units "seconds";
           type union {
             type string {
               pattern "<.*>|$.*";
             }
             type uint32 {
               range "30 .. 65535";
             }
           }
         }
         leaf flaps {
           description "Number of flaps before damping";
           type union {
             type string {
               pattern "<.*>|$.*";
             }
             type uint32 {
               range "2 .. 10";
             }
           }
         }
         leaf period {
           description "Time period for flaps";
           units "seconds";
           type union {
             type string {
               pattern "<.*>|$.*";
             }
             type uint32 {
               range "30 .. 65535";
             }
           }
         }
       }
       leaf initiation-message {
         description "User string sent with the initiation message";
         type string {
           length "1 .. 255";
         }
       }
       leaf local-address {
         description "Address of local end of BMP session";
         type jt:ipaddr;
       }
       leaf local-port {
         description "Local port for listening";
         type union {
           type string {
             pattern "<.*>|$.*";
           }
           type uint32 {
             range "1024 .. 65535";
           }
         }
       }
       leaf connection-mode {
         description "Specify active or passive";
         type enumeration {
           enum "active" {
             description "Initiate the connection";
           }
           enum "passive" {
             description "Listen for the connection";
           }
         }
       }
       leaf priority {
         description "Relative dispatch priority";
         type enumeration {
           enum "low" {
             description "Lowest priority";
           }
           enum "medium" {
             description "Medium priority";
           }
           enum "high" {
             description "Highest priority";
           }
         }
       }
       leaf monitor {
         description "Enable/Disable monitoring";
         type enumeration {
           enum "enable" {
             description "Enable monitoring of BGP peer(s)";
           }
           enum "disable" {
             description "Disable monitoring of BGP peer(s)";
           }
         }
       }
       container route-monitoring {
         description "Control route monitoring settings";
         uses apply-advanced;
         leaf none {
           description "Do not send route montoring messages";
           type empty;
         }
         container pre-policy {
           presence "enable pre-policy";
           description "Send pre policy route montoring messages";
           leaf exclude-non-feasible {
             description "Exclude looped routes, etc";
             type empty;
           }
         }
         container post-policy {
           presence "enable post-policy";
           description "Send post policy route montoring messages";
           leaf exclude-non-eligible {
             description "Exclude unresolved routes, etc.";
             type empty;
           }
         }
       }
       leaf station-address {
         description "Address/name of monitoring station";
         type jt:ipaddr;
       }
       leaf routing-instance {
         description "Routing-instance through which BMP station is reachable";
         type string;
       }
       leaf station-port {
         description "Port of monitoring station";
         type union {
           type string {
             pattern "<.*>|$.*";
           }
           type uint32 {
             range "1 .. 65535";
           }
         }
       }
       leaf statistics-timeout {
         description "Statistics message timer, 15-65535, or 0 for no messages";
         units "seconds";
         type union {
           type string {
             pattern "<.*>|$.*";
           }
           type uint32 {
             range "0 .. 65535";
           }
         }
       }
       container traceoptions {
         description "Trace options";
         uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Trace flag information";
           leaf name {
             type enumeration {
               enum "packets" {
                 description "Trace all messages";
               }
               enum "up" {
                 description "Trace up messages";
               }
               enum "down" {
                 description "Trace down messages";
               }
               enum "statistics" {
                 description "Trace statistics messages";
               }
               enum "route-monitoring" {
                 description "Trace route monitoring messages";
               }
               enum "event" {
                 description "Trace major events, station establishment, errors, events";
               }
               enum "error" {
                 description "Trace error conditions";
               }
               enum "write" {
                 description "Trace writing of messages";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       list station {
         key name;
         description "Define a BMP station";
         leaf name {
           description "Station name";
           type string;
         }
         uses apply-advanced;
         leaf authentication-key {
           description "MD5 authentication key";
           type string {
             length "1 .. 126";
           }
         }
         leaf authentication-algorithm {
           description "Authentication algorithm name";
           type enumeration {
             enum "md5" {
               description "Message Digest 5";
             }
             enum "hmac-sha-1-96" {
               description "Hash-based Message Authentication Code (SHA1) (96 bits)";
             }
             enum "aes-128-cmac-96" {
               description "Cipher-based Message Authentication Code (AES128) (96 bits)";
             }
           }
         }
         leaf authentication-key-chain {
           description "Key chain name";
           type string {
             length "1 .. 128";
           }
         }
         container hold-down {
           presence "enable hold-down";
           leaf hold-down-time {
             description "Prevent re-establishment for this time";
             units "seconds";
             type union {
               type string {
                 pattern "<.*>|$.*";
               }
               type uint32 {
                 range "30 .. 65535";
               }
             }
           }
           leaf flaps {
             description "Number of flaps before damping";
             type union {
               type string {
                 pattern "<.*>|$.*";
               }
               type uint32 {
                 range "2 .. 10";
               }
             }
           }
           leaf period {
             description "Time period for flaps";
             units "seconds";
             type union {
               type string {
                 pattern "<.*>|$.*";
               }
               type uint32 {
                 range "30 .. 65535";
               }
             }
           }
         }
         leaf initiation-message {
           description "User string sent with the initiation message";
           type string {
             length "1 .. 255";
           }
         }
         leaf local-address {
           description "Address of local end of BMP session";
           type jt:ipaddr;
         }
         leaf local-port {
           description "Local port for listening";
           type union {
             type string {
               pattern "<.*>|$.*";
             }
             type uint32 {
               range "1024 .. 65535";
             }
           }
         }
         leaf connection-mode {
           description "Specify active or passive";
           type enumeration {
             enum "active" {
               description "Initiate the connection";
             }
             enum "passive" {
               description "Listen for the connection";
             }
           }
         }
         leaf priority {
           description "Relative dispatch priority";
           type enumeration {
             enum "low" {
               description "Lowest priority";
             }
             enum "medium" {
               description "Medium priority";
             }
             enum "high" {
               description "Highest priority";
             }
           }
         }
         leaf monitor {
           description "Enable/Disable monitoring";
           type enumeration {
             enum "enable" {
               description "Enable monitoring of BGP peer(s)";
             }
             enum "disable" {
               description "Disable monitoring of BGP peer(s)";
             }
           }
         }
         container route-monitoring {
           description "Control route monitoring settings";
           uses apply-advanced;
           leaf none {
             description "Do not send route montoring messages";
             type empty;
           }
           container pre-policy {
             presence "enable pre-policy";
             description "Send pre policy route montoring messages";
             leaf exclude-non-feasible {
               description "Exclude looped routes, etc";
               type empty;
             }
           }
           container post-policy {
             presence "enable post-policy";
             description "Send post policy route montoring messages";
             leaf exclude-non-eligible {
               description "Exclude unresolved routes, etc.";
               type empty;
             }
           }
         }
         leaf station-address {
           description "Address/name of monitoring station";
           type jt:ipaddr;
         }
         leaf routing-instance {
           description "Routing-instance through which BMP station is reachable";
           type string;
         }
         leaf station-port {
           description "Port of monitoring station";
           type union {
             type string {
               pattern "<.*>|$.*";
             }
             type uint32 {
               range "1 .. 65535";
             }
           }
         }
         leaf statistics-timeout {
           description "Statistics message timer, 15-65535, or 0 for no messages";
           units "seconds";
           type union {
             type string {
               pattern "<.*>|$.*";
             }
             type uint32 {
               range "0 .. 65535";
             }
           }
         }
         container traceoptions {
           description "Trace options";
           uses apply-advanced;
           container file {
             description "Trace file options";
             leaf filename {
               description "Name of file in which to write trace information";
               type string {
                 length "1 .. 1024";
               }
             }
             leaf replace {
               description "Replace trace file rather than appending to it";
               status deprecated;
               type empty;
             }
             leaf size {
               description "Maximum trace file size";
               type string;
             }
             leaf files {
               description "Maximum number of trace files";
               default "10";
               type union {
                 type string {
                   pattern "<.*>|$.*";
                 }
                 type uint32 {
                   range "2 .. 1000";
                 }
               }
             }
             leaf no-stamp {
               description "Do not timestamp trace file";
               status deprecated;
               type empty;
             }
             choice world-readable-choice {
               leaf world-readable {
                 description "Allow any user to read the log file";
                 type empty;
               }
               leaf no-world-readable {
                 description "Don't allow any user to read the log file";
                 type empty;
               }
             }
           }
           list flag {
             key name;
             ordered-by user;
             description "Trace flag information";
             leaf name {
               type enumeration {
                 enum "packets" {
                   description "Trace all messages";
                 }
                 enum "up" {
                   description "Trace up messages";
                 }
                 enum "down" {
                   description "Trace down messages";
                 }
                 enum "statistics" {
                   description "Trace statistics messages";
                 }
                 enum "route-monitoring" {
                   description "Trace route monitoring messages";
                 }
                 enum "event" {
                   description "Trace major events, station establishment, errors, events";
                 }
                 enum "error" {
                   description "Trace error conditions";
                 }
                 enum "write" {
                   description "Trace writing of messages";
                 }
                 enum "route" {
                   description "Trace routing information";
                 }
                 enum "normal" {
                   description "Trace normal events";
                 }
                 enum "general" {
                   description "Trace general events";
                 }
                 enum "state" {
                   description "Trace state transitions";
                 }
                 enum "policy" {
                   description "Trace policy processing";
                 }
                 enum "task" {
                   description "Trace routing protocol task processing";
                 }
                 enum "timer" {
                   description "Trace routing protocol timer processing";
                 }
                 enum "all" {
                   description "Trace everything";
                 }
               }
             }
             leaf send {
               description "Trace transmitted packets";
               type empty;
             }
             leaf receive {
               description "Trace received packets";
               type empty;
             }
             leaf detail {
               description "Trace detailed information";
               type empty;
             }
             leaf disable {
               description "Disable this trace flag";
               type empty;
             }
           }
         }
       }
     }
     leaf bgp-orf-cisco-mode {
       description "Using BGP ORF capability code 130 and Prefix ORF type 128";
       type empty;
     }
     container ppm {
       presence "enable ppm";
       description "Set periodic packet management properties";
       uses apply-advanced;
       leaf delegate-processing {
         description "Enable distribution of PPM sessions";
         status deprecated;
         type empty;
       }
       leaf no-delegate-processing {
         description "Disable PPM sessions distribution";
         type empty;
       }
       leaf redistribution-timer {
         description "Time to wait after switchover before starting timers";
         type union {
           type string {
             pattern "<.*>|$.*";
           }
           type uint32 {
             range "1 .. 120";
           }
         }
       }
     }
     leaf no-bfd-triggered-local-repair {
       description "Disable bfd triggered local repair";
       type empty;
     }
     container source-routing {
       description "Source-routing options";
       uses apply-advanced;
       leaf ip {
         description "Enable IP Source Routing";
         type empty;
       }
       leaf ipv6 {
         description "Enable Type 0 RouteHeader processing";
         type empty;
       }
     }
     container auto-bandwidth {
       presence "enable auto-bandwidth";
       description "Auto bandwidth";
       uses apply-advanced;
       list template {
         key name;
         ordered-by user;
         description "Auto bandwidth template";
         leaf name {
           description "Auto bandwidth template name (Maximum length 64)";
           type string {
             length "1 .. 64";
           }
         }
         uses apply-advanced;
         leaf adjust-interval {
           description "Adjust interval";
           type union {
             type string {
               pattern "<.*>|$.*";
             }
             type uint32 {
               range "30 .. 3600";
             }
           }
         }
         leaf adjust-threshold {
           description "Percentage threshhold";
           type union {
             type string {
               pattern "<.*>|$.*";
             }
             type uint32 {
               range "0 .. 100";
             }
           }
         }
         leaf statistic-collection-interval {
           description "Collection interval";
           type union {
             type string {
               pattern "<.*>|$.*";
             }
             type uint32 {
               range "10 .. 300";
             }
           }
         }
         leaf auto-bandwidth-subscription {
           description "Percentage threshhold for subscription";
           type union {
             type string {
               pattern "<.*>|$.*";
             }
             type uint32 {
               range "0 .. 200";
             }
           }
         }
       }
       container traceoptions {
         description "Trace options for sr stats";
         uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "all" {
                 description "Trace All";
               }
               enum "timer" {
                 description "Trace traffic recv by periodic timer";
               }
               enum "state" {
                 description "Trace state of sensor";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
     }
     list srlg {
       key name;
       ordered-by user;
       description "SRLG configuration";
       leaf name {
         description "Group name (Maximum length 64)";
         type string {
           length "1 .. 64";
         }
       }
       uses apply-advanced;
       leaf srlg-value {
         description "Group id";
         type union {
           type string {
             pattern "<.*>|$.*";
           }
           type uint32 {
             range "1 .. 4294967295";
           }
         }
       }
       leaf srlg-cost {
         description "Cost value";
         type union {
           type string {
             pattern "<.*>|$.*";
           }
           type uint32 {
             range "1 .. 65535";
           }
         }
       }
     }
     container admin-groups-extended-range {
       description "Extended administrative groups range";
       uses apply-advanced;
       leaf minimum {
         description "Minimum value of the range for extended administrative groups";
         type union {
           type string {
             pattern "<.*>|$.*";
           }
           type uint32 {
             range "32 .. 4294967295";
           }
         }
       }
       leaf maximum {
         description "Maximum value of the range for extended administrative groups";
         type union {
           type string {
             pattern "<.*>|$.*";
           }
           type uint32 {
             range "32 .. 4294967295";
           }
         }
       }
     }
     list admin-groups-extended {
       key name;
       ordered-by user;
       description "Extended administrative groups";
       leaf name {
         description "Group name (Maximum length 64)";
         type string {
           length "1 .. 64";
         }
       }
       uses apply-advanced;
       leaf group-value {
         description "Group id";
         type union {
           type string {
             pattern "<.*>|$.*";
           }
           type uint32 {
             range "32 .. 4294967295";
           }
         }
       }
     }
     container source-packet-routing {
       description "Source packet routing (SPRING)";
       uses apply-advanced;
       list mapping-server-entry {
         key name;
         ordered-by user;
         description "Mapping server entry";
         leaf name {
           description "Mapping server entry name";
           type string {
             length "1 .. 64";
           }
         }
         uses apply-advanced;
         list prefix-segment {
           key name;
           ordered-by user;
           description "Prefix segment";
           max-elements 64;
           leaf name {
             description "Prefix segment prefix";
             type jt:ipprefix;
           }
           uses apply-advanced;
           leaf index {
             description "Prefix segment index";
             type union {
               type string {
                 pattern "<.*>|$.*";
               }
               type uint32 {
                 range "0 .. 199999";
               }
             }
           }
           leaf attached {
             description "Set attached flag in IS-IS mapping server advertisement";
             type empty;
           }
           leaf domain-wide-flooding {
             description "Set S-flag in IS-IS mapping server advertisement";
             type empty;
           }
           leaf no-node-segment {
             description "Clear node segment flag in mapping server prefix segment";
             type empty;
           }
         }
         list prefix-segment-range {
           key name;
           ordered-by user;
           description "Prefix segment range";
           max-elements 64;
           leaf name {
             description "Prefix segment range name";
             type string {
               length "1 .. 64";
             }
           }
           uses apply-advanced;
           leaf start-prefix {
             description "Start prefix";
             type jt:ipprefix;
           }
           leaf start-index {
             description "Start index";
             type union {
               type string {
                 pattern "<.*>|$.*";
               }
               type uint32 {
                 range "0 .. 199999";
               }
             }
           }
           leaf size {
             description "Size of prefix segment range";
             type union {
               type string {
                 pattern "<.*>|$.*";
               }
               type uint32 {
                 range "1 .. 1024";
               }
             }
           }
           leaf attached {
             description "Set attached flag in IS-IS mapping server advertisement";
             type empty;
           }
           leaf domain-wide-flooding {
             description "Set S-flag in IS-IS mapping server advertisement";
             type empty;
           }
           leaf no-node-segment {
             description "Clear node segment flag in mapping server prefix segment";
             type empty;
           }
         }
       }
     }
     container traceoptions {
       description "Global routing protocol trace options";
       uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       container trace-events {
         presence "enable trace-events";
         description "Trace events configuration";
         uses apply-advanced;
         list logging {
           key name;
           ordered-by user;
           description "Logging trace events";
           leaf name {
             description "Event system name";
             type string;
           }
           leaf disable {
             description "Disable these trace events";
             type empty;
           }
           leaf memtrace {
             description "Memtrace logging";
             type empty;
           }
         }
       }
       list flag {
         key name;
         ordered-by user;
         description "Tracing parameters";
         leaf name {
           type enumeration {
             enum "parse" {
               description "Trace configuration parsing";
             }
             enum "regex-parse" {
               description "Trace regular-expression parsing";
             }
             enum "config-internal" {
               description "Trace configuration internals";
             }
             enum "nsr-synchronization" {
               description "Trace nonstop routing synchronization events";
             }
             enum "condition-manager" {
               description "Trace condition manager events";
             }
             enum "graceful-restart" {
               description "Trace Graceful Restart events";
             }
             enum "session" {
               description "Trace Session ID allocations/deallocations";
             }
             enum "hfrr-fsm" {
               description "Host FRR FSM events tracing";
             }
             enum "hfrr-route" {
               description "Host FRR route events tracing";
             }
             enum "statistics-id-group" {
               description "Trace Statistics ID Group operations";
             }
             enum "route-record" {
               description "Trace route-record server-side events";
             }
             enum "jvision-lsp" {
               description "Trace Jvision events and errors";
             }
             enum "dyn-nh-template" {
               description "Dynamic nexthops template events tracing";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf disable {
           description "Disable this trace flag";
           type empty;
         }
       }
     }
     container options {
       description "Miscellaneous options";
       uses apply-advanced;
       leaf no-send {
         description "Listen only; do not send protocol packets";
         status deprecated;
         type empty;
       }
       leaf no-resolve {
         description "Do not use DNS name resolution";
         status deprecated;
         type empty;
       }
       container syslog {
         description "Set system logging level";
         uses apply-advanced;
         container level {
           description "Logging level";
           leaf emergency {
             description "Emergency level";
             type empty;
           }
           leaf alert {
             description "Alert level";
             type empty;
           }
           leaf critical {
             description "Critical level";
             type empty;
           }
           leaf error {
             description "Error level";
             type empty;
           }
           leaf warning {
             description "Warning level";
             type empty;
           }
           leaf notice {
             description "Notice level";
             type empty;
           }
           leaf info {
             description "Informational level";
             type empty;
           }
           leaf debug {
             description "Debugging level";
             type empty;
           }
         }
         leaf upto {
           description "Log up to a particular logging level";
           type enumeration {
             enum "emergency" {
               description "Emergency level";
             }
             enum "alert" {
               description "Alert level";
             }
             enum "critical" {
               description "Critical level";
             }
             enum "error" {
               description "Error level";
             }
             enum "warning" {
               description "Warning level";
             }
             enum "notice" {
               description "Notice level";
             }
             enum "info" {
               description "Informational level";
             }
             enum "debug" {
               description "Debugging level";
             }
           }
         }
       }
       leaf mark {
         description "Periodically mark the trace file";
         units "seconds";
         type union {
           type int32;
           type string {
             pattern "<.*>|$.*";
           }
         }
       }
     }
     container graceful-restart {
       presence "enable graceful-restart";
       description "Graceful or hitless routing restart options";
       uses apply-advanced;
       choice enable-disable {
         case case_1 {
           leaf disable {
             description "Disable graceful restart";
             type empty;
           }
         }
       }
       leaf restart-duration {
         description "Maximum time for which router is in graceful restart";
         type union {
           type string {
             pattern "<.*>|$.*";
           }
           type uint32 {
             range "120 .. 10000";
           }
         }
       }
     }
     leaf warm-standby {
       description "Enable warm-standby";
       type empty;
     }
     leaf nonstop-routing {
       description "Enable nonstop routing";
       type empty;
     }
     container nonstop-routing-options {
       presence "enable nonstop-routing-options";
       description "Nonstop routing options";
       uses apply-advanced;
       leaf precision-timers-max-period {
         description "Set Max period for precision timer support from kernel after switchover";
         type union {
           type string {
             pattern "<.*>|$.*";
           }
           type uint32 {
             range "60 .. 1800";
           }
         }
       }
     }
     leaf nsr-phantom-holdtime {
       description "Set NSR phantom route hold time";
       type union {
         type string {
           pattern "<.*>|$.*";
         }
         type uint32 {
           range "0 .. 10000";
         }
       }
     }
     container interface-routes {
       description "Define routing table groups for interface routes";
       uses apply-advanced;
       container rib-group {
         description "Routing table group";
         uses rib_group_type;
       }
       list family {
         key name;
         ordered-by user;
         description "Address family";
         leaf name {
           type enumeration {
             enum "inet" {
               description "IPv4 family";
             }
             enum "inet6" {
               description "IPv6 family";
             }
           }
         }
         uses apply-advanced;
         leaf-list import {
           ordered-by user;
           description "Import policy";
           type jt:policy-algebra;
         }
         container export {
           description "Control exportability of local routes";
           uses apply-advanced;
           leaf point-to-point {
             description "Make point-to-point routes exportable";
             type empty;
           }
           leaf lan {
             description "Make LAN routes exportable";
             type empty;
           }
         }
       }
     }
     leaf loopback-strict-disable {
       description "Completely disable lo0 host prefix when in admin-down state";
       type empty;
     }
     list rib {
       key name;
       ordered-by user;
       description "Routing table options";
       leaf name {
         description "Routing table name";
         type string;
       }
       uses apply-advanced;
       container static {
         description "Static routes";
         uses apply-advanced;
         leaf rib-group {
           description "Routing table group";
           type string;
         }
         container defaults {
           description "Global route options";
           uses apply-advanced;
           choice retain-choice {
             leaf retain {
               description "Always keep route in forwarding table";
               type empty;
             }
             leaf no-retain {
               description "Don't always keep route in forwarding table";
               type empty;
             }
           }
           choice install-choice {
             leaf install {
               description "Install route into forwarding table";
               type empty;
             }
             leaf no-install {
               description "Don't install route into forwarding table";
               type empty;
             }
           }
           choice readvertise-choice {
             leaf readvertise {
               description "Mark route as eligible to be readvertised";
               type empty;
             }
             leaf no-readvertise {
               description "Don't mark route as eligible to be readvertised";
               type empty;
             }
           }
           choice resolve-choice {
             leaf resolve {
               description "Allow resolution of indirectly connected next hops";
               type empty;
             }
             leaf no-resolve {
               description "Don't allow resolution of indirectly connected next hops";
               type empty;
             }
           }
           choice longest-match-choice {
             leaf longest-match {
               description "Always use longest prefix match to resolve next hops";
               type empty;
             }
             leaf no-longest-match {
               description "Don't always use longest prefix match to resolve next hops";
               type empty;
             }
           }
           choice passive_flag {
             case case_1 {
               leaf active {
                 description "Remove inactive route from forwarding table";
                 type empty;
               }
             }
             case case_2 {
               leaf passive {
                 description "Retain inactive route in forwarding table";
                 type empty;
               }
             }
           }
           container metric {
             description "Metric value";
             presence "enable metric";
             uses rib_static_metric_type;
           }
           container metric2 {
             description "Metric value 2";
             presence "enable metric2";
             uses rib_static_metric_type;
           }
           container metric3 {
             description "Metric value 3";
             presence "enable metric3";
             uses rib_static_metric_type;
           }
           container metric4 {
             description "Metric value 4";
             presence "enable metric4";
             uses rib_static_metric_type;
           }
           container tag {
             description "Tag string";
             presence "enable tag";
             uses rib_static_metric_type;
           }
           container tag2 {
             description "Tag string 2";
             presence "enable tag2";
             uses rib_static_metric_type;
           }
           container preference {
             description "Preference value";
             presence "enable preference";
             uses rib_static_metric_type;
           }
           container preference2 {
             description "Preference value 2";
             presence "enable preference2";
             uses rib_static_metric_type;
           }
           container color {
             description "Color (preference) value";
             presence "enable color";
             uses rib_static_metric_type;
           }
           container color2 {
             description "Color (preference) value 2";
             presence "enable color2";
             uses rib_static_metric_type;
           }
           leaf-list community {
             ordered-by user;
             description "BGP community identifier";
             type jt:community;
           }
           container as-path {
             description "Autonomous system path";
             uses apply-advanced;
             leaf path {
               description "Autonomous system path";
               type string;
             }
             leaf origin {
               type enumeration {
                 enum "igp" {
                   description "Path originated in the local IGP";
                 }
                 enum "egp" {
                   description "Path originated in another AS";
                 }
                 enum "incomplete" {
                   description "Path was learned by some other means";
                 }
               }
             }
             leaf atomic-aggregate {
               description "Add ATOMIC_AGGREGATE path attribute to route";
               type empty;
             }
             container aggregator {
               presence "enable aggregator";
               description "Add AGGREGATOR path attribute to route";
             }
             leaf as-number {
               description " Autonomous system number in plain number or 'higher 16bits'.'Lower 16 bits' (asdot notation) format";
               type string {
               }
             }
             leaf address {
               description "Address of BGP system that formed the route";
               type jt:ipv4addr;
             }
           }
         }
         list route {
           key name;
           ordered-by user;
           description "Static route";
           leaf name {
             type jt:ipprefix;
           }
           uses apply-advanced;
           choice next_hop {
             case case_1 {
               leaf-list next-hop {
                 ordered-by user;
                 description "Next hop to destination";
                 type union {
                   type jt:ipaddr-or-interface;
                   type string {
                     pattern "<.*>|$.*";
                   }
                 }
               }
             }
             case case_2 {
               leaf reject {
                 description "Drop packets to destination; send ICMP unreachables";
                 type empty;
               }
             }
             case case_3 {
               leaf discard {
                 description "Drop packets to destination; send no ICMP unreachables";
                 type empty;
               }
             }
             case case_4 {
               leaf receive {
                 description "Install a receive route for the destination";
                 type empty;
               }
             }
             case case_5 {
               leaf next-table {
                 description "Next hop to another table";
                 type string {
                 }
               }
             }
           }
           list qualified-next-hop {
             key name;
             ordered-by user;
             description "Next hop with qualifiers";
             uses qualified_nh_obj;
           }
           list lsp-next-hop {
             key name;
             ordered-by user;
             description "LSP next hop";
             uses lsp_nh_obj;
           }
           list static-lsp-next-hop {
             key name;
             ordered-by user;
             description "Static LSP next hop";
             uses lsp_nh_obj;
           }
           list p2mp-lsp-next-hop {
             key name;
             ordered-by user;
             description "Point-to-multipoint LSP next hop";
             max-elements 1;
             uses lsp_nh_obj;
           }
           container p2mp-ldp-next-hop {
             description "Point-to-multipoint LDP LSP next hop";
             uses p2mp_ldp_lsp_nh_obj;
           }
           leaf backup-pe-group {
             description "Multicast source redundancy group";
             type string;
           }
           container bfd-liveness-detection {
             description "Bidirectional Forwarding Detection (BFD) options";
             uses apply-advanced;
             leaf version {
               description "BFD protocol version number";
               default "automatic";
               type enumeration {
                 enum "0" {
                   description "BFD version 0 (deprecated)";
                 }
                 enum "1" {
                   description "BFD version 1";
                 }
                 enum "automatic" {
                   description "Choose BFD version automatically";
                 }
               }
             }
             leaf minimum-interval {
               description "Minimum transmit and receive interval";
               units "milliseconds";
               type union {
                 type string {
                   pattern "<.*>|$.*";
                 }
                 type uint32 {
                   range "1 .. 255000";
                 }
               }
             }
             leaf minimum-transmit-interval {
               description "Minimum transmit interval";
               status deprecated;
               units "milliseconds";
               type union {
                 type string {
                   pattern "<.*>|$.*";
                 }
                 type uint32 {
                   range "1 .. 255000";
                 }
               }
             }
             leaf minimum-receive-interval {
               description "Minimum receive interval";
               units "milliseconds";
               type union {
                 type string {
                   pattern "<.*>|$.*";
                 }
                 type uint32 {
                   range "1 .. 255000";
                 }
               }
             }
             leaf multiplier {
               description "Detection time multiplier";
               default "3";
               type union {
                 type string {
                   pattern "<.*>|$.*";
                 }
                 type uint32 {
                   range "1 .. 255";
                 }
               }
             }
             choice adaptation-choice {
               case case_1 {
                 leaf no-adaptation {
                   description "Disable adaptation";
                   type empty;
                 }
               }
             }
             container transmit-interval {
               description "Transmit-interval options";
               uses apply-advanced;
               leaf minimum-interval {
                 description "Minimum transmit interval";
                 units "milliseconds";
                 type union {
                   type string {
                     pattern "<.*>|$.*";
                   }
                   type uint32 {
                     range "1 .. 255000";
                   }
                 }
               }
               leaf threshold {
                 description "High transmit interval triggering a trap";
                 units "milliseconds";
                 type union {
                   type uint32;
                   type string {
                     pattern "<.*>|$.*";
                   }
                 }
               }
             }
             container detection-time {
               description "Detection-time options";
               uses apply-advanced;
               leaf threshold {
                 description "High detection-time triggering a trap";
                 units "milliseconds";
                 type union {
                   type uint32;
                   type string {
                     pattern "<.*>|$.*";
                   }
                 }
               }
             }
             container authentication {
               description "Authentication options";
               uses apply-advanced;
               leaf key-chain {
                 description "Key chain name";
                 type string;
               }
               leaf algorithm {
                 description "Algorithm name";
                 type enumeration {
                   enum "simple-password" {
                     description "Simple password";
                   }
                   enum "keyed-md5" {
                     description "Keyed message Digest 5";
                   }
                   enum "meticulous-keyed-md5" {
                     description "Meticulous keyed message Digest 5";
                   }
                   enum "keyed-sha-1" {
                     description "Keyed secure hash algorithm (SHA1) ";
                   }
                   enum "meticulous-keyed-sha-1" {
                     description "Meticulous keyed secure hash algorithm (SHA1) ";
                   }
                 }
               }
               leaf loose-check {
                 description "Verify authentication only if authentication is negotiated";
                 type empty;
               }
             }
             leaf neighbor {
               description "BFD neighbor address";
               type jt:ipaddr;
             }
             leaf local-address {
               description "BFD local address (for multihop only)";
               type jt:ipaddr;
             }
             leaf holddown-interval {
               description "Time to hold the session-UP notification to the client";
               units "milliseconds";
               type union {
                 type string {
                   pattern "<.*>|$.*";
                 }
                 type uint32 {
                   range "0 .. 255000";
                 }
               }
             }
             leaf minimum-receive-ttl {
               description "Minimum receive TTL below which to drop";
               type union {
                 type string {
                   pattern "<.*>|$.*";
                 }
                 type uint8 {
                   range "1 .. 255";
                 }
               }
             }
           }
           choice retain-choice {
             leaf retain {
               description "Always keep route in forwarding table";
               type empty;
             }
             leaf no-retain {
               description "Don't always keep route in forwarding table";
               type empty;
             }
           }
           choice install-choice {
             leaf install {
               description "Install route into forwarding table";
               type empty;
             }
             leaf no-install {
               description "Don't install route into forwarding table";
               type empty;
             }
           }
           choice readvertise-choice {
             leaf readvertise {
               description "Mark route as eligible to be readvertised";
               type empty;
             }
             leaf no-readvertise {
               description "Don't mark route as eligible to be readvertised";
               type empty;
             }
           }
           choice resolve-choice {
             leaf resolve {
               description "Allow resolution of indirectly connected next hops";
               type empty;
             }
             leaf no-resolve {
               description "Don't allow resolution of indirectly connected next hops";
               type empty;
             }
           }
           choice longest-match-choice {
             leaf longest-match {
               description "Always use longest prefix match to resolve next hops";
               type empty;
             }
             leaf no-longest-match {
               description "Don't always use longest prefix match to resolve next hops";
               type empty;
             }
           }
           choice passive_flag {
             case case_1 {
               leaf active {
                 description "Remove inactive route from forwarding table";
                 type empty;
               }
             }
             case case_2 {
               leaf passive {
                 description "Retain inactive route in forwarding table";
                 type empty;
               }
             }
           }
           container metric {
             description "Metric value";
             presence "enable metric";
             uses rib_static_metric_type;
           }
           container metric2 {
             description "Metric value 2";
             presence "enable metric2";
             uses rib_static_metric_type;
           }
           container metric3 {
             description "Metric value 3";
             presence "enable metric3";
             uses rib_static_metric_type;
           }
           container metric4 {
             description "Metric value 4";
             presence "enable metric4";
             uses rib_static_metric_type;
           }
           container tag {
             description "Tag string";
             presence "enable tag";
             uses rib_static_metric_type;
           }
           container tag2 {
             description "Tag string 2";
             presence "enable tag2";
             uses rib_static_metric_type;
           }
           container preference {
             description "Preference value";
             presence "enable preference";
             uses rib_static_metric_type;
           }
           container preference2 {
             description "Preference value 2";
             presence "enable preference2";
             uses rib_static_metric_type;
           }
           container color {
             description "Color (preference) value";
             presence "enable color";
             uses rib_static_metric_type;
           }
           container color2 {
             description "Color (preference) value 2";
             presence "enable color2";
             uses rib_static_metric_type;
           }
           leaf-list community {
             ordered-by user;
             description "BGP community identifier";
             type jt:community;
           }
           container as-path {
             description "Autonomous system path";
             uses apply-advanced;
             leaf path {
               description "Autonomous system path";
               type string;
             }
             leaf origin {
               type enumeration {
                 enum "igp" {
                   description "Path originated in the local IGP";
                 }
                 enum "egp" {
                   description "Path originated in another AS";
                 }
                 enum "incomplete" {
                   description "Path was learned by some other means";
                 }
               }
             }
             leaf atomic-aggregate {
               description "Add ATOMIC_AGGREGATE path attribute to route";
               type empty;
             }
             container aggregator {
               presence "enable aggregator";
               description "Add AGGREGATOR path attribute to route";
             }
             leaf as-number {
               description " Autonomous system number in plain number or 'higher 16bits'.'Lower 16 bits' (asdot notation) format";
               type string {
               }
             }
             leaf address {
               description "Address of BGP system that formed the route";
               type jt:ipv4addr;
             }
           }
         }
         container static-route {
           description "Static route Status";
           leaf bfd-admin-down {
             description "Static route State on BFD ADMIN DOWN";
             type enumeration {
               enum "active" {
                 description "Static route will be inactive on bfd-admin-down";
               }
               enum "passive" {
                 description "Static route will remain active on bfd-admin-down";
               }
             }
           }
         }
         list iso-route {
           key name;
           ordered-by user;
           description "ISO family static route";
           leaf name {
             type jt:isoprefix;
           }
           uses apply-advanced;
           choice next_hop {
             case case_1 {
               leaf-list next-hop {
                 ordered-by user;
                 description "Next hop to destination";
                 type union {
                   type jt:ipaddr-or-interface;
                   type string {
                     pattern "<.*>|$.*";
                   }
                 }
               }
             }
             case case_2 {
               leaf reject {
                 description "Drop packets to destination; send ICMP unreachables";
                 type empty;
               }
             }
             case case_3 {
               leaf discard {
                 description "Drop packets to destination; send no ICMP unreachables";
                 type empty;
               }
             }
             case case_4 {
               leaf receive {
                 description "Install a receive route for the destination";
                 type empty;
               }
             }
             case case_5 {
               leaf next-table {
                 description "Next hop to another table";
                 type string {
                 }
               }
             }
           }
           list qualified-next-hop {
             key name;
             ordered-by user;
             description "Next hop with qualifiers";
             uses qualified_nh_obj;
           }
           list lsp-next-hop {
             key name;
             ordered-by user;
             description "LSP next hop";
             uses lsp_nh_obj;
           }
           list static-lsp-next-hop {
             key name;
             ordered-by user;
             description "Static LSP next hop";
             uses lsp_nh_obj;
           }
           list p2mp-lsp-next-hop {
             key name;
             ordered-by user;
             description "Point-to-multipoint LSP next hop";
             max-elements 1;
             uses lsp_nh_obj;
           }
           container p2mp-ldp-next-hop {
             description "Point-to-multipoint LDP LSP next hop";
             uses p2mp_ldp_lsp_nh_obj;
           }
           leaf backup-pe-group {
             description "Multicast source redundancy group";
             type string;
           }
           container bfd-liveness-detection {
             description "Bidirectional Forwarding Detection (BFD) options";
             uses apply-advanced;
             leaf version {
               description "BFD protocol version number";
               default "automatic";
               type enumeration {
                 enum "0" {
                   description "BFD version 0 (deprecated)";
                 }
                 enum "1" {
                   description "BFD version 1";
                 }
                 enum "automatic" {
                   description "Choose BFD version automatically";
                 }
               }
             }
             leaf minimum-interval {
               description "Minimum transmit and receive interval";
               units "milliseconds";
               type union {
                 type string {
                   pattern "<.*>|$.*";
                 }
                 type uint32 {
                   range "1 .. 255000";
                 }
               }
             }
             leaf minimum-transmit-interval {
               description "Minimum transmit interval";
               status deprecated;
               units "milliseconds";
               type union {
                 type string {
                   pattern "<.*>|$.*";
                 }
                 type uint32 {
                   range "1 .. 255000";
                 }
               }
             }
             leaf minimum-receive-interval {
               description "Minimum receive interval";
               units "milliseconds";
               type union {
                 type string {
                   pattern "<.*>|$.*";
                 }
                 type uint32 {
                   range "1 .. 255000";
                 }
               }
             }
             leaf multiplier {
               description "Detection time multiplier";
               default "3";
               type union {
                 type string {
                   pattern "<.*>|$.*";
                 }
                 type uint32 {
                   range "1 .. 255";
                 }
               }
             }
             choice adaptation-choice {
               case case_1 {
                 leaf no-adaptation {
                   description "Disable adaptation";
                   type empty;
                 }
               }
             }
             container transmit-interval {
               description "Transmit-interval options";
               uses apply-advanced;
               leaf minimum-interval {
                 description "Minimum transmit interval";
                 units "milliseconds";
                 type union {
                   type string {
                     pattern "<.*>|$.*";
                   }
                   type uint32 {
                     range "1 .. 255000";
                   }
                 }
               }
               leaf threshold {
                 description "High transmit interval triggering a trap";
                 units "milliseconds";
                 type union {
                   type uint32;
                   type string {
                     pattern "<.*>|$.*";
                   }
                 }
               }
             }
             container detection-time {
               description "Detection-time options";
               uses apply-advanced;
               leaf threshold {
                 description "High detection-time triggering a trap";
                 units "milliseconds";
                 type union {
                   type uint32;
                   type string {
                     pattern "<.*>|$.*";
                   }
                 }
               }
             }
             container authentication {
               description "Authentication options";
               uses apply-advanced;
               leaf key-chain {
                 description "Key chain name";
                 type string;
               }
               leaf algorithm {
                 description "Algorithm name";
                 type enumeration {
                   enum "simple-password" {
                     description "Simple password";
                   }
                   enum "keyed-md5" {
                     description "Keyed message Digest 5";
                   }
                   enum "meticulous-keyed-md5" {
                     description "Meticulous keyed message Digest 5";
                   }
                   enum "keyed-sha-1" {
                     description "Keyed secure hash algorithm (SHA1) ";
                   }
                   enum "meticulous-keyed-sha-1" {
                     description "Meticulous keyed secure hash algorithm (SHA1) ";
                   }
                 }
               }
               leaf loose-check {
                 description "Verify authentication only if authentication is negotiated";
                 type empty;
               }
             }
             leaf neighbor {
               description "BFD neighbor address";
               type jt:ipaddr;
             }
             leaf local-address {
               description "BFD local address (for multihop only)";
               type jt:ipaddr;
             }
             leaf holddown-interval {
               description "Time to hold the session-UP notification to the client";
               units "milliseconds";
               type union {
                 type string {
                   pattern "<.*>|$.*";
                 }
                 type uint32 {
                   range "0 .. 255000";
                 }
               }
             }
             leaf minimum-receive-ttl {
               description "Minimum receive TTL below which to drop";
               type union {
                 type string {
                   pattern "<.*>|$.*";
                 }
                 type uint8 {
                   range "1 .. 255";
                 }
               }
             }
           }
           choice retain-choice {
             leaf retain {
               description "Always keep route in forwarding table";
               type empty;
             }
             leaf no-retain {
               description "Don't always keep route in forwarding table";
               type empty;
             }
           }
           choice install-choice {
             leaf install {
               description "Install route into forwarding table";
               type empty;
             }
             leaf no-install {
               description "Don't install route into forwarding table";
               type empty;
             }
           }
           choice readvertise-choice {
             leaf readvertise {
               description "Mark route as eligible to be readvertised";
               type empty;
             }
             leaf no-readvertise {
               description "Don't mark route as eligible to be readvertised";
               type empty;
             }
           }
           choice resolve-choice {
             leaf resolve {
               description "Allow resolution of indirectly connected next hops";
               type empty;
             }
             leaf no-resolve {
               description "Don't allow resolution of indirectly connected next hops";
               type empty;
             }
           }
           choice longest-match-choice {
             leaf longest-match {
               description "Always use longest prefix match to resolve next hops";
               type empty;
             }
             leaf no-longest-match {
               description "Don't always use longest prefix match to resolve next hops";
               type empty;
             }
           }
           choice passive_flag {
             case case_1 {
               leaf active {
                 description "Remove inactive route from forwarding table";
                 type empty;
               }
             }
             case case_2 {
               leaf passive {
                 description "Retain inactive route in forwarding table";
                 type empty;
               }
             }
           }
           container metric {
             description "Metric value";
             presence "enable metric";
             uses rib_static_metric_type;
           }
           container metric2 {
             description "Metric value 2";
             presence "enable metric2";
             uses rib_static_metric_type;
           }
           container metric3 {
             description "Metric value 3";
             presence "enable metric3";
             uses rib_static_metric_type;
           }
           container metric4 {
             description "Metric value 4";
             presence "enable metric4";
             uses rib_static_metric_type;
           }
           container tag {
             description "Tag string";
             presence "enable tag";
             uses rib_static_metric_type;
           }
           container tag2 {
             description "Tag string 2";
             presence "enable tag2";
             uses rib_static_metric_type;
           }
           container preference {
             description "Preference value";
             presence "enable preference";
             uses rib_static_metric_type;
           }
           container preference2 {
             description "Preference value 2";
             presence "enable preference2";
             uses rib_static_metric_type;
           }
           container color {
             description "Color (preference) value";
             presence "enable color";
             uses rib_static_metric_type;
           }
           container color2 {
             description "Color (preference) value 2";
             presence "enable color2";
             uses rib_static_metric_type;
           }
           leaf-list community {
             ordered-by user;
             description "BGP community identifier";
             type jt:community;
           }
           container as-path {
             description "Autonomous system path";
             uses apply-advanced;
             leaf path {
               description "Autonomous system path";
               type string;
             }
             leaf origin {
               type enumeration {
                 enum "igp" {
                   description "Path originated in the local IGP";
                 }
                 enum "egp" {
                   description "Path originated in another AS";
                 }
                 enum "incomplete" {
                   description "Path was learned by some other means";
                 }
               }
             }
             leaf atomic-aggregate {
               description "Add ATOMIC_AGGREGATE path attribute to route";
               type empty;
             }
             container aggregator {
               presence "enable aggregator";
               description "Add AGGREGATOR path attribute to route";
             }
             leaf as-number {
               description " Autonomous system number in plain number or 'higher 16bits'.'Lower 16 bits' (asdot notation) format";
               type string {
               }
             }
             leaf address {
               description "Address of BGP system that formed the route";
               type jt:ipv4addr;
             }
           }
         }
         list route-target-filter {
           key name;
           ordered-by user;
           description "Route-target-filter route";
           leaf name {
             type string {
               length "1 .. 47";
             }
           }
           uses apply-advanced;
           leaf-list neighbor {
             ordered-by user;
             description "BGP peers for filter";
             type jt:ipaddr;
           }
           leaf-list group {
             ordered-by user;
             description "BGP groups for filter";
             type string;
           }
           leaf local {
             description "Locally originated filter";
             type empty;
           }
         }
       }
       list martians {
         key "address choice-ident choice-value";
         ordered-by user;
         description "Invalid routes";
         uses martian_type;
       }
       container aggregate {
         description "Coalesced routes";
         uses rib_aggregate_type;
       }
       container generate {
         description "Route of last resort";
         uses rib_aggregate_type;
       }
       choice maximum-paths-type {
         case case_1 {
           container maximum-routes {
             description "Maximum number of routes";
             status deprecated;
             leaf limit {
               description "Maximum number of routes";
               type union {
                 type string {
                   pattern "<.*>|$.*";
                 }
                 type uint32 {
                   range "1 .. 4294967295";
                 }
               }
             }
             choice log_type {
               case case_1 {
                 leaf threshold {
                   description "Percentage of limit at which to start generating warnings";
                   type union {
                     type string {
                       pattern "<.*>|$.*";
                     }
                     type uint32 {
                       range "1 .. 100";
                     }
                   }
                 }
               }
               case case_2 {
                 leaf log-only {
                   description "Generate warning messages only";
                   type empty;
                 }
               }
             }
             leaf log-interval {
               description "Minimum interval between log messages";
               units "seconds";
               type union {
                 type string {
                   pattern "<.*>|$.*";
                 }
                 type uint32 {
                   range "5 .. 86400";
                 }
               }
             }
           }
         }
         case case_2 {
           container maximum-paths {
             description "Maximum number of paths";
             leaf limit {
               description "Maximum number of paths";
               type union {
                 type string {
                   pattern "<.*>|$.*";
                 }
                 type uint32 {
                   range "1 .. 4294967295";
                 }
               }
             }
             choice log_type {
               case case_1 {
                 leaf threshold {
                   description "Percentage of limit at which to start generating warnings";
                   type union {
                     type string {
                       pattern "<.*>|$.*";
                     }
                     type uint32 {
                       range "1 .. 100";
                     }
                   }
                 }
               }
               case case_2 {
                 leaf log-only {
                   description "Generate warning messages only";
                   type empty;
                 }
               }
             }
             leaf log-interval {
               description "Minimum interval between log messages";
               units "seconds";
               type union {
                 type string {
                   pattern "<.*>|$.*";
                 }
                 type uint32 {
                   range "5 .. 86400";
                 }
               }
             }
           }
         }
       }
       container maximum-prefixes {
         description "Maximum number of prefixes";
         leaf limit {
           description "Maximum number of prefixes";
           type union {
             type string {
               pattern "<.*>|$.*";
             }
             type uint32 {
               range "1 .. 4294967295";
             }
           }
         }
         choice log_type {
           case case_1 {
             leaf threshold {
               description "Percentage of limit at which to start generating warnings";
               type union {
                 type string {
                   pattern "<.*>|$.*";
                 }
                 type uint32 {
                   range "1 .. 100";
                 }
               }
             }
           }
           case case_2 {
             leaf log-only {
               description "Generate warning messages only";
               type empty;
             }
           }
         }
         leaf log-interval {
           description "Minimum interval between log messages";
           units "seconds";
           type union {
             type string {
               pattern "<.*>|$.*";
             }
             type uint32 {
               range "5 .. 86400";
             }
           }
         }
       }
       container multipath {
         presence "enable multipath";
         description "Protocol-independent load balancing";
         uses apply-advanced;
         container vpn-unequal-cost {
           presence "enable vpn-unequal-cost";
           description "Include VPN routes with unequal IGP metrics";
           leaf equal-external-internal {
             description "Include external and internal VPN routes";
             type empty;
           }
         }
         leaf as-path-compare {
           description "Compare AS path sequences in addition to AS path length";
           type empty;
         }
       }
       container policy-multipath {
         description "Policy based multipath";
         uses apply-advanced;
         leaf-list policy {
           ordered-by user;
           description "Import policy to create policy based multipath";
           type jt:policy-algebra;
         }
         container traceoptions {
           description "Trace options";
           uses apply-advanced;
           container file {
             description "Trace file options";
             leaf filename {
               description "Name of file in which to write trace information";
               type string {
                 length "1 .. 1024";
               }
             }
             leaf replace {
               description "Replace trace file rather than appending to it";
               status deprecated;
               type empty;
             }
             leaf size {
               description "Maximum trace file size";
               type string;
             }
             leaf files {
               description "Maximum number of trace files";
               default "10";
               type union {
                 type string {
                   pattern "<.*>|$.*";
                 }
                 type uint32 {
                   range "2 .. 1000";
                 }
               }
             }
             leaf no-stamp {
               description "Do not timestamp trace file";
               status deprecated;
               type empty;
             }
             choice world-readable-choice {
               leaf world-readable {
                 description "Allow any user to read the log file";
                 type empty;
               }
               leaf no-world-readable {
                 description "Don't allow any user to read the log file";
                 type empty;
               }
             }
           }
           list flag {
             key name;
             ordered-by user;
             description "Tracing parameters";
             leaf name {
               type enumeration {
                 enum "route" {
                   description "Policy-multipath route tracing.";
                 }
               }
             }
             leaf send {
               description "Trace transmitted packets";
               type empty;
             }
             leaf receive {
               description "Trace received packets";
               type empty;
             }
             leaf detail {
               description "Trace detailed information";
               type empty;
             }
             leaf disable {
               description "Disable this trace flag";
               type empty;
             }
           }
         }
       }
       container protect {
         description "Protocol-independent protection";
         leaf core {
           description "Protect against unreachability to service-edge router";
           type empty;
         }
       }
       container label {
         presence "enable label";
         description "Label processing";
         uses apply-advanced;
         leaf-list allocation {
           ordered-by user;
           description "Label allocation policy";
           type jt:policy-algebra;
         }
         leaf-list substitution {
           ordered-by user;
           description "Label substitution policy";
           type jt:policy-algebra;
         }
       }
       container access {
         description "Access routes";
         uses apply-advanced;
         list route {
           key name;
           ordered-by user;
           description "Access route";
           leaf name {
             description "IP address of destination";
             type jt:ipprefix;
           }
           uses apply-advanced;
           leaf-list next-hop {
             ordered-by user;
             description "Next hop to destination";
             type union {
               type jt:ipaddr-or-interface;
               type string {
                 pattern "<.*>|$.*";
               }
             }
           }
           list qualified-next-hop {
             key name;
             ordered-by user;
             description "Next hop with qualifiers";
             uses qualified_nh_obj;
           }
           leaf metric {
             description "Metric value";
             type union {
               type string {
                 pattern "<.*>|$.*";
               }
               type uint32 {
                 range "1 .. 255";
               }
             }
           }
           leaf preference {
             description "Preference value";
             type union {
               type uint32;
               type string {
                 pattern "<.*>|$.*";
               }
             }
           }
           leaf tag {
             description "Tag string";
             type union {
               type uint32;
               type string {
                 pattern "<.*>|$.*";
               }
             }
           }
           leaf tag2 {
             description "Tag2 string";
             type union {
               type uint32;
               type string {
                 pattern "<.*>|$.*";
               }
             }
           }
         }
       }
       container access-internal {
         description "Access-internal routes";
         uses apply-advanced;
         list route {
           key name;
           ordered-by user;
           description "Access-internal route";
           leaf name {
             description "IP address and optional prefix length of destination";
             type jt:ipprefix;
           }
           uses apply-advanced;
           leaf-list next-hop {
             ordered-by user;
             description "Next hop to destination";
             type union {
               type jt:ipaddr-or-interface;
               type string {
                 pattern "<.*>|$.*";
               }
             }
           }
           list qualified-next-hop {
             key name;
             ordered-by user;
             description "Next hop with qualifiers";
             uses qualified_nh_obj;
           }
         }
       }
       container bgp-static {
         description "Routes for BGP static advertisements";
         uses apply-advanced;
         list route {
           key name;
           ordered-by user;
           description "BGP-static route";
           leaf name {
             description "IP address and optional prefix length of destination";
             type jt:ipprefix;
           }
           uses apply-advanced;
           container metric {
             description "Metric value";
             presence "enable metric";
             uses rib_static_metric_type;
           }
           container metric2 {
             description "Metric value 2";
             presence "enable metric2";
             uses rib_static_metric_type;
           }
           container metric3 {
             description "Metric value 3";
             presence "enable metric3";
             uses rib_static_metric_type;
           }
           container metric4 {
             description "Metric value 4";
             presence "enable metric4";
             uses rib_static_metric_type;
           }
           container tag {
             description "Tag string";
             presence "enable tag";
             uses rib_static_metric_type;
           }
           container tag2 {
             description "Tag string 2";
             presence "enable tag2";
             uses rib_static_metric_type;
           }
           container preference {
             description "Preference value";
             presence "enable preference";
             uses rib_static_metric_type;
           }
           container preference2 {
             description "Preference value 2";
             presence "enable preference2";
             uses rib_static_metric_type;
           }
           container color {
             description "Color (preference) value";
             presence "enable color";
             uses rib_static_metric_type;
           }
           container color2 {
             description "Color (preference) value 2";
             presence "enable color2";
             uses rib_static_metric_type;
           }
           leaf-list community {
             ordered-by user;
             description "BGP community identifier";
             type jt:community;
           }
           container as-path {
             description "Autonomous system path";
             uses apply-advanced;
             leaf path {
               description "Autonomous system path";
               type string;
             }
             leaf origin {
               type enumeration {
                 enum "igp" {
                   description "Path originated in the local IGP";
                 }
                 enum "egp" {
                   description "Path originated in another AS";
                 }
                 enum "incomplete" {
                   description "Path was learned by some other means";
                 }
               }
             }
             leaf atomic-aggregate {
               description "Add ATOMIC_AGGREGATE path attribute to route";
               type empty;
             }
             container aggregator {
               presence "enable aggregator";
               description "Add AGGREGATOR path attribute to route";
             }
             leaf as-number {
               description " Autonomous system number in plain number or 'higher 16bits'.'Lower 16 bits' (asdot notation) format";
               type string {
               }
             }
             leaf address {
               description "Address of BGP system that formed the route";
               type jt:ipv4addr;
             }
           }
         }
       }
       container flow {
         description "Locally defined flow routing information";
         uses apply-advanced;
         container validation {
           description "Flow route validation options";
           presence "enable validation";
           uses flow-validation;
         }
         list route {
           key name;
           ordered-by user;
           description "Flow route";
           uses flow-route-inet6;
         }
         container interface-group {
           description "Interface-group for applying flow-spec filter";
           uses flow-interface-group;
         }
         leaf discard-action-for-unresolved-redir-addr {
           description "For action redirect to IP if, redirect address is unresolved install discard action filter";
           type empty;
         }
       }
     }
     container static {
       description "Static routes";
       uses apply-advanced;
       leaf rib-group {
         description "Routing table group";
         type string;
       }
       container defaults {
         description "Global route options";
         uses apply-advanced;
         choice retain-choice {
           leaf retain {
             description "Always keep route in forwarding table";
             type empty;
           }
           leaf no-retain {
             description "Don't always keep route in forwarding table";
             type empty;
           }
         }
         choice install-choice {
           leaf install {
             description "Install route into forwarding table";
             type empty;
           }
           leaf no-install {
             description "Don't install route into forwarding table";
             type empty;
           }
         }
         choice readvertise-choice {
           leaf readvertise {
             description "Mark route as eligible to be readvertised";
             type empty;
           }
           leaf no-readvertise {
             description "Don't mark route as eligible to be readvertised";
             type empty;
           }
         }
         choice resolve-choice {
           leaf resolve {
             description "Allow resolution of indirectly connected next hops";
             type empty;
           }
           leaf no-resolve {
             description "Don't allow resolution of indirectly connected next hops";
             type empty;
           }
         }
         choice longest-match-choice {
           leaf longest-match {
             description "Always use longest prefix match to resolve next hops";
             type empty;
           }
           leaf no-longest-match {
             description "Don't always use longest prefix match to resolve next hops";
             type empty;
           }
         }
         choice passive_flag {
           case case_1 {
             leaf active {
               description "Remove inactive route from forwarding table";
               type empty;
             }
           }
           case case_2 {
             leaf passive {
               description "Retain inactive route in forwarding table";
               type empty;
             }
           }
         }
         container metric {
           description "Metric value";
           presence "enable metric";
           uses rib_static_metric_type;
         }
         container metric2 {
           description "Metric value 2";
           presence "enable metric2";
           uses rib_static_metric_type;
         }
         container metric3 {
           description "Metric value 3";
           presence "enable metric3";
           uses rib_static_metric_type;
         }
         container metric4 {
           description "Metric value 4";
           presence "enable metric4";
           uses rib_static_metric_type;
         }
         container tag {
           description "Tag string";
           presence "enable tag";
           uses rib_static_metric_type;
         }
         container tag2 {
           description "Tag string 2";
           presence "enable tag2";
           uses rib_static_metric_type;
         }
         container preference {
           description "Preference value";
           presence "enable preference";
           uses rib_static_metric_type;
         }
         container preference2 {
           description "Preference value 2";
           presence "enable preference2";
           uses rib_static_metric_type;
         }
         container color {
           description "Color (preference) value";
           presence "enable color";
           uses rib_static_metric_type;
         }
         container color2 {
           description "Color (preference) value 2";
           presence "enable color2";
           uses rib_static_metric_type;
         }
         leaf-list community {
           ordered-by user;
           description "BGP community identifier";
           type jt:community;
         }
         container as-path {
           description "Autonomous system path";
           uses apply-advanced;
           leaf path {
             description "Autonomous system path";
             type string;
           }
           leaf origin {
             type enumeration {
               enum "igp" {
                 description "Path originated in the local IGP";
               }
               enum "egp" {
                 description "Path originated in another AS";
               }
               enum "incomplete" {
                 description "Path was learned by some other means";
               }
             }
           }
           leaf atomic-aggregate {
             description "Add ATOMIC_AGGREGATE path attribute to route";
             type empty;
           }
           container aggregator {
             presence "enable aggregator";
             description "Add AGGREGATOR path attribute to route";
           }
           leaf as-number {
             description " Autonomous system number in plain number or 'higher 16bits'.'Lower 16 bits' (asdot notation) format";
             type string {
             }
           }
           leaf address {
             description "Address of BGP system that formed the route";
             type jt:ipv4addr;
           }
         }
       }
       list route {
         key name;
         ordered-by user;
         description "Static route";
         leaf name {
           type jt:ipprefix;
         }
         uses apply-advanced;
         choice next_hop {
           case case_1 {
             leaf-list next-hop {
               ordered-by user;
               description "Next hop to destination";
               type union {
                 type jt:ipaddr-or-interface;
                 type string {
                   pattern "<.*>|$.*";
                 }
               }
             }
           }
           case case_2 {
             leaf reject {
               description "Drop packets to destination; send ICMP unreachables";
               type empty;
             }
           }
           case case_3 {
             leaf discard {
               description "Drop packets to destination; send no ICMP unreachables";
               type empty;
             }
           }
           case case_4 {
             leaf receive {
               description "Install a receive route for the destination";
               type empty;
             }
           }
           case case_5 {
             leaf next-table {
               description "Next hop to another table";
               type string {
               }
             }
           }
         }
         list qualified-next-hop {
           key name;
           ordered-by user;
           description "Next hop with qualifiers";
           uses qualified_nh_obj;
         }
         list lsp-next-hop {
           key name;
           ordered-by user;
           description "LSP next hop";
           uses lsp_nh_obj;
         }
         list static-lsp-next-hop {
           key name;
           ordered-by user;
           description "Static LSP next hop";
           uses lsp_nh_obj;
         }
         list p2mp-lsp-next-hop {
           key name;
           ordered-by user;
           description "Point-to-multipoint LSP next hop";
           max-elements 1;
           uses lsp_nh_obj;
         }
         container p2mp-ldp-next-hop {
           description "Point-to-multipoint LDP LSP next hop";
           uses p2mp_ldp_lsp_nh_obj;
         }
         leaf backup-pe-group {
           description "Multicast source redundancy group";
           type string;
         }
         container bfd-liveness-detection {
           description "Bidirectional Forwarding Detection (BFD) options";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
           container authentication {
             description "Authentication options";
             uses apply-advanced;
             leaf key-chain {
               description "Key chain name";
               type string;
             }
             leaf algorithm {
               description "Algorithm name";
               type enumeration {
                 enum "simple-password" {
                   description "Simple password";
                 }
                 enum "keyed-md5" {
                   description "Keyed message Digest 5";
                 }
                 enum "meticulous-keyed-md5" {
                   description "Meticulous keyed message Digest 5";
                 }
                 enum "keyed-sha-1" {
                   description "Keyed secure hash algorithm (SHA1) ";
                 }
                 enum "meticulous-keyed-sha-1" {
                   description "Meticulous keyed secure hash algorithm (SHA1) ";
                 }
               }
             }
             leaf loose-check {
               description "Verify authentication only if authentication is negotiated";
               type empty;
             }
           }
           leaf neighbor {
             description "BFD neighbor address";
             type jt:ipaddr;
           }
           leaf local-address {
             description "BFD local address (for multihop only)";
             type jt:ipaddr;
           }
           leaf holddown-interval {
             description "Time to hold the session-UP notification to the client";
             units "milliseconds";
             type union {
               type string {
                 pattern "<.*>|$.*";
               }
               type uint32 {
                 range "0 .. 255000";
               }
             }
           }
           leaf minimum-receive-ttl {
             description "Minimum receive TTL below which to drop";
             type union {
               type string {
                 pattern "<.*>|$.*";
               }
               type uint8 {
                 range "1 .. 255";
               }
             }
           }
         }
         choice retain-choice {
           leaf retain {
             description "Always keep route in forwarding table";
             type empty;
           }
           leaf no-retain {
             description "Don't always keep route in forwarding table";
             type empty;
           }
         }
         choice install-choice {
           leaf install {
             description "Install route into forwarding table";
             type empty;
           }
           leaf no-install {
             description "Don't install route into forwarding table";
             type empty;
           }
         }
         choice readvertise-choice {
           leaf readvertise {
             description "Mark route as eligible to be readvertised";
             type empty;
           }
           leaf no-readvertise {
             description "Don't mark route as eligible to be readvertised";
             type empty;
           }
         }
         choice resolve-choice {
           leaf resolve {
             description "Allow resolution of indirectly connected next hops";
             type empty;
           }
           leaf no-resolve {
             description "Don't allow resolution of indirectly connected next hops";
             type empty;
           }
         }
         choice longest-match-choice {
           leaf longest-match {
             description "Always use longest prefix match to resolve next hops";
             type empty;
           }
           leaf no-longest-match {
             description "Don't always use longest prefix match to resolve next hops";
             type empty;
           }
         }
         choice passive_flag {
           case case_1 {
             leaf active {
               description "Remove inactive route from forwarding table";
               type empty;
             }
           }
           case case_2 {
             leaf passive {
               description "Retain inactive route in forwarding table";
               type empty;
             }
           }
         }
         container metric {
           description "Metric value";
           presence "enable metric";
           uses rib_static_metric_type;
         }
         container metric2 {
           description "Metric value 2";
           presence "enable metric2";
           uses rib_static_metric_type;
         }
         container metric3 {
           description "Metric value 3";
           presence "enable metric3";
           uses rib_static_metric_type;
         }
         container metric4 {
           description "Metric value 4";
           presence "enable metric4";
           uses rib_static_metric_type;
         }
         container tag {
           description "Tag string";
           presence "enable tag";
           uses rib_static_metric_type;
         }
         container tag2 {
           description "Tag string 2";
           presence "enable tag2";
           uses rib_static_metric_type;
         }
         container preference {
           description "Preference value";
           presence "enable preference";
           uses rib_static_metric_type;
         }
         container preference2 {
           description "Preference value 2";
           presence "enable preference2";
           uses rib_static_metric_type;
         }
         container color {
           description "Color (preference) value";
           presence "enable color";
           uses rib_static_metric_type;
         }
         container color2 {
           description "Color (preference) value 2";
           presence "enable color2";
           uses rib_static_metric_type;
         }
         leaf-list community {
           ordered-by user;
           description "BGP community identifier";
           type jt:community;
         }
         container as-path {
           description "Autonomous system path";
           uses apply-advanced;
           leaf path {
             description "Autonomous system path";
             type string;
           }
           leaf origin {
             type enumeration {
               enum "igp" {
                 description "Path originated in the local IGP";
               }
               enum "egp" {
                 description "Path originated in another AS";
               }
               enum "incomplete" {
                 description "Path was learned by some other means";
               }
             }
           }
           leaf atomic-aggregate {
             description "Add ATOMIC_AGGREGATE path attribute to route";
             type empty;
           }
           container aggregator {
             presence "enable aggregator";
             description "Add AGGREGATOR path attribute to route";
           }
           leaf as-number {
             description " Autonomous system number in plain number or 'higher 16bits'.'Lower 16 bits' (asdot notation) format";
             type string {
             }
           }
           leaf address {
             description "Address of BGP system that formed the route";
             type jt:ipv4addr;
           }
         }
       }
       container static-route {
         description "Static route Status";
         leaf bfd-admin-down {
           description "Static route State on BFD ADMIN DOWN";
           type enumeration {
             enum "active" {
               description "Static route will be inactive on bfd-admin-down";
             }
             enum "passive" {
               description "Static route will remain active on bfd-admin-down";
             }
           }
         }
       }
       list iso-route {
         key name;
         ordered-by user;
         description "ISO family static route";
         leaf name {
           type jt:isoprefix;
         }
         uses apply-advanced;
         choice next_hop {
           case case_1 {
             leaf-list next-hop {
               ordered-by user;
               description "Next hop to destination";
               type union {
                 type jt:ipaddr-or-interface;
                 type string {
                   pattern "<.*>|$.*";
                 }
               }
             }
           }
           case case_2 {
             leaf reject {
               description "Drop packets to destination; send ICMP unreachables";
               type empty;
             }
           }
           case case_3 {
             leaf discard {
               description "Drop packets to destination; send no ICMP unreachables";
               type empty;
             }
           }
           case case_4 {
             leaf receive {
               description "Install a receive route for the destination";
               type empty;
             }
           }
           case case_5 {
             leaf next-table {
               description "Next hop to another table";
               type string {
               }
             }
           }
         }
         list qualified-next-hop {
           key name;
           ordered-by user;
           description "Next hop with qualifiers";
           uses qualified_nh_obj;
         }
         list lsp-next-hop {
           key name;
           ordered-by user;
           description "LSP next hop";
           uses lsp_nh_obj;
         }
         list static-lsp-next-hop {
           key name;
           ordered-by user;
           description "Static LSP next hop";
           uses lsp_nh_obj;
         }
         list p2mp-lsp-next-hop {
           key name;
           ordered-by user;
           description "Point-to-multipoint LSP next hop";
           max-elements 1;
           uses lsp_nh_obj;
         }
         container p2mp-ldp-next-hop {
           description "Point-to-multipoint LDP LSP next hop";
           uses p2mp_ldp_lsp_nh_obj;
         }
         leaf backup-pe-group {
           description "Multicast source redundancy group";
           type string;
         }
         container bfd-liveness-detection {
           description "Bidirectional Forwarding Detection (BFD) options";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
           container authentication {
             description "Authentication options";
             uses apply-advanced;
             leaf key-chain {
               description "Key chain name";
               type string;
             }
             leaf algorithm {
               description "Algorithm name";
               type enumeration {
                 enum "simple-password" {
                   description "Simple password";
                 }
                 enum "keyed-md5" {
                   description "Keyed message Digest 5";
                 }
                 enum "meticulous-keyed-md5" {
                   description "Meticulous keyed message Digest 5";
                 }
                 enum "keyed-sha-1" {
                   description "Keyed secure hash algorithm (SHA1) ";
                 }
                 enum "meticulous-keyed-sha-1" {
                   description "Meticulous keyed secure hash algorithm (SHA1) ";
                 }
               }
             }
             leaf loose-check {
               description "Verify authentication only if authentication is negotiated";
               type empty;
             }
           }
           leaf neighbor {
             description "BFD neighbor address";
             type jt:ipaddr;
           }
           leaf local-address {
             description "BFD local address (for multihop only)";
             type jt:ipaddr;
           }
           leaf holddown-interval {
             description "Time to hold the session-UP notification to the client";
             units "milliseconds";
             type union {
               type string {
                 pattern "<.*>|$.*";
               }
               type uint32 {
                 range "0 .. 255000";
               }
             }
           }
           leaf minimum-receive-ttl {
             description "Minimum receive TTL below which to drop";
             type union {
               type string {
                 pattern "<.*>|$.*";
               }
               type uint8 {
                 range "1 .. 255";
               }
             }
           }
         }
         choice retain-choice {
           leaf retain {
             description "Always keep route in forwarding table";
             type empty;
           }
           leaf no-retain {
             description "Don't always keep route in forwarding table";
             type empty;
           }
         }
         choice install-choice {
           leaf install {
             description "Install route into forwarding table";
             type empty;
           }
           leaf no-install {
             description "Don't install route into forwarding table";
             type empty;
           }
         }
         choice readvertise-choice {
           leaf readvertise {
             description "Mark route as eligible to be readvertised";
             type empty;
           }
           leaf no-readvertise {
             description "Don't mark route as eligible to be readvertised";
             type empty;
           }
         }
         choice resolve-choice {
           leaf resolve {
             description "Allow resolution of indirectly connected next hops";
             type empty;
           }
           leaf no-resolve {
             description "Don't allow resolution of indirectly connected next hops";
             type empty;
           }
         }
         choice longest-match-choice {
           leaf longest-match {
             description "Always use longest prefix match to resolve next hops";
             type empty;
           }
           leaf no-longest-match {
             description "Don't always use longest prefix match to resolve next hops";
             type empty;
           }
         }
         choice passive_flag {
           case case_1 {
             leaf active {
               description "Remove inactive route from forwarding table";
               type empty;
             }
           }
           case case_2 {
             leaf passive {
               description "Retain inactive route in forwarding table";
               type empty;
             }
           }
         }
         container metric {
           description "Metric value";
           presence "enable metric";
           uses rib_static_metric_type;
         }
         container metric2 {
           description "Metric value 2";
           presence "enable metric2";
           uses rib_static_metric_type;
         }
         container metric3 {
           description "Metric value 3";
           presence "enable metric3";
           uses rib_static_metric_type;
         }
         container metric4 {
           description "Metric value 4";
           presence "enable metric4";
           uses rib_static_metric_type;
         }
         container tag {
           description "Tag string";
           presence "enable tag";
           uses rib_static_metric_type;
         }
         container tag2 {
           description "Tag string 2";
           presence "enable tag2";
           uses rib_static_metric_type;
         }
         container preference {
           description "Preference value";
           presence "enable preference";
           uses rib_static_metric_type;
         }
         container preference2 {
           description "Preference value 2";
           presence "enable preference2";
           uses rib_static_metric_type;
         }
         container color {
           description "Color (preference) value";
           presence "enable color";
           uses rib_static_metric_type;
         }
         container color2 {
           description "Color (preference) value 2";
           presence "enable color2";
           uses rib_static_metric_type;
         }
         leaf-list community {
           ordered-by user;
           description "BGP community identifier";
           type jt:community;
         }
         container as-path {
           description "Autonomous system path";
           uses apply-advanced;
           leaf path {
             description "Autonomous system path";
             type string;
           }
           leaf origin {
             type enumeration {
               enum "igp" {
                 description "Path originated in the local IGP";
               }
               enum "egp" {
                 description "Path originated in another AS";
               }
               enum "incomplete" {
                 description "Path was learned by some other means";
               }
             }
           }
           leaf atomic-aggregate {
             description "Add ATOMIC_AGGREGATE path attribute to route";
             type empty;
           }
           container aggregator {
             presence "enable aggregator";
             description "Add AGGREGATOR path attribute to route";
           }
           leaf as-number {
             description " Autonomous system number in plain number or 'higher 16bits'.'Lower 16 bits' (asdot notation) format";
             type string {
             }
           }
           leaf address {
             description "Address of BGP system that formed the route";
             type jt:ipv4addr;
           }
         }
       }
       list route-target-filter {
         key name;
         ordered-by user;
         description "Route-target-filter route";
         leaf name {
           type string {
             length "1 .. 47";
           }
         }
         uses apply-advanced;
         leaf-list neighbor {
           ordered-by user;
           description "BGP peers for filter";
           type jt:ipaddr;
         }
         leaf-list group {
           ordered-by user;
           description "BGP groups for filter";
           type string;
         }
         leaf local {
           description "Locally originated filter";
           type empty;
         }
       }
     }
     list martians {
       key "address choice-ident choice-value";
       ordered-by user;
       description "Invalid routes";
       uses martian_type;
     }
     container aggregate {
       description "Coalesced routes";
       uses rib_aggregate_type;
     }
     container generate {
       description "Route of last resort";
       uses rib_aggregate_type;
     }
     choice maximum-paths-type {
       case case_1 {
         container maximum-routes {
           description "Maximum number of routes";
           status deprecated;
           leaf limit {
             description "Maximum number of routes";
             type union {
               type string {
                 pattern "<.*>|$.*";
               }
               type uint32 {
                 range "1 .. 4294967295";
               }
             }
           }
           choice log_type {
             case case_1 {
               leaf threshold {
                 description "Percentage of limit at which to start generating warnings";
                 type union {
                   type string {
                     pattern "<.*>|$.*";
                   }
                   type uint32 {
                     range "1 .. 100";
                   }
                 }
               }
             }
             case case_2 {
               leaf log-only {
                 description "Generate warning messages only";
                 type empty;
               }
             }
           }
           leaf log-interval {
             description "Minimum interval between log messages";
             units "seconds";
             type union {
               type string {
                 pattern "<.*>|$.*";
               }
               type uint32 {
                 range "5 .. 86400";
               }
             }
           }
         }
       }
       case case_2 {
         container maximum-paths {
           description "Maximum number of paths";
           leaf limit {
             description "Maximum number of paths";
             type union {
               type string {
                 pattern "<.*>|$.*";
               }
               type uint32 {
                 range "1 .. 4294967295";
               }
             }
           }
           choice log_type {
             case case_1 {
               leaf threshold {
                 description "Percentage of limit at which to start generating warnings";
                 type union {
                   type string {
                     pattern "<.*>|$.*";
                   }
                   type uint32 {
                     range "1 .. 100";
                   }
                 }
               }
             }
             case case_2 {
               leaf log-only {
                 description "Generate warning messages only";
                 type empty;
               }
             }
           }
           leaf log-interval {
             description "Minimum interval between log messages";
             units "seconds";
             type union {
               type string {
                 pattern "<.*>|$.*";
               }
               type uint32 {
                 range "5 .. 86400";
               }
             }
           }
         }
       }
     }
     container maximum-prefixes {
       description "Maximum number of prefixes";
       leaf limit {
         description "Maximum number of prefixes";
         type union {
           type string {
             pattern "<.*>|$.*";
           }
           type uint32 {
             range "1 .. 4294967295";
           }
         }
       }
       choice log_type {
         case case_1 {
           leaf threshold {
             description "Percentage of limit at which to start generating warnings";
             type union {
               type string {
                 pattern "<.*>|$.*";
               }
               type uint32 {
                 range "1 .. 100";
               }
             }
           }
         }
         case case_2 {
           leaf log-only {
             description "Generate warning messages only";
             type empty;
           }
         }
       }
       leaf log-interval {
         description "Minimum interval between log messages";
         units "seconds";
         type union {
           type string {
             pattern "<.*>|$.*";
           }
           type uint32 {
             range "5 .. 86400";
           }
         }
       }
     }
     container multipath {
       presence "enable multipath";
       description "Protocol-independent load balancing";
       uses apply-advanced;
       container vpn-unequal-cost {
         presence "enable vpn-unequal-cost";
         description "Include VPN routes with unequal IGP metrics";
         leaf equal-external-internal {
           description "Include external and internal VPN routes";
           type empty;
         }
       }
       leaf as-path-compare {
         description "Compare AS path sequences in addition to AS path length";
         type empty;
       }
     }
     container policy-multipath {
       description "Policy based multipath";
       uses apply-advanced;
       leaf-list policy {
         ordered-by user;
         description "Import policy to create policy based multipath";
         type jt:policy-algebra;
       }
       container traceoptions {
         description "Trace options";
         uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "route" {
                 description "Policy-multipath route tracing.";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
     }
     container protect {
       description "Protocol-independent protection";
       leaf core {
         description "Protect against unreachability to service-edge router";
         type empty;
       }
     }
     container label {
       presence "enable label";
       description "Label processing";
       uses apply-advanced;
       leaf-list allocation {
         ordered-by user;
         description "Label allocation policy";
         type jt:policy-algebra;
       }
       leaf-list substitution {
         ordered-by user;
         description "Label substitution policy";
         type jt:policy-algebra;
       }
     }
     container access {
       description "Access routes";
       uses apply-advanced;
       list route {
         key name;
         ordered-by user;
         description "Access route";
         leaf name {
           description "IP address of destination";
           type jt:ipprefix;
         }
         uses apply-advanced;
         leaf-list next-hop {
           ordered-by user;
           description "Next hop to destination";
           type union {
             type jt:ipaddr-or-interface;
             type string {
               pattern "<.*>|$.*";
             }
           }
         }
         list qualified-next-hop {
           key name;
           ordered-by user;
           description "Next hop with qualifiers";
           uses qualified_nh_obj;
         }
         leaf metric {
           description "Metric value";
           type union {
             type string {
               pattern "<.*>|$.*";
             }
             type uint32 {
               range "1 .. 255";
             }
           }
         }
         leaf preference {
           description "Preference value";
           type union {
             type uint32;
             type string {
               pattern "<.*>|$.*";
             }
           }
         }
         leaf tag {
           description "Tag string";
           type union {
             type uint32;
             type string {
               pattern "<.*>|$.*";
             }
           }
         }
         leaf tag2 {
           description "Tag2 string";
           type union {
             type uint32;
             type string {
               pattern "<.*>|$.*";
             }
           }
         }
       }
     }
     container access-internal {
       description "Access-internal routes";
       uses apply-advanced;
       list route {
         key name;
         ordered-by user;
         description "Access-internal route";
         leaf name {
           description "IP address and optional prefix length of destination";
           type jt:ipprefix;
         }
         uses apply-advanced;
         leaf-list next-hop {
           ordered-by user;
           description "Next hop to destination";
           type union {
             type jt:ipaddr-or-interface;
             type string {
               pattern "<.*>|$.*";
             }
           }
         }
         list qualified-next-hop {
           key name;
           ordered-by user;
           description "Next hop with qualifiers";
           uses qualified_nh_obj;
         }
       }
     }
     container bgp-static {
       description "Routes for BGP static advertisements";
       uses apply-advanced;
       list route {
         key name;
         ordered-by user;
         description "BGP-static route";
         leaf name {
           description "IP address and optional prefix length of destination";
           type jt:ipprefix;
         }
         uses apply-advanced;
         container metric {
           description "Metric value";
           presence "enable metric";
           uses rib_static_metric_type;
         }
         container metric2 {
           description "Metric value 2";
           presence "enable metric2";
           uses rib_static_metric_type;
         }
         container metric3 {
           description "Metric value 3";
           presence "enable metric3";
           uses rib_static_metric_type;
         }
         container metric4 {
           description "Metric value 4";
           presence "enable metric4";
           uses rib_static_metric_type;
         }
         container tag {
           description "Tag string";
           presence "enable tag";
           uses rib_static_metric_type;
         }
         container tag2 {
           description "Tag string 2";
           presence "enable tag2";
           uses rib_static_metric_type;
         }
         container preference {
           description "Preference value";
           presence "enable preference";
           uses rib_static_metric_type;
         }
         container preference2 {
           description "Preference value 2";
           presence "enable preference2";
           uses rib_static_metric_type;
         }
         container color {
           description "Color (preference) value";
           presence "enable color";
           uses rib_static_metric_type;
         }
         container color2 {
           description "Color (preference) value 2";
           presence "enable color2";
           uses rib_static_metric_type;
         }
         leaf-list community {
           ordered-by user;
           description "BGP community identifier";
           type jt:community;
         }
         container as-path {
           description "Autonomous system path";
           uses apply-advanced;
           leaf path {
             description "Autonomous system path";
             type string;
           }
           leaf origin {
             type enumeration {
               enum "igp" {
                 description "Path originated in the local IGP";
               }
               enum "egp" {
                 description "Path originated in another AS";
               }
               enum "incomplete" {
                 description "Path was learned by some other means";
               }
             }
           }
           leaf atomic-aggregate {
             description "Add ATOMIC_AGGREGATE path attribute to route";
             type empty;
           }
           container aggregator {
             presence "enable aggregator";
             description "Add AGGREGATOR path attribute to route";
           }
           leaf as-number {
             description " Autonomous system number in plain number or 'higher 16bits'.'Lower 16 bits' (asdot notation) format";
             type string {
             }
           }
           leaf address {
             description "Address of BGP system that formed the route";
             type jt:ipv4addr;
           }
         }
       }
     }
     container flow {
       description "Locally defined flow routing information";
       uses apply-advanced;
       container validation {
         description "Flow route validation options";
         presence "enable validation";
         uses flow-validation;
       }
       list route {
         key name;
         ordered-by user;
         description "Flow route";
         uses flow-route-inet;
       }
       container interface-group {
         description "Interface-group for applying flow-spec filter";
         uses flow-interface-group;
       }
       leaf discard-action-for-unresolved-redir-addr {
         description "For action redirect to IP if, redirect address is unresolved install discard action filter";
         type empty;
       }
       leaf firewall-install-disable {
         description "Disable installing flowspec firewall filters in dfwd ";
         type empty;
       }
       leaf term-order {
         description "Term evaluation order for flow routes";
         type enumeration {
           enum "legacy" {
             description "Legacy term order (default)";
           }
           enum "standard" {
             description "RFC compliant term order";
           }
         }
       }
     }
     list rib-groups {
       key name;
       ordered-by user;
       description "Group of routing tables";
       uses rpd_rib_group_type;
     }
     leaf route-record {
       description "Enable route recording";
       type empty;
     }
     leaf router-id {
       description "Router identifier";
       type jt:ipv4addr;
     }
     leaf route-distinguisher-id {
       description "Identifier used in route distinguishers for routing instances";
       type jt:ipv4addr;
     }
     container autonomous-system {
       description "Autonomous system number";
       leaf as-number {
         description " Autonomous system number in plain number or 'higher 16bits'.'Lower 16 bits' (asdot notation) format";
         type string {
         }
       }
       leaf loops {
         description "Maximum number of times this AS can be in an AS path";
         type union {
           type string {
             pattern "<.*>|$.*";
           }
           type int32 {
             range "1 .. 10";
           }
         }
       }
       leaf asdot-notation {
         description "Use AS-Dot notation to display true 4 byte AS numbers";
         type empty;
       }
       container independent-domain {
         presence "enable independent-domain";
         description "Independent autonomous-system domain from master instance";
         leaf no-attrset {
           description "Do not tunnel ce bgp attributes across provider network";
           type empty;
         }
       }
     }
     container confederation {
       description "Confederation autonomous system number";
       leaf confederation-as {
         description " Autonomous system number in plain number or 'higher 16bits'.'Lower 16 bits' (asdot notation) format";
         type string {
         }
       }
       leaf-list members {
         ordered-by user;
         description " Autonomous system number in plain number or 'higher 16bits'.'Lower 16 bits' (asdot notation) format";
         type string;
       }
     }
     list interface {
       key name;
       ordered-by user;
       description "Direct/Host route FRR protection";
       leaf name {
         description "Interface name";
         type union {
           type jt:interface-name;
           type string {
             pattern "<.*>|$.*";
           }
         }
       }
       uses apply-advanced;
       leaf arp-prefix-limit {
         description "Max ARP/Host FRR routes allowed";
         type union {
           type string {
             pattern "<.*>|$.*";
           }
           type uint32 {
             range "1 .. 10000";
           }
         }
       }
       leaf supplementary-blackout-timer {
         description "ARP plimit blackout timer = kernel ARP timeout + supplementary-blackout-timer minutes.";
         type union {
           type string {
             pattern "<.*>|$.*";
           }
           type uint32 {
             range "1 .. 15";
           }
         }
       }
       choice protection-type {
         case case_1 {
           leaf link-protection {
             description "Protect interface from link faults only";
             type empty;
           }
         }
       }
     }
     container host-fast-reroute {
       presence "enable host-fast-reroute";
       description "Host Fast Re-route global values. Applies to all host FRR profiles.";
       uses apply-advanced;
       leaf global-arp-prefix-limit {
         description "Max ARP/Host FRR routes allowed per protected IFL";
         type union {
           type string {
             pattern "<.*>|$.*";
           }
           type uint32 {
             range "1 .. 10000";
           }
         }
       }
       leaf global-supplementary-blackout-timer {
         description "ARP plimit global blackout timer = kernel ARP timeout + global-supplementary-blackout-timer minutes.";
         type union {
           type string {
             pattern "<.*>|$.*";
           }
           type uint32 {
             range "1 .. 15";
           }
         }
       }
     }
     container forwarding-table {
       uses forwarding-table-type;
     }
     container resolution {
       presence "enable resolution";
       description "Route next-hop resolution options";
       uses apply-advanced;
       leaf-list tracefilter {
         ordered-by user;
         description "Filter policy";
         type jt:policy-algebra;
       }
       container traceoptions {
         description "Trace options";
         uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "event" {
                 description "Event processing";
               }
               enum "flash" {
                 description "Flash processing";
               }
               enum "kernel" {
                 description "Kernel communication";
               }
               enum "indirect" {
                 description "Indirect next-hop addition, change, or deletion";
               }
               enum "task" {
                 description "Task or job processing";
               }
               enum "igp-frr" {
                 description "IGP triggered FRR events";
               }
               enum "igp-frr-extensive" {
                 description "IGP triggered FRR Extensive events";
               }
               enum "tunnel" {
                 description "Resolver dynamic tunnel events";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       list rib {
         key name;
         ordered-by user;
         description "Routing table resolution options";
         leaf name {
           description "Routing table name";
           type string;
         }
         uses apply-advanced;
         leaf-list resolution-family {
           ordered-by user;
           description "Family of resultion tree";
           type string;
         }
         leaf-list resolution-ribs {
           ordered-by user;
           description "Routing tables to use for default routing table family resolution";
           type string;
         }
         leaf-list inet-resolution-ribs {
           ordered-by user;
           description "Routing tables to use for ipv4 family protocol-next-hop resolution";
           type string;
         }
         leaf-list inet6-resolution-ribs {
           ordered-by user;
           description "Routing tables to use for ipv6 family protocol-next-hop resolution";
           type string;
         }
         leaf-list iso-resolution-ribs {
           ordered-by user;
           description "Routing tables to use for iso family protocol-next-hop resolution";
           type string;
         }
         leaf-list import {
           ordered-by user;
           description "Import policy";
           type jt:policy-algebra;
         }
         leaf-list inet-import {
           ordered-by user;
           description "Import policy for IPV4 family resolution tree";
           type jt:policy-algebra;
         }
         leaf-list inet6-import {
           ordered-by user;
           description "Import policy for IPV6 family resolution tree";
           type jt:policy-algebra;
         }
         leaf-list iso-import {
           ordered-by user;
           description "Import policy for ISO family resolution tree";
           type jt:policy-algebra;
         }
         leaf-list inetcolor-import {
           ordered-by user;
           description "Import policy for INETCOLOR family resolution tree";
           type jt:policy-algebra;
         }
         leaf-list inet6color-import {
           ordered-by user;
           description "Import policy for INET6COLOR family resolution tree";
           type jt:policy-algebra;
         }
       }
       choice prefer-recursive-primary-path-choice {
         leaf prefer-recursive-primary-path {
           description "Prefer primary path to resolve nexthop during recursive-resolution";
           type empty;
         }
         leaf no-prefer-recursive-primary-path {
           description "Don't prefer primary path to resolve nexthop during recursive-resolution";
           type empty;
         }
       }
     }
     leaf-list instance-import {
       ordered-by user;
       description "Import policy for instance RIBs";
       type jt:policy-algebra;
     }
     leaf-list instance-export {
       ordered-by user;
       description "Export policy for instance RIBs";
       type jt:policy-algebra;
     }
     container auto-export {
       presence "enable auto-export";
       description "Export routes between routing instances";
       uses apply-advanced;
       choice enable-disable {
         case case_1 {
           leaf disable {
             description "Disable auto-export";
             type empty;
           }
         }
       }
       container traceoptions {
         description "Trace options";
         uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "export" {
                 description "Export processing";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       container family {
         container inet {
           description "IPv4 parameters";
           uses export-af-obj;
         }
         container inet6 {
           description "IPv6 parameters";
           uses export-af-obj;
         }
         container iso {
           description "ISO parameters";
           uses export-af-obj;
         }
       }
     }
     container programmable-rpd {
       description "RPD Server module management options";
       uses programmable-rpd-type;
     }
     container topologies {
       description "Define routing topologies";
       uses apply-advanced;
       list family {
         key name;
         ordered-by user;
         description "Address family";
         leaf name {
           type enumeration {
             enum "inet" {
               description "IPv4 family";
             }
             enum "inet6" {
               description "IPv6 family";
             }
           }
         }
         uses apply-advanced;
         list topology {
           key name;
           ordered-by user;
           description "Topology information";
           leaf name {
             description "Topology name";
             type string {
             }
           }
           uses apply-advanced;
         }
       }
     }
     container backup-selection {
       presence "enable backup-selection";
       description "Backup selection options";
       uses apply-advanced;
       list destination {
         key name;
         description "IP/IPv6 prefix for which backup selection policy is configured";
         leaf name {
           description "IP/IPv6 address (and optional prefix length)";
           type jt:ipprefix-mandatory;
         }
         uses apply-advanced;
         list interface {
           key name;
           description "Primary nexthop interface for which backup selection policy is configured";
           leaf name {
             description "Interface name";
             type union {
               type jt:interface-name;
               type string {
                 pattern "<.*>|$.*";
               }
             }
           }
           uses apply-advanced;
           container admin-group {
             description "Administrative group policies for backup-selection";
             uses apply-advanced;
             leaf-list exclude {
               description "Do not use interface if any admin group available";
               type string;
             }
             leaf-list include-all {
               description "Use interface if admin groups available entirely";
               type string;
             }
             leaf-list include-any {
               description "Use interface if any admin group is available";
               type string;
             }
             leaf-list preference {
               ordered-by user;
               description "Administrative groups in descending preference order";
               type string;
             }
           }
           leaf srlg {
             description "Evaluate Shared Risk Link Group(SRLG) characteristics for backup selection";
             default "loose";
             type enumeration {
               enum "loose" {
                 description "Loose SRLG";
               }
               enum "strict" {
                 description "Strict SRLG";
               }
             }
           }
           leaf protection-type {
             description "Type of protection to be considered";
             type enumeration {
               enum "link" {
                 description "Protect the primary interface from link faults only";
               }
               enum "node" {
                 description "Protect the primary interface from node faults only";
               }
               enum "node-link" {
                 description "Protect the primary interface from either link or node faults; prefer node protection";
               }
             }
           }
           leaf downstream-paths-only {
             description "Choose only the downstream nodes for backup";
             type empty;
           }
           leaf bandwidth-greater-equal-primary {
             description "Use backup nexthop only if bandwidth is >= bandwidth of primary nexthop";
             type empty;
           }
           container backup-neighbor {
             description "Backup Neighbor ID based policies for backup selection";
             uses apply-advanced;
             leaf-list exclude {
               description "List of backup neighbors to be excluded";
               type jt:ipv4addr;
             }
             leaf-list preference {
               ordered-by user;
               description "List of backup neighbors in descending order preference";
               type jt:ipv4addr;
             }
           }
           container node {
             description "Node ID based policies for backup selection";
             uses apply-advanced;
             leaf-list exclude {
               description "List of nodes to be excluded";
               type jt:ipv4addr;
             }
             leaf-list preference {
               ordered-by user;
               description "List of nodes in the descending order of preference";
               type jt:ipv4addr;
             }
           }
           container node-tag {
             description "Node  tag policies";
             uses apply-advanced;
             leaf-list exclude {
               description "The set of node tags to be excluded";
               type union {
                 type uint32;
                 type string {
                   pattern "<.*>|$.*";
                 }
               }
             }
             leaf-list preference {
               ordered-by user;
               description "The set of node tags in the descending order of preference";
               type union {
                 type uint32;
                 type string {
                   pattern "<.*>|$.*";
                 }
               }
             }
           }
           leaf root-metric {
             description "Root metric";
             type enumeration {
               enum "lowest" {
                 description "Choose lowest root metric";
               }
               enum "highest" {
                 description "Choose highest root metric";
               }
             }
           }
           leaf dest-metric {
             description "Destination metric";
             type enumeration {
               enum "lowest" {
                 description "Choose lowest destination metric";
               }
               enum "highest" {
                 description "Choose highest destination metric";
               }
             }
           }
           leaf-list metric-order {
             ordered-by user;
             description "Metric evaluation order";
             type enumeration {
               enum "root" {
               }
               enum "dest" {
               }
             }
             max-elements 2;
           }
           leaf-list evaluation-order {
             ordered-by user;
             description "Interface policy criteria evaluation order";
             type enumeration {
               enum "admin-group" {
                 description "Administrative Group/Link Color";
               }
               enum "srlg" {
                 description "SRLG";
               }
               enum "bandwidth" {
                 description "Bandwidth";
               }
               enum "protection-type" {
                 description "Type of protection";
               }
               enum "backup-neighbor" {
                 description "Backup Neighbor";
               }
               enum "node" {
                 description "Node";
               }
               enum "node-tag" {
                 description "Node tag";
               }
               enum "metric" {
                 description "Metric related parameters";
               }
             }
           }
         }
       }
     }
     container validation {
       description "Define Route validation";
       uses apply-advanced;
       container traceoptions {
         description "Trace options for route validation";
         uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "error" {
                 description "Trace errored packets";
               }
               enum "packets" {
                 description "Trace all I/O packets";
               }
               enum "keepalive" {
                 description "Trace keepalive packets";
               }
               enum "update" {
                 description "Trace update packets";
               }
               enum "nsr-synchronization" {
                 description "Trace NSR synchronization events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       leaf-list notification-rib {
         ordered-by user;
         description "Define routing tables that get notified upon validation state change";
         type string;
       }
       list group {
         key name;
         description "Define a group of sessions";
         leaf name {
           description "Group name";
           type string;
         }
         uses apply-advanced;
         leaf max-sessions {
           description "Maximum connected session in this group";
           type union {
             type string {
               pattern "<.*>|$.*";
             }
             type uint32 {
               range "1 .. 63";
             }
           }
         }
         list session {
           key name;
           description "Configure a session";
           leaf name {
             type jt:ipaddr;
           }
           uses apply-advanced;
           container traceoptions {
             description "Trace options for route validation";
             uses apply-advanced;
             container file {
               description "Trace file options";
               leaf filename {
                 description "Name of file in which to write trace information";
                 type string {
                   length "1 .. 1024";
                 }
               }
               leaf replace {
                 description "Replace trace file rather than appending to it";
                 status deprecated;
                 type empty;
               }
               leaf size {
                 description "Maximum trace file size";
                 type string;
               }
               leaf files {
                 description "Maximum number of trace files";
                 default "10";
                 type union {
                   type string {
                     pattern "<.*>|$.*";
                   }
                   type uint32 {
                     range "2 .. 1000";
                   }
                 }
               }
               leaf no-stamp {
                 description "Do not timestamp trace file";
                 status deprecated;
                 type empty;
               }
               choice world-readable-choice {
                 leaf world-readable {
                   description "Allow any user to read the log file";
                   type empty;
                 }
                 leaf no-world-readable {
                   description "Don't allow any user to read the log file";
                   type empty;
                 }
               }
             }
             list flag {
               key name;
               ordered-by user;
               description "Tracing parameters";
               leaf name {
                 type enumeration {
                   enum "error" {
                     description "Trace errored packets";
                   }
                   enum "packets" {
                     description "Trace all I/O packets";
                   }
                   enum "keepalive" {
                     description "Trace keepalive packets";
                   }
                   enum "update" {
                     description "Trace update packets";
                   }
                   enum "state" {
                     description "Trace state transitions";
                   }
                   enum "task" {
                     description "Trace routing protocol task processing";
                   }
                   enum "timer" {
                     description "Trace routing protocol timer processing";
                   }
                   enum "all" {
                     description "Trace everything";
                   }
                 }
               }
               leaf send {
                 description "Trace transmitted packets";
                 type empty;
               }
               leaf receive {
                 description "Trace received packets";
                 type empty;
               }
               leaf detail {
                 description "Trace detailed information";
                 type empty;
               }
               leaf disable {
                 description "Disable this trace flag";
                 type empty;
               }
             }
           }
           leaf refresh-time {
             description "Interval between keepalive packet transmissions";
             units "seconds";
             type union {
               type string {
                 pattern "<.*>|$.*";
               }
               type uint32 {
                 range "1 .. 1800";
               }
             }
           }
           leaf hold-time {
             description "Time after which the session is declared down.";
             units "seconds";
             type union {
               type string {
                 pattern "<.*>|$.*";
               }
               type uint32 {
                 range "10 .. 3600";
               }
             }
           }
           leaf record-lifetime {
             description "Lifetime of route validation records";
             units "seconds";
             type union {
               type string {
                 pattern "<.*>|$.*";
               }
               type uint32 {
                 range "60 .. 604800";
               }
             }
           }
           leaf preference {
             description "Preference for session establishment";
             type union {
               type string {
                 pattern "<.*>|$.*";
               }
               type uint32 {
                 range "1 .. 255";
               }
             }
           }
           leaf port {
             description "Portnumber to connect";
             type union {
               type string {
                 pattern "<.*>|$.*";
               }
               type uint16 {
                 range "1 .. 65535";
               }
             }
           }
           leaf local-address {
             type jt:ipaddr;
           }
         }
       }
       container static {
         description "Define static route validation record";
         uses apply-advanced;
         list record {
           key name;
           description "Static route validation record";
           leaf name {
             type jt:ipprefix;
           }
           uses apply-advanced;
           list maximum-length {
             key name;
             ordered-by user;
             leaf name {
               description "Maximum prefix-length for route validation record";
               type union {
                 type string {
                   pattern "<.*>|$.*";
                 }
                 type uint32 {
                   range "1 .. 128";
                 }
               }
             }
             uses apply-advanced;
             list origin-autonomous-system {
               key name;
               ordered-by user;
               leaf name {
                 description "Legitimate Origin Autonomous System";
                 type union {
                   type uint32;
                   type string {
                     pattern "<.*>|$.*";
                   }
                 }
               }
               uses apply-advanced;
               leaf validation-state {
                 description "Validation state for route validation record";
                 type enumeration {
                   enum "invalid" {
                     description "Invalid route validation state";
                   }
                   enum "valid" {
                     description "Valid route validation state";
                   }
                 }
               }
             }
           }
         }
       }
     }
     container multicast {
       description "Global multicast options";
       uses apply-advanced;
       container traceoptions {
         description "Global multicast trace options";
         uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "parse" {
                 description "Trace configuration parsing";
               }
               enum "config-internal" {
                 description "Trace configuration internals";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf disable {
             description "Disable this trace flag";
             type empty;
           }
         }
       }
       leaf rpf {
         status deprecated;
         type string;
       }
       list scope {
         key name;
         ordered-by user;
         description "Multicast address scope";
         leaf name {
           description "Name to identify multicast address scope";
           type string;
         }
         uses apply-advanced;
         leaf prefix {
           description "Administratively scoped address";
           type jt:ipprefix;
         }
         leaf-list interface {
           ordered-by user;
           description "Interface on which to configure scoping";
           type union {
             type jt:interface-name;
             type string {
               pattern "<.*>|$.*";
             }
           }
         }
       }
       leaf-list scope-policy {
         ordered-by user;
         description "Scoping policy";
         type jt:policy-algebra;
       }
       list flow-map {
         key name;
         ordered-by user;
         description "Multicast flow map configuration";
         leaf name {
           description "Name of the flow map";
           type string;
         }
         uses apply-advanced;
         leaf-list policy {
           ordered-by user;
           description "Policy for matched flows";
           type jt:policy-algebra;
         }
         container bandwidth {
           presence "enable bandwidth";
           description "Bandwidth properties for matched flows";
           leaf bandwidth-value {
             description "Static or default bandwidth for the matched flows";
             units "bps";
             type string;
           }
           leaf adaptive {
             description "Auto-sense bandwidth for matched flows";
             type empty;
           }
         }
         leaf-list redundant-sources {
           ordered-by user;
           description "Redundant source addresses";
           type jt:ipaddr;
         }
         container forwarding-cache {
           description "Forwarding cache properties for matched flows";
           uses apply-advanced;
           container timeout {
             description "Timeout properties for matched flows";
             choice timeout_choice {
               case case_1 {
                 leaf timeout-value {
                   description "Timeout for forwarding cache entry";
                   units "minutes";
                   type union {
                     type string {
                       pattern "<.*>|$.*";
                     }
                     type uint32 {
                       range "1 .. 720";
                     }
                   }
                 }
               }
               case case_2 {
                 container never {
                   presence "enable never";
                   description "Forwarding cache entries never time out";
                   uses apply-advanced;
                   leaf non-discard-entry-only {
                     description "Apply only to non-discard entries";
                     type empty;
                   }
                 }
               }
             }
           }
         }
       }
       leaf-list resolve-filter {
         ordered-by user;
         description "Multicast resolve policy filter";
         status deprecated;
         type jt:policy-algebra;
       }
       leaf-list ssm-groups {
         ordered-by user;
         description "Source-specific multicast group ranges";
         type jt:ipprefix;
       }
       leaf asm-override-ssm {
         description "Allow ASM state for SSM group ranges";
         type empty;
       }
       leaf-list rpf-check-policy {
         ordered-by user;
         description "Disable RPF check for a source group pair";
         type jt:policy-algebra;
       }
       container pim-to-igmp-proxy {
         description "PIM-to-IGMP proxy";
         uses apply-advanced;
         leaf-list upstream-interface {
           ordered-by user;
           description "Upstream interface list";
           type union {
             type jt:interface-name;
             type string {
               pattern "<.*>|$.*";
             }
           }
           max-elements 2;
         }
       }
       container pim-to-mld-proxy {
         description "PIM-to-MLD proxy";
         uses apply-advanced;
         leaf-list upstream-interface {
           ordered-by user;
           description "Upstream interface list";
           type union {
             type jt:interface-name;
             type string {
               pattern "<.*>|$.*";
             }
           }
           max-elements 2;
         }
       }
       container forwarding-cache {
         description "Multicast forwarding cache";
         uses apply-advanced;
         leaf allow-maximum {
           description "Allow maximum of global and family level threshold values for suppress and reuse";
           type empty;
         }
         list family {
           key name;
           ordered-by user;
           description "Protocol family";
           leaf name {
             description "Protocol family";
             type enumeration {
               enum "inet" {
                 description "IPv4 family";
               }
               enum "inet6" {
                 description "IPv6 family";
               }
             }
           }
           uses apply-advanced;
           container threshold {
             presence "enable threshold";
             description "Multicast forwarding cache suppress threshold";
             uses apply-advanced;
             leaf suppress {
               description "Suppress threshold";
               type union {
                 type string {
                   pattern "<.*>|$.*";
                 }
                 type uint32 {
                   range "1 .. 200000";
                 }
               }
             }
             leaf reuse {
               description "Reuse threshold";
               type union {
                 type string {
                   pattern "<.*>|$.*";
                 }
                 type uint32 {
                   range "1 .. 200000";
                 }
               }
             }
             leaf mvpn-rpt-suppress {
               description "MVPN RP tree entry suppress threshold";
               type union {
                 type string {
                   pattern "<.*>|$.*";
                 }
                 type uint32 {
                   range "1 .. 200000";
                 }
               }
             }
             leaf mvpn-rpt-reuse {
               description "MVPN RP tree entry reuse threshold";
               type union {
                 type string {
                   pattern "<.*>|$.*";
                 }
                 type uint32 {
                   range "1 .. 200000";
                 }
               }
             }
             leaf log-warning {
               description "Percentage at which to start generating warnings";
               type union {
                 type string {
                   pattern "<.*>|$.*";
                 }
                 type uint32 {
                   range "1 .. 100";
                 }
               }
             }
           }
         }
         container threshold {
           description "Threshold";
           uses apply-advanced;
           leaf suppress {
             description "Suppress threshold";
             type union {
               type string {
                 pattern "<.*>|$.*";
               }
               type uint32 {
                 range "1 .. 200000";
               }
             }
           }
           leaf reuse {
             description "Reuse threshold";
             type union {
               type string {
                 pattern "<.*>|$.*";
               }
               type uint32 {
                 range "1 .. 200000";
               }
             }
           }
           leaf mvpn-rpt-suppress {
             description "MVPN RP tree entry suppress threshold";
             type union {
               type string {
                 pattern "<.*>|$.*";
               }
               type uint32 {
                 range "1 .. 200000";
               }
             }
           }
           leaf mvpn-rpt-reuse {
             description "MVPN RP tree entry reuse threshold";
             type union {
               type string {
                 pattern "<.*>|$.*";
               }
               type uint32 {
                 range "1 .. 200000";
               }
             }
           }
           leaf log-warning {
             description "Percentage at which to start generating warnings";
             type union {
               type string {
                 pattern "<.*>|$.*";
               }
               type uint32 {
                 range "1 .. 100";
               }
             }
           }
         }
         leaf timeout {
           description "Forwarding cache entry timeout in minutes";
           type union {
             type string {
               pattern "<.*>|$.*";
             }
             type uint32 {
               range "1 .. 720";
             }
           }
         }
       }
       list interface {
         key name;
         ordered-by user;
         description "Multicast interface options";
         uses multicast_interface_options_type;
       }
       list ssm-map {
         key name;
         ordered-by user;
         description "SSM map definitions";
         leaf name {
           description "SSM map name";
           type string;
         }
         uses apply-advanced;
         leaf-list policy {
           ordered-by user;
           description "Policy for matching group";
           type jt:policy-algebra;
         }
         leaf-list source {
           ordered-by user;
           description "One or more source addresses";
           type jt:ipaddr;
         }
       }
       list backup-pe-group {
         key name;
         ordered-by user;
         description "Backup PE group definitions";
         leaf name {
           description "PE group name";
           type string;
         }
         uses apply-advanced;
         leaf-list backups {
           ordered-by user;
           description "One or more IP addresses";
           type jt:ipaddr;
           max-elements 8;
         }
         leaf local-address {
           description "Address to be used as local-address for this group";
           type jt:ipaddr;
         }
       }
       leaf omit-wildcard-address {
         description "Omit wildcard source/group fields in SPMSI AD NLRI";
         type empty;
       }
       leaf local-address {
         description "Local address for PIM and MVPN sessions";
         type jt:ipv4addr;
       }
     }
     container dynamic-tunnels {
       description "Dynamic tunnel definitions";
       uses apply-advanced;
       list tunnel-attributes {
         key name;
         ordered-by user;
         description "Dynamic tunnel attributes definition";
         leaf name {
           description "Dynamic Tunnel attribute name";
           type string {
           }
         }
         uses apply-advanced;
         leaf dynamic-tunnel-source-prefix {
           description "Tunnel source address";
           type jt:ipaddr;
         }
         leaf dynamic-tunnel-type {
           type enumeration {
             enum "GRE" {
               description "Tunnel type GRE";
             }
             enum "V4oV6" {
               description "Tunnel type is IPV4oIPV6";
             }
             enum "UDP" {
               description "Tunnel type UDP";
             }
             enum "BGP-SIGNAL" {
               description "Tunnel type BGP-SIGNAL";
             }
           }
         }
         leaf dynamic-tunnel-mtu {
           description "Dynamic Tunnel MTU value";
           type union {
             type string {
               pattern "<.*>|$.*";
             }
             type uint32 {
               range "296 .. 9232";
             }
           }
         }
         leaf dynamic-tunnel-anchor-pfe {
           description "Dynamic Tunnel anchor PFE name of format pfe-x/y/z";
           type string {
           }
         }
         leaf dynamic-tunnel-anti-spoof {
           type enumeration {
             enum "on" {
               description "Enable antispoofing check. Default is enabled";
             }
             enum "off" {
               description "Disable antispoofing check";
             }
           }
         }
       }
       container traceoptions {
         description "Trace options";
         uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "kernel" {
                 description "Trace kernel communication";
               }
               enum "tunnel" {
                 description "Trace tunnel addition, change, or deletion";
               }
               enum "task" {
                 description "Trace task or job processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       leaf gre {
         description "Enable dynamic gre tunnel mode";
         type enumeration {
           enum "next-hop-based-tunnel" {
             description "Enable nh base dynamic-tunnel";
           }
         }
       }
       list dynamic-tunnel {
         key name;
         ordered-by user;
         uses dynamic_tunnel_type;
       }
     }
     container logical-system-mux {
       description "Logical system control daemon information";
       uses apply-advanced;
       container traceoptions {
         description "Trace options";
         uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "debug" {
                 description "Trace debug-level lrmuxd activities";
               }
               enum "parse" {
                 description "Trace configuration parsing";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
     }
     container fate-sharing {
       description "Fate-sharing links or nodes database";
       uses apply-advanced;
       list group {
         key name;
         ordered-by user;
         description "Group of objects sharing common characteristics";
         leaf name {
           description "Name of object groups sharing the same fate";
           type string {
           }
         }
         uses apply-advanced;
         leaf cost {
           description "Cost value";
           type union {
             type string {
               pattern "<.*>|$.*";
             }
             type uint32 {
               range "1 .. 65535";
             }
           }
         }
         leaf use-for-post-convergence-lfa {
           description "Use this fate-sharing group as a constraint for post-convergence-lfa";
           type empty;
         }
         list from {
           key name;
           uses fate_sharing_links;
         }
       }
     }
   }
   grouping dynamic_tunnel_type {
     description "Dynamic tunnel definition";
     leaf name {
       description "Tunnel name";
       type string {
       }
     }
     uses apply-advanced;
     leaf source-address {
       description "Tunnel source address";
       type jt:ipaddr;
     }
     choice tunnel-type {
       case case_1 {
         list rsvp-te {
           key name;
           ordered-by user;
           description "RSVP-TE point-to-point LSP";
           leaf name {
             description "Configure multiple entries for RSVP tunnel";
             type string;
           }
           uses apply-advanced;
           container label-switched-path-template {
             description "Template for dynamic point-to-point LSP parameters";
             uses apply-advanced;
             choice dynamic-template {
               case case_1 {
                 leaf template-name {
                   description "Name of point-to-point LSP template";
                   type string {
                   }
                 }
               }
               case case_2 {
                 leaf default-template {
                   description "Use default parameters";
                   type empty;
                 }
               }
             }
           }
           list destination-networks {
             key name;
             ordered-by user;
             description "Create tunnels for routes in these destination networks";
             uses network_type;
           }
         }
       }
       case case_2 {
         leaf gre {
           description "Generic routing encapsulation type for IPv4";
           type empty;
         }
       }
       case case_3 {
       }
       case case_4 {
         leaf bgp-signal {
           description "BGP signals the encapsulation type for IPv4";
           type empty;
         }
       }
     }
     list destination-networks {
       key name;
       ordered-by user;
       description "Create tunnels for routes in these destination networks";
       uses network_type;
     }
   }
   grouping export-af-obj {
     uses apply-advanced;
     choice enable-disable {
       case case_1 {
         leaf disable {
           description "Disable auto-export for address family";
           type empty;
         }
       }
     }
     container unicast {
       description "Unicast routing information";
       presence "enable unicast";
       uses export-subaf-obj;
     }
     container multicast {
       description "Multicast routing information";
       presence "enable multicast";
       uses export-subaf-obj;
     }
     container flow {
       description "Flow routing information";
       presence "enable flow";
       uses export-subaf-obj;
     }
   }
   grouping export-subaf-obj {
     uses apply-advanced;
     choice enable-disable {
       case case_1 {
         leaf disable {
           description "Disable instance export";
           type empty;
         }
       }
     }
     leaf rib-group {
       description "Auxiliary rib-group of additional RIBs to consider";
       type string;
     }
   }
   grouping fate_sharing_links {
     leaf name {
       description "Router ID or LAN interface address";
       type jt:ipv4addr;
     }
     leaf to {
       description "Point-to-point links";
       type jt:ipv4addr;
     }
   }
   grouping flow-interface-group {
     leaf group {
       description "Interface group ID to match traffic";
       type union {
         type string {
           pattern "<.*>|$.*";
         }
         type uint32 {
           range "1 .. 255";
         }
       }
     }
     leaf exclude {
       description "Don't apply flow-spec filter to traffic on this group";
       type empty;
     }
   }
   grouping flow-route-inet {
     leaf name {
       type string;
     }
     uses apply-advanced;
     leaf no-install {
       description "Don't install firewall filter in forwarding";
       type empty;
     }
     container match {
       description "Flow definition";
       uses flow-route-qualifier-inet;
     }
     container then {
       description "Actions to take for this flow";
       uses flow-route-op;
     }
   }
   grouping flow-route-inet6 {
     leaf name {
       type string;
     }
     uses apply-advanced;
     leaf no-install {
       description "Don't install firewall filter in forwarding";
       type empty;
     }
     container match {
       description "Flow definition";
       uses flow-route-qualifier-inet6;
     }
     container then {
       description "Actions to take for this flow";
       uses flow-route-op;
     }
   }
   grouping flow-route-op {
     uses apply-advanced;
     leaf community {
       description "Name of BGP community";
       type string;
     }
     choice flow_op_action {
       case case_1 {
         leaf accept {
           description "Allow traffic through";
           type empty;
         }
       }
       case case_2 {
         leaf discard {
           description "Discard all traffic for this flow";
           type empty;
         }
       }
       case case_3 {
         leaf rate-limit {
           description "Rate in bits/sec to limit the flow traffic";
           type string;
         }
       }
     }
     leaf routing-instance {
       description "Redirect to instance identified via Route Target community";
       type string {
       }
     }
     leaf sample {
       description "Sample traffic that matches this flow";
       type empty;
     }
     leaf mark {
       description "Set DSCP value for traffic that matches this flow";
       type union {
         type string {
           pattern "<.*>|$.*";
         }
         type uint32 {
           range "0 .. 63";
         }
       }
     }
     leaf next-term {
       description "Continue the filter evaluation after matching this flow";
       type empty;
     }
     choice redirect_op_action {
       case case_1 {
         leaf-list redirect {
           ordered-by user;
           description "Redirect(Tunnel) this flow's traffic to given next-hop address";
           type jt:ipaddr;
         }
       }
     }
   }
   grouping flow-route-qualifier-inet {
     uses apply-advanced;
     leaf-list protocol {
       ordered-by user;
       description "IP protocol value";
       type string;
     }
     leaf-list port {
       ordered-by user;
       type string;
     }
     leaf-list destination-port {
       ordered-by user;
       type string;
     }
     leaf-list source-port {
       ordered-by user;
       type string;
     }
     leaf-list tcp-flags {
       ordered-by user;
       description "TCP flags";
       type string;
     }
     leaf-list packet-length {
       ordered-by user;
       description "Packet length (0-65535)";
       type jt:policy-algebra;
     }
     leaf-list dscp {
       ordered-by user;
       description "Differentiated Services (DiffServ) code point (DSCP) (0-63)";
       type jt:policy-algebra;
     }
     leaf-list fragment {
       ordered-by user;
       type enumeration {
         enum "dont-fragment" {
           description "Don't Fragment flag is set";
         }
         enum "not-a-fragment" {
           description "Not a fragment";
         }
         enum "is-fragment" {
           description "Fragmented packet";
         }
         enum "first-fragment" {
           description "First fragment";
         }
         enum "last-fragment" {
           description "Last fragment";
         }
       }
     }
     leaf destination {
       description "Destination prefix for this traffic flow";
       type jt:ipv4prefix;
     }
     leaf source {
       description "Source prefix for this traffic flow";
       type jt:ipv4prefix;
     }
     leaf-list icmp-code {
       ordered-by user;
       description "ICMP message code";
       type string;
     }
     leaf-list icmp-type {
       ordered-by user;
       description "ICMP message type";
       type string;
     }
   }
   grouping flow-route-qualifier-inet6 {
     uses apply-advanced;
     leaf-list protocol {
       ordered-by user;
       description "IP protocol value";
       type string;
     }
     leaf-list port {
       ordered-by user;
       type string;
     }
     leaf-list destination-port {
       ordered-by user;
       type string;
     }
     leaf-list source-port {
       ordered-by user;
       type string;
     }
     leaf-list tcp-flags {
       ordered-by user;
       description "TCP flags";
       type string;
     }
     leaf-list packet-length {
       ordered-by user;
       description "Packet length (0-65535)";
       type jt:policy-algebra;
     }
     leaf-list dscp {
       ordered-by user;
       description "Differentiated Services (DiffServ) code point (DSCP) (0-63)";
       type jt:policy-algebra;
     }
     leaf-list fragment {
       ordered-by user;
       type enumeration {
         enum "dont-fragment" {
           description "Don't Fragment flag is set";
         }
         enum "not-a-fragment" {
           description "Not a fragment";
         }
         enum "is-fragment" {
           description "Fragmented packet";
         }
         enum "first-fragment" {
           description "First fragment";
         }
         enum "last-fragment" {
           description "Last fragment";
         }
       }
     }
     container destination {
       description "Destination prefix for this traffic flow";
       presence "enable destination";
       uses flow-prefix-with-offset;
     }
     container source {
       description "Source prefix for this traffic flow";
       presence "enable source";
       uses flow-prefix-with-offset;
     }
     leaf-list icmp6-type {
       ordered-by user;
       description "ICMP message type";
       type string;
     }
     leaf-list icmp6-code {
       ordered-by user;
       description "ICMP message code";
       type string;
     }
     leaf-list flow-label {
       ordered-by user;
       description "Flow-label (0-1048575)";
       type jt:policy-algebra;
     }
   }
   grouping flow-prefix-with-offset {
     leaf prefix {
       type jt:ipv6prefix;
     }
     leaf prefix-offset {
       description "Offset from where prefix match will start";
       type union {
         type uint32;
         type string {
           pattern "<.*>|$.*";
         }
       }
     }
   }
   grouping flow-validation {
     uses apply-advanced;
     container traceoptions {
       description "Trace options";
       uses flow-dep-traceoptions;
     }
   }
   grouping flow-dep-traceoptions {
     uses apply-advanced;
     container file {
       description "Trace file options";
       leaf filename {
         description "Name of file in which to write trace information";
         type string {
           length "1 .. 1024";
         }
       }
       leaf replace {
         description "Replace trace file rather than appending to it";
         status deprecated;
         type empty;
       }
       leaf size {
         description "Maximum trace file size";
         type string;
       }
       leaf files {
         description "Maximum number of trace files";
         default "10";
         type union {
           type string {
             pattern "<.*>|$.*";
           }
           type uint32 {
             range "2 .. 1000";
           }
         }
       }
       leaf no-stamp {
         description "Do not timestamp trace file";
         status deprecated;
         type empty;
       }
       choice world-readable-choice {
         leaf world-readable {
           description "Allow any user to read the log file";
           type empty;
         }
         leaf no-world-readable {
           description "Don't allow any user to read the log file";
           type empty;
         }
       }
     }
     list flag {
       key name;
       ordered-by user;
       description "Tracing parameters";
       leaf name {
         type enumeration {
           enum "resolution" {
             description "Trace flow to unicast route resolution";
           }
           enum "flash" {
             description "Trace flash processing";
           }
           enum "route" {
             description "Trace routing information";
           }
           enum "normal" {
             description "Trace normal events";
           }
           enum "general" {
             description "Trace general events";
           }
           enum "state" {
             description "Trace state transitions";
           }
           enum "policy" {
             description "Trace policy processing";
           }
           enum "task" {
             description "Trace routing protocol task processing";
           }
           enum "timer" {
             description "Trace routing protocol timer processing";
           }
           enum "all" {
             description "Trace everything";
           }
         }
       }
       leaf send {
         description "Trace transmitted packets";
         type empty;
       }
       leaf receive {
         description "Trace received packets";
         type empty;
       }
       leaf detail {
         description "Trace detailed information";
         type empty;
       }
       leaf disable {
         description "Disable this trace flag";
         type empty;
       }
       container filter {
         presence "enable filter";
         description "Filter to apply to tracing";
         leaf match-on {
           description "Argument on which to match";
           type enumeration {
             enum "prefix" {
               description "Filter based on prefix";
             }
             enum "route-attribute" {
               description "Filter based on route attributes";
             }
           }
         }
         leaf-list policy {
           ordered-by user;
           description "Filter policy";
           type jt:policy-algebra;
         }
       }
     }
   }
   grouping forwarding-table-type {
     description "Forwarding table management options";
     uses apply-advanced;
     leaf remnant-holdtime {
       description "Time to hold inherited routes from FIB";
       type union {
         type string {
           pattern "<.*>|$.*";
         }
         type uint32 {
           range "0 .. 10000";
         }
       }
     }
     leaf krt-nexthop-ack-timeout {
       description "Kernel nexthop ack timeout interval";
       type union {
         type string {
           pattern "<.*>|$.*";
         }
         type uint32 {
           range "1 .. 400";
         }
       }
     }
     container consistency-checking {
       description "RIB/FIB consistency checking";
       status deprecated;
       uses apply-advanced;
       choice enable-disable {
         case case_1 {
           leaf enable {
             description "Enable consistency checking";
             type empty;
           }
         }
         case case_2 {
           leaf disable {
             description "Disable consistency checking";
             type empty;
           }
         }
       }
       leaf period {
         description "Periodicity of scan in seconds";
         type union {
           type string {
             pattern "<.*>|$.*";
           }
           type uint32 {
             range "30 .. 4294967295";
           }
         }
       }
       leaf threshold {
         description "Mismatch threshold until complaint";
         type union {
           type uint32;
           type string {
             pattern "<.*>|$.*";
           }
         }
       }
     }
     leaf-list export {
       ordered-by user;
       description "Export policy";
       type jt:policy-algebra;
     }
     leaf dynamic-list-next-hop {
       description "Dynamic next-hop mode for EVPN";
       type empty;
     }
     choice indirect-next-hop-choice {
       leaf indirect-next-hop {
         description "Install indirect next hops in Packet Forwarding Engine";
         type empty;
       }
       leaf no-indirect-next-hop {
         description "Don't install indirect next hops in Packet Forwarding Engine";
         type empty;
       }
     }
     choice indirect-next-hop-change-acknowledgements-choice {
       leaf indirect-next-hop-change-acknowledgements {
         description "Request acknowledgements for Indirect next hop changes";
         type empty;
       }
       leaf no-indirect-next-hop-change-acknowledgements {
         description "Don't request acknowledgements for Indirect next hop changes";
         type empty;
       }
     }
     list rib {
       key name;
       ordered-by user;
       status deprecated;
       leaf name {
         type string;
       }
     }
     leaf unicast-reverse-path {
       description "Unicast reverse path (RP) verification";
       type enumeration {
         enum "active-paths" {
           description "Consider active paths when performing RP verification";
         }
         enum "feasible-paths" {
           description "Consider all feasible paths for RP verification";
         }
       }
     }
     container ip-tunnel-rpf-check {
       presence "enable ip-tunnel-rpf-check";
       description "IP tunnel Reverse Path Forwarding Check";
       uses apply-advanced;
       leaf mode {
         default "strict";
         type enumeration {
           enum "strict" {
             description "Strict mode for rpf-check(Default)";
           }
           enum "loose" {
             description "Loose mode for rpf-check";
           }
         }
       }
       leaf fail-filter {
         description "Fail filter name for RPF check(family inet|inet6|any)";
         type string {
         }
       }
     }
   }
   grouping juniper-sampling-options {
     uses apply-advanced;
     choice enable-disable {
       case case_1 {
         leaf disable {
           description "Disable global sampling instance";
           type empty;
         }
       }
     }
     container traceoptions {
       description "Traffic sampling trace options";
       uses sampling_traceoptions_type;
     }
     container input {
       description "Traffic Sampling data acquisition";
       uses sampling_input_type;
     }
     container output {
       description "Traffic sampling data disposition";
       status deprecated;
       uses sampling_output_type;
     }
     container family {
       description "Address family of packets to sample";
       container inet {
         description "Sample IPv4 packets";
         uses apply-advanced;
         choice enable-disable {
           case case_1 {
             leaf disable {
               description "Disable sampling family inet";
               type empty;
             }
           }
         }
         container input {
           description "Settings for sampling of input packets";
           uses sampling_family_input_type;
         }
         container output {
           description "Traffic sampling data disposition";
           uses sampling_instance_inet_global_output_type;
         }
       }
       container inet6 {
         description "Sample IPv6 packets";
         uses apply-advanced;
         choice enable-disable {
           case case_1 {
             leaf disable {
               description "Disable sampling family inet6";
               type empty;
             }
           }
         }
         container input {
           description "Settings for sampling of input packets";
           uses sampling_family_input_type;
         }
         container output {
           description "Traffic sampling data disposition";
           uses sampling_family_inet6_output_type;
         }
       }
     }
     list instance {
       key name;
       ordered-by user;
       description "Instance of sampling parameters";
       leaf name {
         description "Name for sampling instance";
         type string;
       }
       uses apply-advanced;
       choice enable-disable {
         case case_1 {
           leaf disable {
             description "Disable sampling instance";
             type empty;
           }
         }
       }
       container input {
         description "Traffic Sampling data acquisition";
         uses sampling_instance_input_type;
       }
       container family {
         description "Address family of packets to sample";
         container inet {
           description "Sample IPv4 packets";
           uses apply-advanced;
           choice enable-disable {
             case case_1 {
               leaf disable {
                 description "Disable instance family inet";
                 status deprecated;
                 type empty;
               }
             }
           }
           container input {
             description "Settings for sampling of input packets";
             uses sampling_family_input_type;
           }
           container output {
             description "Traffic sampling data disposition";
             uses sampling_instance_inet_output_type;
           }
         }
         container inet6 {
           description "Sample IPv6 packets";
           uses apply-advanced;
           choice enable-disable {
             case case_1 {
               leaf disable {
                 description "Disable instance family inet6";
                 status deprecated;
                 type empty;
               }
             }
           }
           container input {
             description "Settings for sampling of input packets";
             uses sampling_family_input_type;
           }
           container output {
             description "Traffic sampling data disposition";
             uses sampling_instance_inet6_output_type;
           }
         }
         container mpls {
           description "Sample mpls packets";
           uses apply-advanced;
           choice enable-disable {
             case case_1 {
               leaf disable {
                 description "Disable instance family mpls";
                 status deprecated;
                 type empty;
               }
             }
           }
           container input {
             description "Settings for sampling of input packets";
             uses sampling_family_input_type;
           }
           container output {
             description "Traffic sampling data disposition";
             uses sampling_instance_mpls_output_type;
           }
         }
         container vpls {
           description "Sample vpls packets";
           status deprecated;
           uses apply-advanced;
           choice enable-disable {
             case case_1 {
               leaf disable {
                 description "Disable instance family vpls";
                 type empty;
               }
             }
           }
           container input {
             description "Settings for sampling of input packets";
             uses sampling_family_input_type;
           }
           container output {
             description "Traffic sampling data disposition";
             uses sampling_instance_vpls_output_type;
           }
         }
         container bridge {
           description "Sample bridge packets";
           uses apply-advanced;
           choice enable-disable {
             case case_1 {
               leaf disable {
                 description "Disable instance family bridge";
                 type empty;
               }
             }
           }
           container input {
             description "Settings for sampling of input packets";
             uses sampling_family_input_type;
           }
           container output {
             description "Traffic sampling data disposition";
             uses sampling_instance_bridge_output_type;
           }
         }
       }
     }
     container jflow-service {
       description "Jflow service configuration";
       uses apply-advanced;
       container traceoptions {
         description "Jflow service trace options";
         uses jflow_service_traceoptions;
       }
     }
     container route-record {
       description "Sampling route record configuration";
       uses apply-advanced;
       container traceoptions {
         description "Sampling route record trace options";
         uses route_record_traceoptions;
       }
     }
   }
   grouping jflow_service_traceoptions {
     description "Traceoptions for jflow-service";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Area of jflow-service to enable debuging output";
       leaf name {
         type enumeration {
           enum "parse" {
             description "Trace parsing code";
           }
           enum "rtsock" {
             description "Trace rtsock code";
           }
           enum "sm" {
             description "Trace State machine code";
           }
           enum "all" {
             description "Trace all area of jflow-service code";
           }
         }
       }
     }
   }
   grouping junos_hash_key {
     description "Select data used in the hash key";
     uses apply-advanced;
     container family {
       description "Protocol family";
       container fcoe {
         description "FCoE protocol family";
         uses apply-advanced;
         container ethernet-interfaces {
           description "FCoE hash-key configuration on ethernet interfaces";
           uses apply-advanced;
           leaf oxid {
             description "Originator Exchange ID";
             type enumeration {
               enum "enable" {
                 description "Include Originator Exchange ID in the hash key";
               }
               enum "disable" {
                 description "Do not include Originator Exchange ID in the hash key";
               }
             }
           }
         }
         container fabric-interfaces {
           description "FCoE hash-key configuration on fabric interfaces";
           uses apply-advanced;
           leaf oxid {
             description "Originator Exchange ID";
             type enumeration {
               enum "enable" {
                 description "Include Originator Exchange ID in the hash key";
               }
               enum "disable" {
                 description "Do not include Originator Exchange ID in the hash key";
               }
             }
           }
         }
       }
       container inet {
         description "IPv4 protocol family";
         uses apply-advanced;
         container layer-3 {
           presence "enable layer-3";
           description "Include Layer 3 (IP) data in the hash key";
           uses apply-advanced;
           leaf destination-address {
             description "Include IP destination address in the hash key";
             type empty;
           }
         }
         container layer-4 {
           presence "enable layer-4";
           description "Include Layer 4 (TCP or UDP) data in the hash key";
           uses apply-advanced;
         }
         leaf session-id {
           description "Include session ID in the hash key";
           type empty;
         }
       }
       container inet6 {
         description "IPv6 protocol family";
         uses apply-advanced;
         container layer-3 {
           presence "enable layer-3";
           description "Include Layer 3 (IP) data in the hash key";
           uses apply-advanced;
           leaf destination-address {
             description "Include IP destination address in the hash key";
             type empty;
           }
           leaf incoming-interface-index {
             description "Include incoming interface index in the hash key";
             type empty;
           }
           leaf next-header {
             description "Include IP Next Header field in the hash key";
             type empty;
           }
           leaf source-address {
             description "Include IP source address in the hash key";
             type empty;
           }
           leaf traffic-class {
             description "Include Traffic Class field in the hash key";
             type empty;
           }
         }
         container layer-4 {
           presence "enable layer-4";
           description "Include Layer 4 (TCP or UDP) data in the hash key";
           uses apply-advanced;
           leaf destination-port {
             description "Include IP destination port in the hash key";
             type empty;
           }
           leaf source-port {
             description "Include IP source port in the hash key";
             type empty;
           }
         }
         leaf session-id {
           description "Include session ID in the hash key";
           type empty;
         }
       }
       container mpls {
         description "MPLS protocol family";
         uses apply-advanced;
         choice label {
           case case_1 {
             leaf label-1 {
               description "Include the first MPLS label in the hash key";
               type empty;
             }
           }
           case case_2 {
             leaf all-labels {
               description "Include all MPLS labels in hash key";
               type empty;
             }
           }
           case case_3 {
             leaf no-labels {
               description "Exclude all MPLS labels from hash key";
               type empty;
             }
           }
           case case_4 {
             leaf bottom-label-1 {
               description "Include the first MPLS label from bottom-of-stack in the hash key";
               type empty;
             }
           }
         }
         leaf label-2 {
           description "Include the second MPLS label in the hash key";
           type empty;
         }
         leaf label-3 {
           description "Include the third MPLS label in the hash key";
           type empty;
         }
         container payload {
           description "Include payload data in the hash key";
           uses apply-advanced;
           container ip {
             presence "enable ip";
             description "Include IPv4 or IPv6 payload data in the hash key";
             uses apply-advanced;
             choice layer-4-select {
               case case_1 {
                 choice ip-payload {
                   case case_1 {
                     leaf layer-3-only {
                       description "Include only layer-3 IP information";
                       type empty;
                     }
                   }
                   case case_2 {
                     leaf enable {
                       description "Include layer3/4 IP payload in the hash key";
                       type empty;
                     }
                   }
                   case case_3 {
                     leaf disable {
                       description "Exclude layer3/4 IP payload in the hash key";
                       type empty;
                     }
                   }
                 }
               }
               case case_2 {
                 container port-data {
                   presence "enable port-data";
                   uses apply-advanced;
                   leaf source-msb {
                     description "Include the most significant byte of the source port";
                     type empty;
                   }
                   leaf source-lsb {
                     description "Include the least significant byte of the source port";
                     type empty;
                   }
                   leaf destination-msb {
                     description "Include the most significant byte of the destination port";
                     type empty;
                   }
                   leaf destination-lsb {
                     description "Include the least significant byte of the destination port";
                     type empty;
                   }
                 }
               }
             }
           }
         }
       }
       container multiservice {
         description "Multiservice protocol family";
         uses apply-advanced;
         leaf source-mac {
           description "Include source MAC address in hash key";
           type empty;
         }
         leaf destination-mac {
           description "Include destination MAC address in hash key";
           type empty;
         }
       }
     }
   }
   grouping layer2_pm_family_output_type {
     uses apply-advanced;
     choice interface-or-next-hop-index {
       case case_1 {
         leaf interface {
           description "Interface through which to send sampled traffic";
           type union {
             type jt:interface-name;
             type string {
               pattern "<.*>|$.*";
             }
           }
         }
       }
       case case_2 {
         leaf next-hop-group {
           description "Next-hop-group through which to send port-mirror traffic";
           type string;
         }
       }
       case case_3 {
         list routing-instance {
           key name;
           description "Routing instances";
           max-elements 1;
           uses layer2_pm_output-routing-instance-type;
         }
       }
       case case_4 {
         list vlan {
           key name;
           description "Outgoing VLAN for mirrored packets";
           max-elements 1;
           uses pm-rspan-vlan;
         }
       }
       case case_5 {
       }
     }
     leaf no-filter-check {
       description "Do not check for filters on port-mirroring interface";
       type empty;
     }
   }
   grouping layer2_pm_output-routing-instance-type {
     leaf name {
       description "Routing instance name";
       type string {
       }
     }
     uses apply-advanced;
     list vlan {
       key name;
       description "Outgoing VLAN for mirrored packets";
       max-elements 1;
       uses pm-rspan-vlan;
     }
   }
   grouping ldp-sync-obj {
     uses apply-advanced;
     choice enable-disable {
       case case_1 {
         leaf disable {
           description "Disable LDP synchronization";
           type empty;
         }
       }
     }
     leaf hold-time {
       description "Time during which maximum metric is advertised";
       type union {
         type string {
           pattern "<.*>|$.*";
         }
         type uint32 {
           range "1 .. 65535";
         }
       }
     }
   }
   grouping ldp_filter_obj {
     description "Filter to apply to tracing";
     leaf match-on {
       description "Argument on which to match";
       type enumeration {
         enum "fec" {
           description "Filter based on FEC associated to the traced object.";
         }
         enum "address" {
           description "Filter based on packet source and destination addresses.";
         }
       }
     }
     leaf-list policy {
       ordered-by user;
       description "Filter policy";
       type jt:policy-algebra;
     }
   }
   grouping lmp_control_channel_type {
     leaf name {
       description "Control channel interface";
       type union {
         type jt:interface-name;
         type string {
           pattern "<.*>|$.*";
         }
       }
     }
     uses apply-advanced;
     leaf remote-address {
       description "Control channel remote address";
       type jt:ipaddr;
     }
   }
   grouping log-object {
     description "Configure security log";
     uses apply-advanced;
     list exclude {
       key name;
       ordered-by user;
       description "List of security log criteria to exclude from the audit log";
       status deprecated;
       leaf name {
         description "Exclude criteria name";
         type string;
       }
       uses apply-advanced;
       leaf destination-address {
         description "Destination address";
         type jt:ipaddr;
       }
       leaf destination-port {
         description "Destination port";
         type union {
           type uint32;
           type string {
             pattern "<.*>|$.*";
           }
         }
       }
       leaf event-id {
         description "Event ID filter";
         type string;
       }
       leaf failure {
         description "Event was a failure";
         type empty;
       }
       leaf interface-name {
         description "Name of interface";
         type string;
       }
       leaf policy-name {
         description "Policy name filter";
         type string;
       }
       leaf process {
         description "Process that generated the event";
         type string;
       }
       leaf protocol {
         description "Protocol filter";
         type string;
       }
       leaf source-address {
         description "Source address";
         type jt:ipaddr;
       }
       leaf source-port {
         description "Source port";
         type union {
           type uint32;
           type string {
             pattern "<.*>|$.*";
           }
         }
       }
       leaf success {
         description "Event was successful";
         type empty;
       }
       leaf username {
         description "Username filter";
         type string;
       }
     }
     leaf limit {
       description "Limit number of security log entries to keep in memory";
       status deprecated;
       default "10000";
       type union {
         type uint32;
         type string {
           pattern "<.*>|$.*";
         }
       }
     }
     container cache {
       presence "enable cache";
       description "Cache security log events in the audit log buffer";
       uses apply-advanced;
       list exclude {
         key name;
         ordered-by user;
         description "List of security log criteria to exclude from the audit log";
         leaf name {
           description "Exclude criteria name";
           type string;
         }
         uses apply-advanced;
         leaf destination-address {
           description "Destination address";
           type jt:ipaddr;
         }
         leaf destination-port {
           description "Destination port";
           type union {
             type uint32;
             type string {
               pattern "<.*>|$.*";
             }
           }
         }
         leaf event-id {
           description "Event ID filter";
           type string;
         }
         leaf failure {
           description "Event was a failure";
           type empty;
         }
         leaf interface-name {
           description "Name of interface";
           type string;
         }
         leaf policy-name {
           description "Policy name filter";
           type string;
         }
         leaf process {
           description "Process that generated the event";
           type string;
         }
         leaf protocol {
           description "Protocol filter";
           type string;
         }
         leaf source-address {
           description "Source address";
           type jt:ipaddr;
         }
         leaf source-port {
           description "Source port";
           type union {
             type uint32;
             type string {
               pattern "<.*>|$.*";
             }
           }
         }
         leaf success {
           description "Event was successful";
           type empty;
         }
         leaf username {
           description "Username filter";
           type string;
         }
       }
       leaf limit {
         description "Limit number of security log entries to keep in memory";
         default "10000";
         type union {
           type uint32;
           type string {
             pattern "<.*>|$.*";
           }
         }
       }
     }
     leaf disable {
       description "Disable security logging for the device";
       type empty;
     }
     leaf utc-timestamp {
       description "Use UTC time for security log timestamps";
       type empty;
     }
     leaf mode {
       description "Controls how security logs are processed and exported";
       type enumeration {
         enum "stream" {
           description "Process security logs directly in the forwarding plane";
         }
         enum "event" {
           description "Process security logs in the control plane";
         }
       }
     }
     leaf event-rate {
       description "Control plane event rate";
       units "logs per second";
       type union {
         type string {
           pattern "<.*>|$.*";
         }
         type uint32 {
           range "0 .. 1500";
         }
       }
     }
     leaf format {
       description "Set security log format for the device";
       type enumeration {
         enum "syslog" {
           description "Traditional syslog";
         }
         enum "sd-syslog" {
           description "Structured syslog";
         }
         enum "binary" {
           description "Binary log";
         }
       }
     }
     leaf rate-cap {
       description "Data plane event rate";
       units "logs per second";
       type union {
         type string {
           pattern "<.*>|$.*";
         }
         type uint32 {
           range "0 .. 5000";
         }
       }
     }
     leaf max-database-record {
       description "Maximum records in database";
       default "0";
       type union {
         type string {
           pattern "<.*>|$.*";
         }
         type uint32;
       }
     }
     container report {
       presence "enable report";
       description "Set security log report settings";
     }
     choice source {
       case case_1 {
         leaf source-address {
           description "Source ip address used when exporting security logs";
           type jt:ipaddr;
         }
       }
       case case_2 {
         leaf source-interface {
           description "Source interface used when exporting security logs";
           type union {
             type jt:interface-name;
             type string {
               pattern "<.*>|$.*";
             }
           }
         }
       }
     }
     container transport {
       presence "enable transport";
       description "Set security log transport settings";
       uses apply-advanced;
       leaf tcp-connections {
         description "Set tcp connection number per-stream";
         type union {
           type string {
             pattern "<.*>|$.*";
           }
           type uint32 {
             range "1 .. 5";
           }
         }
       }
       leaf protocol {
         description "Set security log transport protocol for the device";
         type enumeration {
           enum "udp" {
             description "UDP transfer for log";
           }
           enum "tcp" {
             description "TCP transfer for log";
           }
           enum "tls" {
             description "TLS transfer for log";
           }
         }
       }
       leaf tls-profile {
         description "TLS profile";
         type string;
       }
     }
     leaf facility-override {
       description "Alternate facility for logging to remote host";
       type enumeration {
         enum "authorization" {
           description "Authorization system";
         }
         enum "daemon" {
           description "Various system processes";
         }
         enum "ftp" {
           description "FTP process";
         }
         enum "kernel" {
           description "Kernel";
         }
         enum "user" {
           description "User processes";
         }
         enum "local0" {
           description "Local logging option number 0";
         }
         enum "local1" {
           description "Local logging option number 1";
         }
         enum "local2" {
           description "Local logging option number 2";
         }
         enum "local3" {
           description "Local logging option number 3";
         }
         enum "local4" {
           description "Local logging option number 4";
         }
         enum "local5" {
           description "Local logging option number 5";
         }
         enum "local6" {
           description "Local logging option number 6";
         }
         enum "local7" {
           description "Local logging option number 7";
         }
       }
     }
     leaf local-log-tag {
       description "Tag included in logs";
       type string {
       }
     }
     list local-category {
       key name;
       ordered-by user;
       description "Selects the type of events that may be logged locally";
       leaf name {
         type enumeration {
           enum "all" {
             description "All events are logged";
           }
           enum "content-security" {
             description "Content security events are logged";
           }
           enum "fw-auth" {
             description "Fw-auth events are logged";
           }
           enum "screen" {
             description "Screen events are logged";
           }
           enum "alg" {
             description "Alg events are logged";
           }
           enum "nat" {
             description "Nat events are logged";
           }
           enum "flow" {
             description "Flow events are logged";
           }
           enum "sctp" {
             description "Sctp events are logged";
           }
           enum "gtp" {
             description "Gtp events are logged";
           }
           enum "ipsec" {
             description "Ipsec events are logged";
           }
           enum "idp" {
             description "Idp events are logged";
           }
           enum "rtlog" {
             description "Rtlog events are logged";
           }
           enum "pst-ds-lite" {
             description "Pst-ds-lite events are logged";
           }
           enum "appqos" {
             description "Appqos events are logged";
           }
           enum "secintel" {
             description "Secintel events are logged";
           }
           enum "aamw" {
             description "AAMW events are logged";
           }
           enum "sfw" {
             description "Stateful Firewall events are logged";
           }
           enum "session" {
             description "Session events are logged";
           }
         }
       }
       uses apply-advanced;
     }
     list stream {
       key name;
       ordered-by user;
       description "Set security log stream settings";
       max-elements 8;
       leaf name {
         description "Name of security log stream";
         type string {
           length "1 .. 63";
         }
       }
       uses apply-advanced;
       leaf severity {
         description "Severity threshold for security logs";
         type enumeration {
           enum "emergency" {
             description "Conditions that cause security functions to stop";
           }
           enum "alert" {
             description "Conditions that require immediate attention";
           }
           enum "critical" {
             description "Critical conditions";
           }
           enum "error" {
             description "General error conditions";
           }
           enum "warning" {
             description "General warning conditions";
           }
           enum "notice" {
             description "Non-error conditions that are of interest";
           }
           enum "info" {
             description "Information about normal security operations";
           }
           enum "debug" {
             description "Information normally used in debugging";
           }
         }
       }
       leaf format {
         description "Specify the log stream format";
         type enumeration {
           enum "syslog" {
             description "Traditional syslog";
           }
           enum "sd-syslog" {
             description "Structured syslog";
           }
           enum "welf" {
             description "Web Trends Extended Log Format";
           }
           enum "binary" {
             description "Binary log";
           }
         }
       }
       list category {
         key name;
         ordered-by user;
         description "Selects the type of events that may be logged";
         leaf name {
           type enumeration {
             enum "all" {
               description "All events are logged";
             }
             enum "content-security" {
               description "Content security events are logged";
             }
             enum "fw-auth" {
               description "Fw-auth events are logged";
             }
             enum "screen" {
               description "Screen events are logged";
             }
             enum "alg" {
               description "Alg events are logged";
             }
             enum "nat" {
               description "Nat events are logged";
             }
             enum "flow" {
               description "Flow events are logged";
             }
             enum "sctp" {
               description "Sctp events are logged";
             }
             enum "gtp" {
               description "Gtp events are logged";
             }
             enum "ipsec" {
               description "Ipsec events are logged";
             }
             enum "idp" {
               description "Idp events are logged";
             }
             enum "rtlog" {
               description "Rtlog events are logged";
             }
             enum "pst-ds-lite" {
               description "Pst-ds-lite events are logged";
             }
             enum "appqos" {
               description "Appqos events are logged";
             }
             enum "secintel" {
               description "Secintel events are logged";
             }
             enum "aamw" {
               description "AAMW events are logged";
             }
             enum "sfw" {
               description "Stateful Firewall events are logged";
             }
             enum "session" {
               description "Session events are logged";
             }
           }
         }
         uses apply-advanced;
       }
       list filter {
         key name;
         ordered-by user;
         description "Selects the filter to filter the logs to be logged";
         leaf name {
           type enumeration {
             enum "threat-attack" {
               description "Threat-attack security events are logged";
             }
           }
         }
         uses apply-advanced;
       }
       container host {
         description "Destination to send security logs to";
         uses host-object;
       }
       container rate-limit {
         description "Rate-limit for security logs";
         uses apply-advanced;
         leaf rate {
           description "Log rate";
           units "logs per second";
           type union {
             type string {
               pattern "<.*>|$.*";
             }
             type uint32 {
               range "1 .. 65535";
             }
           }
         }
       }
       container file {
         description "Security log file options for logs in local file";
         uses apply-advanced;
         leaf localfilename {
           description "Name of local log file";
           type string {
             length "1 .. 256";
           }
         }
         leaf size {
           description "Maximum size of local log file in megabytes";
           type union {
             type string {
               pattern "<.*>|$.*";
             }
             type uint32;
           }
         }
         leaf rotation {
           description "Maximum number of rotate files";
           default "10";
           type union {
             type string {
               pattern "<.*>|$.*";
             }
             type uint32 {
               range "2 .. 19";
             }
           }
         }
         leaf allow-duplicates {
           description "To disable log consolidation";
           type empty;
         }
       }
     }
     container file {
       description "Security log file options for logs in binary format";
       uses apply-advanced;
       leaf filename {
         description "Name of binary log file";
         type string {
           length "1 .. 256";
         }
       }
       leaf size {
         description "Maximum size of binary log file in megabytes";
         type union {
           type string {
             pattern "<.*>|$.*";
           }
           type uint32 {
             range "1 .. 10";
           }
         }
       }
       leaf path {
         description "Path to binary log files";
         type string {
           length "1 .. 256";
         }
       }
       leaf files {
         description "Maximum number of binary log files";
         type union {
           type string {
             pattern "<.*>|$.*";
           }
           type uint32 {
             range "2 .. 10";
           }
         }
       }
     }
     container traceoptions {
       description "Security log daemon trace options";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "List of things to include in trace";
         leaf name {
           type enumeration {
             enum "source" {
               description "Communication with security log forwarder";
             }
             enum "configuration" {
               description "Reading of configuration";
             }
             enum "all" {
               description "Everything";
             }
             enum "report" {
               description "Trace report";
             }
             enum "hpl" {
               description "Trace HPL logging";
             }
           }
         }
       }
     }
   }
   grouping host-object {
     uses apply-advanced;
     leaf ipaddr {
       description "IP address";
       type jt:ipaddr;
     }
     leaf port {
       description "Host port number";
       type union {
         type uint16;
         type string {
           pattern "<.*>|$.*";
         }
       }
     }
     leaf routing-instance {
       description "Routing-instance name";
       type string;
     }
     leaf log-tag {
       description "Tag included in logs to this host";
       type string {
       }
     }
   }
   grouping logical-system-type {
     description "Logical system name";
     leaf name {
       description "Logical system name";
       type string;
     }
     uses apply-advanced;
     leaf max-sessions {
       description "Max number of IDP sessions";
       type union {
         type uint32;
         type string {
           pattern "<.*>|$.*";
         }
       }
     }
   }
   grouping lr_interfaces_type {
     description "Physical interface";
     leaf name {
       description "Interface name";
       type union {
         type jt:interface-unit;
         type string {
           pattern "<.*>|$.*";
         }
       }
     }
     uses apply-advanced;
     list unit {
       key name;
       description "Logical interface";
       leaf name {
         type string;
       }
       uses apply-advanced;
       container policer-overhead {
         description "Policer overhead adjustment for this unit";
         uses apply-advanced;
         leaf policer-overhead-value {
           description "Policer overhead bytes to be accounted in ingress and egress";
           units "bytes";
           type union {
             type string {
               pattern "<.*>|$.*";
             }
             type int32 {
               range "-64 .. 64";
             }
           }
         }
         leaf ingress {
           description "Ingress value in bytes";
           units "bytes";
           type union {
             type string {
               pattern "<.*>|$.*";
             }
             type int32 {
               range "-64 .. 64";
             }
           }
         }
         leaf egress {
           description "Egress value in bytes";
           units "bytes";
           type union {
             type string {
               pattern "<.*>|$.*";
             }
             type int32 {
               range "-64 .. 64";
             }
           }
         }
       }
       leaf alias {
         description "Interface alias";
         type string;
       }
       container peer-psd {
         presence "enable peer-psd";
         description "Peer psd";
         leaf psd-name {
           description "Peer psd name";
           type string;
         }
       }
       container peer-interface {
         presence "enable peer-interface";
         description "Peer interface";
         uses apply-advanced;
         leaf interface-name {
           description "Peer interface name";
           type union {
             type jt:interface-unit;
             type string {
               pattern "<.*>|$.*";
             }
           }
         }
       }
       container interface-shared-with {
         presence "enable interface-shared-with";
         description "Specify which PSD owns this logical interface";
         uses apply-advanced;
         leaf psd-name {
           description "Name of protected system domain (psd[1-31], ex. psd2)";
           type string {
           }
         }
       }
       choice enable-disable {
         case case_1 {
           leaf disable {
             description "Disable this logical interface";
             type empty;
           }
         }
       }
       leaf passive-monitor-mode {
         description "Use interface to tap packets from another router";
         type empty;
       }
       leaf clear-dont-fragment-bit {
         description "Clear DF bit in packet (AS PIC and J-series only as well as MIF)";
         type empty;
       }
       leaf description {
         description "Text description of interface";
         type string;
       }
       leaf encapsulation {
         description "Logical link-layer encapsulation";
         type enumeration {
           enum "atm-nlpid" {
             description "ATM NLPID encapsulation";
           }
           enum "atm-cisco-nlpid" {
             description "Cisco-compatible ATM NLPID encapsulation";
           }
           enum "atm-snap" {
             description "ATM LLC/SNAP encapsulation";
           }
           enum "atm-vc-mux" {
             description "ATM VC multiplexing";
           }
           enum "atm-ccc-vc-mux" {
             description "ATM VC for CCC";
           }
           enum "atm-tcc-vc-mux" {
             description "ATM VC for translational cross-connect";
           }
           enum "atm-tcc-snap" {
             description "ATM LLC/SNAP for translational cross-connect";
           }
           enum "atm-ccc-cell-relay" {
             description "ATM cell relay for CCC";
           }
           enum "vlan-vci-ccc" {
             description "CCC for VLAN Q-in-Q and ATM VPI/VCI interworking";
           }
           enum "ether-over-atm-llc" {
             description "Ethernet over ATM (LLC/SNAP) encapsulation";
           }
           enum "ether-vpls-over-atm-llc" {
             description "Ethernet VPLS over ATM (bridging) encapsulation";
           }
           enum "ppp-over-ether-over-atm-llc" {
             description "PPPoE over ATM (LLC/SNAP) encapsulation";
           }
           enum "ppp-over-ether" {
             description "PPPoE encapsulation";
           }
           enum "atm-ppp-vc-mux" {
             description "ATM PPP over raw AAL5";
           }
           enum "atm-ppp-llc" {
             description "ATM PPP over AAL5/LLC";
           }
           enum "atm-mlppp-llc" {
             description "ATM MLPPP over AAL5/LLC";
           }
           enum "frame-relay-ppp" {
             description "PPP over Frame Relay";
           }
           enum "frame-relay-ccc" {
             description "Frame Relay DLCI for CCC";
           }
           enum "frame-relay" {
             description "Frame Relay DLCI";
           }
           enum "frame-relay-tcc" {
             description "Frame Relay DLCI for translational cross-connect";
           }
           enum "frame-relay-ether-type" {
             description "Cisco-compatible Frame Relay Encapsulation DLCI";
           }
           enum "frame-relay-ether-type-tcc" {
             description "Cisco-compatible Frame Relay Encapsulation DLCI for TCC";
           }
           enum "ether-vpls-fr" {
             description "Ethernet VPLS over Frame Relay (bridging) encapsulation";
           }
           enum "vlan-ccc" {
             description "802.1q tagging for a cross-connect";
           }
           enum "ethernet-ccc" {
             description "Ethernet for a cross-connect";
           }
           enum "vlan-vpls" {
             description "VLAN virtual private LAN service";
           }
           enum "vlan-bridge" {
             description "VLAN layer-2 bridging";
           }
           enum "dix" {
             description "Ethernet DIXv2 (RFC 894)";
           }
           enum "ethernet" {
             description "Ethernet II (RFC 894)";
           }
           enum "ethernet-vpls" {
             description "Ethernet II virtual private LAN service";
           }
           enum "ethernet-bridge" {
             description "Ethernet II bridging";
           }
           enum "vlan" {
             description "802.1q-tagged Ethernet";
           }
           enum "vlan-tcc" {
             description "802.1q tagging for a translational cross-connect";
           }
           enum "multilink-ppp" {
             description "Multilink PPP";
           }
           enum "multilink-frame-relay-end-to-end" {
             description "Multilink Frame Relay end-to-end (FRF.15)";
           }
           enum "ppp-ccc" {
             description "Serial PPP device for a cross-connect";
           }
         }
       }
       leaf mtu {
         description "Maximum transmission unit packet size";
         type union {
           type string {
             pattern "<.*>|$.*";
           }
           type uint32;
         }
       }
       choice pointedness {
         case case_1 {
           leaf point-to-point {
             description "Point-to-point connection";
             type empty;
           }
         }
         case case_2 {
           leaf multipoint {
             description "Multipoint connection";
             type empty;
           }
         }
       }
       leaf bandwidth {
         description "Logical unit bandwidth (informational only)";
         type string;
       }
       container radio-router {
         description "Parameters for dynamic link cost management";
         presence "enable radio-router";
         uses dynamic_ifbw_parms_type;
       }
       choice traps-choice {
         leaf traps {
           description "Enable SNMP notifications on state changes";
           type empty;
         }
         leaf no-traps {
           description "Don't enable SNMP notifications on state changes";
           type empty;
         }
       }
       choice routing-services-choice {
         leaf routing-services {
           description "Enable routing services";
           status deprecated;
           type empty;
         }
         leaf no-routing-services {
           description "Don't enable routing services";
           status deprecated;
           type empty;
         }
       }
       container routing-service {
         description "Routing Services on this interface";
         uses apply-advanced;
         choice enable-disable {
           case case_1 {
             leaf enable {
               description "Enable Routing Service";
               type empty;
             }
           }
           case case_2 {
             leaf disable {
               description "Disable Routing Service";
               type empty;
             }
           }
         }
       }
       container arp-resp {
         presence "enable arp-resp";
         description "Knob to control ARP response on the interface, default is restricted";
         choice arp-response-options {
           case case_1 {
             leaf unrestricted {
               description "Enable unrestricted ARP respone on the interface";
               type empty;
             }
           }
           case case_2 {
             leaf restricted {
               description "Enable restricted proxy ARP response on the interface";
               type empty;
             }
           }
         }
       }
       container proxy-arp {
         presence "enable proxy-arp";
         description "Enable proxy ARP on the interface, default is unrestricted";
         choice proxyarp-options {
           case case_1 {
             leaf unrestricted {
               description "Enable unrestricted proxy ARP on the interface";
               type empty;
             }
           }
           case case_2 {
             leaf restricted {
               description "Enable restricted proxy ARP on the interface";
               type empty;
             }
           }
         }
       }
       choice vlan_choice {
         case case_1 {
           leaf vlan-id {
             description "Virtual LAN identifier value for 802.1q VLAN tags";
             type string;
           }
         }
         case case_2 {
           leaf vlan-id-range {
             description "Virtual LAN identifier range of form vid1-vid2";
             type string {
             }
           }
         }
         case case_3 {
           leaf-list inner-vlan-id-swap-ranges {
             description "Inner vlan-id swap range(s) of form vid1-vid2 for dynamic L2 VLANs";
             type jt:vlan-range;
           }
         }
         case case_4 {
           leaf-list vlan-id-list {
             description "List of VLAN identifiers";
             type jt:vlan-range;
           }
         }
         case case_5 {
           leaf-list vlan-tag {
             ordered-by user;
             description "IEEE 802.1q tag list for VLAN tagged frames";
             status deprecated;
             type string;
           }
         }
         case case_6 {
           container vlan-tags {
             presence "enable vlan-tags";
             description "IEEE 802.1q tags";
             leaf outer {
               description "[tpid.]vlan-id, tpid format is 0xNNNN and is optional";
               type string;
             }
             choice inner_choice {
               case case_1 {
                 leaf inner {
                   description "[tpid.]vlan-id, tpid format is 0xNNNN and is optional";
                   type string;
                 }
               }
               case case_2 {
                 leaf inner-range {
                   description "[tpid.]vid1-vid2, tpid format is 0xNNNN and is optional";
                   type string {
                   }
                 }
               }
               case case_3 {
                 leaf-list inner-list {
                   description "List of VLAN identifiers";
                   type jt:vlan-range;
                 }
               }
             }
           }
         }
       }
       leaf deep-vlan-qualified-learning {
         description "Enable qualified MAC-address learning on the specified vlan tag";
         type union {
           type string {
             pattern "<.*>|$.*";
           }
           type uint32 {
             range 3;
           }
         }
       }
       leaf native-inner-vlan-id {
         description "Native virtual LAN identifier for singly tagged frames";
         type union {
           type string {
             pattern "<.*>|$.*";
           }
           type uint32 {
             range "0 .. 4094";
           }
         }
       }
       container accept-source-mac {
         description "Remote media access control address to/from which to accept traffic";
         uses apply-advanced;
         list mac-address {
           key name;
           description "Remote MAC address";
           uses mac_list;
         }
       }
       container input-vlan-map {
         description "VLAN map operation on input";
         uses vlan_map;
       }
       container output-vlan-map {
         description "VLAN map operation on output";
         uses vlan_map;
       }
       leaf swap-by-poppush {
         description "Pop original vlan tag and then push a new vlan tag";
         type empty;
       }
       leaf receive-lsp {
         description "Name of incoming label-switched path";
         type string;
       }
       leaf transmit-lsp {
         description "Name of outgoing label-switched path";
         type string;
       }
       leaf dlci {
         description "Frame Relay data-link control identifier";
         type union {
           type string {
             pattern "<.*>|$.*";
           }
           type uint32 {
             range "1 .. 1022";
           }
         }
       }
       leaf multicast-dlci {
         description "Frame Relay data-link control identifier for multicast packets";
         type union {
           type string {
             pattern "<.*>|$.*";
           }
           type uint32 {
             range "1 .. 1022";
           }
         }
       }
       choice vci_type {
         case case_1 {
           leaf vci {
             description "ATM point-to-point virtual circuit identifier ([vpi.]vci)";
             type jt:atm-vci;
           }
         }
         case case_2 {
           leaf allow-any-vci {
             description "Allow all VCIs to open in atm-ccc-cell-relay mode";
             type empty;
           }
         }
         case case_3 {
           leaf vpi {
             description "ATM point-to-point virtual path identifier (vpi)";
             type union {
               type string {
                 pattern "<.*>|$.*";
               }
               type uint32 {
                 range "0 .. 255";
               }
             }
           }
         }
         case case_4 {
           leaf trunk-id {
             description "ATM trunk identifier";
             type union {
               type string {
                 pattern "<.*>|$.*";
               }
               type uint32 {
                 range "0 .. 31";
               }
             }
           }
         }
       }
       choice psn_vci_type {
         case case_1 {
         }
         case case_2 {
         }
       }
       container atm-l2circuit-mode {
         description "Select ATM Layer 2 circuit transport mode";
         choice mode_choice {
           case case_1 {
             leaf cell {
               description "ATM Layer 2 circuit cell mode";
               type empty;
             }
           }
           case case_2 {
             leaf aal5 {
               description "ATM Layer 2 circuit AAL5 mode";
               type empty;
             }
           }
         }
       }
       container vci-range {
         description "ATM VCI range start <start-vci> end <end-vci>";
         leaf start {
           description "ATM VCI range's start value";
           type union {
             type string {
               pattern "<.*>|$.*";
             }
             type uint16 {
               range "32 .. 4094";
             }
           }
         }
         leaf end {
           description "ATM VCI range's end value";
           type union {
             type string {
               pattern "<.*>|$.*";
             }
             type uint16 {
               range "32 .. 4094";
             }
           }
         }
       }
       leaf trunk-bandwidth {
         description "ATM trunk bandwidth";
         units "bits per second";
         type string;
       }
       leaf multicast-vci {
         description "ATM virtual circuit identifier for multicast packets";
         type jt:atm-vci;
       }
       container shaping {
         description "Virtual circuit traffic-shaping options";
         uses dcd_shaping_config;
       }
       container oam-period {
         description "OAM cell period";
         choice oam_period_choices {
           case case_1 {
             leaf oam-period {
               description "OAM cell period";
               units "seconds";
               type union {
                 type string {
                   pattern "<.*>|$.*";
                 }
                 type uint32 {
                   range "1 .. 900";
                 }
               }
             }
           }
           case case_2 {
             container disable {
               presence "enable disable";
               description "Disable F5 OAM loopback";
             }
           }
         }
       }
       container oam-liveness {
         description "OAM virtual circuit liveness parameters";
         uses apply-advanced;
         leaf up-count {
           description "Number of OAM cells to consider VC up";
           type union {
             type string {
               pattern "<.*>|$.*";
             }
             type uint32 {
               range "1 .. 255";
             }
           }
         }
         leaf down-count {
           description "Number of OAM cells to consider VC down";
           type union {
             type string {
               pattern "<.*>|$.*";
             }
             type uint32 {
               range "1 .. 255";
             }
           }
         }
       }
       container ppp-options {
         description "Point-to-Point Protocol interface-specific options";
         uses ppp_options_type;
       }
       container pppoe-options {
         description "PPP over Ethernet interface-specific options";
         uses pppoe_options_type;
       }
       choice keepalive_choices {
         case case_1 {
           container keepalives {
             description "Send or demand keepalive messages";
             presence "enable keepalives";
             uses keepalives_type;
           }
         }
         case case_2 {
           leaf no-keepalives {
             description "Do not send or demand keepalive messages";
             type empty;
           }
         }
       }
       leaf inverse-arp {
         description "Enable inverse ARP";
         type empty;
       }
       leaf transmit-weight {
         description "ATM2 transmit weight for VC under VP tunnel";
         type union {
           type string {
             pattern "<.*>|$.*";
           }
           type uint16 {
             range "1 .. 32767";
           }
         }
       }
       container epd-threshold {
         description "Early packet discard threshold for ATM2";
         uses epd_threshold_config;
       }
       leaf cell-bundle-size {
         description "L2 circuit cell bundle size";
         units "cells";
         type union {
           type string {
             pattern "<.*>|$.*";
           }
           type uint32 {
             range "1 .. 176";
           }
         }
       }
       leaf cell-bundle-timeout {
         description "L2 circuit cell bundle timeout";
         units "microseconds";
         type union {
           type string {
             pattern "<.*>|$.*";
           }
           type uint32 {
             range "1 .. 512";
           }
         }
       }
       leaf plp-to-clp {
         description "Enable ATM2 PLP to CLP copy";
         type empty;
       }
       leaf atm-scheduler-map {
         description "Assign ATM2 CoS scheduling map";
         type union {
           type string {
             pattern "default";
           }
           type string;
         }
       }
       leaf mrru {
         description "Maximum received reconstructed unit";
         units "bytes";
         type union {
           type string {
             pattern "<.*>|$.*";
           }
           type uint16 {
             range "1500 .. 4500";
           }
         }
       }
       leaf short-sequence {
         description "Short sequence number header format (MLPPP only)";
         type empty;
       }
       leaf fragment-threshold {
         description "Fragmentation threshold";
         units "bytes";
         type union {
           type string {
             pattern "<.*>|$.*";
           }
           type uint32 {
             range "64 .. 4500";
           }
         }
       }
       leaf drop-timeout {
         description "Drop timeout";
         units "milliseconds";
         type union {
           type string {
             pattern "<.*>|$.*";
           }
           type uint16 {
             range "0 .. 2000";
           }
         }
       }
       leaf disable-mlppp-inner-ppp-pfc {
         description "Disable compression for inner PPP header in MLPPP payload";
         type empty;
       }
       leaf minimum-links {
         description "Minimum number of links to sustain the bundle";
         type union {
           type string {
             pattern "<.*>|$.*";
           }
           type uint16;
         }
       }
       leaf multilink-max-classes {
         description "Number of multilink classes";
         type union {
           type string {
             pattern "<.*>|$.*";
           }
           type uint16;
         }
       }
       container compression {
         presence "enable compression";
         description "Various packet header compressions";
         uses apply-advanced;
         container rtp {
           presence "enable rtp";
           description "Compress and decompress RTP";
           uses apply-advanced;
           leaf f-max-period {
             description "Maximum number of compressed packets between transmission of full headers";
             type union {
               type string {
                 pattern "<.*>|$.*";
               }
               type uint32 {
                 range "1 .. 65535";
               }
             }
           }
           leaf-list queues {
             ordered-by user;
             description "Queue holding RTP packets. Default is queue 1";
             type enumeration {
               enum "q0" {
                 description "RTP packets assigned to queue 0";
               }
               enum "q1" {
                 description "RTP packets assigned to queue 1";
               }
               enum "q2" {
                 description "RTP packets assigned to queue 2";
               }
               enum "q3" {
                 description "RTP packets assigned to queue 3";
               }
             }
           }
           container port {
             presence "enable port";
             description "UDP destination ports reserved for RTP packets";
             leaf minimum {
               type union {
                 type string {
                   pattern "<.*>|$.*";
                 }
                 type uint32 {
                   range "0 .. 65535";
                 }
               }
             }
             leaf maximum {
               type union {
                 type string {
                   pattern "<.*>|$.*";
                 }
                 type uint32 {
                   range "0 .. 65535";
                 }
               }
             }
           }
           container maximum-contexts {
             description "Maximum number of simultaneous RTP contexts";
             leaf number {
               description "Maximum number of simultaneous RTP contexts";
               type union {
                 type string {
                   pattern "<.*>|$.*";
                 }
                 type uint32 {
                   range "16 .. 2048";
                 }
               }
             }
           }
         }
       }
       leaf interleave-fragments {
         description "Interleave long packets with high priority ones";
         type empty;
       }
       leaf link-layer-overhead {
         description "Link layer bit stuffing overhead (0.0 .. 50.0 percent)";
         type jt:unsigned-float;
       }
       leaf accounting-profile {
         description "Accounting profile name";
         type string;
       }
       leaf peer-unit {
         description "Peer unit number";
         type union {
           type string {
             pattern "<.*>|$.*";
           }
           type uint32 {
             range "0 .. 16385";
           }
         }
       }
       container tunnel {
         description "Tunnel parameters";
         uses apply-advanced;
         container encapsulation {
           presence "enable encapsulation";
           description "Encapsulation over tunnel";
           container vxlan-gpe {
             presence "enable vxlan-gpe";
             uses apply-advanced;
             container source {
               presence "enable source";
               uses apply-advanced;
               leaf address {
                 description "Interface address prefix";
                 type jt:ipv4addr;
               }
               leaf interface {
                 description "Name of the interface";
                 type union {
                   type jt:interface-name;
                   type string {
                     pattern "<.*>|$.*";
                   }
                 }
               }
             }
             container destination {
               presence "enable destination";
               uses apply-advanced;
               leaf address {
                 description "Interface address prefix";
                 type jt:ipv4addr;
               }
             }
             leaf tunnel-endpoint {
               description "Tunnel end point type";
               type enumeration {
                 enum "vxlan" {
                   description "To configure vxlan tunnel-end-point";
                 }
               }
             }
             leaf destination-udp-port {
               description "Value to write to the destination-udp-port field";
               type union {
                 type string {
                   pattern "<.*>|$.*";
                 }
                 type uint32 {
                   range "1 .. 65535";
                 }
               }
             }
             leaf vni {
               description "Value to write to the vni field";
               type union {
                 type string {
                   pattern "<.*>|$.*";
                 }
                 type uint32 {
                   range "0 .. 16777214";
                 }
               }
             }
           }
         }
         leaf source {
           description "Tunnel source";
           type jt:ipaddr;
         }
         leaf destination {
           description "Tunnel destination";
           type jt:ipaddr;
         }
         leaf key {
           description "Tunnel key";
           type union {
             type string {
               pattern "<.*>|$.*";
             }
             type uint32 {
               range "0 .. 4294967295";
             }
           }
         }
         leaf backup-destination {
           description "Backup tunnel destination";
           type jt:ipaddr;
         }
         choice fragmentation {
           case case_1 {
             leaf allow-fragmentation {
               description "Do not set DF bit on packets";
               type empty;
             }
           }
           case case_2 {
             leaf do-not-fragment {
               description "Set DF bit on packets";
               type empty;
             }
           }
         }
         leaf ttl {
           description "Time to live";
           type union {
             type string {
               pattern "<.*>|$.*";
             }
             type uint32 {
               range "1 .. 255";
             }
           }
         }
         leaf traffic-class {
           description "TOS/Traffic class field of IP-header";
           type union {
             type string {
               pattern "<.*>|$.*";
             }
             type uint32 {
               range "0 .. 255";
             }
           }
         }
         leaf flow-label {
           description "Flow label field of IP6-header";
           type union {
             type string {
               pattern "<.*>|$.*";
             }
             type uint32 {
               range "0 .. 1048575";
             }
           }
         }
         choice path-mtu-discovery-choice {
           leaf path-mtu-discovery {
             description "Enable path MTU discovery for tunnels";
             type empty;
           }
           leaf no-path-mtu-discovery {
             description "Don't enable path MTU discovery for tunnels";
             type empty;
           }
         }
         container routing-instance {
           description "Routing instance to which tunnel ends belong";
           uses apply-advanced;
           leaf destination {
             description "Routing instance of tunnel destination";
             type string;
           }
         }
       }
       leaf compression-device {
         description "Logical interface used for compression";
         type union {
           type jt:interface-unit;
           type string {
             pattern "<.*>|$.*";
           }
         }
       }
       choice virtual-gateway {
         case case_1 {
           leaf no-auto-virtual-gateway-esi {
             description "Disable auto ESI generation for virtual gateway address";
             type empty;
           }
         }
         case case_2 {
           container virtual-gateway-esi {
             description "ESI configuration of virtual gateway";
             uses apply-advanced;
             leaf identifier {
               description "ESI value for the interface";
               type jt:esi;
             }
             choice mode {
               case case_1 {
                 leaf single-active {
                   description "Single-active mode";
                   type empty;
                 }
               }
               case case_2 {
                 leaf all-active {
                   description "All-active mode";
                   type empty;
                 }
               }
             }
           }
         }
       }
       container service {
         description "Service operations";
         uses apply-advanced;
         list pcef {
           key name;
           ordered-by user;
           description "PCEF configuration";
           leaf name {
             description "PCEF Profile name";
             type string;
           }
           uses apply-advanced;
           leaf activate-all {
             description "Activate all rules and rulebases in the pcef profile";
             type empty;
           }
           list activate {
             key name;
             ordered-by user;
             description "Name of pcef profile rule or rulebase to activate";
             leaf name {
               description "Name of pcef profile rule or rulebase to activate";
               type string;
             }
             uses apply-advanced;
           }
         }
       }
       choice generate-eui64-choice {
         leaf generate-eui64 {
           description "To generate Link Local EUI-64 addresses";
           type empty;
         }
         leaf no-generate-eui64 {
           description "Don't to generate Link Local EUI-64 addresses";
           type empty;
         }
       }
       container family {
         description "Protocol family";
         container inet {
           presence "enable inet";
           description "IPv4 parameters";
           uses apply-advanced;
           container dhcp {
             description "Dynamic Host Configuration Protocol client configuration";
             presence "enable dhcp";
             uses dhcp-client-type;
           }
           container targeted-broadcast {
             presence "enable targeted-broadcast";
             description "Directed broadcast";
             uses apply-advanced;
             choice targeted-bcast-choice {
               case case_1 {
                 leaf forward-and-send-to-re {
                   description "Allow packets to be forwarded and sent to re";
                   type empty;
                 }
               }
               case case_2 {
                 leaf forward-only {
                   description "Allow packets only to be forwarded";
                   type empty;
                 }
               }
             }
           }
           leaf destination-class-usage {
             description "Enable destination class usage on this interface";
             status deprecated;
             type empty;
           }
           leaf transit-options-packets {
             description "Transit IP options packets (don't send to Routing Engine)";
             status deprecated;
             type empty;
           }
           leaf transit-ttl-exceeded {
             description "Transit IP TTL-exceeded packets (don't send to Routing Engine)";
             status deprecated;
             type empty;
           }
           leaf receive-options-packets {
             description "Receive IP options packets (don't send to Routing Engine)";
             type empty;
           }
           leaf receive-ttl-exceeded {
             description "Receive IP TTL-exceeded packets (don't send to Routing Engine)";
             type empty;
           }
           container accounting {
             description "Configure interface-based accounting options";
             uses apply-advanced;
             container source-class-usage {
               description "Enable source class usage on this interface";
               uses apply-advanced;
               leaf input {
                 description "Specify this interface for source-class-usage input";
                 type empty;
               }
               leaf output {
                 description "Specify this interface for source-class-usage output";
                 type empty;
               }
             }
             leaf destination-class-usage {
               description "Enable destination class usage on this interface";
               type empty;
             }
           }
           container rpf-check {
             presence "enable rpf-check";
             description "Enable reverse-path-forwarding checks on this interface";
             uses apply-advanced;
             leaf fail-filter {
               description "Name of filter applied to packets failing RPF check";
               type string;
             }
             container mode {
               description "Mode for reverse path forwarding";
               leaf loose {
                 description "Reverse-path-forwarding loose mode";
                 type empty;
               }
             }
           }
           leaf mtu {
             description "Protocol family maximum transmission unit";
             type union {
               type uint32;
               type string {
                 pattern "<.*>|$.*";
               }
             }
           }
           leaf arp-max-cache {
             description "Max interface ARP nexthop cache size";
             type union {
               type string {
                 pattern "<.*>|$.*";
               }
               type uint32 {
                 range "1 .. 2000000";
               }
             }
           }
           leaf arp-new-hold-limit {
             description "Max no. of new unresolved nexthops";
             type union {
               type string {
                 pattern "<.*>|$.*";
               }
               type uint32 {
                 range "1 .. 2000000";
               }
             }
           }
           leaf no-redirects {
             description "Do not redirect traffic";
             type empty;
           }
           leaf no-neighbor-learn {
             description "Disable neighbor address learning on interface";
             type empty;
           }
           leaf unconditional-src-learn {
             description "Glean from arp packets even when source cannot be validated";
             type empty;
           }
           leaf multicast-only {
             description "Allow only multicast traffic (tunnels only)";
             type empty;
           }
           leaf primary {
             description "Candidate for primary interface in system";
             type empty;
           }
           leaf ipsec-sa {
             description "Name of security association";
             type string {
               length "1 .. 32";
             }
           }
           container filter {
             description "Packet filtering";
             uses apply-advanced;
             choice input_choice {
               case case_1 {
                 container input {
                   description "Filter to be applied to received packets";
                   leaf filter-name {
                     description "Name of the filter";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list input-list {
                   ordered-by user;
                   description "List of filter modules applied to received packets ";
                   type string;
                 }
               }
             }
             choice output_choice {
               case case_1 {
                 container output {
                   description "Filter to be applied to transmitted packets";
                   leaf filter-name {
                     description "Name of the filter";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list output-list {
                   ordered-by user;
                   description "List of filter modules applied to transmitted packets ";
                   type string;
                 }
               }
             }
             container adf {
               description "Ascend Data Filter definition";
               uses apply-advanced;
               list rule {
                 key name;
                 ordered-by user;
                 description "Set of ADF rules";
                 leaf name {
                   description "Value for a single rule";
                   type string;
                 }
                 uses apply-advanced;
               }
               leaf counter {
                 description "Add a counter to each rule";
                 type empty;
               }
               leaf input-precedence {
                 description "Precedence of the input rules";
                 type union {
                   type string {
                     pattern "<.*>|$.*";
                   }
                   type uint32 {
                     range "0 .. 255";
                   }
                 }
               }
               leaf not-mandatory {
                 description "No errors will be reported if no rules are present";
                 type empty;
               }
               leaf output-precedence {
                 description "Precedence of the output rules";
                 type union {
                   type string {
                     pattern "<.*>|$.*";
                   }
                   type uint32 {
                     range "0 .. 255";
                   }
                 }
               }
             }
             leaf group {
               description "Group to which interface belongs";
               type union {
                 type string {
                   pattern "<.*>|$.*";
                 }
                 type uint32 {
                   range "1 .. 255";
                 }
               }
             }
             leaf dialer {
               description "Name of filter applied on dialer";
               type string;
             }
           }
           container simple-filter {
             description "Filter for doing multifield classification";
             uses apply-advanced;
             leaf input {
               description "Name of simple filter applied to received packets";
               type string;
             }
           }
           container policer {
             description "Interface policing";
             uses apply-advanced;
             leaf arp {
               description "Name of policer applied to received ARP packets";
               type string;
             }
             leaf input {
               description "Name of policer applied to received packets";
               type string;
             }
             leaf output {
               description "Name of policer applied to transmitted packets";
               type string;
             }
           }
           container sampling {
             description "Interface sampling";
             uses apply-advanced;
             leaf input {
               description "Sample all packets input on this interface";
               type empty;
             }
             leaf output {
               description "Sample all packets output on this interface";
               type empty;
             }
           }
           container service {
             description "Service operations";
             uses apply-advanced;
             container input {
               description "Service sets to consider for received packets";
               uses apply-advanced;
               list service-set {
                 key name;
                 ordered-by user;
                 description "Service set to consider for received packets";
                 leaf name {
                   description "Name of service set";
                   type string {
                   }
                 }
                 uses apply-advanced;
                 leaf service-filter {
                   description "Name of service filter";
                   type string;
                 }
               }
               leaf post-service-filter {
                 description "Post-service filter to apply to received packets";
                 type string;
               }
             }
             container output {
               description "Service sets to consider for transmitted packets";
               uses apply-advanced;
               list service-set {
                 key name;
                 ordered-by user;
                 description "Service set to consider for transmitted packets";
                 leaf name {
                   description "Name of service set";
                   type string {
                   }
                 }
                 uses apply-advanced;
                 leaf service-filter {
                   description "Name of service filter";
                   type string;
                 }
               }
             }
           }
           list next-hop-tunnel {
             key name;
             ordered-by user;
             description "One or more next-hop tunnel tables";
             leaf name {
               description "Next-hop tunnel gateway address";
               type string;
             }
             uses apply-advanced;
             leaf ipsec-vpn {
               description "Name of IPSec VPN";
               type string;
             }
           }
           list address {
             key name;
             ordered-by user;
             description "Interface address/destination prefix";
             leaf name {
               description "Interface address/destination prefix";
               type jt:ipv4prefix;
             }
             uses apply-advanced;
             leaf destination {
               description "Destination address";
               type jt:ipv4addr;
             }
             leaf destination-profile {
               description "Profile to use for destination address";
               type string;
             }
             leaf broadcast {
               description "Broadcast address";
               type jt:ipv4addr;
             }
             leaf primary {
               description "Candidate for primary address in system";
               type empty;
             }
             leaf preferred {
               description "Preferred address on interface";
               type empty;
             }
             leaf master-only {
               description "Master management IP address for router";
               type empty;
             }
             list multipoint-destination {
               key name;
               ordered-by user;
               description "Multipoint NBMA destination";
               leaf name {
                 description "Destination address";
                 type jt:ipv4addr;
               }
               uses apply-advanced;
               choice link-address {
                 case case_1 {
                   leaf dlci {
                     description "Frame Relay data-link control identifier";
                     type union {
                       type string {
                         pattern "<.*>|$.*";
                       }
                       type uint32 {
                         range "1 .. 1022";
                       }
                     }
                   }
                 }
                 case case_2 {
                   leaf vci {
                     description "ATM virtual circuit identifier ([vpi.]vci)";
                     type jt:atm-vci;
                   }
                 }
               }
               container shaping {
                 description "Virtual circuit traffic-shaping options";
                 uses dcd_shaping_config;
               }
               container oam-period {
                 description "OAM cell period";
                 choice oam_period_choices {
                   case case_1 {
                     leaf oam_period {
                       description "OAM cell period";
                       units "seconds";
                       type union {
                         type string {
                           pattern "<.*>|$.*";
                         }
                         type uint32 {
                           range "1 .. 900";
                         }
                       }
                     }
                   }
                   case case_2 {
                     container disable {
                       presence "enable disable";
                       description "Disable OAM loopback";
                     }
                   }
                 }
               }
               container oam-liveness {
                 description "OAM virtual circuit liveness parameters";
                 uses apply-advanced;
                 leaf up-count {
                   description "Number of OAM cells to consider VC up";
                   type union {
                     type string {
                       pattern "<.*>|$.*";
                     }
                     type uint32 {
                       range "1 .. 255";
                     }
                   }
                 }
                 leaf down-count {
                   description "Number of OAM cells to consider VC down";
                   type union {
                     type string {
                       pattern "<.*>|$.*";
                     }
                     type uint32 {
                       range "1 .. 255";
                     }
                   }
                 }
               }
               leaf inverse-arp {
                 description "Enable inverse ARP reply messages";
                 type empty;
               }
               leaf transmit-weight {
                 description "ATM2 transmit weight for VC under VP tunnel";
                 type union {
                   type string {
                     pattern "<.*>|$.*";
                   }
                   type uint16 {
                     range "1 .. 32767";
                   }
                 }
               }
               container epd-threshold {
                 description "Early packet discard threshold for ATM2";
                 uses epd_threshold_config;
               }
             }
             list arp {
               key name;
               ordered-by user;
               description "Static Address Resolution Protocol entries";
               leaf name {
                 description "Destination IP address";
                 type jt:ipv4addr;
               }
               leaf l2-interface {
                 description "Layer 2 interface name for ARP entry";
                 type union {
                   type jt:interface-name;
                   type string {
                     pattern "<.*>|$.*";
                   }
                 }
               }
               choice mac_address_type {
                 case case_1 {
                   leaf mac {
                     description "MAC address";
                     type jt:mac-unicast;
                   }
                 }
                 case case_2 {
                   leaf multicast-mac {
                     description "Multicast MAC address";
                     type jt:mac-multicast;
                   }
                 }
               }
               leaf publish {
                 description "Reply to ARP requests for this entry";
                 type empty;
               }
             }
             container web-authentication {
               description "Parameters for web-based firewall-user authentication";
               uses apply-advanced;
               leaf http {
                 description "Enable authentication via HTTP";
                 type empty;
               }
               leaf https {
                 description "Enable authentication via HTTPS";
                 type empty;
               }
               leaf redirect-to-https {
                 description "Web authentication redirect to HTTPS";
                 type empty;
               }
             }
             list vrrp-group {
               key name;
               ordered-by user;
               description "VRRP group";
               uses vrrp-group;
             }
             leaf virtual-gateway-address {
               description "Virtual Gateway IP address";
               type jt:ipv4addr;
             }
           }
           container unnumbered-address {
             description "Unnumbered interface address/destination prefix";
             leaf source {
               description "Interface from which to take local address";
               type union {
                 type jt:interface-unit;
                 type string {
                   pattern "<.*>|$.*";
                 }
               }
             }
             leaf preferred-source-address {
               description "Preferred address on the donor interface";
               type string;
             }
             leaf destination {
               description "Destination address";
               type jt:ipv4addr;
             }
             leaf destination-profile {
               description "Profile to use for destination address";
               type string;
             }
           }
           container location-pool-address {
             presence "enable location-pool-address";
             description "Location-based IP address pool";
             uses apply-advanced;
             leaf pool-name {
               description "Pool name";
               type string {
                 length "1 .. 64";
               }
             }
           }
           leaf negotiate-address {
             description "Negotiate address with remote";
             type empty;
           }
         }
         container iso {
           presence "enable iso";
           description "OSI ISO protocol parameters";
           uses apply-advanced;
           list address {
             key name;
             ordered-by user;
             description "Interface address";
             leaf name {
               description "Interface address";
               type jt:isoaddr;
             }
             uses apply-advanced;
           }
           leaf mtu {
             description "Protocol family maximum transmission unit";
             type union {
               type uint32;
               type string {
                 pattern "<.*>|$.*";
               }
             }
           }
         }
         container inet6 {
           presence "enable inet6";
           description "IPv6 protocol parameters";
           uses apply-advanced;
           container dhcpv6-client {
             description "Dynamic Host Configuration Protocol DHCPv6 client configuration";
             uses apply-advanced;
             leaf client-type {
               description "DHCPv6 client type";
               type enumeration {
                 enum "stateful" {
                   description "Stateful client type for address assignment.";
                 }
                 enum "autoconfig" {
                   description "Autoconfig  client type for router-advertisement";
                 }
               }
             }
             list client-ia-type {
               key name;
               ordered-by user;
               description "DHCPv6 client identity association type";
               leaf name {
                 type enumeration {
                   enum "ia-na" {
                     description "Identity Association-Non-temporary Address";
                   }
                   enum "ia-pd" {
                     description "Identity Association-Prefix Address";
                   }
                 }
               }
               uses apply-advanced;
             }
             container rapid-commit {
               presence "enable rapid-commit";
               description "Option is used to signal the use of the two message exchange for address assignment";
             }
             container prefix-delegating {
               description "Prefix delegating parameters";
               uses apply-advanced;
               leaf preferred-prefix-length {
                 description "Client preferred prefix length";
                 type union {
                   type string {
                     pattern "<.*>|$.*";
                   }
                   type uint32 {
                     range "0 .. 64";
                   }
                 }
               }
               leaf sub-prefix-length {
                 description "The sub prefix length for LAN interfaces";
                 type union {
                   type string {
                     pattern "<.*>|$.*";
                   }
                   type uint32 {
                     range "1 .. 127";
                   }
                 }
               }
             }
             container client-identifier {
               description "DHCP Server identifies a client by client-identifier value ";
               leaf duid-type {
                 description "DUID identifying a client";
                 type enumeration {
                   enum "duid-llt" {
                     description "Link-layer address plus time";
                   }
                   enum "vendor" {
                     description "Vendor-assigned unique ID based on Enterprise Number";
                   }
                   enum "duid-ll" {
                     description "Link-layer address";
                   }
                 }
               }
             }
             list req-option {
               key name;
               ordered-by user;
               description "DHCPV6 client requested option configuration";
               leaf name {
                 type enumeration {
                   enum "dns-server" {
                     description "Dns-server option";
                   }
                   enum "domain" {
                     description "Dns-server option";
                   }
                   enum "ntp-server" {
                     description "Ntp-server option";
                   }
                   enum "time-zone" {
                     description "Time-zone option";
                   }
                   enum "sip-server" {
                     description "Sip-server option";
                   }
                   enum "sip-domain" {
                     description "Sip-domain option";
                   }
                   enum "nis-server" {
                     description "Nis-server option";
                   }
                   enum "nis-domain" {
                     description "Nis-domain option";
                   }
                   enum "fqdn" {
                     description "Fully-qualified-domain option";
                   }
                   enum "vendor-spec" {
                     description "Vendor-spec option";
                   }
                 }
               }
               uses apply-advanced;
             }
             leaf retransmission-attempt {
               description "Number of attempts to retransmit the DHCPV6 client protocol packet";
               default "9";
               type union {
                 type string {
                   pattern "<.*>|$.*";
                 }
                 type uint32 {
                   range "0 .. 9";
                 }
               }
             }
             container no-dns-install {
               presence "enable no-dns-install";
               description "Not propagate DNS to kernel";
             }
             container update-router-advertisement {
               description "Dhcpv6 client update rpd for prefix delegation";
               uses apply-advanced;
               list interface {
                 key name;
                 ordered-by user;
                 description "Interfaces on which to delegate prefix";
                 max-elements 3;
                 leaf name {
                   description "Interfaces-name on which to delegate prefix";
                   type union {
                     type jt:interface-name;
                     type string {
                       pattern "<.*>|$.*";
                     }
                   }
                 }
                 uses apply-advanced;
                 choice managed-configuration-choice {
                   leaf managed-configuration {
                     description "Set managed address configuration";
                     type empty;
                   }
                   leaf no-managed-configuration {
                     description "Don't set managed address configuration";
                     type empty;
                   }
                 }
                 choice other-stateful-configuration-choice {
                   leaf other-stateful-configuration {
                     description "Set other stateful configuration";
                     type empty;
                   }
                   leaf no-other-stateful-configuration {
                     description "Don't set other stateful configuration";
                     type empty;
                   }
                 }
                 leaf max-advertisement-interval {
                   description "Maximum advertisement interval";
                   units "seconds";
                   type union {
                     type string {
                       pattern "<.*>|$.*";
                     }
                     type uint32 {
                       range "4 .. 1800";
                     }
                   }
                 }
                 leaf min-advertisement-interval {
                   description "Minimum advertisement interval";
                   units "seconds";
                   type union {
                     type string {
                       pattern "<.*>|$.*";
                     }
                     type uint32 {
                       range "3 .. 1350";
                     }
                   }
                 }
                 choice enable-recursive-dns-server-option-choice {
                   leaf enable-recursive-dns-server-option {
                     description "Enables the recursive DNS server option";
                     type empty;
                   }
                   leaf no-enable-recursive-dns-server-option {
                     description "Don't enables the recursive DNS server option";
                     type empty;
                   }
                 }
               }
             }
             leaf update-server {
               description "Propagate TCP/IP settings to DHCP server";
               type empty;
             }
           }
           container rpf-check {
             presence "enable rpf-check";
             description "Enable reverse-path-forwarding checks on this interface";
             uses apply-advanced;
             leaf fail-filter {
               description "Name of filter applied to packets failing RPF check";
               type string;
             }
             container mode {
               description "Mode for reverse path forwarding";
               leaf loose {
                 description "Reverse-path-forwarding loose mode";
                 type empty;
               }
             }
           }
           container accounting {
             description "Interface-based accounting options";
             uses apply-advanced;
             container source-class-usage {
               uses apply-advanced;
               leaf input {
                 description "Interface for source-class-usage input";
                 type empty;
               }
               leaf output {
                 description "Interface for source-class-usage output";
                 type empty;
               }
             }
             leaf destination-class-usage {
               description "Enable destination class usage on this interface";
               type empty;
             }
           }
           leaf mtu {
             description "Protocol family maximum transmission unit";
             type union {
               type uint32;
               type string {
                 pattern "<.*>|$.*";
               }
             }
           }
           leaf nd6-stale-time {
             description "Stale time to reconfirm reachability with inet6 neighbour";
             units "seconds";
             type union {
               type string {
                 pattern "<.*>|$.*";
               }
               type uint32 {
                 range "1 .. 18000";
               }
             }
           }
           leaf no-neighbor-learn {
             description "Disable neighbor address learning on interface";
             type empty;
           }
           container ndp-proxy {
             description "Enable ndp proxy on interface";
             uses apply-advanced;
             leaf interface-restricted {
               description "Enable ndp interface proxy restricted to interface";
               type empty;
             }
           }
           container dad-proxy {
             description "DAD proxy on interface";
             uses apply-advanced;
             leaf interface-restricted {
               description "Enable DAD interface proxy restricted to interface";
               type empty;
             }
           }
           leaf nd6-max-cache {
             description "Max interface ND nexthop cache size";
             type union {
               type string {
                 pattern "<.*>|$.*";
               }
               type uint32 {
                 range "1 .. 2000000";
               }
             }
           }
           leaf nd6-new-hold-limit {
             description "Max no. of new unresolved nexthops";
             type union {
               type string {
                 pattern "<.*>|$.*";
               }
               type uint32 {
                 range "1 .. 2000000";
               }
             }
           }
           leaf no-redirects {
             description "Do not redirect traffic";
             type empty;
           }
           container filter {
             description "Packet filtering";
             uses apply-advanced;
             choice input_choice {
               case case_1 {
                 container input {
                   description "Filter to be applied to received packets";
                   leaf filter-name {
                     description "Name of the filter";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list input-list {
                   ordered-by user;
                   description "List of filter modules applied to received packets ";
                   type string;
                 }
               }
             }
             choice output_choice {
               case case_1 {
                 container output {
                   description "Filter to be applied to transmitted packets";
                   leaf filter-name {
                     description "Name of the filter";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list output-list {
                   ordered-by user;
                   description "List of filter modules applied to transmitted packets ";
                   type string;
                 }
               }
             }
             container adf {
               description "Ascend Data Filter definition";
               uses apply-advanced;
               list rule {
                 key name;
                 ordered-by user;
                 description "Set of ADF rules";
                 leaf name {
                   description "Value for a single rule";
                   type string;
                 }
                 uses apply-advanced;
               }
               leaf counter {
                 description "Add a counter to each rule";
                 type empty;
               }
               leaf input-precedence {
                 description "Precedence of the input rules";
                 type union {
                   type string {
                     pattern "<.*>|$.*";
                   }
                   type uint32 {
                     range "0 .. 255";
                   }
                 }
               }
               leaf not-mandatory {
                 description "No errors will be reported if no rules are present";
                 type empty;
               }
               leaf output-precedence {
                 description "Precedence of the output rules";
                 type union {
                   type string {
                     pattern "<.*>|$.*";
                   }
                   type uint32 {
                     range "0 .. 255";
                   }
                 }
               }
             }
             leaf group {
               description "Group to which interface belongs";
               type union {
                 type string {
                   pattern "<.*>|$.*";
                 }
                 type uint32 {
                   range "1 .. 255";
                 }
               }
             }
             leaf dialer {
               description "Name of filter applied on dialer";
               type string;
             }
           }
           container policer {
             description "Interface policing";
             uses apply-advanced;
             leaf input {
               description "Name of policer applied to received packets";
               type string;
             }
             leaf output {
               description "Name of policer applied to transmitted packets";
               type string;
             }
           }
           container sampling {
             description "Interface sampling";
             uses apply-advanced;
             leaf input {
               description "Sample all packets input on this interface";
               type empty;
             }
             leaf output {
               description "Sample all packets output on this interface";
               type empty;
             }
           }
           container service {
             description "Service operations";
             uses apply-advanced;
             container input {
               description "Service sets to consider for received packets";
               uses apply-advanced;
               list service-set {
                 key name;
                 ordered-by user;
                 description "Service set to consider for received packets";
                 leaf name {
                   description "Name of service set";
                   type string {
                   }
                 }
                 uses apply-advanced;
                 leaf service-filter {
                   description "Name of service filter";
                   type string;
                 }
               }
               leaf post-service-filter {
                 description "Post-service filter to apply to received packets";
                 type string;
               }
             }
             container output {
               description "Service sets to consider for transmitted packets";
               uses apply-advanced;
               list service-set {
                 key name;
                 ordered-by user;
                 description "Service set to consider for transmitted packets";
                 leaf name {
                   description "Name of service set";
                   type string {
                   }
                 }
                 uses apply-advanced;
                 leaf service-filter {
                   description "Name of service filter";
                   type string;
                 }
               }
             }
           }
           list address {
             key name;
             ordered-by user;
             description "Interface address or destination prefix";
             leaf name {
               description "Interface address or destination prefix";
               type jt:ipv6prefix;
             }
             uses apply-advanced;
             leaf destination {
               description "Destination address";
               type jt:ipv6addr;
             }
             leaf eui-64 {
               description "Generate EUI-64 interface ID";
               type empty;
             }
             leaf primary {
               description "Candidate for primary address in system";
               type empty;
             }
             leaf preferred {
               description "Preferred address on interface";
               type empty;
             }
             leaf master-only {
               description "Master management IP address for router";
               type empty;
             }
             list ndp {
               key name;
               ordered-by user;
               description "Static Neighbor Discovery Protocol  entries";
               leaf name {
                 description "Destination IP address";
                 type jt:ipv6addr;
               }
               leaf l2-interface {
                 description "Layer 2 interface name for NDP entry";
                 type union {
                   type jt:interface-name;
                   type string {
                     pattern "<.*>|$.*";
                   }
                 }
               }
               choice mac_address_type {
                 case case_1 {
                   leaf mac {
                     description "MAC address";
                     type jt:mac-unicast;
                   }
                 }
                 case case_2 {
                   leaf multicast-mac {
                     description "Multicast MAC address";
                     type jt:mac-multicast;
                   }
                 }
               }
               leaf publish {
                 description "Reply to NDP requests for this entry";
                 type empty;
               }
             }
             list vrrp-inet6-group {
               key name;
               ordered-by user;
               description "VRRP group";
               uses vrrp-group;
             }
             container web-authentication {
               description "Parameters for web-based firewall-user authentication";
               uses apply-advanced;
               leaf http {
                 description "Enable authentication via HTTP";
                 type empty;
               }
               leaf https {
                 description "Enable authentication via HTTPS";
                 type empty;
               }
               leaf redirect-to-https {
                 description "Web authentication redirect to HTTPS";
                 type empty;
               }
             }
             leaf virtual-gateway-address {
               description "Virtual Gateway IP address";
               type jt:ipv6addr;
             }
             leaf subnet-router-anycast {
               description "Create a subnet roter anycast address for this address.";
               type empty;
             }
           }
           container unnumbered-address {
             description "Unnumbered interface address/destination prefix";
             leaf source {
               description "Interface from which to take local address";
               type union {
                 type jt:interface-unit;
                 type string {
                   pattern "<.*>|$.*";
                 }
               }
             }
             leaf preferred-source-address {
               description "Preferred address on the donor interface";
               type string;
             }
           }
           choice dad-disable-choice {
             leaf dad-disable {
               description "Disable duplicate-address-detection";
               type empty;
             }
             leaf no-dad-disable {
               description "Don't disable duplicate-address-detection";
               type empty;
             }
           }
           leaf negotiate-address {
             description "Negotiate address with remote";
             type empty;
           }
         }
         container mpls {
           presence "enable mpls";
           description "MPLS protocol parameters";
           uses apply-advanced;
           leaf mtu {
             description "Protocol family maximum transmission unit";
             type union {
               type uint32;
               type string {
                 pattern "<.*>|$.*";
               }
             }
           }
           container filter {
             description "Packet filtering";
             uses apply-advanced;
             choice input_choice {
               case case_1 {
                 leaf input {
                   description "Name of filter applied to received packets";
                   type string;
                 }
               }
               case case_2 {
                 leaf-list input-list {
                   ordered-by user;
                   description "List of filter modules applied to received packets ";
                   type string;
                 }
               }
             }
             leaf-list input-chain {
               ordered-by user;
               description "List of filter modules applied to received packets ";
               type string;
             }
             choice output_choice {
               case case_1 {
                 leaf output {
                   description "Name of filter applied to transmitted packets";
                   type string;
                 }
               }
               case case_2 {
                 leaf-list output-list {
                   ordered-by user;
                   description "List of filter modules applied to transmitted packets ";
                   type string;
                 }
               }
             }
             leaf-list output-chain {
               ordered-by user;
               description "List of filter modules applied to transmitted packets ";
               type string;
             }
             leaf group {
               description "Interface group to which interface belongs";
               type union {
                 type string {
                   pattern "<.*>|$.*";
                 }
                 type uint32 {
                   range "1 .. 255";
                 }
               }
             }
             leaf dialer {
               description "Name of filter applied on dialer";
               type string;
             }
           }
           container ingress-queuing-filter {
             description "Protocol family ingress-queuing-filter";
             leaf filter-name {
               description "Name of the ingress-queuing-filter";
               type string;
             }
           }
           container policer {
             description "Interface policing";
             uses apply-advanced;
             leaf input {
               description "Name of policer applied to received packets";
               type string;
             }
             leaf output {
               description "Name of policer applied to transmitted packets";
               type string;
             }
           }
         }
         container mlppp {
           description "Multilink PPP protocol parameters";
           uses apply-advanced;
           leaf bundle {
             description "Logical interface name this link will join";
             type string;
           }
           choice anchor-points {
             case case_1 {
             }
             case case_2 {
             }
           }
           leaf dynamic-profile {
             description " dynamic profile for interface to use";
             type string {
               length "1 .. 80";
             }
           }
         }
         container mlfr-end-to-end {
           presence "enable mlfr-end-to-end";
           description "Multilink Frame Relay end-to-end protocol parameters";
           uses apply-advanced;
           leaf bundle {
             description "Logical interface name this link will join";
             type union {
               type jt:interface-unit;
               type string {
                 pattern "<.*>|$.*";
               }
             }
           }
         }
         container mlfr-uni-nni {
           presence "enable mlfr-uni-nni";
           description "Multilink Frame Relay UNI NNI protocol parameters";
           uses apply-advanced;
           leaf bundle {
             description "Logical interface name this link will join";
             type union {
               type jt:interface-unit;
               type string {
                 pattern "<.*>|$.*";
               }
             }
           }
         }
         container ccc {
           presence "enable ccc";
           description "Circuit cross-connect parameters";
           uses apply-advanced;
           container filter {
             description "Packet filtering";
             uses apply-advanced;
             choice input_choice {
               case case_1 {
                 leaf input {
                   description "Name of filter applied to received packets";
                   type string;
                 }
               }
               case case_2 {
                 leaf-list input-list {
                   ordered-by user;
                   description "List of filter modules applied to received packets ";
                   type string;
                 }
               }
             }
             leaf-list input-chain {
               ordered-by user;
               description "List of filter modules applied to received packets ";
               type string;
             }
             choice output_choice {
               case case_1 {
                 leaf output {
                   description "Name of filter applied to transmitted packets";
                   type string;
                 }
               }
               case case_2 {
                 leaf-list output-list {
                   ordered-by user;
                   description "List of filter modules applied to transmitted packets ";
                   type string;
                 }
               }
             }
             leaf-list output-chain {
               ordered-by user;
               description "List of filter modules applied to transmitted packets ";
               type string;
             }
             leaf group {
               description "Interface group to which interface belongs";
               type union {
                 type string {
                   pattern "<.*>|$.*";
                 }
                 type uint32 {
                   range "1 .. 255";
                 }
               }
             }
           }
           container policer {
             description "Interface policing";
             uses apply-advanced;
             leaf input {
               description "Name of policer applied to received packets";
               type string;
             }
             leaf output {
               description "Name of policer applied to transmitted packets";
               type string;
             }
           }
           leaf translate-fecn-and-becn {
             description "Translate FECN and BECN bits";
             type empty;
           }
           choice de-or-plp {
             case case_1 {
               leaf translate-discard-eligible {
                 description "Translate DE bit";
                 type empty;
               }
             }
             case case_2 {
             }
           }
           leaf keep-address-and-control {
             description "Don't strip PPP address and control bytes";
             type empty;
           }
         }
         container tcc {
           presence "enable tcc";
           description "Translational cross-connect parameters";
           uses apply-advanced;
           container policer {
             description "Interface policing";
             uses apply-advanced;
             leaf input {
               description "Name of policer applied to received packets";
               type string;
             }
             leaf output {
               description "Name of policer applied to transmitted packets";
               type string;
             }
           }
           container proxy {
             presence "enable proxy";
             uses apply-advanced;
             leaf inet-address {
               description "Remote host address on non-Ethernet side of Ethernet TCC";
               type jt:ipv4addr;
             }
           }
           container remote {
             presence "enable remote";
             uses apply-advanced;
             leaf inet-address {
               description "Remote host address on Ethernet side of Ethernet TCC";
               type jt:ipv4addr;
             }
             leaf mac-address {
               description "Remote host MAC address on Ethernet side of Ethernet TCC";
               type jt:mac-addr;
             }
           }
         }
         container vpls {
           presence "enable vpls";
           description "Virtual private LAN service parameters";
           uses apply-advanced;
           leaf core-facing {
             description "Interface is core facing";
             type empty;
           }
           container filter {
             description "Packet filtering";
             uses apply-advanced;
             choice input_choice {
               case case_1 {
                 container input {
                   description "Filter to be applied to received packets";
                   leaf filter-name {
                     description "Name of the filter";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list input-list {
                   ordered-by user;
                   description "List of filter modules applied to received packets ";
                   type string;
                 }
               }
             }
             choice output_choice {
               case case_1 {
                 container output {
                   description "Filter to be applied to transmitted packets";
                   leaf filter-name {
                     description "Name of the filter";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list output-list {
                   ordered-by user;
                   description "List of filter modules applied to transmitted packets ";
                   type string;
                 }
               }
             }
             container adf {
               description "Ascend Data Filter definition";
               uses apply-advanced;
               list rule {
                 key name;
                 ordered-by user;
                 description "Set of ADF rules";
                 leaf name {
                   description "Value for a single rule";
                   type string;
                 }
                 uses apply-advanced;
               }
               leaf counter {
                 description "Add a counter to each rule";
                 type empty;
               }
               leaf input-precedence {
                 description "Precedence of the input rules";
                 type union {
                   type string {
                     pattern "<.*>|$.*";
                   }
                   type uint32 {
                     range "0 .. 255";
                   }
                 }
               }
               leaf not-mandatory {
                 description "No errors will be reported if no rules are present";
                 type empty;
               }
               leaf output-precedence {
                 description "Precedence of the output rules";
                 type union {
                   type string {
                     pattern "<.*>|$.*";
                   }
                   type uint32 {
                     range "0 .. 255";
                   }
                 }
               }
             }
             leaf group {
               description "Group to which interface belongs";
               type union {
                 type string {
                   pattern "<.*>|$.*";
                 }
                 type uint32 {
                   range "1 .. 255";
                 }
               }
             }
           }
           container policer {
             description "Interface policing";
             uses apply-advanced;
             leaf input {
               description "Name of policer applied to received packets";
               type string;
             }
             leaf output {
               description "Name of policer applied to transmitted packets";
               type string;
             }
           }
         }
         container bridge {
           presence "enable bridge";
           description "Layer-2 bridging parameters";
           uses apply-advanced;
           leaf core-facing {
             description "Interface is core facing";
             type empty;
           }
           container filter {
             description "Packet filtering";
             uses apply-advanced;
             choice input_choice {
               case case_1 {
                 container input {
                   description "Filter to be applied to received packets";
                   leaf filter-name {
                     description "Name of the filter";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list input-list {
                   ordered-by user;
                   description "List of filter modules applied to received packets ";
                   type string;
                 }
               }
             }
             choice output_choice {
               case case_1 {
                 container output {
                   description "Filter to be applied to transmitted packets";
                   leaf filter-name {
                     description "Name of the filter";
                     type string;
                   }
                   leaf shared-name {
                     description "Filter shared-name of instances of interface-shared filter";
                     type string;
                   }
                   leaf precedence {
                     description "Precedence of the filter";
                     type union {
                       type string {
                         pattern "<.*>|$.*";
                       }
                       type uint32 {
                         range "0 .. 255";
                       }
                     }
                   }
                 }
               }
               case case_2 {
                 leaf-list output-list {
                   ordered-by user;
                   description "List of filter modules applied to transmitted packets ";
                   type string;
                 }
               }
             }
             container adf {
               description "Ascend Data Filter definition";
               uses apply-advanced;
               list rule {
                 key name;
                 ordered-by user;
                 description "Set of ADF rules";
                 leaf name {
                   description "Value for a single rule";
                   type string;
                 }
                 uses apply-advanced;
               }
               leaf counter {
                 description "Add a counter to each rule";
                 type empty;
               }
               leaf input-precedence {
                 description "Precedence of the input rules";
                 type union {
                   type string {
                     pattern "<.*>|$.*";
                   }
                   type uint32 {
                     range "0 .. 255";
                   }
                 }
               }
               leaf not-mandatory {
                 description "No errors will be reported if no rules are present";
                 type empty;
               }
               leaf output-precedence {
                 description "Precedence of the output rules";
                 type union {
                   type string {
                     pattern "<.*>|$.*";
                   }
                   type uint32 {
                     range "0 .. 255";
                   }
                 }
               }
             }
             leaf group {
               description "Group to which interface belongs";
               type union {
                 type string {
                   pattern "<.*>|$.*";
                 }
                 type uint32 {
                   range "1 .. 255";
                 }
               }
             }
           }
           container policer {
             description "Interface policing";
             uses apply-advanced;
             leaf input {
               description "Name of policer applied to received packets";
               type string;
             }
             leaf output {
               description "Name of policer applied to transmitted packets";
               type string;
             }
           }
           leaf interface-mode {
             description "Interface mode (access or trunk)";
             type enumeration {
               enum "access" {
                 description "Interface mode is access";
               }
               enum "trunk" {
                 description "Interface mode is trunk";
               }
             }
           }
           leaf vlan-auto-sense {
             description "Enable VLAN auto sense on this interface";
             type empty;
           }
           leaf bridge-domain-type {
             description "Bridge domain type (svlan or bvlan)";
             type enumeration {
               enum "svlan" {
                 description "Bridge domain type svlan";
               }
               enum "bvlan" {
                 description "Bridge domain type bvlan";
               }
             }
           }
           leaf inter-switch-link {
             description "PVLAN inter switch link";
             type empty;
           }
           choice vlan_list {
             case case_1 {
               leaf vlan-id {
                 description "Access mode and trunk mode VLAN membership";
                 type union {
                   type string {
                     pattern "<.*>|$.*";
                   }
                   type uint32 {
                     range "1 .. 4094";
                   }
                 }
               }
             }
             case case_2 {
               leaf-list vlan-id-list {
                 description "Trunk mode VLAN membership for this interface";
                 type jt:vlan-range;
               }
             }
             case case_3 {
               leaf-list inner-vlan-id-list {
                 description "Trunk mode VLAN membership for this interface based on inner VLAN tag";
                 type jt:vlan-range;
               }
             }
           }
           container vlan-rewrite {
             description "Specify vlan translation";
             uses apply-advanced;
             list translate {
               key name;
               ordered-by user;
               description "Translate incoming VLAN tag";
               leaf name {
                 description "Specify the incoming VLAN tag";
                 type union {
                   type string {
                     pattern "<.*>|$.*";
                   }
                   type uint32 {
                     range "1 .. 4094";
                   }
                 }
               }
               leaf to-vlan-id {
                 description "Specify the bridge-domain VLAN-ID";
                 type union {
                   type string {
                     pattern "<.*>|$.*";
                   }
                   type uint32 {
                     range "1 .. 4094";
                   }
                 }
               }
             }
           }
           choice isid_list {
             case case_1 {
             }
           }
           container recovery-timeout {
             description "Recovery timeout for this interface";
             leaf time-in-seconds {
               units "seconds";
               type union {
                 type string {
                   pattern "<.*>|$.*";
                 }
                 type uint32 {
                   range "10 .. 3600";
                 }
               }
             }
           }
         }
         container ethernet-switching {
           description "Ethernet switching parameters";
           presence "enable ethernet-switching";
           uses ethernet-switching-type;
         }
         container fibre-channel {
           description "Fibre channel switching parameters";
           presence "enable fibre-channel";
           uses fibre-channel-type;
         }
         container any {
           presence "enable any";
           description "Parameters for 'any' family";
           uses apply-advanced;
           container filter {
             description "Layer 2 packet filtering";
             uses apply-advanced;
             leaf input {
               description "Name of filter applied to received packets";
               type string {
               }
             }
             leaf group {
               description "Group to which interface belongs";
               type union {
                 type string {
                   pattern "<.*>|$.*";
                 }
                 type uint32 {
                   range "1 .. 255";
                 }
               }
             }
           }
         }
         uses apply-advanced;
       }
       leaf service-domain {
         description "Service domain to which interface belongs";
         type enumeration {
           enum "inside" {
             description "Inside network";
           }
           enum "outside" {
             description "Outside network";
           }
         }
       }
       leaf copy-tos-to-outer-ip-header {
         description "Copy IP payload header's ToS field to GRE delivery header";
         type empty;
       }
       container load-balancing-options {
         description "AMS subunit load balancing options";
         uses apply-advanced;
         leaf preferred-active {
           description "Preferred active Interface name";
           type union {
             type jt:interface-device;
             type string {
               pattern "<.*>|$.*";
             }
           }
         }
         leaf disable-hash {
           description "Hash based distribution is not needed for this subunit";
           type empty;
         }
         container hash-keys {
           uses apply-advanced;
           leaf-list ingress-key {
             ordered-by user;
             description "Hash Key for the ingress direction";
             type enumeration {
               enum "source-ip" {
                 description "Source Ip Address";
               }
               enum "destination-ip" {
                 description "Destination Ip Address";
               }
               enum "protocol" {
                 description "Protocol";
               }
               enum "iif" {
                 description "Incoming Interface";
               }
             }
           }
           leaf-list egress-key {
             ordered-by user;
             description "Hash Key for the egress direction";
             status deprecated;
             type enumeration {
               enum "source-ip" {
                 description "Source Ip Address";
                 status deprecated;
               }
               enum "destination-ip" {
                 description "Destination Ip Address";
                 status deprecated;
               }
               enum "protocol" {
                 description "Protocol";
                 status deprecated;
               }
               enum "oif" {
                 description "Outgoing Interface";
                 status deprecated;
               }
             }
           }
           leaf ipv6-source-prefix-length {
             description "IPv6 source prefix length for hash computation";
             type enumeration {
               enum "56" {
                 description "56 bit IPv6 address prefix";
               }
               enum "64" {
                 description "64 bit IPv6 address prefix";
               }
               enum "96" {
                 description "96 bit IPv6 address prefix";
               }
               enum "128" {
                 description "Complete 128 bit IPv6 address";
               }
             }
           }
         }
       }
       leaf virtual-gateway-v4-mac {
         description "Configure virtual gateway IPV4 virtual MAC address";
         type jt:mac-unicast;
       }
       leaf virtual-gateway-v6-mac {
         description "Configure virtual gateway IPV6 virtual MAC address";
         type jt:mac-unicast;
       }
       leaf etree-ac-role {
         description "ETREE attachment circuit role";
         type enumeration {
           enum "root" {
             description "ETREE root interface";
           }
           enum "leaf" {
             description "ETREE leaf interface";
           }
         }
       }
       container dialer-options {
         presence "enable dialer-options";
         description "Dialer options";
         uses apply-advanced;
         leaf pool {
           description "Dialer pool";
           type string {
             length "1 .. 64";
           }
         }
         leaf-list dial-string {
           ordered-by user;
           description "String to dial out";
           type string {
             length "1 .. 63";
           }
           max-elements 15;
         }
         container incoming-map {
           description "Map incoming call to dialer";
           uses apply-advanced;
           choice caller-type {
             case case_1 {
               list caller {
                 key name;
                 ordered-by user;
                 description "Caller Id to be screened";
                 max-elements 300;
                 leaf name {
                   description "Caller ID (upto 15 digits)";
                   type string {
                   }
                 }
               }
             }
             case case_2 {
               leaf accept-all {
                 description "Accept all incoming calls";
                 type empty;
               }
             }
           }
         }
         leaf callback {
           description "Call back on any incoming call to the dialer";
           type empty;
         }
         leaf callback-wait-period {
           description "Time to wait before calling back";
           units "seconds";
           type union {
             type string {
               pattern "<.*>|$.*";
             }
             type uint32 {
               range "2 .. 255";
             }
           }
         }
         leaf redial-delay {
           description "Time to wait before redialing";
           units "seconds";
           type union {
             type string {
               pattern "<.*>|$.*";
             }
             type uint32 {
               range "2 .. 255";
             }
           }
         }
         leaf idle-timeout {
           description "Delay before taking down the interface";
           default "120";
           units "seconds";
           type union {
             type string {
               pattern "<.*>|$.*";
             }
             type uint32 {
               range "0 .. 4294967295";
             }
           }
         }
         list watch-list {
           key name;
           description "Dialer watch list";
           leaf name {
             description "Address prefix";
             type jt:ipprefix-only;
           }
           uses apply-advanced;
         }
         leaf load-threshold {
           description "Load threshold for adding interfaces";
           type union {
             type string {
               pattern "<.*>|$.*";
             }
             type uint32 {
               range "0 .. 100";
             }
           }
         }
         leaf load-interval {
           description "Interval used to calculate average load";
           units "seconds";
           type union {
             type string {
               pattern "<.*>|$.*";
             }
             type uint32 {
               range "20 .. 180";
             }
           }
         }
         leaf activation-delay {
           description "Activation delay";
           units "seconds";
           type union {
             type string {
               pattern "<.*>|$.*";
             }
             type uint32 {
               range "1 .. 4294967295";
             }
           }
         }
         leaf deactivation-delay {
           description "Deactivation delay";
           units "seconds";
           type union {
             type string {
               pattern "<.*>|$.*";
             }
             type uint32 {
               range "1 .. 4294967295";
             }
           }
         }
         leaf initial-route-check {
           description "Delay to check primary after the router is up";
           default "120";
           units "seconds";
           type union {
             type string {
               pattern "<.*>|$.*";
             }
             type uint16 {
               range "1 .. 300";
             }
           }
         }
         leaf-list route {
           ordered-by user;
           description "Route on dialer";
           type jt:ipprefix;
         }
         leaf always-on {
           description "Always keep on-line";
           type empty;
         }
       }
       container backup-options {
         description "Backup interface configuration options";
         uses apply-advanced;
         leaf interface {
           description "Backup interface";
           type union {
             type jt:interface-name;
             type string {
               pattern "<.*>|$.*";
             }
           }
         }
       }
       container dynamic-call-admission-control {
         description "Dynamic call admission control configuration";
         uses apply-advanced;
         leaf bearer-bandwidth-limit {
           description "Bearer bandwidth limit";
           units "kilobits per second";
           type union {
             type string {
               pattern "<.*>|$.*";
             }
             type uint16 {
               range "0 .. 9999";
             }
           }
         }
         leaf activation-priority {
           description "Priority assigned to bearer bandwidth limit";
           default "50";
           type union {
             type string {
               pattern "<.*>|$.*";
             }
             type uint8 {
               range "0 .. 255";
             }
           }
         }
       }
     }
   }
   grouping dcd_shaping_config {
     description "Traffic-shaping profile";
     uses apply-advanced;
     choice useless_shaping_choice {
       case case_1 {
         container cbr {
           presence "enable cbr";
           description "Constant bandwidth utilization";
           leaf cbr-value {
             description "Constant bandwidth utilization";
             type string;
           }
           leaf cdvt {
             description "Cell Delay Variation Tolerance";
             units "microseconds";
             type union {
               type string {
                 pattern "<.*>|$.*";
               }
               type uint32 {
                 range "1 .. 9999";
               }
             }
           }
         }
       }
       case case_2 {
         container vbr {
           description "Variable bandwidth utilization";
           leaf peak {
             description "Peak rate";
             type string;
           }
           leaf sustained {
             description "Sustained rate";
             type string;
           }
           leaf burst {
             description "Burst size";
             type string;
           }
           leaf cdvt {
             description "Cell Delay Variation Tolerance";
             units "microseconds";
             type union {
               type string {
                 pattern "<.*>|$.*";
               }
               type uint32 {
                 range "1 .. 9999";
               }
             }
           }
         }
       }
       case case_3 {
         container rtvbr {
           description "ATM2 real-time variable bandwidth utilization";
           leaf peak {
             description "Peak rate";
             type string;
           }
           leaf sustained {
             description "Sustained rate";
             type string;
           }
           leaf burst {
             description "Burst size";
             type string;
           }
         }
       }
     }
     leaf queue-length {
       description "Queue length";
       type union {
         type string {
           pattern "<.*>|$.*";
         }
         type uint32 {
           range "1 .. 16383";
         }
       }
     }
   }
   grouping dhcp-client-type {
     description "Dynamic Host Configuration Protocol client configuration";
     uses apply-advanced;
     container client-identifier {
       description "DHCP server identifies a client by client-identifier value ";
       uses apply-advanced;
       choice client-identifier-choice {
         case case_1 {
           leaf ascii {
             description "Client identifier as an ASCII string";
             type string;
           }
         }
         case case_2 {
           leaf hexadecimal {
             description "Client identifier as a hexadecimal string";
             type string {
             }
           }
         }
       }
       container user-id {
         description "Add user id to client-id option ";
         choice user-id-choice {
           case case_1 {
             leaf ascii {
               description "Client identifier as an ASCII string";
               type string;
             }
           }
           case case_2 {
             leaf hexadecimal {
               description "Client identifier as a hexadecimal string";
               type string {
               }
             }
           }
         }
       }
       container prefix {
         description "Add prefix to client-id option";
         uses apply-advanced;
         leaf host-name {
           description "Add router host name to client-id option";
           type empty;
         }
         leaf logical-system-name {
           description "Add logical system name to client-id option";
           type empty;
         }
         leaf routing-instance-name {
           description "Add routing instance name to client-id option";
           type empty;
         }
       }
       leaf use-interface-description {
         description "Use the interface description";
         type enumeration {
           enum "logical" {
             description "Use the logical interface description";
           }
           enum "device" {
             description "Use the device interface description";
           }
         }
       }
     }
     container no-dns-install {
       presence "enable no-dns-install";
       description "Do not install DNS information learned from DHCP server";
     }
     leaf lease-time {
       description "Lease time in seconds requested in DHCP client protocol packet";
       units "seconds";
       type string;
     }
     leaf retransmission-attempt {
       description "Number of attempts to retransmit the DHCP client protocol packet";
       default "4";
       type union {
         type string {
           pattern "<.*>|$.*";
         }
         type uint32 {
           range "0 .. 50000";
         }
       }
     }
     leaf retransmission-interval {
       description "Number of seconds between successive retransmission";
       default "4";
       units "seconds";
       type union {
         type string {
           pattern "<.*>|$.*";
         }
         type uint32 {
           range "4 .. 64";
         }
       }
     }
     leaf metric {
       description "Client initiated default-route metric";
       default "0";
       type union {
         type string {
           pattern "<.*>|$.*";
         }
         type uint32 {
           range "0 .. 255";
         }
       }
     }
     leaf server-address {
       description "DHCP Server-address";
       type jt:ipv4addr;
     }
     leaf update-server {
       description "Propagate TCP/IP settings to DHCP server";
       type empty;
     }
     leaf vendor-id {
       description "Vendor class id for the DHCP Client";
       type string {
         length "1 .. 60";
       }
     }
     leaf force-discover {
       description "Send DHCPDISCOVER after DHCPREQUEST retransmission failure";
       type empty;
     }
     container options {
       description "DHCP options";
       uses apply-advanced;
       leaf no-hostname {
         description "Do not carry hostname (RFC option code is 12) in packet";
         type empty;
       }
     }
   }
   grouping dynamic_ifbw_parms_type {
     uses apply-advanced;
     leaf capacity {
       description "Weight of current (vs. maximum) data rate";
       status deprecated;
       units "percent";
       type union {
         type string {
           pattern "<.*>|$.*";
         }
         type uint32 {
           range "0 .. 100";
         }
       }
     }
     leaf margin {
       description "Maximum reduction in bandwidth due to low link quality";
       status deprecated;
       units "percent";
       type union {
         type string {
           pattern "<.*>|$.*";
         }
         type uint32 {
           range "0 .. 100";
         }
       }
     }
     leaf delay {
       description "Bandwidth reduction when delay is announced as 1 second";
       status deprecated;
       units "bits per second";
       type string;
     }
     leaf bandwidth {
       description "Weight of current (vs. maximum) data rate";
       type union {
         type string {
           pattern "<.*>|$.*";
         }
         type uint32 {
           range "0 .. 100";
         }
       }
     }
     leaf resource {
       description "Resource weight";
       type union {
         type string {
           pattern "<.*>|$.*";
         }
         type uint32 {
           range "0 .. 100";
         }
       }
     }
     leaf latency {
       description "Latency weight";
       type union {
         type string {
           pattern "<.*>|$.*";
         }
         type uint32 {
           range "0 .. 100";
         }
       }
     }
     leaf quality {
       description "Relative Link Quality weight";
       type union {
         type string {
           pattern "<.*>|$.*";
         }
         type uint32 {
           range "0 .. 100";
         }
       }
     }
     leaf data-rate {
       description "Data rate weight";
       type union {
         type string {
           pattern "<.*>|$.*";
         }
         type uint32 {
           range "0 .. 100";
         }
       }
     }
     leaf threshold {
       description "Percentage bandwidth change required for routing updates";
       units "percent";
       type union {
         type string {
           pattern "<.*>|$.*";
         }
         type uint32 {
           range "0 .. 100";
         }
       }
     }
     container credit {
       presence "enable credit";
       description "Credit-based scheduling parameters";
       uses apply-advanced;
       leaf interval {
         description "Grant rate interval in 100mS steps";
         type union {
           type string {
             pattern "<.*>|$.*";
           }
           type uint16 {
             range "1 .. 60";
           }
         }
       }
     }
   }
   grouping epd_threshold_config {
     uses apply-advanced;
     leaf epd-threshold-plp0 {
       description "Early packet discard threshold value";
       units "cells";
       type string;
     }
     leaf plp1 {
       description "Early packet drop threshold value for PLP 1";
       units "cells";
       type string;
     }
   }
   grouping ethernet-switching-type {
     description "Ethernet switching family";
     uses apply-advanced;
     leaf port-mode {
       description "Type of port mode";
       type enumeration {
         enum "access" {
           description "Interface mode is access";
         }
         enum "tagged-access" {
           description "Interface mode is tagged-access";
         }
         enum "trunk" {
           description "Interface mode is trunk";
         }
       }
     }
     leaf interface-mode {
       description "Type of interface mode";
       default "access";
       type enumeration {
         enum "access" {
           description "Interface mode is access";
         }
         enum "trunk" {
           description "Interface mode is trunk";
         }
       }
     }
     leaf inter-switch-link {
       description "PVLAN inter switch link";
       type empty;
     }
     leaf reflective-relay {
       description "Reflective-relay mode for this interface";
       type empty;
     }
     choice vlan_choice_list {
       case case_1 {
         container vlan {
           description "Virtual LAN parameters";
           uses apply-advanced;
           leaf-list members {
             ordered-by user;
             description "Membership for this interface (name or id)";
             type string;
           }
         }
       }
       case case_2 {
         container inner-vlan {
           description "Trunk mode vlan membership for this interface";
           uses apply-advanced;
           leaf-list members {
             ordered-by user;
             description "Membership for this interface (name or id)";
             type string;
           }
         }
       }
       case case_3 {
         leaf-list inner-vlan-id-list {
           description "Trunk mode VLAN membership for this interface based on inner VLAN tag";
           type jt:vlan-range;
         }
       }
     }
     leaf vlan-auto-sense {
       description "Enable VLAN auto sense on this interface";
       type empty;
     }
     leaf bridge-domain-type {
       description "Bridge domain type";
       type enumeration {
         enum "svlan" {
           description "Bridge domain type SVLAN";
         }
         enum "bvlan" {
           description "Bridge domain type BVLAN";
         }
       }
     }
     container vlan-rewrite {
       description "Specify VLAN translation";
       uses apply-advanced;
       list translate {
         key name;
         ordered-by user;
         description "Translate incoming VLAN tag";
         leaf name {
           description "Specify the incoming VLAN tag";
           type union {
             type string {
               pattern "<.*>|$.*";
             }
             type uint32 {
               range "1 .. 4094";
             }
           }
         }
         leaf to-vlan-id {
           description "Specify the bridge-domain VLAN-ID";
           type union {
             type string {
               pattern "<.*>|$.*";
             }
             type uint32 {
               range "1 .. 4094";
             }
           }
         }
       }
     }
     leaf native-vlan-id {
       description "Untagged packets on a trunk/tagged-access interface belong to this vlan";
       type string {
       }
     }
     choice isid_list {
       case case_1 {
       }
     }
     leaf core-facing {
       description "Interface is core facing";
       type empty;
     }
     container filter {
       description "Packet filtering";
       uses apply-advanced;
       leaf input {
         description "Name of filter applied to received packets";
         type string;
       }
       leaf input-precedence {
         description "Precedence of the filter";
         type union {
           type string {
             pattern "<.*>|$.*";
           }
           type uint32 {
             range "0 .. 255";
           }
         }
       }
       leaf-list input-list {
         ordered-by user;
         description "List of filter modules applied to received packets ";
         type string;
       }
       leaf output {
         description "Name of filter applied to transmitted packets";
         type string;
       }
       leaf output-precedence {
         description "Precedence of the filter";
         type union {
           type string {
             pattern "<.*>|$.*";
           }
           type uint32 {
             range "0 .. 255";
           }
         }
       }
       leaf-list output-list {
         ordered-by user;
         description "List of filter modules applied to transmitted packets ";
         type string;
       }
       container adf {
         description "Ascend Data Filter definition";
         uses apply-advanced;
         list rule {
           key name;
           ordered-by user;
           description "Set of ADF rules";
           leaf name {
             description "Value for a single rule";
             type string;
           }
           uses apply-advanced;
         }
         leaf counter {
           description "Add a counter to each rule";
           type empty;
         }
         leaf input-precedence {
           description "Precedence of the input rules";
           type union {
             type string {
               pattern "<.*>|$.*";
             }
             type uint32 {
               range "0 .. 255";
             }
           }
         }
         leaf not-mandatory {
           description "No errors will be reported if no rules are present";
           type empty;
         }
         leaf output-precedence {
           description "Precedence of the output rules";
           type union {
             type string {
               pattern "<.*>|$.*";
             }
             type uint32 {
               range "0 .. 255";
             }
           }
         }
       }
       leaf group {
         description "Group to which interface belongs";
         type union {
           type string {
             pattern "<.*>|$.*";
           }
           type uint32 {
             range "1 .. 255";
           }
         }
       }
     }
     container policer {
       description "Interface policing";
       uses apply-advanced;
       leaf input {
         description "Name of policer applied to received packets";
         type string;
       }
       leaf output {
         description "Name of policer applied to transmitted packets";
         type string;
       }
     }
     container storm-control {
       description "Storm control profile name to bind";
       uses apply-advanced;
       leaf profile-name {
         description "Profile name";
         type string;
       }
     }
     container recovery-timeout {
       description "Recovery timeout for this interface";
       leaf time-in-seconds {
         units "seconds";
         type union {
           type string {
             pattern "<.*>|$.*";
           }
           type uint32 {
             range "10 .. 3600";
           }
         }
       }
     }
   }
   grouping fibre-channel-type {
     description "Fibre Channel switching family";
     uses apply-advanced;
     leaf port-mode {
       description "Port mode";
       type enumeration {
         enum "f-port" {
           description "Fabric port";
         }
         enum "e-port" {
           description "Inter-switch port";
         }
         enum "np-port" {
           description "Proxy node port";
         }
         enum "auto" {
           description "Interface mode (F/E) is determined at runtime";
         }
       }
     }
     leaf no-npiv {
       description "Disable NPIV";
       type empty;
     }
     container fc-fabric {
       description "Virtual fabric parameters";
       uses apply-advanced;
       leaf-list members {
         ordered-by user;
         description "Virtual Fabric Membership for this interface (name or id)";
         type string;
       }
     }
     leaf native-fabric {
       description "FC frames with no virtual fabric header on a interface belong to this fabric";
       type string {
       }
     }
   }
   grouping keepalives_type {
     uses apply-advanced;
     leaf interval {
       description "Keepalive period";
       units "seconds";
       type union {
         type string {
           pattern "<.*>|$.*";
         }
         type uint16 {
           range "1 .. 32767";
         }
       }
     }
     leaf up-count {
       description "Keepalive received to bring link up";
       type union {
         type string {
           pattern "<.*>|$.*";
         }
         type uint16 {
           range "1 .. 255";
         }
       }
     }
     leaf down-count {
       description "Keepalive missed to bring link down";
       type union {
         type string {
           pattern "<.*>|$.*";
         }
         type uint16 {
           range "1 .. 255";
         }
       }
     }
   }
   grouping lsp-set-match-type {
     uses apply-advanced;
     leaf lsp-name {
       description "LSP name that matches this string";
       type string;
     }
     leaf lsp-regex {
       description "All LSPs that match this regular expression pattern";
       type string;
     }
     leaf p2mp-name {
       description "P2MP names that match this string";
       type string;
     }
     leaf p2mp-regex {
       description "P2MP names that match this regular expression pattern";
       type string;
     }
     choice router-type {
       case case_1 {
         leaf egress {
           description "All LSPs for which this router is egress";
           type empty;
         }
       }
       case case_2 {
         leaf ingress {
           description "All LSPs for which this router is ingress";
           type empty;
         }
       }
       case case_3 {
         leaf transit {
           description "All LSPs for which this router is transit";
           type empty;
         }
       }
     }
   }
   grouping lsp_nh_obj {
     leaf name {
       description "LSP to use to reach destination";
       type string;
     }
     uses apply-advanced;
     leaf preference {
       description "Preference of LSP next hop";
       type union {
         type uint32;
         type string {
           pattern "<.*>|$.*";
         }
       }
     }
     leaf metric {
       description "Metric of LSP next hop";
       type union {
         type uint32;
         type string {
           pattern "<.*>|$.*";
         }
       }
     }
   }
   grouping mac_addr_list_items {
     leaf name {
       description "Mac Address";
       type jt:mac-addr;
     }
     uses apply-advanced;
   }
   grouping mac_list {
     description "MAC address";
     leaf name {
       type jt:mac-addr;
     }
     uses apply-advanced;
     container policer {
       description "MAC policing";
       uses apply-advanced;
       leaf input {
         description "Name of policer applied to received packets";
         type string;
       }
       leaf output {
         description "Name of policer applied to transmitted packets";
         type string;
       }
     }
   }
   grouping macro-data-type {
     leaf name {
       description "Keyword part of the keyword-value pair";
       type string;
     }
     leaf value {
       description "Value part of the keyword-value pair";
       type string;
     }
   }
   grouping martian_type {
     description "Invalid routes";
     leaf address {
       description "IP address or hostname";
       type jt:ipprefix;
     }
     leaf choice-ident {
       type enumeration {
         enum "exact" {
         }
         enum "longer" {
         }
         enum "orlonger" {
         }
         enum "upto" {
         }
         enum "through" {
         }
         enum "prefix-length-range" {
         }
         enum "allow" {
         }
       }
     }
     leaf choice-value {
       type string;
     }
     leaf allow {
       type empty;
     }
   }
   grouping match_interface_object {
     leaf name {
       description "Interface to match";
       type union {
         type jt:interface-wildcard;
         type string {
           pattern "<.*>|$.*";
         }
       }
     }
   }
   grouping match_interface_object_oam {
     leaf name {
       description "Interface to match";
       type union {
         type jt:interface-wildcard;
         type string {
           pattern "<.*>|$.*";
         }
       }
     }
   }
   grouping match_interface_set_object {
     leaf name {
       description "Interface set to match";
       type string;
     }
   }
   grouping match_simple_dscp_value {
     uses apply-advanced;
     leaf value_keyword {
       type string;
     }
   }
   grouping match_simple_port_value {
     uses apply-advanced;
     leaf value_keyword {
       type string;
     }
   }
   grouping match_simple_protocol_value {
     uses apply-advanced;
     leaf value_keyword {
       type string;
     }
   }
   grouping metric_expression_type {
     uses apply-advanced;
     container metric {
       description "Parameters for metric attribute";
       leaf multiplier {
         description "Coefficient for metric attribute";
         type decimal64 {
           fraction-digits 2;
         }
       }
       leaf offset {
         description "Offset for metric attribute";
         type union {
           type int32;
           type string {
             pattern "<.*>|$.*";
           }
         }
       }
     }
     container metric2 {
       description "Parameters for metric2 attribute";
       leaf multiplier {
         description "Coefficient for metric2 attribute";
         default "1.0";
         type decimal64 {
           fraction-digits 2;
         }
       }
       leaf offset {
         description "Offset for metric2 attribute";
         type union {
           type int32;
           type string {
             pattern "<.*>|$.*";
           }
         }
       }
     }
   }
   grouping mime-list-type {
     description "Configure mime-list object";
     leaf name {
       description "Configure name of mime-list object";
       type string {
         length "1 .. 40";
       }
     }
     uses apply-advanced;
     leaf-list value {
       ordered-by user;
       description "Configure MIME value";
       type string {
         length "1 .. 255";
       }
     }
   }
   grouping mirror-filter-type {
     description "Secuirty mirror filter settings";
     leaf name {
       description "Name of the filter";
       type string {
         length "1 .. 63";
       }
     }
     uses apply-advanced;
     leaf protocol {
       description "Match IP protocol type";
       type string;
     }
     leaf source-prefix {
       description "Source IP address prefix";
       type jt:ipprefix;
     }
     leaf destination-prefix {
       description "Destination IP address prefix";
       type jt:ipprefix;
     }
     leaf source-port {
       description "Match TCP/UDP source port";
       type string;
     }
     leaf destination-port {
       description "Match TCP/UDP destination port";
       type string;
     }
     leaf interface-in {
       description "Incoming Logical interface";
       type union {
         type jt:interface-name;
         type string {
           pattern "<.*>|$.*";
         }
       }
     }
     leaf interface-out {
       description "Outgoing Logical interface";
       type union {
         type jt:interface-name;
         type string {
           pattern "<.*>|$.*";
         }
       }
     }
     container output {
       description "Configure output interface and MAC address";
       uses apply-advanced;
       leaf interface {
         description "Outgoing Logical interface";
         type union {
           type jt:interface-name;
           type string {
             pattern "<.*>|$.*";
           }
         }
       }
       leaf destination-mac {
         description "MAC address to match";
         type string;
       }
     }
   }
   grouping mpls_dialer_filter {
     description "Define an MPLS DIALER filter";
     leaf name {
       description "Filter name";
       type string {
       }
     }
     uses apply-advanced;
     leaf-list accounting-profile {
       ordered-by user;
       description "Accounting profile name";
       type string;
     }
     list term {
       key name;
       ordered-by user;
       description "Define a firewall term";
       leaf name {
         description "Term name";
         type string {
         }
       }
       uses apply-advanced;
       container from {
         description "Define match criteria";
         uses apply-advanced;
         choice exp_choice {
           case case_1 {
             leaf-list exp {
               ordered-by user;
               description "Range of values";
               type string;
             }
           }
           case case_2 {
             leaf-list exp-except {
               ordered-by user;
               description "Range of values";
               type string;
             }
           }
         }
       }
       container then {
         description "Action to take if the 'from' condition is matched";
         uses apply-advanced;
         leaf log {
           description "Log the packet";
           type empty;
         }
         leaf syslog {
           description "System log (syslog) information about the packet";
           type empty;
         }
         leaf sample {
           description "Sample the packet";
           type empty;
         }
         choice designation {
           case case_1 {
             leaf note {
               description "Interested ISDN packet";
               type empty;
             }
           }
           case case_2 {
             leaf ignore {
               description "Non-interested ISDN packet";
               type empty;
             }
           }
         }
       }
     }
   }
   grouping mpls_filter {
     description "Define an MPLS firewall filter";
     leaf name {
       description "Filter name";
       type string {
       }
     }
     uses apply-advanced;
     leaf-list accounting-profile {
       ordered-by user;
       description "Accounting profile name";
       type string;
     }
     leaf interface-specific {
       description "Defined counters are interface specific";
       type empty;
     }
     leaf physical-interface-filter {
       description "Filter is physical interface filter";
       type empty;
     }
     list term {
       key name;
       ordered-by user;
       description "Define a firewall term";
       leaf name {
         description "Term name";
         type string {
         }
       }
       uses apply-advanced;
       leaf filter {
         description "Filter to include";
         type string {
         }
       }
       container from {
         description "Define match criteria";
         uses apply-advanced;
         choice interface-group_choice {
           case case_1 {
             leaf-list interface-group {
               ordered-by user;
               description "Range of values";
               type string;
             }
           }
           case case_2 {
             leaf-list interface-group-except {
               ordered-by user;
               description "Range of values";
               type string;
             }
           }
         }
         choice exp_choice {
           case case_1 {
             leaf-list exp {
               ordered-by user;
               description "Range of values between 0 and 7 in decimal, binary or hex";
               type string;
             }
           }
           case case_2 {
             leaf-list exp-except {
               ordered-by user;
               description "Range of values between 0 and 7 in decimal, binary or hex";
               type string;
             }
           }
         }
         list interface {
           key name;
           ordered-by user;
           description "Match interface name";
           uses match_interface_object;
         }
         list interface-set {
           key name;
           ordered-by user;
           description "Match interface in set";
           uses match_interface_set_object;
         }
         choice forwarding-class_choice {
           case case_1 {
             leaf-list forwarding-class {
               ordered-by user;
               description "String name";
               type string {
               }
             }
           }
           case case_2 {
             leaf-list forwarding-class-except {
               ordered-by user;
               description "String name";
               type string {
               }
             }
           }
         }
         choice loss-priority_choice {
           case case_1 {
           }
           case case_2 {
           }
         }
         choice policy-map_choice {
           case case_1 {
             leaf-list policy-map {
               ordered-by user;
               description "String name";
               type string {
                 length "1 .. 64";
               }
             }
           }
           case case_2 {
             leaf-list policy-map-except {
               ordered-by user;
               description "String name";
               type string {
                 length "1 .. 64";
               }
             }
           }
         }
       }
       container then {
         description "Action to take if the 'from' condition is matched";
         uses apply-advanced;
         choice policer-choice {
           case case_1 {
             leaf policer {
               description "Name of policer to use to rate-limit traffic";
               type string {
               }
             }
           }
           case case_2 {
             container three-color-policer {
               description "Police the packet using a three-color-policer";
               uses apply-advanced;
               choice type-choice {
                 case case_1 {
                   leaf single-rate {
                     description "Name of single-rate three-color policer to use to rate-limit traffic";
                     type string {
                     }
                   }
                 }
                 case case_2 {
                   leaf single-packet-rate {
                     description "Name of single-packet-rate three-color policer to use to rate-limit traffic";
                     type string {
                     }
                   }
                 }
                 case case_3 {
                   leaf two-rate {
                     description "Name of two-rate three-color policer to use to rate-limit traffic";
                     type string {
                     }
                   }
                 }
                 case case_4 {
                   leaf two-packet-rate {
                     description "Name of two-packet-rate three-color policer to use to rate-limit traffic";
                     type string {
                     }
                   }
                 }
               }
             }
           }
           case case_3 {
           }
         }
         choice policy-map-choice {
           case case_1 {
             leaf clear-policy-map {
               description "Clear the policy marking";
               type empty;
             }
           }
           case case_2 {
             leaf policy-map {
               description "Policy map action";
               type string {
               }
             }
           }
         }
         choice mplscnt {
           case case_1 {
           }
           case case_2 {
             leaf count {
               description "Count the packet in the named counter";
               type string {
               }
             }
           }
         }
         leaf sample {
           description "Sample the packet";
           type empty;
         }
         leaf loss-priority {
           description "Classify packet to loss-priority";
           type enumeration {
             enum "low" {
               description "Loss priority low";
             }
             enum "high" {
               description "Loss priority high";
             }
             enum "medium-low" {
               description "Loss priority medium-low";
             }
             enum "medium-high" {
               description "Loss priority medium-high";
             }
           }
         }
         leaf forwarding-class {
           description "Classify packet to forwarding class";
           type string {
           }
         }
         leaf port-mirror-instance {
           description "Port-mirror the packet to specified instance";
           type string {
           }
         }
         leaf packet-mode {
           description "Bypass flow mode for the packet";
           type empty;
         }
         choice designation {
           case case_1 {
           }
           case case_2 {
             leaf accept {
               description "Accept the packet";
               type empty;
             }
           }
           case case_3 {
             leaf discard {
               description "Discard the packet";
               type empty;
             }
           }
           case case_4 {
             leaf next {
               description "Continue to next term in a filter";
               type enumeration {
                 enum "term" {
                   description "Continue to next term in a filter";
                 }
               }
             }
           }
         }
       }
     }
   }
   grouping mpls_pm_family_output_type {
     uses apply-advanced;
   }
   grouping mrp-trace-options {
     description "Trace options for MMRP Protocol";
     uses apply-advanced;
     container file {
       description "Trace file options";
       leaf filename {
         description "Name of file in which to write trace information";
         type string {
           length "1 .. 1024";
         }
       }
       leaf replace {
         description "Replace trace file rather than appending to it";
         status deprecated;
         type empty;
       }
       leaf size {
         description "Maximum trace file size";
         type string;
       }
       leaf files {
         description "Maximum number of trace files";
         default "10";
         type union {
           type string {
             pattern "<.*>|$.*";
           }
           type uint32 {
             range "2 .. 1000";
           }
         }
       }
       leaf no-stamp {
         description "Do not timestamp trace file";
         status deprecated;
         type empty;
       }
       choice world-readable-choice {
         leaf world-readable {
           description "Allow any user to read the log file";
           type empty;
         }
         leaf no-world-readable {
           description "Don't allow any user to read the log file";
           type empty;
         }
       }
     }
     list flag {
       key name;
       ordered-by user;
       description "Tracing parameters";
       leaf name {
         type enumeration {
           enum "events" {
             description "Trace events to the protocol state machine";
           }
           enum "pdu" {
             description "Trace RAPS PDU reception and transmission";
           }
           enum "timers" {
             description "Trace protocol timers";
           }
           enum "state-machine" {
             description "Trace information of the state machine";
           }
           enum "socket" {
             description "Trace soccket activity";
           }
           enum "error" {
             description "Trace all failure conditions";
           }
           enum "all" {
             description "Trace all";
           }
         }
       }
       leaf disable {
         description "Disable this trace flag";
         type empty;
       }
     }
   }
   grouping mstp-interface {
     leaf name {
       type string;
     }
     uses apply-advanced;
     leaf priority {
       description "Interface priority (in increments of 16 - 0,16,..240)";
       type union {
         type string {
           pattern "<.*>|$.*";
         }
         type uint16 {
           range "0 .. 255";
         }
       }
     }
     leaf cost {
       description "Cost of the interface";
       type union {
         type string {
           pattern "<.*>|$.*";
         }
         type uint32 {
           range "1 .. 200000000";
         }
       }
     }
     leaf mode {
       description "Interface mode (P2P or shared)";
       type enumeration {
         enum "point-to-point" {
           description "Interface mode is point-to-point";
         }
         enum "shared" {
           description "Interface mode is shared";
         }
       }
     }
     leaf edge {
       description "Port is an edge port";
       type empty;
     }
     leaf access-trunk {
       description "Send/Receive untagged RSTP BPDUs on this interface";
       type empty;
     }
     container bpdu-timeout-action {
       presence "enable bpdu-timeout-action";
       description "Define action on BPDU expiry (Loop Protect)";
       uses apply-advanced;
       leaf block {
         description "Block the interface";
         type empty;
       }
       leaf alarm {
         description "Generate an alarm";
         type empty;
       }
     }
     leaf no-root-port {
       description "Do not allow the interface to become root (Root Protect)";
       type empty;
     }
     leaf disable {
       description "Disable Spanning Tree on port";
       type empty;
     }
   }
   grouping multicast_interface_options_type {
     description "Multicast interface options";
     leaf name {
       description "Interface name";
       type union {
         type jt:interface-unit;
         type string {
           pattern "<.*>|$.*";
         }
       }
     }
     uses apply-advanced;
     container maximum-bandwidth {
       presence "enable maximum-bandwidth";
       description "Maximum multicast bandwidth for the interface";
       leaf bandwidth-limit {
         description "Maximum multicast bandwidth on the interface";
         units "bps";
         type string;
       }
     }
     choice enable-disable {
       case case_1 {
         leaf enable {
           description "Enable Multicast";
           status deprecated;
           type empty;
         }
       }
       case case_2 {
         leaf disable {
           description "Disable Multicast";
           status deprecated;
           type empty;
         }
       }
     }
     container reverse-oif-mapping {
       presence "enable reverse-oif-mapping";
       description "Enable reverse OIF mapping on the multicast interface";
       uses apply-advanced;
       leaf no-qos-adjust {
         description "Disable reverse OIF mapping QoS adjustment";
         type empty;
       }
     }
     leaf subscriber-leave-timer {
       description "Timeout in seconds to credit back the bandwidth on the subscriber interface";
       units "seconds";
       type union {
         type string {
           pattern "<.*>|$.*";
         }
         type uint32 {
           range "0 .. 30";
         }
       }
     }
     leaf no-qos-adjust {
       description "Disable QoS adjustment for this interface";
       type empty;
     }
   }
   grouping named-address-book-type {
     description "Configure global address book";
     leaf name {
       description "Address book name";
       type string;
     }
     uses apply-advanced;
     leaf description {
       description "Text description of address book";
       type string {
         length "1 .. 900";
       }
     }
     list address {
       key name;
       ordered-by user;
       description "Define a security address";
       uses address_type;
     }
     list address-set {
       key name;
       ordered-by user;
       description "Define a security address set";
       uses address_set_type;
     }
     container attach {
       description "Attach this address book to interface, zone or routing-instance";
       uses apply-advanced;
       list zone {
         key name;
         ordered-by user;
         description "Define a zone to be attached";
         leaf name {
           description "Security zone name";
           type string {
             length "1 .. 63";
           }
         }
         uses apply-advanced;
       }
     }
   }
   grouping address_set_type {
     leaf name {
       description "Security address-set name";
       type string {
         length "1 .. 63";
       }
     }
     uses apply-advanced;
     leaf description {
       description "Text description of address set";
       type string {
         length "1 .. 900";
       }
     }
     list address {
       key name;
       ordered-by user;
       description "Address to be included in this set";
       max-elements 4096;
       leaf name {
         description "Security address name";
         type string {
           length "1 .. 63";
         }
       }
       uses apply-advanced;
     }
     list address-set {
       key name;
       ordered-by user;
       description "Define an address-set name";
       max-elements 4096;
       leaf name {
         type string {
           length "1 .. 63";
         }
       }
       uses apply-advanced;
     }
   }
   grouping address_type {
     leaf name {
       description "Security address name";
       type string {
         length "1 .. 63";
       }
     }
     uses apply-advanced;
     leaf description {
       description "Text description of address";
       type string {
         length "1 .. 900";
       }
     }
     choice address-content {
       case case_1 {
         leaf ip-prefix {
           description "Numeric IPv4 or IPv6 address with prefix";
           type jt:ipprefix;
         }
       }
       case case_2 {
         list dns-name {
           key name;
           ordered-by user;
           description "DNS address name";
           max-elements 1;
           uses dns-name-type;
         }
       }
       case case_3 {
         list wildcard-address {
           key name;
           ordered-by user;
           description "Numeric IPv4 wildcard address with in the form of a.d.d.r/netmask";
           max-elements 1;
           uses wildcard-address-type;
         }
       }
       case case_4 {
         list range-address {
           key name;
           ordered-by user;
           description "Address range";
           max-elements 1;
           uses range-address-type;
         }
       }
     }
   }
   grouping dns-name-type {
     description "DNS address name";
     leaf name {
       description "Fully qualified hostname";
       type string {
         length "1 .. 63";
       }
     }
     uses apply-advanced;
     leaf ipv4-only {
       description "IPv4 dns address";
       type empty;
     }
     leaf ipv6-only {
       description "IPv6 dns address";
       type empty;
     }
   }
   grouping nat-object {
     description "Configure Network Address Translation";
     uses apply-advanced;
     container source {
       description "Configure Source NAT";
       uses ssg-source-nat-object;
     }
     container destination {
       description "Configure Destination NAT";
       uses ssg-destination-nat-object;
     }
     container static {
       description "Configure Static NAT";
       uses ssg-static-nat-object;
     }
     container proxy-arp {
       description "Configure Proxy ARP";
       uses ssg-proxy-arp-object;
     }
     container proxy-ndp {
       description "Configure Proxy NDP";
       uses ssg-proxy-ndp-object;
     }
     container natv6v4 {
       description "Configure NAT between IPv6 and IPv4 options";
       uses apply-advanced;
       leaf no-v6-frag-header {
         description "V6 packet does not always add fragment header when performing nat translation from v4 side to v6 side ";
         type empty;
       }
       leaf clear-dont-fragment-bit {
         description "Clear DF bit in IPv4 header if IPv6 packet size is less than 1280 bytes";
         type empty;
       }
     }
     leaf allow-overlapping-pools {
       description "IP addresses of NAT pools can overlap with other pool";
       type empty;
     }
     container traceoptions {
       description "NAT trace options";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing parameters";
         leaf name {
           type enumeration {
             enum "configuration" {
               description "Trace configuration events";
             }
             enum "flow" {
               description "Trace flow events";
             }
             enum "routing-socket" {
               description "Trace routing socket events";
             }
             enum "routing-protocol" {
               description "Trace routing protocol events";
             }
             enum "all" {
               description "Trace everything";
             }
             enum "source-nat-re" {
               description "Trace source nat events on RE side";
             }
             enum "source-nat-rt" {
               description "Trace source nat events on PFE-RT side";
             }
             enum "source-nat-pfe" {
               description "Trace source nat events on PFE-ukernel side";
             }
             enum "destination-nat-re" {
               description "Trace destination nat events on RE side";
             }
             enum "destination-nat-rt" {
               description "Trace destination nat events on PFE-RT side";
             }
             enum "destination-nat-pfe" {
               description "Trace destination nat events on PFE-ukernel side";
             }
             enum "static-nat-re" {
               description "Trace static nat events on RE side";
             }
             enum "static-nat-rt" {
               description "Trace static nat events on PFE-RT side";
             }
             enum "static-nat-pfe" {
               description "Trace static nat events on PFE-ukernel side";
             }
             enum "nat-svc-set-re" {
               description "Trace NAT and svc-set events on RE side";
             }
           }
         }
         leaf syslog {
           description "Write NAT flow traces to system log also";
           type empty;
         }
       }
     }
     list ipv6-multicast-interfaces {
       key name;
       ordered-by user;
       description "Enable IPv6 multicast filter for IPv6 NAT";
       leaf name {
         description "Interface name";
         type string;
       }
       uses apply-advanced;
       leaf disable {
         description "Disable IPv6 multicast filter for IPv6 NAT";
         type empty;
       }
     }
     list port-forwarding {
       key name;
       ordered-by user;
       description "Define a port-forwarding pool";
       uses pf_mapping;
     }
   }
   grouping network_type {
     leaf name {
       description "Network prefix";
       type jt:ipprefix;
     }
     uses apply-advanced;
   }
   grouping next_hop_group_intf_type {
     leaf name {
       description "Interface through which to send sampled traffic";
       type union {
         type jt:interface-name;
         type string {
           pattern "<.*>|$.*";
         }
       }
     }
     uses apply-advanced;
     list next-hop {
       key name;
       ordered-by user;
       description "Address of next hop through which to send sampled traffic";
       uses next_hop_type;
     }
   }
   grouping next_hop_subgroup_intf_type {
     leaf name {
       description "Interface through which to send sampled traffic";
       type union {
         type jt:interface-name;
         type string {
           pattern "<.*>|$.*";
         }
       }
     }
     uses apply-advanced;
     list next-hop {
       key name;
       ordered-by user;
       description "Address of next hop through which to send sampled traffic";
       uses next_hop_type;
     }
   }
   grouping next_hop_type {
     description "Address of next hop through which to send sampled traffic";
     leaf name {
       type jt:ipaddr;
     }
     uses apply-advanced;
   }
   grouping override-local-server-type {
     description "DHCP override processing";
     uses apply-advanced;
     leaf bootp-support {
       description "Allow processing of bootp requests";
       type empty;
     }
     container delay-offer {
       description "Filter options for dhcp-server";
       uses dhcpv4-filter-option;
     }
     container process-inform {
       presence "enable process-inform";
       description "Process INFORM PDUs";
       uses apply-advanced;
       leaf pool {
         description "Pool name for family inet";
         type string {
           length "1 .. 64";
         }
       }
     }
     container include-option-82 {
       description "Include option-82 in reply packets";
       uses apply-advanced;
       leaf nak {
         description "Include option-82 in NAK";
         type empty;
       }
       leaf forcerenew {
         description "Include option-82 in FORCERENEW";
         type empty;
       }
     }
     leaf delete-binding-on-renegotiation {
       description "Delete binding on renegotiation";
       type empty;
     }
     leaf allow-no-end-option {
       description "Allow packets without end-of-option";
       type empty;
     }
     leaf asymmetric-lease-time {
       description "Use a reduced lease time for the client. In seconds";
       units "seconds";
       type union {
         type string {
           pattern "<.*>|$.*";
         }
         type uint32 {
           range "600 .. 86400";
         }
       }
     }
     leaf protocol-attributes {
       description "DHCPv4 attributes to use as defined under access protocol-attributes";
       type string {
         length "1 .. 64";
       }
     }
     leaf dual-stack {
       description "Dual stack group to use";
       type string {
         length "1 .. 64";
       }
     }
   }
   grouping dhcpv4-filter-option {
     description "Generic DHCPv4 filter processing";
     uses apply-advanced;
     leaf delay-time {
       description "Time delay between discover and offer";
       default "3";
       units "seconds";
       type union {
         type string {
           pattern "<.*>|$.*";
         }
         type uint32 {
           range "1 .. 30";
         }
       }
     }
     container based-on {
       description "Option number";
       uses apply-advanced;
       container option-82 {
         presence "enable option-82";
         description "Option 82";
         uses apply-advanced;
         container equals {
           description "Generic option equals";
           uses server-v6-option-ascii-hex;
         }
         container not-equals {
           description "Generic option not equals";
           uses server-v6-option-ascii-hex;
         }
         container starts-with {
           description "Generic option starts-with";
           uses server-v6-option-ascii-hex;
         }
       }
       container option-60 {
         presence "enable option-60";
         description "Option 60";
         uses apply-advanced;
         container equals {
           description "Generic option equals";
           uses server-v6-option-ascii-hex;
         }
         container not-equals {
           description "Generic option not equals";
           uses server-v6-option-ascii-hex;
         }
         container starts-with {
           description "Generic option starts-with";
           uses server-v6-option-ascii-hex;
         }
       }
       container option-77 {
         presence "enable option-77";
         description "Option 77";
         uses apply-advanced;
         container equals {
           description "Generic option equals";
           uses server-v6-option-ascii-hex;
         }
         container not-equals {
           description "Generic option not equals";
           uses server-v6-option-ascii-hex;
         }
         container starts-with {
           description "Generic option starts-with";
           uses server-v6-option-ascii-hex;
         }
       }
     }
   }
   grouping override-type {
     description "DHCP override processing";
     uses apply-advanced;
     leaf allow-no-end-option {
       description "Allow packets without end-of-option";
       type empty;
     }
     container always-write-option-82 {
       description "Overwrite existing value of option 82, when present";
       presence "enable always-write-option-82";
       uses write-option-82-type;
     }
     leaf user-defined-option-82 {
       description "Set user defined description for option-82";
       type string {
         length "1 .. 252";
       }
     }
     leaf trust-option-82 {
       description "Trust options-82 option";
       type empty;
     }
     leaf disable-relay {
       description "Disable DHCP relay processing";
       type empty;
     }
     leaf no-bind-on-request {
       description "Do not bind if stray DHCP request is received";
       type empty;
     }
     leaf bootp-support {
       description "Allows relay of bootp req and reply";
       type empty;
     }
     leaf dual-stack {
       description "Dual stack group to use.";
       type string {
         length "1 .. 64";
       }
     }
     leaf asymmetric-lease-time {
       description "Use a reduced lease time for the client. In seconds";
       units "seconds";
       type union {
         type string {
           pattern "<.*>|$.*";
         }
         type uint32 {
           range "600 .. 86400";
         }
       }
     }
     container replace-ip-source-with {
       description "Replace IP source address in request and release packets";
       choice replacement-type {
         case case_1 {
           leaf giaddr {
             description "Replace IP source address with giaddr";
             type empty;
           }
         }
       }
     }
     leaf send-release-on-delete {
       description "Always send RELEASE to the server when a binding is deleted";
       type empty;
     }
     leaf relay-source {
       description "Interface for relay source";
       type union {
         type jt:interface-name;
         type string {
           pattern "<.*>|$.*";
         }
       }
     }
     leaf delete-binding-on-renegotiation {
       description "Delete binding on rengotiation";
       type empty;
     }
   }
   grouping p2mp_ldp_lsp_nh_obj {
     uses apply-advanced;
     list root-address {
       key name;
       description "Configure the root address of P2MP LSP";
       leaf name {
         description "Root address of the P2MP LSP";
         type jt:ipaddr;
       }
       uses apply-advanced;
       leaf lsp-id {
         description "Configure the generic LSP identifier";
         type union {
           type string {
             pattern "<.*>|$.*";
           }
           type uint32 {
             range "1 .. 65535";
           }
         }
       }
       list group-address {
         key name;
         description "IPv4/Ipv6 group address for mLDP LSP";
         leaf name {
           description "IPv4/Ipv6 group address";
           type jt:ipaddr;
         }
         uses apply-advanced;
         list source-address {
           key name;
           description "IPv4/Ipv6 source address";
           leaf name {
             description "IPv4/Ipv6 source address for mLDP LSP";
             type jt:ipaddr;
           }
           uses apply-advanced;
         }
       }
     }
   }
   grouping packet_accounting_output_type {
     uses apply-advanced;
     leaf aggregate-export-interval {
       description "Interval of exporting aggregate accounting information";
       default "90";
       units "seconds";
       type union {
         type string {
           pattern "<.*>|$.*";
         }
         type uint32 {
           range "90 .. 1800";
         }
       }
     }
     leaf flow-inactive-timeout {
       description "Interval of inactivity that marks a flow inactive";
       default "60";
       units "seconds";
       type union {
         type string {
           pattern "<.*>|$.*";
         }
         type uint32 {
           range "15 .. 1800";
         }
       }
     }
     leaf flow-active-timeout {
       description "Interval after which an active flow is exported";
       default "1800";
       units "seconds";
       type union {
         type string {
           pattern "<.*>|$.*";
         }
         type uint32 {
           range "60 .. 1800";
         }
       }
     }
     list cflowd {
       key name;
       description "Cflowd collector where flow records are sent";
       uses cflowd_packet_accounting_type;
     }
     list interface {
       key name;
       description "Interfaces used to send monitored information";
       uses packet_export_intf_type;
     }
   }
   grouping cflowd_packet_accounting_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       type union {
         type string {
           pattern "<.*>|$.*";
         }
         type uint8 {
           range "0 .. 63";
         }
       }
     }
     leaf forwarding-class {
       description "Forwarding-class for exported jflow packets, applicable only for inline-jflow";
       type string {
         length "1 .. 64";
       }
     }
     leaf routing-instance {
       description "Name of routing instance on which flow collector is reachable";
       type string;
     }
     leaf version {
       description "Format of exported cflowd aggregates";
       default "5";
       type enumeration {
         enum "5" {
           description "Export cflowd aggregates in version 5 format";
         }
         enum "8" {
           description "Export cflowd aggregates in version 8 format";
         }
       }
     }
     leaf autonomous-system-type {
       description "Type of autonomous system number to export";
       default "origin";
       type enumeration {
         enum "origin" {
           description "Export origin-AS numbers";
         }
         enum "peer" {
           description "Export peer-AS numbers";
         }
       }
     }
     container aggregation {
       description "Aggregations to perform for exported flows (version 8 only)";
       uses aggregation_type;
     }
   }
   grouping packet_export_intf_type {
     leaf name {
       description "Interfaces used to send monitored information";
       type union {
         type jt:interface-unit;
         type string {
           pattern "<.*>|$.*";
         }
       }
     }
     uses apply-advanced;
     leaf engine-id {
       description "Identity (number) of this accounting interface";
       type union {
         type uint8;
         type string {
           pattern "<.*>|$.*";
         }
       }
     }
     leaf engine-type {
       description "Type (number) of this accounting interface";
       type union {
         type uint8;
         type string {
           pattern "<.*>|$.*";
         }
       }
     }
     leaf source-address {
       description "Address to use for generating monitored packets";
       type jt:ipaddr;
     }
   }
   grouping pccd-traceoptions-type {
     description "Trace options for PCCD";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Area of PCCD to enable debugging output";
       leaf name {
         type enumeration {
           enum "pccd-main" {
             description "Trace main module";
           }
           enum "pccd-config" {
             description "Trace configuration parsing operations";
           }
           enum "pccd-core" {
             description "Trace PCCD's core operations";
           }
           enum "pccd-ui" {
             description "Trace user interface handling";
           }
           enum "pccd-rpd" {
             description "Trace communication with RPD";
           }
           enum "pccd-functions" {
             description "Trace function entries/outs";
           }
           enum "all" {
             description "Trace all areas of PCCD code";
           }
         }
       }
     }
   }
   grouping peer-group {
     leaf name {
       description "IP address for this peer";
       type jt:ipv4addr;
     }
     uses apply-advanced;
     leaf local-ip-addr {
       description "Local IP address to use for this peer alone.";
       type jt:ipv4addr;
     }
     leaf session-establishment-hold-time {
       description "Time within which connection must succeed with this peer";
       units "seconds";
       type union {
         type string {
           pattern "<.*>|$.*";
         }
         type uint32 {
           range "45 .. 600";
         }
       }
     }
     leaf-list redundancy-group-id-list {
       ordered-by user;
       description "List of redundacy groups this peer is part of";
       type union {
         type uint32;
         type string {
           pattern "<.*>|$.*";
         }
       }
     }
     container backup-liveness-detection {
       presence "enable backup-liveness-detection";
       description "Backup liveness detection";
       uses apply-advanced;
       leaf backup-peer-ip {
         description "Backup livelness detection peer's IP address";
         type jt:ipv4addr;
       }
     }
     container liveness-detection {
       presence "enable liveness-detection";
       description "Bidirectional Forwarding Detection options for the peer";
       uses apply-advanced;
       leaf version {
         description "BFD protocol version number";
         default "automatic";
         type enumeration {
           enum "0" {
             description "BFD version 0 (deprecated)";
           }
           enum "1" {
             description "BFD version 1";
           }
           enum "automatic" {
             description "Choose BFD version automatically";
           }
         }
       }
       leaf minimum-interval {
         description "Minimum transmit and receive interval";
         units "milliseconds";
         type union {
           type string {
             pattern "<.*>|$.*";
           }
           type uint32 {
             range "1 .. 255000";
           }
         }
       }
       leaf minimum-transmit-interval {
         description "Minimum transmit interval";
         status deprecated;
         units "milliseconds";
         type union {
           type string {
             pattern "<.*>|$.*";
           }
           type uint32 {
             range "1 .. 255000";
           }
         }
       }
       leaf minimum-receive-interval {
         description "Minimum receive interval";
         units "milliseconds";
         type union {
           type string {
             pattern "<.*>|$.*";
           }
           type uint32 {
             range "1 .. 255000";
           }
         }
       }
       leaf multiplier {
         description "Detection time multiplier";
         default "3";
         type union {
           type string {
             pattern "<.*>|$.*";
           }
           type uint32 {
             range "1 .. 255";
           }
         }
       }
       choice adaptation-choice {
         case case_1 {
           leaf no-adaptation {
             description "Disable adaptation";
             type empty;
           }
         }
       }
       container transmit-interval {
         description "Transmit-interval options";
         uses apply-advanced;
         leaf minimum-interval {
           description "Minimum transmit interval";
           units "milliseconds";
           type union {
             type string {
               pattern "<.*>|$.*";
             }
             type uint32 {
               range "1 .. 255000";
             }
           }
         }
         leaf threshold {
           description "High transmit interval triggering a trap";
           units "milliseconds";
           type union {
             type uint32;
             type string {
               pattern "<.*>|$.*";
             }
           }
         }
       }
       container detection-time {
         description "Detection-time options";
         uses apply-advanced;
         leaf threshold {
           description "High detection-time triggering a trap";
           units "milliseconds";
           type union {
             type uint32;
             type string {
               pattern "<.*>|$.*";
             }
           }
         }
       }
     }
     leaf authentication-key {
       description "MD5 authentication key";
       type string {
         length "1 .. 126";
       }
     }
   }
   grouping periodic_oam {
     uses apply-advanced;
     container mpls-tp-mode {
       presence "enable mpls-tp-mode";
       description "MPLS-TP Mode, Do not use IP addressing for OAM";
       uses apply-advanced;
       container lsping-channel-type {
         description "Supported Control-channel types for MPLS-TP mode....";
         uses apply-advanced;
         choice action-choice {
           case case_1 {
             leaf ipv4 {
               description "Use channel-type IPv4(0x0021), With IP-UDP encapsulation";
               type empty;
             }
           }
           case case_2 {
             leaf on-demand-cv {
               description "Use channel-type On-Demand-CV(0x0025), Without IP-UDP encapsulation";
               type empty;
             }
           }
         }
       }
     }
     container bfd-port {
       description "Egress knob to select MHOP-BFD port for MPLS BFD";
       uses apply-advanced;
       leaf-list import {
         ordered-by user;
         description "Import policy";
         type jt:policy-algebra;
       }
     }
     container bfd-liveness-detection {
       description "Bidirectional Forwarding Detection options";
       uses apply-advanced;
       leaf version {
         description "BFD protocol version number";
         default "automatic";
         type enumeration {
           enum "0" {
             description "BFD version 0 (deprecated)";
           }
           enum "1" {
             description "BFD version 1";
           }
           enum "automatic" {
             description "Choose BFD version automatically";
           }
         }
       }
       leaf minimum-interval {
         description "Minimum transmit and receive interval";
         units "milliseconds";
         type union {
           type string {
             pattern "<.*>|$.*";
           }
           type uint32 {
             range "1 .. 255000";
           }
         }
       }
       leaf minimum-transmit-interval {
         description "Minimum transmit interval";
         status deprecated;
         units "milliseconds";
         type union {
           type string {
             pattern "<.*>|$.*";
           }
           type uint32 {
             range "1 .. 255000";
           }
         }
       }
       leaf minimum-receive-interval {
         description "Minimum receive interval";
         units "milliseconds";
         type union {
           type string {
             pattern "<.*>|$.*";
           }
           type uint32 {
             range "1 .. 255000";
           }
         }
       }
       leaf multiplier {
         description "Detection time multiplier";
         default "3";
         type union {
           type string {
             pattern "<.*>|$.*";
           }
           type uint32 {
             range "1 .. 255";
           }
         }
       }
       choice adaptation-choice {
         case case_1 {
           leaf no-adaptation {
             description "Disable adaptation";
             type empty;
           }
         }
       }
       container transmit-interval {
         description "Transmit-interval options";
         uses apply-advanced;
         leaf minimum-interval {
           description "Minimum transmit interval";
           units "milliseconds";
           type union {
             type string {
               pattern "<.*>|$.*";
             }
             type uint32 {
               range "1 .. 255000";
             }
           }
         }
         leaf threshold {
           description "High transmit interval triggering a trap";
           units "milliseconds";
           type union {
             type uint32;
             type string {
               pattern "<.*>|$.*";
             }
           }
         }
       }
       container detection-time {
         description "Detection-time options";
         uses apply-advanced;
         leaf threshold {
           description "High detection-time triggering a trap";
           units "milliseconds";
           type union {
             type uint32;
             type string {
               pattern "<.*>|$.*";
             }
           }
         }
       }
       container failure-action {
         description "Action to take when BFD session goes down";
         choice action-choice {
           case case_1 {
             leaf teardown {
               description "Teardown label switched path and resignal";
               type empty;
             }
           }
           case case_2 {
             container make-before-break {
               presence "enable make-before-break";
               description "Resignal the label switched path before teardown";
               uses apply-advanced;
               leaf teardown-timeout {
                 description "Time to wait before teardown";
                 units "seconds";
                 type union {
                   type string {
                     pattern "<.*>|$.*";
                   }
                   type uint32 {
                     range "0 .. 30";
                   }
                 }
               }
             }
           }
         }
       }
       leaf no-router-alert-option {
         description "Do not set Router-Alert options in IP header for MPLS-BFD";
         type empty;
       }
       leaf use-ip-ttl-1 {
         description "Set TTL value to 1 in IP header for MPLS-BFD";
         type empty;
       }
     }
     container performance-monitoring {
       description "Performance monitoring options";
       uses apply-advanced;
       container traceoptions {
         description "Trace options for PM";
         uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "init" {
                 description "Trace init commnad";
               }
               enum "error" {
                 description "Trace error conditions";
               }
               enum "event" {
                 description "Trace state machine events";
               }
               enum "general" {
                 description "Trace general events";
               }
               enum "packet" {
                 description "Trace various packets ";
               }
               enum "timer" {
                 description "Trace timer processing";
               }
               enum "all" {
                 description "Trace everything";
               }
             }
           }
         }
       }
       container querier {
         description "Querier options";
         uses apply-advanced;
         container loss {
           description "Loss measurement options";
           uses apply-advanced;
           list traffic-class {
             key name;
             description "Traffic class specific options";
             leaf name {
               description "Traffic class value";
               type enumeration {
                 enum "tc-0" {
                   description "Traffic class 0";
                 }
                 enum "tc-1" {
                   description "Traffic class 1";
                 }
                 enum "tc-2" {
                   description "Traffic class 2";
                 }
                 enum "tc-3" {
                   description "Traffic class 3";
                 }
                 enum "tc-4" {
                   description "Traffic class 4";
                 }
                 enum "tc-5" {
                   description "Traffic class 5";
                 }
                 enum "tc-6" {
                   description "Traffic class 6";
                 }
                 enum "tc-7" {
                   description "Traffic class 7";
                 }
                 enum "all" {
                   description "All Traffic class";
                 }
                 enum "none" {
                   description "No Traffic class";
                 }
               }
             }
             uses apply-advanced;
             leaf query-interval {
               description "Minimum transmit interval";
               units "milliseconds";
               type union {
                 type string {
                   pattern "<.*>|$.*";
                 }
                 type uint32 {
                   range "1000 .. 4294967295";
                 }
               }
             }
             leaf measurement-quantity {
               description "Loss measurement quantity";
               default "packets";
               type enumeration {
                 enum "bytes" {
                   description "Byte loss measurement";
                 }
                 enum "packets" {
                   description "Packet loss measurement";
                 }
               }
             }
             leaf average-sample-size {
               description "Number of samples used in average calculation";
               type union {
                 type string {
                   pattern "<.*>|$.*";
                 }
                 type uint16 {
                   range "1 .. 30";
                 }
               }
             }
             leaf loss-threshold {
               description "Loss threshold value";
               type union {
                 type string {
                   pattern "<.*>|$.*";
                 }
                 type uint32 {
                   range "1 .. 4294967295";
                 }
               }
             }
             leaf loss-threshold-window {
               description "Number of samples for loss threshold calculation";
               type union {
                 type string {
                   pattern "<.*>|$.*";
                 }
                 type uint32 {
                   range "1 .. 30";
                 }
               }
             }
           }
         }
         container delay {
           description "Delay measurement options";
           uses apply-advanced;
           list traffic-class {
             key name;
             description "Traffic class specific options";
             leaf name {
               description "Traffic class value";
               type enumeration {
                 enum "tc-0" {
                   description "Traffic class 0";
                 }
                 enum "tc-1" {
                   description "Traffic class 1";
                 }
                 enum "tc-2" {
                   description "Traffic class 2";
                 }
                 enum "tc-3" {
                   description "Traffic class 3";
                 }
                 enum "tc-4" {
                   description "Traffic class 4";
                 }
                 enum "tc-5" {
                   description "Traffic class 5";
                 }
                 enum "tc-6" {
                   description "Traffic class 6";
                 }
                 enum "tc-7" {
                   description "Traffic class 7";
                 }
                 enum "all" {
                   description "All Traffic classes";
                 }
               }
             }
             uses apply-advanced;
             leaf query-interval {
               description "Minimum transmit interval";
               units "milliseconds";
               type union {
                 type string {
                   pattern "<.*>|$.*";
                 }
                 type uint32 {
                   range "1000 .. 4294967295";
                 }
               }
             }
             leaf padding-size {
               description "Size of padding";
               type union {
                 type string {
                   pattern "<.*>|$.*";
                 }
                 type uint16 {
                   range "1 .. 1500";
                 }
               }
             }
             leaf average-sample-size {
               description "Number of samples used in average calculation";
               type union {
                 type string {
                   pattern "<.*>|$.*";
                 }
                 type uint16 {
                   range "1 .. 30";
                 }
               }
             }
             leaf twcd-delay-threshold {
               description "Two way channel delay threshold value";
               units "microseconds";
               type union {
                 type string {
                   pattern "<.*>|$.*";
                 }
                 type uint32 {
                   range "1 .. 4294967295";
                 }
               }
             }
             leaf rtt-delay-threshold {
               description "Round trip delay threshold value";
               units "microseconds";
               type union {
                 type string {
                   pattern "<.*>|$.*";
                 }
                 type uint32 {
                   range "1 .. 4294967295";
                 }
               }
             }
           }
         }
         container loss-delay {
           description "Combined loss-delay measurement options";
           uses apply-advanced;
           list traffic-class {
             key name;
             description "Traffic class specific options";
             leaf name {
               description "Traffic class value";
               type enumeration {
                 enum "tc-0" {
                   description "Traffic class 0";
                 }
                 enum "tc-1" {
                   description "Traffic class 1";
                 }
                 enum "tc-2" {
                   description "Traffic class 2";
                 }
                 enum "tc-3" {
                   description "Traffic class 3";
                 }
                 enum "tc-4" {
                   description "Traffic class 4";
                 }
                 enum "tc-5" {
                   description "Traffic class 5";
                 }
                 enum "tc-6" {
                   description "Traffic class 6";
                 }
                 enum "tc-7" {
                   description "Traffic class 7";
                 }
                 enum "all" {
                   description "All Traffic classes";
                 }
                 enum "none" {
                   description "No Traffic class";
                 }
               }
             }
             uses apply-advanced;
             leaf query-interval {
               description "Minimum transmit interval";
               units "milliseconds";
               type union {
                 type string {
                   pattern "<.*>|$.*";
                 }
                 type uint32 {
                   range "1000 .. 4294967295";
                 }
               }
             }
             leaf measurement-quantity {
               description "Loss measurement quantity";
               default "packets";
               type enumeration {
                 enum "bytes" {
                   description "Byte loss measurement";
                 }
                 enum "packets" {
                   description "Packet loss measurement";
                 }
               }
             }
             leaf padding-size {
               description "Size of padding";
               type union {
                 type string {
                   pattern "<.*>|$.*";
                 }
                 type uint16 {
                   range "1 .. 1500";
                 }
               }
             }
             leaf average-sample-size {
               description "Number of samples used in average calculation";
               type union {
                 type string {
                   pattern "<.*>|$.*";
                 }
                 type uint16 {
                   range "1 .. 30";
                 }
               }
             }
             leaf loss-threshold {
               description "Loss threshold value";
               type union {
                 type string {
                   pattern "<.*>|$.*";
                 }
                 type uint32 {
                   range "1 .. 4294967295";
                 }
               }
             }
             leaf loss-threshold-window {
               description "Number of samples for loss threshold calculation";
               type union {
                 type string {
                   pattern "<.*>|$.*";
                 }
                 type uint32 {
                   range "1 .. 30";
                 }
               }
             }
             leaf twcd-delay-threshold {
               description "Two way channel delay threshold value";
               units "microseconds";
               type union {
                 type string {
                   pattern "<.*>|$.*";
                 }
                 type uint32 {
                   range "1 .. 4294967295";
                 }
               }
             }
             leaf rtt-delay-threshold {
               description "Round trip delay threshold value";
               units "microseconds";
               type union {
                 type string {
                   pattern "<.*>|$.*";
                 }
                 type uint32 {
                   range "1 .. 4294967295";
                 }
               }
             }
           }
         }
       }
       container responder {
         description "Responder options";
         uses apply-advanced;
         container loss {
           description "Loss measurement options";
           uses apply-advanced;
           leaf min-query-interval {
             description "Minimum query interval";
             units "milliseconds";
             type union {
               type string {
                 pattern "<.*>|$.*";
               }
               type uint32 {
                 range "1000 .. 4294967295";
               }
             }
           }
         }
         container delay {
           description "Delay measurement options";
           uses apply-advanced;
           leaf min-query-interval {
             description "Minimum query interval";
             units "milliseconds";
             type union {
               type string {
                 pattern "<.*>|$.*";
               }
               type uint32 {
                 range "1000 .. 4294967295";
               }
             }
           }
         }
       }
     }
     leaf lsp-ping-interval {
       description "Time interval between LSP ping messages";
       units "seconds";
       type union {
         type string {
           pattern "<.*>|$.*";
         }
         type uint16 {
           range "30 .. 3600";
         }
       }
     }
     leaf lsp-ping-multiplier {
       description "Number of ping reply missed before declaring BFD down";
       type union {
         type string {
           pattern "<.*>|$.*";
         }
         type uint8 {
           range "1 .. 5";
         }
       }
     }
     container traceoptions {
       description "Trace options for MPLSOAM process";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing parameters";
         leaf name {
           type enumeration {
             enum "configuration" {
               description "Trace configuration events";
             }
             enum "pipe" {
               description "Trace pipe activity";
             }
             enum "rpc-packet-details" {
               description "Trace RPC packet details";
             }
             enum "database" {
               description "Trace database activity";
             }
             enum "network" {
               description "Trace network activity";
             }
             enum "traceroute" {
               description "Trace traceroute activity";
             }
             enum "all" {
               description "Trace everything";
             }
           }
         }
       }
     }
   }
   grouping pf_mapping {
     leaf name {
       description "Port Forwarding name";
       type string {
         length "1 .. 63";
       }
     }
     uses apply-advanced;
     list destined-port {
       key "port translated-port";
       ordered-by user;
       description "Port forwarding mappings";
       max-elements 32;
       leaf port {
         description "Destination port";
         type union {
           type string {
             pattern "<.*>|$.*";
           }
           type uint16 {
             range "1 .. 65535";
           }
         }
       }
       leaf translated-port {
         description "Translated port";
         type union {
           type string {
             pattern "<.*>|$.*";
           }
           type uint16 {
             range "1 .. 65535";
           }
         }
       }
     }
   }
   grouping pim_bootstrap_options_type {
     uses apply-advanced;
     leaf priority {
       description "Eligibility to be the bootstrap router";
       type union {
         type string {
           pattern "<.*>|$.*";
         }
         type uint32 {
           range "0 .. 255";
         }
       }
     }
     leaf-list import {
       ordered-by user;
       description "Bootstrap import policy";
       type jt:policy-algebra;
     }
     leaf-list export {
       ordered-by user;
       description "Bootstrap export policy";
       type jt:policy-algebra;
     }
   }
   grouping pim_filter_obj {
     description "Filter to apply to tracing";
     leaf match-on {
       description "Argument on which to match";
       type enumeration {
         enum "prefix" {
           description "Filter based on prefix";
         }
       }
     }
     leaf-list policy {
       ordered-by user;
       description "Filter policy";
       type jt:policy-algebra;
     }
   }
   grouping pim_rp_group_range_type {
     leaf name {
       type jt:ipprefix;
     }
     uses apply-advanced;
     leaf nexthop-hold-time {
       description "Nexthop hold time in milliseconds";
       units "milliseconds";
       type union {
         type string {
           pattern "<.*>|$.*";
         }
         type uint32 {
           range "1 .. 1000";
         }
       }
     }
   }
   grouping pm-rspan-vlan {
     description "RSPAN vlan for pm";
     leaf name {
       description "VLAN name or VLAN id";
       type string {
       }
     }
     uses apply-advanced;
     leaf no-tag {
       description "Removes extra RSPAN tag from mirrored packets";
       type empty;
     }
   }
   grouping pm_family_input_type {
     description "Input options for port mirroring";
     uses apply-advanced;
     leaf rate {
       description "Ratio of packets to be sampled (1 out of N)";
       type union {
         type string {
           pattern "<.*>|$.*";
         }
         type uint16 {
           range "1 .. 65535";
         }
       }
     }
     leaf run-length {
       description "Number of samples after initial trigger";
       type union {
         type string {
           pattern "<.*>|$.*";
         }
         type uint32 {
           range "0 .. 20";
         }
       }
     }
     leaf maximum-packet-length {
       description "Maximum length of the mirrored packet";
       default "0";
       units "bytes";
       type union {
         type string {
           pattern "<.*>|$.*";
         }
         type uint32 {
           range "0 .. 9216";
         }
       }
     }
   }
   grouping policy-object-type {
     uses apply-advanced;
     container traceoptions {
       description "Network Security Policy Tracing Options";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing parameters";
         leaf name {
           type enumeration {
             enum "configuration" {
               description "Trace configuration events";
             }
             enum "routing-socket" {
               description "Trace routing socket events";
             }
             enum "compilation" {
               description "Policy compilation events";
             }
             enum "ipc" {
               description "Inter-process communication events";
             }
             enum "rules" {
               description "Policy rules related events";
             }
             enum "lookup" {
               description "Policy lookup events";
             }
             enum "all" {
               description "Trace everything";
             }
           }
         }
       }
     }
     list policy {
       key "from-zone-name to-zone-name";
       ordered-by user;
       description "Define a policy context from this zone";
       leaf from-zone-name {
         description "Source zone";
         type string {
           length "1 .. 63";
         }
       }
       leaf to-zone-name {
         description "Destination zone";
         type string {
           length "1 .. 63";
         }
       }
       uses apply-advanced;
       list policy {
         key name;
         ordered-by user;
         description "Define security policy in specified zone-to-zone direction";
         uses policy_type;
       }
     }
     container global {
       description "Define a global policy context";
       uses apply-advanced;
       list policy {
         key name;
         ordered-by user;
         description "Define security policy in global context";
         uses policy_type;
       }
     }
     container default-policy {
       description "Configure default action when no user-defined policy match";
       uses apply-advanced;
       leaf default-action {
         description "Default action";
         default "deny-all";
         type enumeration {
           enum "permit-all" {
             description "Permit all traffic if no policy match";
           }
           enum "deny-all" {
             description "Deny all traffic if no policy match";
           }
         }
       }
     }
     container policy-rematch {
       presence "enable policy-rematch";
       description "Re-evaluate the policy when changed";
       leaf extensive {
         description "Perform policy extensive rematch";
         type empty;
       }
     }
     container policy-stats {
       presence "enable policy-stats";
       description "Parameters for policy statistics";
       uses apply-advanced;
       leaf system-wide {
         description "Enable/Disable system-wide policy statistics";
         type enumeration {
           enum "enable" {
             description "Enable policy system-wide statistics";
           }
           enum "disable" {
             description "Disable policy system-wide statistics";
           }
         }
       }
     }
     container pre-id-default-policy {
       description "Configure default policy action before dynamic application is finally identified";
       uses apply-advanced;
       container then {
         description "Specify policy action to take when packet match criteria";
         uses apply-advanced;
         container log {
           description "Enable log";
           uses log_type;
         }
         container session-timeout {
           description "Session timeout";
           uses session_timeout_type;
         }
       }
     }
     list stateful-firewall-rule {
       key name;
       ordered-by user;
       description "Define a stateful-firewall-rule";
       max-elements 16960;
       leaf name {
         description "Stateful-firewall-rule name";
         type string {
           length "1 .. 63";
         }
       }
       uses apply-advanced;
       leaf match-direction {
         description "Direction for which the rule match is applied";
         type enumeration {
           enum "input" {
             description "Match on input to interface";
           }
           enum "output" {
             description "Match on output from interface";
           }
           enum "input-output" {
             description "Match on input to or output from interface";
           }
         }
       }
       list policy {
         key name;
         ordered-by user;
         description "Define a stateful-firewall policy";
         uses policy_type;
       }
     }
     list stateful-firewall-rule-set {
       key name;
       ordered-by user;
       description "Defines a set of stateful firewall rules";
       max-elements 16960;
       leaf name {
         description "Name of the stateful firewall rule set";
         type string {
           length "1 .. 63";
         }
       }
       uses apply-advanced;
       list stateful-firewall-rule {
         key name;
         ordered-by user;
         description "Rule to be included in this stateful firewall rule set";
         max-elements 16960;
         leaf name {
           description "Stateful-firewall-rule name";
           type string {
           }
         }
         uses apply-advanced;
       }
     }
   }
   grouping log_type {
     uses apply-advanced;
     leaf session-init {
       description "Log at session init time";
       type empty;
     }
     leaf session-close {
       description "Log at session close time";
       type empty;
     }
   }
   grouping policy_type {
     leaf name {
       description "Security policy name";
       type string {
         length "1 .. 63";
       }
     }
     uses apply-advanced;
     leaf description {
       description "Text description of policy";
       type string {
         length "1 .. 900";
       }
     }
     container match {
       description "Specify security policy match-criteria";
       uses apply-advanced;
       choice source-address_choice {
         case case_1 {
           leaf-list source-address {
             ordered-by user;
             type string;
           }
         }
       }
       choice destination-address_choice {
         case case_1 {
           leaf-list destination-address {
             ordered-by user;
             type string;
           }
         }
       }
       leaf source-address-excluded {
         description "Exclude source addresses";
         type empty;
       }
       leaf destination-address-excluded {
         description "Exclude destination addresses";
         type empty;
       }
       choice application_type_choice {
         case case_1 {
           leaf-list application {
             ordered-by user;
             type string;
           }
         }
       }
       choice source_identity_choice {
         case case_1 {
           leaf-list source-identity {
             ordered-by user;
             type string;
           }
         }
       }
       choice source_end_user_profile_choice {
         case case_1 {
           container source-end-user-profile {
             description "Match source end user profile";
             uses match_source_end_user_profile_value;
           }
         }
       }
       choice dynamic_application_type_choice {
         case case_1 {
           leaf-list dynamic-application {
             ordered-by user;
             type string;
           }
         }
       }
       choice url_category_type_choice {
         case case_1 {
           leaf-list url-category {
             ordered-by user;
             type string;
           }
         }
       }
       choice from_zone_choice {
         case case_1 {
           leaf-list from-zone {
             ordered-by user;
             type string;
           }
         }
       }
       choice to_zone_choice {
         case case_1 {
           leaf-list to-zone {
             ordered-by user;
             type string;
           }
         }
       }
     }
     container then {
       description "Specify policy action to take when packet match criteria";
       uses apply-advanced;
       choice action {
         case case_1 {
           leaf deny {
             description "Deny packets";
             type empty;
           }
         }
         case case_2 {
           container reject {
             presence "enable reject";
             description "Reject packets";
             uses apply-advanced;
             leaf profile {
               description "Profile for redirect HTTP/S traffic";
               type string;
             }
             container ssl-proxy {
               presence "enable ssl-proxy";
               description "SSL proxy services";
               uses apply-advanced;
               leaf profile-name {
                 description "Specify SSL proxy service profile name";
                 type string;
               }
             }
           }
         }
         case case_3 {
           container permit {
             presence "enable permit";
             description "Permit packets";
             uses apply-advanced;
             container tunnel {
               description "Tunnel packets";
               uses tunnel_type;
             }
             container firewall-authentication {
               description "Enable authentication for this policy if permit or tunnel";
               uses firewall_authentication_type;
             }
             container destination-address {
               description "Enable destination address translation";
               presence "enable destination-address";
               uses destination_nat_enable_type;
             }
             container application-services {
               description "Application Services";
               uses application_services_type;
             }
             container tcp-options {
               description "Transmission Control Protocol session configuration";
               uses apply-advanced;
               leaf syn-check-required {
                 description "Enable per policy SYN-flag check";
                 type empty;
               }
               leaf sequence-check-required {
                 description "Enable per policy sequence-number checking";
                 type empty;
               }
               leaf initial-tcp-mss {
                 description "Override MSS value for initial direction";
                 type union {
                   type string {
                     pattern "<.*>|$.*";
                   }
                   type uint32 {
                     range "64 .. 65535";
                   }
                 }
               }
               leaf reverse-tcp-mss {
                 description "Override MSS value for reverse direction";
                 type union {
                   type string {
                     pattern "<.*>|$.*";
                   }
                   type uint32 {
                     range "64 .. 65535";
                   }
                 }
               }
               leaf window-scale {
                 description "Enable per policy window-scale";
                 type empty;
               }
             }
             leaf services-offload {
               description "Enable services offloading";
               type empty;
             }
           }
         }
       }
       container log {
         description "Enable log";
         uses log_type;
       }
       container count {
         description "Enable count";
         presence "enable count";
         uses count_type;
       }
     }
     leaf scheduler-name {
       description "Name of scheduler";
       type string {
         length "1 .. 63";
       }
     }
   }
   grouping application_services_type {
     description "Application Services";
     uses apply-advanced;
     leaf gprs-gtp-profile {
       description "Specify GPRS Tunneling Protocol profile name";
       type string {
         length "1 .. 63";
       }
     }
     leaf gprs-sctp-profile {
       description "Specify GPRS stream control protocol profile name";
       type string {
         length "1 .. 63";
       }
     }
     leaf idp {
       description "Intrusion detection and prevention";
       type empty;
     }
     leaf idp-policy {
       description "Specify idp policy name";
       type string {
         length "1 .. 255";
       }
     }
     container ssl-proxy {
       presence "enable ssl-proxy";
       description "SSL proxy services";
       uses apply-advanced;
       leaf profile-name {
         description "Specify SSL proxy service profile name";
         type string;
       }
     }
     container uac-policy {
       presence "enable uac-policy";
       description "Enable unified access control enforcement of policy";
       uses apply-advanced;
       leaf captive-portal {
         type string {
           length "1 .. 128";
         }
       }
     }
     leaf utm-policy {
       description "Specify utm policy name";
       type string {
         length "1 .. 255";
       }
     }
     leaf icap-redirect {
       description "Specify icap redirect profile name";
       type string {
         length "1 .. 31";
       }
     }
     container application-firewall {
       description "Application firewall services";
       status deprecated;
       uses jsf_service_rule_set_type;
     }
     container application-traffic-control {
       description "Application traffic control services";
       uses jsf_application_traffic_control_rule_set_type;
     }
     choice wx-redirection {
       case case_1 {
         leaf redirect-wx {
           description "Set WX redirection";
           type empty;
         }
       }
       case case_2 {
         leaf reverse-redirect-wx {
           description "Set WX reverse redirection";
           type empty;
         }
       }
     }
     leaf security-intelligence-policy {
       description "Specify security-intelligence policy name";
       type string {
         length "1 .. 255";
       }
     }
     leaf advanced-anti-malware-policy {
       description "Specify advanced-anti-malware policy name";
       type string {
         length "1 .. 255";
       }
     }
   }
   grouping count_type {
     uses apply-advanced;
   }
   grouping destination_nat_enable_type {
     description "Enable Destination NAT";
     uses apply-advanced;
     choice destination_nat {
       case case_1 {
         leaf drop-translated {
           description "Drop the policy if NAT translated";
           type empty;
         }
       }
       case case_2 {
         leaf drop-untranslated {
           description "Drop the policy if NAT untranslated";
           type empty;
         }
       }
     }
   }
   grouping firewall_authentication_type {
     uses apply-advanced;
     choice auth-type {
       case case_1 {
         container pass-through {
           presence "enable pass-through";
           description "Pass-through firewall authentication settings";
           uses apply-advanced;
           leaf access-profile {
             description "Specify access profile name";
             type string {
               length "1 .. 63";
             }
           }
           leaf-list client-match {
             ordered-by user;
             description "Name of user or group to match";
             type string {
               length "1 .. 63";
             }
           }
           leaf web-redirect {
             description "Redirect unauthenticated HTTP requests to the device's internal web server";
             type empty;
           }
           leaf web-redirect-to-https {
             description "Redirect unauthenticated HTTP requests to the device's internal HTTPS web server";
             type empty;
           }
           leaf ssl-termination-profile {
             description "Specify SSL termination profile used to the SSL offload";
             type string {
               length "1 .. 63";
             }
           }
           leaf auth-only-browser {
             description "Authenticate only browser traffic";
             type empty;
           }
           list auth-user-agent {
             key name;
             ordered-by user;
             description "Authenticate HTTP traffic with specified user agent";
             leaf name {
               description "Authenticate HTTP traffic with specified user agent";
               type string {
                 length "1 .. 16";
               }
             }
             uses apply-advanced;
           }
         }
       }
       case case_2 {
         container web-authentication {
           presence "enable web-authentication";
           description "Web-authentication settings";
           uses apply-advanced;
           leaf-list client-match {
             ordered-by user;
             description "Name of user or group to match";
             type string {
               length "1 .. 63";
             }
           }
         }
       }
       case case_3 {
         container user-firewall {
           description "User-firewall firewall authentication settings";
           uses apply-advanced;
           leaf access-profile {
             description "Specify access profile name";
             type string {
               length "1 .. 63";
             }
           }
           leaf web-redirect {
             description "Redirect unauthenticated HTTP req to web server";
             type empty;
           }
           leaf web-redirect-to-https {
             description "Redirect unauthenticated HTTP req to HTTPS web server";
             type empty;
           }
           leaf ssl-termination-profile {
             description "Specify SSL termination profile used to the SSL offload";
             type string {
               length "1 .. 63";
             }
           }
           leaf auth-only-browser {
             description "Authenticate only browser traffic";
             type empty;
           }
           list auth-user-agent {
             key name;
             ordered-by user;
             description "Authenticate HTTP traffic with specified user agent";
             leaf name {
               description "Authenticate HTTP traffic with specified user agent";
               type string {
                 length "1 .. 16";
               }
             }
             uses apply-advanced;
           }
           leaf domain {
             description "Specify domain name";
             type string {
               length "1 .. 64";
             }
           }
         }
       }
     }
     leaf push-to-identity-management {
       description "Push auth entry to identity management server";
       type empty;
     }
   }
   grouping jsf_service_rule_set_type {
     description "Define service rule set reference";
     uses apply-advanced;
     leaf rule-set {
       description "Service rule set name";
       type string {
         length "1 .. 64";
       }
     }
   }
   grouping match_source_end_user_profile_value {
     uses apply-advanced;
     leaf source-end-user-profile-name {
       description "Specify source-end-user-profile name from list to match";
       type string;
     }
   }
   grouping port-range {
     description "Port ranges";
     leaf name {
       description "Single port/minimum port in the port range";
       type union {
         type string {
           pattern "<.*>|$.*";
         }
         type uint32 {
           range "0 .. 65535";
         }
       }
     }
     leaf maximum-port {
       description "Maximum port in the port range";
       type union {
         type string {
           pattern "<.*>|$.*";
         }
         type uint32 {
           range "0 .. 65535";
         }
       }
     }
   }
   grouping ppp-traceoptions-type {
     description "Trace options for PPP process";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Area of PPP process to enable debugging output";
       leaf name {
         type enumeration {
           enum "access" {
             description "Trace access code";
           }
           enum "address-pool" {
             description "Trace address pool code";
           }
           enum "auth" {
             description "Trace authentication code";
           }
           enum "chap" {
             description "Trace CHAP code";
           }
           enum "pap" {
             description "Trace PAP code";
           }
           enum "config" {
             description "Trace configuration code";
           }
           enum "ifdb" {
             description "Trace interface database code";
           }
           enum "lcp" {
             description "Trace LCP state machine code";
           }
           enum "memory" {
             description "Trace memory management code";
           }
           enum "message" {
             description "Trace message processing code";
           }
           enum "mlppp" {
             description "Trace MLPPP code";
           }
           enum "ncp" {
             description "Trace NCP state machine code";
           }
           enum "ppp" {
             description "Trace PPP protocol processing code";
           }
           enum "radius" {
             description "Trace RADIUS processing code";
           }
           enum "redundancy" {
             description "Trace redundancy code";
           }
           enum "rtsock" {
             description "Trace routing socket code";
           }
           enum "session" {
             description "Trace session management code";
           }
           enum "signal" {
             description "Trace signal handling code";
           }
           enum "timer" {
             description "Trace timer code";
           }
           enum "ui" {
             description "Trace user interface code";
           }
           enum "ci" {
             description "Trace ci code";
           }
           enum "all" {
             description "Trace all areas of code";
           }
         }
       }
     }
   }
   grouping ppp_options_type {
     uses apply-advanced;
     leaf dynamic-profile {
       description "Dynamic profile name";
       type string;
     }
     container chap {
       presence "enable chap";
       description "Challenge Handshake Authentication Protocol options";
       uses apply-advanced;
       choice access-data {
         case case_1 {
           leaf access-profile {
             description "Profile containing client list and access parameters";
             type string {
               length "1 .. 63";
             }
           }
         }
         case case_2 {
           leaf default-chap-secret {
             description "Default CHAP secret to be used when no matching access profile exists";
             type jt:unreadable;
           }
         }
       }
       leaf local-name {
         description "Name sent in CHAP-Challenge and CHAP-Response";
         type string;
       }
       leaf no-rfc2486 {
         description "RFC2486 compliance is not enforced";
         type empty;
       }
       leaf passive {
         description "Handle incoming CHAP requests only";
         type empty;
       }
     }
     container pap {
       presence "enable pap";
       description "Password Authentication Protocol options";
       uses apply-advanced;
       choice access-data {
         case case_1 {
           leaf access-profile {
             description "Profile containing client list and access parameters";
             type string {
               length "1 .. 63";
             }
           }
         }
         case case_2 {
           leaf default-password {
             description "Default PAP password used in the absence of matching profile";
             type jt:unreadable;
           }
         }
       }
       leaf local-name {
         description "Name sent in PAP request packet";
         type string;
       }
       leaf no-rfc2486 {
         description "RFC2486 compliance is not enforced";
         type empty;
       }
       leaf local-password {
         description "Password sent in PAP request packet";
         type jt:unreadable;
       }
       leaf passive {
         description "Do not handle PAP authentication requests";
         type empty;
       }
     }
     container compression {
       description "Set compression options";
       leaf acfc {
         description "Negotiate Address/Control field compression";
         type empty;
       }
       leaf pfc {
         description "Negotiate Protocol field compression";
         type empty;
       }
     }
     leaf lcp-restart-timer {
       description "LCP restart timer";
       units "milliseconds";
       type union {
         type string {
           pattern "<.*>|$.*";
         }
         type uint16 {
           range "20 .. 10000";
         }
       }
     }
     leaf ncp-restart-timer {
       description "NCP restart timer";
       units "milliseconds";
       type union {
         type string {
           pattern "<.*>|$.*";
         }
         type uint16 {
           range "500 .. 10000";
         }
       }
     }
     leaf no-termination-request {
       description "Don't send PPP termination requests";
       type empty;
     }
     leaf loopback-clear-timer {
       description "Loopback clear timer";
       units "seconds";
       type union {
         type string {
           pattern "<.*>|$.*";
         }
         type uint8 {
           range "1 .. 60";
         }
       }
     }
     leaf lcp-max-conf-req {
       description "Maximum LCP Conf-Req to be sent, 0 means infinite";
       type union {
         type string {
           pattern "<.*>|$.*";
         }
         type uint32 {
           range "0 .. 65535";
         }
       }
     }
     leaf ncp-max-conf-req {
       description "Maximum NCP Conf-Req to be sent, 0 means infinite";
       type union {
         type string {
           pattern "<.*>|$.*";
         }
         type uint32 {
           range "0 .. 65535";
         }
       }
     }
     leaf on-demand-ip-address {
       description "Enable On-Demand IPv4 address allocation and de-allocation";
       type empty;
     }
     leaf aaa-options {
       description "Attach AAA options name to dynamic-profile";
       type string {
         length "1 .. 63";
       }
     }
     container initiate-ncp {
       description "Enable server initiated NCP";
       uses apply-advanced;
       leaf ip {
         description "Enable server initiated IPNCP";
         type empty;
       }
       leaf ipv6 {
         description "Enable server initiated IPv6NCP";
         type empty;
       }
       leaf dual-stack-passive {
         description "Disable server initiated IPNCP/IPv6NCP for dual-stack client";
         type empty;
       }
     }
     leaf mtu {
       description "The Maximum Transfer Unit size in bytes";
       type string;
     }
     leaf peer-ip-address-optional {
       description "Set Peer IP Address Optional in IP NCP Negotiations";
       type empty;
     }
     leaf ipcp-suggest-dns-option {
       description "Suggest peer to negotiate with DNS Addresses options";
       type empty;
     }
     leaf ignore-magic-number-mismatch {
       description "Ignore magic-number validation failure in LCP keepalive";
       type empty;
     }
     container local-authentication {
       description "Local Authentication Protocol options";
       uses local_auth_type;
     }
   }
   grouping local_auth_type {
     description "Local authentication";
     uses apply-advanced;
     leaf password {
       description "Username password";
       type string {
         length "1 .. 64";
       }
     }
     container username-include {
       description "Add username options";
       uses apply-advanced;
       leaf mac-address {
         description "Include MAC address";
         type empty;
       }
       leaf circuit-id {
         description "Include circuit-id ";
         type empty;
       }
       leaf remote-id {
         description "Include remote-id ";
         type empty;
       }
       leaf domain-name {
         description "Domain name";
         type string {
           length "1 .. 64";
         }
       }
       leaf delimiter {
         description "Delimiter/separator character";
         type string {
           length 1;
         }
       }
     }
   }
   grouping pppoe-traceoptions-type {
     description "Trace options for PPPoE process";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Area of PPPoE process to enable debugging output";
       leaf name {
         type enumeration {
           enum "config" {
             description "Trace configuration code";
           }
           enum "events" {
             description "Trace event code";
           }
           enum "gres" {
             description "Trace GRES code";
           }
           enum "init" {
             description "Trace initialization code";
           }
           enum "interface-db" {
             description "Trace interface database code";
           }
           enum "memory" {
             description "Trace memory management code";
           }
           enum "protocol" {
             description "Trace PPPoE protocol processing code";
           }
           enum "rtsock" {
             description "Trace routing socket code";
           }
           enum "session-db" {
             description "Trace Session DB code";
           }
           enum "signal" {
             description "Trace signal handling code";
           }
           enum "state" {
             description "Trace state handling code";
           }
           enum "stats" {
             description "Trace Stats Handling code";
           }
           enum "timer" {
             description "Trace timer code";
           }
           enum "ui" {
             description "Trace user interface code";
           }
           enum "all" {
             description "Trace all areas of code";
           }
         }
       }
     }
     container filter {
       presence "enable filter";
       description "Trace filtering";
       uses apply-advanced;
       leaf aci {
         description "Regular expression to match ACI";
         type string {
           length "1 .. 64";
         }
       }
       leaf ari {
         description "Regular expression to match ARI";
         type string {
           length "1 .. 64";
         }
       }
       leaf service-name {
         description "Service name";
         type string {
           length "1 .. 64";
         }
       }
       leaf underlying-interface {
         description "Underlying interface name";
         type string;
       }
     }
   }
   grouping pppoe_options_type {
     uses apply-advanced;
     leaf underlying-interface {
       description "Underlying interface name";
       type string;
     }
     leaf idle-timeout {
       description "Time for which session can be idle (0 = forever)";
       units "seconds";
       type union {
         type string {
           pattern "<.*>|$.*";
         }
         type uint32 {
           range "0 .. 4294967295";
         }
       }
     }
     leaf access-concentrator {
       description "Name of the access concentrator (PPPoE server)";
       type string;
     }
     leaf service-name {
       description "Service to be requested (from PPPoE server)";
       type string;
     }
     leaf auto-reconnect {
       description "Time to reconnect after session terminates (0 = never)";
       units "seconds";
       type union {
         type string {
           pattern "<.*>|$.*";
         }
         type uint32 {
           range "0 .. 4294967295";
         }
       }
     }
     choice pppoe-mode {
       case case_1 {
         leaf server {
           description "PPPoE operates in server mode";
           type empty;
         }
       }
       case case_2 {
         leaf client {
           description "PPPoE operates in client mode";
           type empty;
         }
       }
     }
     leaf ppp-max-payload {
       description "Specify the value of ppp-max-payload tag";
       type union {
         type string {
           pattern "<.*>|$.*";
         }
         type uint32 {
           range "1492 .. 9192";
         }
       }
     }
   }
   grouping prefix_action {
     leaf name {
       description "Prefix action name";
       type string {
       }
     }
     uses apply-advanced;
     leaf policer {
       description "Police the packet using a set of named policer";
       type string {
       }
     }
     leaf count {
       description "Enable counters";
       type empty;
     }
     leaf filter-specific {
       description "Filter specific, else term specific";
       type empty;
     }
     leaf subnet-prefix-length {
       description "Prefix length for the total address range";
       type union {
         type string {
           pattern "<.*>|$.*";
         }
         type uint32 {
           range "0 .. 32";
         }
       }
     }
     choice source_or_dest {
       case case_1 {
         leaf source-prefix-length {
           description "Source prefix range";
           type union {
             type string {
               pattern "<.*>|$.*";
             }
             type uint32 {
               range "0 .. 32";
             }
           }
         }
       }
       case case_2 {
         leaf destination-prefix-length {
           description "Destination prefix range";
           type union {
             type string {
               pattern "<.*>|$.*";
             }
             type uint32 {
               range "0 .. 32";
             }
           }
         }
       }
     }
   }
   grouping prefix_list_items {
     leaf name {
       description "Address prefix";
       type jt:ipprefix-only;
     }
     uses apply-advanced;
   }
   grouping profile-setting {
     description "UTM policy settings";
     leaf name {
       description "UTM policy name";
       type string {
         length "1 .. 29";
       }
     }
     uses apply-advanced;
     container anti-virus {
       description "UTM policy anti-virus profile";
       uses apply-advanced;
       leaf http-profile {
         description "Anti-virus profile";
         type string;
       }
       container ftp {
         description "FTP profile";
         uses apply-advanced;
         leaf upload-profile {
           description "Anti-virus profile";
           type string;
         }
         leaf download-profile {
           description "Anti-virus profile";
           type string;
         }
       }
       leaf smtp-profile {
         description "Anti-virus profile";
         type string;
       }
       leaf pop3-profile {
         description "Anti-virus profile";
         type string;
       }
       leaf imap-profile {
         description "Anti-virus profile";
         type string;
       }
     }
     container content-filtering {
       description "Content-filtering profile";
       uses apply-advanced;
       leaf http-profile {
         description "Content-filtering profile";
         type string;
       }
       container ftp {
         description "FTP profile";
         uses apply-advanced;
         leaf upload-profile {
           description "Content-filtering FTP upload profile";
           type string;
         }
         leaf download-profile {
           description "Content-filtering FTP download profile";
           type string;
         }
       }
       leaf smtp-profile {
         description "Content-filtering SMTP profile";
         type string;
       }
       leaf pop3-profile {
         description "Content-filtering POP3 profile";
         type string;
       }
       leaf imap-profile {
         description "Content-filtering IMAP profile";
         type string;
       }
     }
     container web-filtering {
       description "Web-filtering profile";
       uses apply-advanced;
       leaf http-profile {
         description "Web-filtering HTTP profile";
         type string;
       }
     }
     container anti-spam {
       description "Anti-spam profile";
       uses apply-advanced;
       leaf smtp-profile {
         description "Anti-spam profile";
         type string;
       }
     }
     container traffic-options {
       description "Traffic options";
       status deprecated;
       uses apply-advanced;
       container sessions-per-client {
         description "Sessions per client";
         uses apply-advanced;
         leaf limit {
           description "Sessions limit";
           default "2000";
           type union {
             type string {
               pattern "<.*>|$.*";
             }
             type uint32 {
               range "0 .. 2000";
             }
           }
         }
         leaf over-limit {
           description "Over limit number";
           type enumeration {
             enum "log-and-permit" {
             }
             enum "block" {
             }
           }
         }
       }
     }
   }
   grouping programmable-rpd-type {
     uses apply-advanced;
     container traceoptions {
       description "Trace options";
       uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "client" {
               description "Client events";
             }
             enum "japi" {
               description "JAPI related traces";
             }
             enum "routing-interface" {
               description "Routing interface traces";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
       }
     }
     container purge-timeout {
       presence "enable purge-timeout";
       description "Purge timeout for all programmable-rpd clients in seconds";
       choice purge-parm {
         case case_1 {
           leaf never {
             description "Client programmed objects are never purged";
             type empty;
           }
         }
         case case_2 {
           leaf timeout {
             description "Timeout value, in seconds, for purging client programmed objects";
             units "seconds";
             type union {
               type string {
                 pattern "<.*>|$.*";
               }
               type uint32 {
                 range "1 .. 604800";
               }
             }
           }
         }
       }
     }
     list client {
       key name;
       ordered-by user;
       description "Programmable-rpd client options";
       leaf name {
         description "Client ID";
         type string {
           length "1 .. 255";
         }
       }
       uses apply-advanced;
       list interface-notification {
         key name;
         ordered-by user;
         description "Interfaces for notification";
         leaf name {
           description "Interface";
           type string {
             length "1 .. 32";
           }
         }
         uses apply-advanced;
       }
     }
   }
   grouping proto-object {
     leaf name {
       type string;
     }
     uses apply-advanced;
     list tunable-name {
       key name;
       ordered-by user;
       description "Protocol tunable name";
       uses tunable-object;
     }
   }
   grouping qualified_nh_obj {
     leaf name {
       description "Next hop to destination";
       type union {
         type jt:ipaddr-or-interface;
         type string {
           pattern "<.*>|$.*";
         }
       }
     }
     uses apply-advanced;
     leaf preference {
       description "Preference of qualified next hop";
       type union {
         type uint32;
         type string {
           pattern "<.*>|$.*";
         }
       }
     }
     leaf metric {
       description "Metric of qualified next hop";
       type union {
         type uint32;
         type string {
           pattern "<.*>|$.*";
         }
       }
     }
     leaf interface {
       description "Interface of qualified next hop";
       type union {
         type jt:interface-name;
         type string {
           pattern "<.*>|$.*";
         }
       }
     }
     leaf mac-address {
       description "Next-hop Mac Address";
       type jt:mac-unicast;
     }
     leaf tag {
       description "Tag string";
       type union {
         type uint32;
         type string {
           pattern "<.*>|$.*";
         }
       }
     }
     container bfd-liveness-detection {
       description "Bidirectional Forwarding Detection (BFD) options";
       uses apply-advanced;
       leaf version {
         description "BFD protocol version number";
         default "automatic";
         type enumeration {
           enum "0" {
             description "BFD version 0 (deprecated)";
           }
           enum "1" {
             description "BFD version 1";
           }
           enum "automatic" {
             description "Choose BFD version automatically";
           }
         }
       }
       leaf minimum-interval {
         description "Minimum transmit and receive interval";
         units "milliseconds";
         type union {
           type string {
             pattern "<.*>|$.*";
           }
           type uint32 {
             range "1 .. 255000";
           }
         }
       }
       leaf minimum-transmit-interval {
         description "Minimum transmit interval";
         status deprecated;
         units "milliseconds";
         type union {
           type string {
             pattern "<.*>|$.*";
           }
           type uint32 {
             range "1 .. 255000";
           }
         }
       }
       leaf minimum-receive-interval {
         description "Minimum receive interval";
         units "milliseconds";
         type union {
           type string {
             pattern "<.*>|$.*";
           }
           type uint32 {
             range "1 .. 255000";
           }
         }
       }
       leaf multiplier {
         description "Detection time multiplier";
         default "3";
         type union {
           type string {
             pattern "<.*>|$.*";
           }
           type uint32 {
             range "1 .. 255";
           }
         }
       }
       choice adaptation-choice {
         case case_1 {
           leaf no-adaptation {
             description "Disable adaptation";
             type empty;
           }
         }
       }
       container transmit-interval {
         description "Transmit-interval options";
         uses apply-advanced;
         leaf minimum-interval {
           description "Minimum transmit interval";
           units "milliseconds";
           type union {
             type string {
               pattern "<.*>|$.*";
             }
             type uint32 {
               range "1 .. 255000";
             }
           }
         }
         leaf threshold {
           description "High transmit interval triggering a trap";
           units "milliseconds";
           type union {
             type uint32;
             type string {
               pattern "<.*>|$.*";
             }
           }
         }
       }
       container detection-time {
         description "Detection-time options";
         uses apply-advanced;
         leaf threshold {
           description "High detection-time triggering a trap";
           units "milliseconds";
           type union {
             type uint32;
             type string {
               pattern "<.*>|$.*";
             }
           }
         }
       }
       container authentication {
         description "Authentication options";
         uses apply-advanced;
         leaf key-chain {
           description "Key chain name";
           type string;
         }
         leaf algorithm {
           description "Algorithm name";
           type enumeration {
             enum "simple-password" {
               description "Simple password";
             }
             enum "keyed-md5" {
               description "Keyed message Digest 5";
             }
             enum "meticulous-keyed-md5" {
               description "Meticulous keyed message Digest 5";
             }
             enum "keyed-sha-1" {
               description "Keyed secure hash algorithm (SHA1) ";
             }
             enum "meticulous-keyed-sha-1" {
               description "Meticulous keyed secure hash algorithm (SHA1) ";
             }
           }
         }
         leaf loose-check {
           description "Verify authentication only if authentication is negotiated";
           type empty;
         }
       }
       leaf neighbor {
         description "BFD neighbor address";
         type jt:ipaddr;
       }
       leaf local-address {
         description "BFD local address (for multihop only)";
         type jt:ipaddr;
       }
       leaf holddown-interval {
         description "Time to hold the session-UP notification to the client";
         units "milliseconds";
         type union {
           type string {
             pattern "<.*>|$.*";
           }
           type uint32 {
             range "0 .. 255000";
           }
         }
       }
       leaf minimum-receive-ttl {
         description "Minimum receive TTL below which to drop";
         type union {
           type string {
             pattern "<.*>|$.*";
           }
           type uint8 {
             range "1 .. 255";
           }
         }
       }
     }
   }
   grouping r2cp-traceoptions-type {
     description "Trace options for R2CP process";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Area of R2CP process to enable debugging output";
       leaf name {
         type enumeration {
           enum "configuration" {
             description "Trace configuration code";
           }
           enum "event" {
             description "Trace events";
           }
           enum "interface" {
             description "Trace interface processing";
           }
           enum "node" {
             description "Trace node table code";
           }
           enum "packet" {
             description "Trace packet processing";
           }
           enum "rtsock" {
             description "Trace routing socket code";
           }
           enum "session" {
             description "Trace session events";
           }
           enum "socket" {
             description "Trace socket calls";
           }
           enum "timer" {
             description "Trace timer code";
           }
           enum "virtual-channel" {
             description "Trace virtual channel mapping code";
           }
           enum "all" {
             description "Trace all areas of code";
           }
         }
       }
     }
   }
   grouping ragw-traceoptions {
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "brief";
       type enumeration {
         enum "brief" {
           description "Brief debugging output";
         }
         enum "detail" {
           description "Detailed debugging output";
         }
         enum "extensive" {
           description "Extensive debugging output";
         }
         enum "verbose" {
           description "Verbose debugging output";
         }
       }
     }
     list flag {
       key name;
       ordered-by user;
       description "Tracing parameters";
       leaf name {
         type enumeration {
           enum "configuration" {
             description "Trace CLI configuration events";
           }
           enum "tunnel" {
             description "Trace tunnel install/encap/decap events";
           }
           enum "session" {
             description "Trace session related events";
           }
           enum "all" {
             description "Trace everything";
           }
         }
       }
     }
   }
   grouping range-address-type {
     description "Range address";
     leaf name {
       description "Lower limit of address range";
       type jt:ipv4addr;
     }
     uses apply-advanced;
     container to {
       description "Port range upper limit";
       uses apply-advanced;
       leaf range-high {
         description "Upper limit of address range";
         type jt:ipv4addr;
       }
     }
   }
   grouping reconfigure-trigger-type {
     description "DHCP reconfigure trigger";
     uses apply-advanced;
     leaf radius-disconnect {
       description "Trigger DHCP reconfigure by radius initiated disconnect";
       type empty;
     }
   }
   grouping relay-bulk-leasequery-v4-type {
     description "Configure bulk leasequery";
     uses apply-advanced;
     leaf attempts {
       description "Number of retry attempts";
       default "360";
       type union {
         type string {
           pattern "<.*>|$.*";
         }
         type uint32 {
           range "1 .. 720";
         }
       }
     }
     leaf timeout {
       description "Number of seconds";
       default "10";
       units "seconds";
       type union {
         type string {
           pattern "<.*>|$.*";
         }
         type uint32 {
           range "1 .. 10";
         }
       }
     }
   }
   grouping relay-bulk-leasequery-v6-type {
     description "Configure bulk leasequery";
     uses apply-advanced;
     leaf attempts {
       description "Number of retry attempts";
       default "6";
       type union {
         type string {
           pattern "<.*>|$.*";
         }
         type uint32 {
           range "1 .. 10";
         }
       }
     }
     leaf timeout {
       description "Number of seconds";
       default "10";
       units "seconds";
       type union {
         type string {
           pattern "<.*>|$.*";
         }
         type uint32 {
           range "1 .. 10";
         }
       }
     }
     container trigger {
       description "Trigger for bulk leasequery";
       leaf automatic {
         description "Trigger automatically";
         type empty;
       }
     }
   }
   grouping relay-leasequery-type {
     description "Configure leasequery";
     uses apply-advanced;
     leaf attempts {
       description "Number of retry attempts";
       default "6";
       type union {
         type string {
           pattern "<.*>|$.*";
         }
         type uint32 {
           range "1 .. 10";
         }
       }
     }
     leaf timeout {
       description "Number of seconds";
       default "10";
       units "seconds";
       type union {
         type string {
           pattern "<.*>|$.*";
         }
         type uint32 {
           range "1 .. 10";
         }
       }
     }
   }
   grouping relay-option-60-type-group {
     description "DHCP option-60 processing";
     uses apply-advanced;
     container vendor-option {
       description "Add vendor option";
       uses apply-advanced;
       container equals {
         description "Option 60 equals";
         uses relay-option-60-match-group;
       }
       container not-equals {
         description "Option 60 does not equal";
         status deprecated;
         uses relay-option-60-match-group;
       }
       container starts-with {
         description "Option 60 starts with";
         uses relay-option-60-match-group;
       }
       choice server-group-choice {
         case case_1 {
           leaf default-relay-server-group {
             description "Name of DHCP relay server group when match is not made";
             type string {
               length "1 .. 64";
             }
           }
         }
         case case_2 {
           leaf default-local-server-group {
             description "Name of DHCP local server group when match is not made";
             type string {
               length "1 .. 64";
             }
           }
         }
         case case_3 {
           leaf drop {
             description "Discard when a match is not made";
             type empty;
           }
         }
         case case_4 {
           leaf forward-only {
             description "Forward without subscriber services when a match is not made";
             type empty;
           }
         }
       }
     }
   }
   grouping relay-option-60-match-group {
     uses apply-advanced;
     list ascii {
       key name;
       description "ASCII string";
       leaf name {
         description "ASCII string";
         type string {
           length "1 .. 256";
         }
       }
       uses apply-advanced;
       choice server-group-choice {
         case case_1 {
           leaf relay-server-group {
             description "Name of DHCP relay server group when match is made";
             type string {
               length "1 .. 64";
             }
           }
         }
         case case_2 {
           leaf local-server-group {
             description "Name of DHCP local server group when match is made";
             type string {
               length "1 .. 64";
             }
           }
         }
         case case_3 {
           leaf drop {
             description "Discard when a match is made";
             type empty;
           }
         }
         case case_4 {
           leaf forward-only {
             description "Forward without subscriber services when a match is made";
             type empty;
           }
         }
       }
     }
     list hexadecimal {
       key name;
       description "Hexadecimal string";
       leaf name {
         description "Hexadecimal string";
         type string {
           length "1 .. 512";
         }
       }
       uses apply-advanced;
       choice server-group-choice {
         case case_1 {
           leaf relay-server-group {
             description "Name of DHCP relay server group when match is made";
             type string {
               length "1 .. 64";
             }
           }
         }
         case case_2 {
           leaf local-server-group {
             description "Name of DHCP local server group when match is made";
             type string {
               length "1 .. 64";
             }
           }
         }
         case case_3 {
           leaf drop {
             description "Discard when a match is made";
             type empty;
           }
         }
         case case_4 {
           leaf forward-only {
             description "Forward without subscriber services when a match is made";
             type empty;
           }
         }
       }
     }
   }
   grouping relay-option-60-type-top {
     description "DHCP option-60 processing";
     uses apply-advanced;
     container vendor-option {
       description "Add vendor option";
       uses apply-advanced;
       container equals {
         description "Option 60 equals";
         uses relay-option-60-match-top;
       }
       container not-equals {
         description "Option 60 does not equal";
         status deprecated;
         uses relay-option-60-match-top;
       }
       container starts-with {
         description "Option 60 starts with";
         uses relay-option-60-match-top;
       }
       choice server-group-choice {
         case case_1 {
           leaf default-relay-server-group {
             description "Name of DHCP relay server group when match is not made";
             type string {
               length "1 .. 64";
             }
           }
         }
         case case_2 {
           leaf default-local-server-group {
             description "Name of DHCP local server group when match is not made";
             type string {
               length "1 .. 64";
             }
           }
         }
         case case_3 {
           leaf drop {
             description "Discard when a match is not made";
             type empty;
           }
         }
         case case_4 {
           leaf forward-only {
             description "Forward without subscriber services when a match is not made";
             type empty;
           }
         }
       }
     }
   }
   grouping relay-option-60-match-top {
     uses apply-advanced;
     list ascii {
       key name;
       description "ASCII string";
       leaf name {
         description "ASCII string";
         type string {
           length "1 .. 256";
         }
       }
       uses apply-advanced;
       choice server-group-choice {
         case case_1 {
           leaf relay-server-group {
             description "Name of DHCP relay server group when match is made";
             type string {
               length "1 .. 64";
             }
           }
         }
         case case_2 {
           leaf local-server-group {
             description "Name of DHCP local server group when match is made";
             type string {
               length "1 .. 64";
             }
           }
         }
         case case_3 {
           leaf drop {
             description "Discard when a match is made";
             type empty;
           }
         }
         case case_4 {
           leaf forward-only {
             description "Forward without subscriber services when a match is made";
             type empty;
           }
         }
       }
     }
     list hexadecimal {
       key name;
       description "Hexadecimal string";
       leaf name {
         description "Hexadecimal string";
         type string {
           length "1 .. 512";
         }
       }
       uses apply-advanced;
       choice server-group-choice {
         case case_1 {
           leaf relay-server-group {
             description "Name of DHCP relay server group when match is made";
             type string {
               length "1 .. 64";
             }
           }
         }
         case case_2 {
           leaf local-server-group {
             description "Name of DHCP local server group when match is made";
             type string {
               length "1 .. 64";
             }
           }
         }
         case case_3 {
           leaf drop {
             description "Discard when a match is made";
             type empty;
           }
         }
         case case_4 {
           leaf forward-only {
             description "Forward without subscriber services when a match is made";
             type empty;
           }
         }
       }
     }
   }
   grouping relay-option-82-type {
     description "DHCP option-82 processing";
     uses apply-advanced;
     container circuit-id {
       presence "enable circuit-id";
       description "Add circuit identifier";
       uses apply-advanced;
       container prefix {
         description "Add prefix to circuit/interface-id or remote-id";
         uses apply-advanced;
         leaf host-name {
           description "Add router host name to circuit / interface-id or remote-id";
           type empty;
         }
         leaf logical-system-name {
           description "Add logical system name to circuit / interface-id or remote-id";
           type empty;
         }
         leaf routing-instance-name {
           description "Add routing instance name to circuit / interface-id or remote-id";
           type empty;
         }
       }
       leaf use-interface-description {
         description "Use interface description instead of circuit identifier";
         type enumeration {
           enum "logical" {
             description "Use the logical interface description";
           }
           enum "device" {
             description "Use the device interface description";
           }
         }
       }
       leaf use-vlan-id {
         description "Use VLAN id instead of name";
         type empty;
       }
       leaf no-vlan-interface-name {
         description "Not include vlan or interface name";
         type empty;
       }
       leaf include-irb-and-l2 {
         description "Include IRB and L2 interface name";
         type empty;
       }
       leaf user-defined {
         description "Include user defined string";
         type empty;
       }
       leaf keep-incoming-circuit-id {
         description "Keep incoming circuit identifier";
         type empty;
       }
     }
     container remote-id {
       presence "enable remote-id";
       description "Add remote identifier";
       uses apply-advanced;
       container prefix {
         description "Add prefix to circuit/interface-id or remote-id";
         uses apply-advanced;
         leaf host-name {
           description "Add router host name to circuit / interface-id or remote-id";
           type empty;
         }
         leaf logical-system-name {
           description "Add logical system name to circuit / interface-id or remote-id";
           type empty;
         }
         leaf routing-instance-name {
           description "Add routing instance name to circuit / interface-id or remote-id";
           type empty;
         }
       }
       leaf use-interface-description {
         description "Use interface description instead of circuit identifier";
         type enumeration {
           enum "logical" {
             description "Use the logical interface description";
           }
           enum "device" {
             description "Use the device interface description";
           }
         }
       }
       leaf use-vlan-id {
         description "Use VLAN id instead of name";
         type empty;
       }
       leaf no-vlan-interface-name {
         description "Not include vlan or interface name";
         type empty;
       }
       leaf include-irb-and-l2 {
         description "Include IRB and L2 interface name";
         type empty;
       }
       leaf keep-incoming-remote-id {
         description "Keep incoming remote identifier";
         type empty;
       }
       leaf use-string {
         description "Use raw string instead of the default remote id";
         type string;
       }
     }
     leaf server-id-override {
       description "Add link-selection and server-id sub-options on packets to server";
       type empty;
     }
     container vendor-specific {
       description "Add vendor-specific information";
       uses jdhcp-vendor-specific-type;
     }
   }
   grouping relay-v4-option-ascii-hex {
     uses apply-advanced;
     list ascii {
       key name;
       description "ASCII string";
       leaf name {
         description "ASCII string";
         type string {
           length "1 .. 256";
         }
       }
       uses apply-advanced;
       choice server-group-choice {
         case case_1 {
           leaf relay-server-group {
             description "Name of DHCP relay server group when match is made";
             type string {
               length "1 .. 64";
             }
           }
         }
         case case_2 {
           leaf local-server-group {
             description "Name of DHCP local server group when match is made";
             type string {
               length "1 .. 64";
             }
           }
         }
         case case_3 {
           leaf drop {
             description "Discard when a match is made";
             type empty;
           }
         }
         case case_4 {
           leaf forward-only {
             description "Forward without subscriber services when a match is made";
             type empty;
           }
         }
       }
     }
     list hexadecimal {
       key name;
       description "Hexadecimal string";
       leaf name {
         description "Hexadecimal string";
         type string {
           length "1 .. 512";
         }
       }
       uses apply-advanced;
       choice server-group-choice {
         case case_1 {
           leaf relay-server-group {
             description "Name of DHCP relay server group when match is made";
             type string {
               length "1 .. 64";
             }
           }
         }
         case case_2 {
           leaf local-server-group {
             description "Name of DHCP local server group when match is made";
             type string {
               length "1 .. 64";
             }
           }
         }
         case case_3 {
           leaf drop {
             description "Discard when a match is made";
             type empty;
           }
         }
         case case_4 {
           leaf forward-only {
             description "Forward without subscriber services when a match is made";
             type empty;
           }
         }
       }
     }
   }
   grouping relay-v6-option-ascii-hex {
     uses apply-advanced;
     list ascii {
       key name;
       description "ASCII string";
       leaf name {
         description "ASCII string";
         type string {
           length "1 .. 256";
         }
       }
       uses apply-advanced;
       choice server-group-choice {
         case case_1 {
           leaf relay-server-group {
             description "Name of DHCP relay server group when match is made";
             type string {
               length "1 .. 64";
             }
           }
         }
         case case_2 {
           leaf drop {
             description "Discard when a match is made";
             type empty;
           }
         }
         case case_3 {
           leaf forward-only {
             description "Forward without subscriber services when a match is made";
             type empty;
           }
         }
       }
     }
     list hexadecimal {
       key name;
       description "Hexadecimal string";
       leaf name {
         description "Hexadecimal string";
         type string {
           length "1 .. 512";
         }
       }
       uses apply-advanced;
       choice server-group-choice {
         case case_1 {
           leaf relay-server-group {
             description "Name of DHCP relay server group when match is made";
             type string {
               length "1 .. 64";
             }
           }
         }
         case case_2 {
           leaf drop {
             description "Discard when a match is made";
             type empty;
           }
         }
         case case_3 {
           leaf forward-only {
             description "Forward without subscriber services when a match is made";
             type empty;
           }
         }
       }
     }
   }
   grouping rib_aggregate_type {
     uses apply-advanced;
     container defaults {
       description "Global route options";
       uses apply-advanced;
       container metric {
         description "Metric value";
         presence "enable metric";
         uses rib_static_metric_type;
       }
       container metric2 {
         description "Metric value 2";
         presence "enable metric2";
         uses rib_static_metric_type;
       }
       container metric3 {
         description "Metric value 3";
         presence "enable metric3";
         uses rib_static_metric_type;
       }
       container metric4 {
         description "Metric value 4";
         presence "enable metric4";
         uses rib_static_metric_type;
       }
       container tag {
         description "Tag string";
         presence "enable tag";
         uses rib_static_metric_type;
       }
       container tag2 {
         description "Tag string 2";
         presence "enable tag2";
         uses rib_static_metric_type;
       }
       container preference {
         description "Preference value";
         presence "enable preference";
         uses rib_static_metric_type;
       }
       container preference2 {
         description "Preference value 2";
         presence "enable preference2";
         uses rib_static_metric_type;
       }
       container color {
         description "Color (preference) value";
         presence "enable color";
         uses rib_static_metric_type;
       }
       container color2 {
         description "Color (preference) value 2";
         presence "enable color2";
         uses rib_static_metric_type;
       }
       leaf-list community {
         ordered-by user;
         description "BGP community identifier";
         type jt:community;
       }
       container as-path {
         description "Autonomous system path";
         uses apply-advanced;
         leaf path {
           description "Autonomous system path";
           type string;
         }
         leaf origin {
           type enumeration {
             enum "igp" {
               description "Path originated in the local IGP";
             }
             enum "egp" {
               description "Path originated in another AS";
             }
             enum "incomplete" {
               description "Path was learned by some other means";
             }
           }
         }
         leaf atomic-aggregate {
           description "Add ATOMIC_AGGREGATE path attribute to route";
           type empty;
         }
         container aggregator {
           presence "enable aggregator";
           description "Add AGGREGATOR path attribute to route";
         }
         leaf as-number {
           description " Autonomous system number in plain number or 'higher 16bits'.'Lower 16 bits' (asdot notation) format";
           type string {
           }
         }
         leaf address {
           description "Address of BGP system that formed the route";
           type jt:ipv4addr;
         }
       }
       leaf discard {
         description "Drop packets to destination; send no ICMP unreachables";
         type empty;
       }
       leaf next-table {
         description "Next hop to another table";
         type string;
       }
       choice brief_flag {
         case case_1 {
           leaf brief {
             description "Include longest common sequences from contributing paths";
             type empty;
           }
         }
         case case_2 {
           leaf full {
             description "Include all AS numbers from all contributing paths";
             type empty;
           }
         }
       }
       choice passive_flag {
         case case_1 {
           leaf active {
             description "Remove inactive route from forwarding table";
             type empty;
           }
         }
         case case_2 {
           leaf passive {
             description "Retain inactive route in forwarding table";
             type empty;
           }
         }
       }
     }
     list route {
       key name;
       ordered-by user;
       description "Individual route options";
       leaf name {
         description "Destination prefix";
         type jt:ipprefix;
       }
       uses apply-advanced;
       leaf-list policy {
         ordered-by user;
         description "Policy filter";
         type jt:policy-algebra;
       }
       container metric {
         description "Metric value";
         presence "enable metric";
         uses rib_static_metric_type;
       }
       container metric2 {
         description "Metric value 2";
         presence "enable metric2";
         uses rib_static_metric_type;
       }
       container metric3 {
         description "Metric value 3";
         presence "enable metric3";
         uses rib_static_metric_type;
       }
       container metric4 {
         description "Metric value 4";
         presence "enable metric4";
         uses rib_static_metric_type;
       }
       container tag {
         description "Tag string";
         presence "enable tag";
         uses rib_static_metric_type;
       }
       container tag2 {
         description "Tag string 2";
         presence "enable tag2";
         uses rib_static_metric_type;
       }
       container preference {
         description "Preference value";
         presence "enable preference";
         uses rib_static_metric_type;
       }
       container preference2 {
         description "Preference value 2";
         presence "enable preference2";
         uses rib_static_metric_type;
       }
       container color {
         description "Color (preference) value";
         presence "enable color";
         uses rib_static_metric_type;
       }
       container color2 {
         description "Color (preference) value 2";
         presence "enable color2";
         uses rib_static_metric_type;
       }
       leaf-list community {
         ordered-by user;
         description "BGP community identifier";
         type jt:community;
       }
       container as-path {
         description "Autonomous system path";
         uses apply-advanced;
         leaf path {
           description "Autonomous system path";
           type string;
         }
         leaf origin {
           type enumeration {
             enum "igp" {
               description "Path originated in the local IGP";
             }
             enum "egp" {
               description "Path originated in another AS";
             }
             enum "incomplete" {
               description "Path was learned by some other means";
             }
           }
         }
         leaf atomic-aggregate {
           description "Add ATOMIC_AGGREGATE path attribute to route";
           type empty;
         }
         container aggregator {
           presence "enable aggregator";
           description "Add AGGREGATOR path attribute to route";
         }
         leaf as-number {
           description " Autonomous system number in plain number or 'higher 16bits'.'Lower 16 bits' (asdot notation) format";
           type string {
           }
         }
         leaf address {
           description "Address of BGP system that formed the route";
           type jt:ipv4addr;
         }
       }
       leaf discard {
         description "Drop packets to destination; send no ICMP unreachables";
         type empty;
       }
       leaf next-table {
         description "Next hop to another table";
         type string;
       }
       choice brief_flag {
         case case_1 {
           leaf brief {
             description "Include longest common sequences from contributing paths";
             type empty;
           }
         }
         case case_2 {
           leaf full {
             description "Include all AS numbers from all contributing paths";
             type empty;
           }
         }
       }
       choice passive_flag {
         case case_1 {
           leaf active {
             description "Remove inactive route from forwarding table";
             type empty;
           }
         }
         case case_2 {
           leaf passive {
             description "Retain inactive route in forwarding table";
             type empty;
           }
         }
       }
     }
   }
   grouping rib_group_inet_type {
     description "Routing table group";
     leaf ribgroup-name {
       description "Name of the routing table group";
       type string;
     }
   }
   grouping rib_group_type {
     uses apply-advanced;
     leaf inet-old-style {
       description "Name of the IPv4 routing table group";
       status deprecated;
       type string;
     }
     leaf inet {
       description "Name of the IPv4 routing table group";
       type string;
     }
     leaf inet3 {
       description "Name of the IPv4 inet.3 routing table group";
       type string;
     }
     leaf inet6 {
       description "Name of the IPv6 routing table group";
       type string;
     }
     leaf inet63 {
       description "Name of the IPv6 inet6.3 routing table group";
       type string;
     }
   }
   grouping rib_static_metric_type {
     leaf metric-value {
       description "Metric value";
       type union {
         type uint32;
         type string {
           pattern "<.*>|$.*";
         }
       }
     }
     leaf type {
       description "Metric type";
       type union {
         type string {
           pattern "<.*>|$.*";
         }
         type uint32 {
           range "1 .. 16";
         }
       }
     }
   }
   grouping rip_filter_obj {
     description "Filter to apply to tracing";
     leaf match-on {
       description "Argument on which to match";
       type enumeration {
         enum "prefix" {
           description "Filter based on prefix";
         }
       }
     }
     leaf-list policy {
       ordered-by user;
       description "Filter policy";
       type jt:policy-algebra;
     }
   }
   grouping route_filter_list_items {
     leaf address {
       description "IP address or hostname";
       type jt:ipprefix;
     }
     leaf choice-ident {
       type enumeration {
         enum "exact" {
         }
         enum "longer" {
         }
         enum "orlonger" {
         }
         enum "upto" {
         }
         enum "through" {
         }
         enum "prefix-length-range" {
         }
         enum "address-mask" {
         }
         enum "apply-advanced" {
         }
         enum "label" {
         }
         enum "metric" {
         }
         enum "metric2" {
         }
         enum "metric3" {
         }
         enum "metric4" {
         }
         enum "tag" {
         }
         enum "tag2" {
         }
         enum "preference" {
         }
         enum "preference2" {
         }
         enum "color" {
         }
         enum "color2" {
         }
         enum "local-preference" {
         }
         enum "priority" {
         }
         enum "prefix-segment" {
         }
         enum "label-allocation" {
         }
         enum "add-path" {
         }
         enum "validation-state" {
         }
         enum "origin" {
         }
         enum "aigp-originate" {
         }
         enum "aigp-adjust" {
         }
         enum "community" {
         }
         enum "damping" {
         }
         enum "aggregate-bandwidth" {
         }
         enum "limit-bandwidth" {
         }
         enum "no-entropy-label-capability" {
         }
         enum "as-path-prepend" {
         }
         enum "as-path-expand" {
         }
         enum "next-hop" {
         }
         enum "install-nexthop" {
         }
         enum "trace" {
         }
         enum "external" {
         }
         enum "load-balance" {
         }
         enum "no-route-localize" {
         }
         enum "install-to-fib" {
         }
         enum "analyze" {
         }
         enum "class" {
         }
         enum "destination-class" {
         }
         enum "source-class" {
         }
         enum "forwarding-class" {
         }
         enum "map-to-interface" {
         }
         enum "ssm-source" {
         }
         enum "p2mp-lsp-root" {
         }
         enum "cos-next-hop-map" {
         }
         enum "dynamic-tunnel-attributes" {
         }
         enum "selected-mldp-egress" {
         }
         enum "mhop-bfd-port" {
         }
         enum "no-backup" {
         }
         enum "default-action" {
         }
         enum "next" {
         }
         enum "accept_reject" {
         }
         enum "bgp-output-queue-priority" {
         }
         enum "multipath-resolve" {
         }
         enum "label-allocation-fallback-reject" {
         }
       }
     }
     leaf choice-value {
       type string;
     }
     uses apply-advanced;
     container label {
       description "Set label for BGP LU label allocation";
       choice label_value {
         case case_1 {
           container range {
             description "Label range";
             choice range_value {
               case case_1 {
                 leaf range {
                   description "Label range in <start>:<end> format";
                   type string {
                   }
                 }
               }
             }
           }
         }
         case case_2 {
           leaf label {
             description "Label value";
             type union {
               type string {
                 pattern "<.*>|$.*";
               }
               type uint32 {
                 range "0 .. 1048575";
               }
             }
           }
         }
       }
     }
     container metric {
       description "Metric value";
       uses apply-advanced;
       choice metric_action {
         case case_1 {
           leaf metric {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
         case case_4 {
           container igp {
             presence "enable igp";
             description "Track the IGP metric (BGP only)";
             leaf metric_offset {
               description "Metric offset for MED";
               type union {
                 type int32;
                 type string {
                   pattern "<.*>|$.*";
                 }
               }
             }
           }
         }
         case case_5 {
           container minimum-igp {
             presence "enable minimum-igp";
             description "Track the minimum IGP metric (BGP only)";
             leaf metric_offset {
               description "Metric offset for MED";
               type union {
                 type int32;
                 type string {
                   pattern "<.*>|$.*";
                 }
               }
             }
           }
         }
         case case_6 {
           container expression {
             description "Calculate value based on route metric and metric2";
             uses metric_expression_type;
           }
         }
         case case_7 {
           leaf aigp {
             description "Use aigp, if it exists, to set the IGP metric";
             type empty;
           }
         }
       }
     }
     container metric2 {
       description "Metric value 2";
       uses apply-advanced;
       choice metric_action {
         case case_1 {
           leaf metric2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric3 {
       description "Metric value 3";
       uses apply-advanced;
       choice metric_action {
         case case_1 {
           leaf metric3 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric4 {
       description "Metric value 4";
       uses apply-advanced;
       choice metric_action {
         case case_1 {
           leaf metric4 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag {
       description "Tag string";
       uses apply-advanced;
       choice metric_action {
         case case_1 {
           leaf tag {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag2 {
       description "Tag string 2";
       uses apply-advanced;
       choice metric_action {
         case case_1 {
           leaf tag2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference {
       description "Preference value";
       uses apply-advanced;
       choice metric_action {
         case case_1 {
           leaf preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference2 {
       description "Preference value 2";
       uses apply-advanced;
       choice metric_action {
         case case_1 {
           leaf preference2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color {
       description "Color (preference) value";
       uses apply-advanced;
       choice metric_action {
         case case_1 {
           leaf color {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color2 {
       description "Color (preference) value 2";
       uses apply-advanced;
       choice metric_action {
         case case_1 {
           leaf color2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container local-preference {
       description "Local preference associated with a route";
       uses apply-advanced;
       choice metric_action {
         case case_1 {
           leaf local-preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     leaf priority {
       description "Set priority for route installation";
       type enumeration {
         enum "high" {
           description "Set priority to high";
         }
         enum "medium" {
           description "Set priority to medium";
         }
         enum "low" {
           description "Set priority to low";
         }
       }
     }
     container prefix-segment {
       description "Set prefix segment attributes";
       leaf index {
         description "Set prefix segment index ";
         type union {
           type string {
             pattern "<.*>|$.*";
           }
           type uint32 {
             range "0 .. 199999";
           }
         }
       }
       leaf node-segment {
         description "Set node segment flag for this prefix segment";
         type empty;
       }
     }
     leaf label-allocation {
       description "Set label allocation mode";
       type enumeration {
         enum "per-table" {
           description "Set per-table label allocation mode";
         }
         enum "per-nexthop" {
           description "Set per-nexthop label allocation mode";
         }
         enum "per-table-localize" {
           description "Set per-table-localize label allocation mode";
         }
       }
     }
     container add-path {
       description "Set BGP add-path attributes";
       leaf send-count {
         description "Number of add-paths sent";
         type union {
           type string {
             pattern "<.*>|$.*";
           }
           type uint32 {
             range "2 .. 64";
           }
         }
       }
     }
     leaf validation-state {
       description "Set validation-state of a route";
       type enumeration {
         enum "valid" {
           description "Set validaton-state to valid";
         }
         enum "invalid" {
           description "Set validation-state to invalid";
         }
         enum "unknown" {
           description "Set validation-state to unknown";
         }
       }
     }
     leaf origin {
       description "BGP path origin";
       type enumeration {
         enum "igp" {
           description "Path originated in the local IGP";
         }
         enum "egp" {
           description "Path originated in another AS";
         }
         enum "incomplete" {
           description "Path was learned by some other means";
         }
       }
     }
     container aigp-originate {
       presence "enable aigp-originate";
       description "Originate a BGP AIGP attribute";
       leaf distance {
         description "AIGP distance";
         type union {
           type uint32;
           type string {
             pattern "<.*>|$.*";
           }
         }
       }
     }
     container aigp-adjust {
       description "Adjust a BGP AIGP attribute";
       choice math-op {
         case case_1 {
           leaf add {
             type empty;
           }
         }
         case case_2 {
           leaf subtract {
             type empty;
           }
         }
         case case_3 {
           leaf multiply {
             type empty;
           }
         }
         case case_4 {
           leaf divide {
             type empty;
           }
         }
       }
       choice adjust-value {
         case case_1 {
           leaf user-value {
             description "Adjustment value";
             type union {
               type uint64;
               type string {
                 pattern "<.*>|$.*";
               }
             }
           }
         }
         case case_2 {
           leaf distance-to-protocol-nexthop {
             description "Metric2";
             type empty;
           }
         }
       }
     }
     list community {
       key "choice-ident choice-value community-name";
       ordered-by user;
       description "BGP community properties associated with a route";
       leaf choice-ident {
         type enumeration {
           enum "equal-literal" {
           }
           enum "set" {
           }
           enum "plus-literal" {
           }
           enum "add" {
           }
           enum "minus-literal" {
           }
           enum "delete" {
           }
           enum "community-name" {
           }
         }
       }
       leaf choice-value {
         type string;
       }
       leaf community-name {
         description "Name to identify a BGP community";
         type string;
       }
     }
     leaf damping {
       description "Define BGP route flap damping parameters";
       type string;
     }
     leaf aggregate-bandwidth {
       description "Advertise aggregate outbound link bandwidth";
       type empty;
     }
     leaf limit-bandwidth {
       description "Limit advertised aggregate outbound link bandwidth";
       type union {
         type string {
           pattern "<.*>|$.*";
         }
         type uint32 {
           range "0 .. 4294967295";
         }
       }
     }
     leaf no-entropy-label-capability {
       description "Don't advertise entropy label capability";
       type empty;
     }
     leaf as-path-prepend {
       description "Prepend AS numbers to an AS path (BGP only)";
       type string;
     }
     container as-path-expand {
       description "Prepend AS numbers prior to adding local-as (BGP only)";
       choice aspath_exp_value {
         case case_1 {
           container last-as {
             presence "enable last-as";
             description "Prepend last AS";
             leaf count {
               description "Repeat count";
               type union {
                 type string {
                   pattern "<.*>|$.*";
                 }
                 type uint32 {
                   range "1 .. 32";
                 }
               }
             }
           }
         }
         case case_2 {
           leaf aspath {
             description "AS path string";
             type string;
           }
         }
       }
     }
     container next-hop {
       description "Set the address of the next-hop router";
       choice nexthop_value {
         case case_1 {
           leaf self {
             description "Use a local address as the next-hop address";
             type empty;
           }
         }
         case case_2 {
           leaf peer-address {
             description "Use the remote peer address as the next-hop address";
             type empty;
           }
         }
         case case_3 {
           leaf address {
             description "Next-hop address";
             type jt:ipaddr;
           }
         }
         case case_4 {
           leaf reject {
             description "Use a reject next hop";
             type empty;
           }
         }
         case case_5 {
           leaf discard {
             description "Use a discard next hop";
             type empty;
           }
         }
         case case_6 {
           leaf next-table {
             description "Perform a forwarding lookup in the specified table";
             type string;
           }
         }
       }
     }
     container install-nexthop {
       description "Choose the next hop to be used for forwarding";
       leaf strict {
         description "Do not use any other available next hops";
         type empty;
       }
       choice nexthop-value {
         case case_1 {
           leaf-list lsp {
             ordered-by user;
             description "Next-hop LSP name";
             type string;
           }
         }
         case case_2 {
           leaf-list lsp-regex {
             ordered-by user;
             description "Next-hop LSP name regular expression";
             type string;
           }
         }
         case case_3 {
           leaf-list static-lsp {
             ordered-by user;
             description "Next-hop static LSP name";
             type string;
           }
         }
         case case_4 {
           leaf-list static-lsp-regex {
             ordered-by user;
             description "Next-hop static LSP name regular expression";
             type string;
           }
         }
       }
       container except {
         description "Do not choose to install matching next hops";
         uses apply-advanced;
         choice nexthop-value {
           case case_1 {
             leaf-list lsp {
               ordered-by user;
               description "Next-hop LSP name";
               type string;
             }
           }
           case case_2 {
             leaf-list lsp-regex {
               ordered-by user;
               description "Next-hop LSP name regular expression";
               type string;
             }
           }
           case case_3 {
             leaf-list static-lsp {
               ordered-by user;
               description "Next-hop static LSP name";
               type string;
             }
           }
           case case_4 {
             leaf-list static-lsp-regex {
               ordered-by user;
               description "Next-hop static LSP name regular expression";
               type string;
             }
           }
         }
       }
     }
     leaf trace {
       description "Log matches to a trace file";
       type empty;
     }
     container external {
       presence "enable external";
       description "External route";
       uses apply-advanced;
       leaf type {
         description "OSPF external metric type";
         type union {
           type string {
             pattern "<.*>|$.*";
           }
           type int32 {
             range "1 .. 2";
           }
         }
       }
       leaf nssa-only {
         description "Clear P-bit on lsa type 7";
         type empty;
       }
     }
     container load-balance {
       description "Type of load balancing in forwarding table";
       choice load_balance_type {
         case case_1 {
           leaf per-packet {
             description "Load balance on a per-packet basis";
             type empty;
           }
         }
         case case_2 {
         }
         case case_3 {
         }
         case case_4 {
           leaf consistent-hash {
             description "Give a prefix consistent load-balancing";
             type empty;
           }
         }
         case case_5 {
         }
         case case_6 {
         }
       }
     }
     leaf analyze {
       description "Send to registered controllers for analysis";
       type empty;
     }
     leaf class {
       description "Set class-of-service parameters";
       type string;
     }
     leaf destination-class {
       description "Set destination class in forwarding table";
       type string;
     }
     leaf source-class {
       description "Set source class in forwarding table";
       type string;
     }
     leaf forwarding-class {
       description "Set source or destination class in forwarding table";
       type string;
     }
     container map-to-interface {
       description "Set output logical interface";
       choice map_to_interface_value {
         case case_1 {
           leaf self {
             description "Map the interface to itself";
             type empty;
           }
         }
         case case_2 {
           leaf interface {
             description "Output logical interface";
             type union {
               type jt:interface-name;
               type string {
                 pattern "<.*>|$.*";
               }
             }
           }
         }
       }
     }
     leaf-list ssm-source {
       ordered-by user;
       description "List of Sources for SSM mapping";
       type jt:ipaddr;
     }
     container p2mp-lsp-root {
       description "P2mp lsp root address";
       uses apply-advanced;
       leaf address {
         description "Ipv4 root address";
         type jt:ipv4addr;
       }
     }
     leaf cos-next-hop-map {
       description "Set CoS-based next-hop map in forwarding table";
       type string;
     }
     leaf dynamic-tunnel-attributes {
       description "Choose the dynamic tunnel attributes used for forwarding";
       type string;
     }
     leaf selected-mldp-egress {
       description "This node should act as egress node for MLDP inband signalling";
       type empty;
     }
     leaf mhop-bfd-port {
       description "Use port number 4784 for MPLS-BFD as per RFC5884";
       type empty;
     }
     leaf no-backup {
       description "This prefix should not have backup";
       type empty;
     }
     leaf default-action {
       description "Set default policy action";
       type enumeration {
         enum "accept" {
           description "Accept a route";
         }
         enum "reject" {
           description "Reject a route";
         }
       }
     }
     leaf next {
       description "Skip to next policy or term";
       type enumeration {
         enum "policy" {
           description "Skip to next policy filter";
         }
         enum "term" {
           description "Skip to next term in a policy filter";
         }
       }
     }
     choice accept_reject {
       case case_1 {
         leaf accept {
           description "Accept a route";
           type empty;
         }
       }
       case case_2 {
         leaf reject {
           description "Reject a route";
           type empty;
         }
       }
     }
     container bgp-output-queue-priority {
       description "Set the BGP Update output queue priority.";
       choice class {
         case case_1 {
           leaf priority {
             description "Output queue priority; higher is better";
             type union {
               type string {
                 pattern "<.*>|$.*";
               }
               type uint32 {
                 range "1 .. 16";
               }
             }
           }
         }
         case case_2 {
           leaf expedited {
             description "Expedited queue; highest priority";
             type empty;
           }
         }
       }
     }
     leaf multipath-resolve {
       description "Use all paths for resolution over this prefix";
       type empty;
     }
     leaf label-allocation-fallback-reject {
       description "Suppress prefix export when label allocation fails";
       type empty;
     }
   }
   grouping route_record_traceoptions {
     description "Traceoptions for sampling route record";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Area of route-record to enable debuging output";
       leaf name {
         type enumeration {
           enum "parse" {
             description "Trace parsing code";
           }
           enum "all" {
             description "Trace all area of jflow-service code";
           }
         }
       }
     }
   }
   grouping rpd_rib_group_type {
     description "Routing table group";
     leaf name {
       description "Routing table group";
       type string;
     }
     uses apply-advanced;
     leaf export-rib {
       description "Export routing table";
       type string;
     }
     leaf-list import-rib {
       ordered-by user;
       description "Import routing table";
       type string;
     }
     leaf-list import-policy {
       ordered-by user;
       description "Import policy";
       type jt:policy-algebra;
     }
   }
   grouping rtf_prefix_list_items {
     leaf name {
       description "Family route-target prefix";
       type string {
         length "1 .. 63";
       }
     }
     uses apply-advanced;
   }
   grouping sampling_family_inet6_output_type {
     description "Configure output options for packet sampling";
     uses apply-advanced;
     leaf aggregate-export-interval {
       description "Interval of exporting aggregate accounting information";
       default "90";
       units "seconds";
       type union {
         type string {
           pattern "<.*>|$.*";
         }
         type uint32 {
           range "90 .. 1800";
         }
       }
     }
     leaf flow-inactive-timeout {
       description "Interval of inactivity that marks a flow inactive";
       default "60";
       units "seconds";
       type union {
         type string {
           pattern "<.*>|$.*";
         }
         type uint32 {
           range "15 .. 1800";
         }
       }
     }
     leaf flow-active-timeout {
       description "Interval after which an active flow is exported";
       default "1800";
       units "seconds";
       type union {
         type string {
           pattern "<.*>|$.*";
         }
         type uint32 {
           range "60 .. 1800";
         }
       }
     }
     list flow-server {
       key name;
       description "Configure sending traffic aggregates in cflowd format";
       max-elements 8;
       uses cflowd_sampling_inet6_sampling_type;
     }
     container inline-jflow {
       description "Inline processing of sampled packets";
       presence "enable inline-jflow";
       uses packet_export_inline;
     }
     list extension-service {
       key name;
       ordered-by user;
       description "Define the customer specific sampling configuration";
       leaf name {
         description "Customer prefixed sampling service name";
         type string {
           length "1 .. 63";
         }
       }
       uses apply-advanced;
     }
   }
   grouping cflowd_sampling_inet6_sampling_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       type union {
         type string {
           pattern "<.*>|$.*";
         }
         type uint8 {
           range "0 .. 63";
         }
       }
     }
     leaf forwarding-class {
       description "Forwarding-class for exported jflow packets, applicable only for inline-jflow";
       type string {
         length "1 .. 64";
       }
     }
     leaf routing-instance {
       description "Name of routing instance on which flow collector is reachable";
       type string;
     }
     leaf autonomous-system-type {
       description "Type of autonomous system number to export";
       default "origin";
       type enumeration {
         enum "origin" {
           description "Export origin-AS numbers";
         }
         enum "peer" {
           description "Export peer-AS numbers";
         }
       }
     }
     container aggregation {
       description "Aggregations to perform for exported flows (version 8 only)";
       uses aggregation_type;
     }
     choice local-dump-choice {
       leaf local-dump {
         description "Dump cflowd records to log file before exporting";
         type empty;
       }
       leaf no-local-dump {
         description "Don't dump cflowd records to log file before exporting";
         type empty;
       }
     }
     leaf source-address {
       description "Source IPv4 address for cflowd packets";
       type jt:ipv4addr;
     }
     container version9 {
       presence "enable version9";
       description "Export data in version 9 format";
       uses apply-advanced;
       container template {
         description "Template configuration";
         uses apply-advanced;
         leaf template-name {
           description "Template name";
           type string;
         }
       }
     }
   }
   grouping packet_export_inline {
     uses apply-advanced;
     leaf source-address {
       description "Address to use for generating monitored packets";
       type jt:ipaddr;
     }
     leaf flow-export-rate {
       description "Flow export rate of monitored packets in kpps";
       type union {
         type string {
           pattern "<.*>|$.*";
         }
         type uint32 {
           range "1 .. 3200";
         }
       }
     }
   }
   grouping sampling_family_input_type {
     description "Configure input options for packet sampling";
     uses apply-advanced;
     leaf rate {
       description "Ratio of packets to be sampled (1 out of N)";
       type union {
         type string {
           pattern "<.*>|$.*";
         }
         type uint32;
       }
     }
     leaf run-length {
       description "Number of samples after initial trigger";
       default "0";
       type union {
         type string {
           pattern "<.*>|$.*";
         }
         type uint32 {
           range "0 .. 20";
         }
       }
     }
     leaf max-packets-per-second {
       description "Threshold of samples per second before dropping";
       default "1000";
       type union {
         type uint16;
         type string {
           pattern "<.*>|$.*";
         }
       }
     }
     leaf maximum-packet-length {
       description "Maximum length of the sampled packet";
       default "0";
       units "bytes";
       type union {
         type string {
           pattern "<.*>|$.*";
         }
         type uint32 {
           range "0 .. 9192";
         }
       }
     }
   }
   grouping sampling_input_type {
     description "Configure input options for packet sampling";
     uses apply-advanced;
     leaf rate {
       description "Ratio of packets to be sampled (1 out of N)";
       type union {
         type string {
           pattern "<.*>|$.*";
         }
         type uint32;
       }
     }
     leaf run-length {
       description "Number of samples after initial trigger";
       default "0";
       type union {
         type string {
           pattern "<.*>|$.*";
         }
         type uint32 {
           range "0 .. 20";
         }
       }
     }
     leaf max-packets-per-second {
       description "Threshold of samples per second before dropping";
       default "1000";
       type union {
         type uint16;
         type string {
           pattern "<.*>|$.*";
         }
       }
     }
     leaf maximum-packet-length {
       description "Maximum length of the sampled packet";
       default "0";
       units "bytes";
       type union {
         type string {
           pattern "<.*>|$.*";
         }
         type uint32 {
           range "0 .. 9192";
         }
       }
     }
     container family {
       presence "enable family";
       description "Protocol family";
       status deprecated;
       container inet {
         description "Sampling parameters for IPv4";
         uses apply-advanced;
         leaf rate {
           description "Ratio of packets to be sampled (1 out of N)";
           type union {
             type string {
               pattern "<.*>|$.*";
             }
             type uint32;
           }
         }
         leaf run-length {
           description "Number of samples after initial trigger";
           default "0";
           type union {
             type string {
               pattern "<.*>|$.*";
             }
             type uint32 {
               range "0 .. 20";
             }
           }
         }
         leaf max-packets-per-second {
           description "Threshold of samples per second before dropping";
           default "1000";
           type union {
             type uint16;
             type string {
               pattern "<.*>|$.*";
             }
           }
         }
         leaf maximum-packet-length {
           description "Maximum length of the sampled packet";
           default "0";
           units "bytes";
           type union {
             type string {
               pattern "<.*>|$.*";
             }
             type uint32 {
               range "0 .. 9192";
             }
           }
         }
       }
       container mpls {
         description "Sampling parameters for MPLS";
         uses apply-advanced;
         leaf rate {
           description "Ratio of packets to be sampled (1 out of N)";
           type union {
             type string {
               pattern "<.*>|$.*";
             }
             type uint32;
           }
         }
         leaf run-length {
           description "Number of samples after initial trigger";
           default "0";
           type union {
             type string {
               pattern "<.*>|$.*";
             }
             type uint32 {
               range "0 .. 20";
             }
           }
         }
         leaf max-packets-per-second {
           description "Threshold of samples per second before dropping";
           default "1000";
           type union {
             type uint16;
             type string {
               pattern "<.*>|$.*";
             }
           }
         }
         leaf maximum-packet-length {
           description "Maximum length of the sampled packet";
           default "0";
           units "bytes";
           type union {
             type string {
               pattern "<.*>|$.*";
             }
             type uint32 {
               range "0 .. 9192";
             }
           }
         }
       }
     }
   }
   grouping sampling_instance_bridge_output_type {
     description "Configure output options for packet sampling";
     uses apply-advanced;
     list flow-server {
       key name;
       description "Configure sending traffic aggregates in cflowd format";
       max-elements 8;
       uses cflowd_instance_bridge_sampling_type;
     }
     container inline-jflow {
       description "Inline processing of sampled packets";
       presence "enable inline-jflow";
       uses packet_export_inline_instance;
     }
   }
   grouping cflowd_instance_bridge_sampling_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       type union {
         type string {
           pattern "<.*>|$.*";
         }
         type uint8 {
           range "0 .. 63";
         }
       }
     }
     leaf forwarding-class {
       description "Forwarding-class for exported jflow packets, applicable only for inline-jflow";
       type string {
         length "1 .. 64";
       }
     }
     leaf routing-instance {
       description "Name of routing instance on which flow collector is reachable";
       type string;
     }
     container version-ipfix {
       presence "enable version-ipfix";
       description "Export data in version ipfix format";
       uses apply-advanced;
       container template {
         description "Template configuration";
         uses apply-advanced;
         leaf template-name {
           description "Template name";
           type string;
         }
       }
     }
   }
   grouping packet_export_inline_instance {
     uses apply-advanced;
     leaf source-address {
       description "Address to use for generating monitored packets";
       type jt:ipaddr;
     }
     leaf flow-export-rate {
       description "Flow export rate of monitored packets in kpps";
       type union {
         type string {
           pattern "<.*>|$.*";
         }
         type uint32 {
           range "1 .. 3200";
         }
       }
     }
   }
   grouping sampling_instance_inet6_output_type {
     description "Configure output options for packet sampling";
     uses apply-advanced;
     leaf aggregate-export-interval {
       description "Interval of exporting aggregate accounting information";
       default "90";
       units "seconds";
       type union {
         type string {
           pattern "<.*>|$.*";
         }
         type uint32 {
           range "90 .. 1800";
         }
       }
     }
     leaf flow-inactive-timeout {
       description "Interval of inactivity that marks a flow inactive";
       default "60";
       units "seconds";
       type union {
         type string {
           pattern "<.*>|$.*";
         }
         type uint32 {
           range "15 .. 1800";
         }
       }
     }
     leaf flow-active-timeout {
       description "Interval after which an active flow is exported";
       default "1800";
       units "seconds";
       type union {
         type string {
           pattern "<.*>|$.*";
         }
         type uint32 {
           range "60 .. 1800";
         }
       }
     }
     list flow-server {
       key name;
       description "Configure sending traffic aggregates in cflowd format";
       max-elements 8;
       uses cflowd_instance_inet6_sampling_type;
     }
     container inline-jflow {
       description "Inline processing of sampled packets";
       presence "enable inline-jflow";
       uses packet_export_inline_instance;
     }
     list extension-service {
       key name;
       ordered-by user;
       description "Define the customer specific sampling configuration";
       leaf name {
         description "Customer prefixed sampling service name";
         type string {
           length "1 .. 63";
         }
       }
       uses apply-advanced;
     }
   }
   grouping cflowd_instance_inet6_sampling_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       type union {
         type string {
           pattern "<.*>|$.*";
         }
         type uint8 {
           range "0 .. 63";
         }
       }
     }
     leaf forwarding-class {
       description "Forwarding-class for exported jflow packets, applicable only for inline-jflow";
       type string {
         length "1 .. 64";
       }
     }
     leaf routing-instance {
       description "Name of routing instance on which flow collector is reachable";
       type string;
     }
     leaf autonomous-system-type {
       description "Type of autonomous system number to export";
       default "origin";
       type enumeration {
         enum "origin" {
           description "Export origin-AS numbers";
         }
         enum "peer" {
           description "Export peer-AS numbers";
         }
       }
     }
     container aggregation {
       description "Aggregations to perform for exported flows (version 8 only)";
       uses aggregation_type;
     }
     choice local-dump-choice {
       leaf local-dump {
         description "Dump cflowd records to log file before exporting";
         type empty;
       }
       leaf no-local-dump {
         description "Don't dump cflowd records to log file before exporting";
         type empty;
       }
     }
     leaf source-address {
       description "Source IPv4 address for cflowd packets";
       type jt:ipv4addr;
     }
     container version9 {
       presence "enable version9";
       description "Export data in version 9 format";
       uses apply-advanced;
       container template {
         description "Template configuration";
         uses apply-advanced;
         leaf template-name {
           description "Template name";
           type string;
         }
       }
     }
     container version-ipfix {
       presence "enable version-ipfix";
       description "Export data in version ipfix format";
       uses apply-advanced;
       container template {
         description "Template configuration";
         uses apply-advanced;
         leaf template-name {
           description "Template name";
           type string;
         }
       }
     }
   }
   grouping sampling_instance_inet_global_output_type {
     description "Configure output options for packet sampling";
     uses apply-advanced;
     leaf aggregate-export-interval {
       description "Interval of exporting aggregate accounting information";
       default "90";
       units "seconds";
       type union {
         type string {
           pattern "<.*>|$.*";
         }
         type uint32 {
           range "90 .. 1800";
         }
       }
     }
     leaf flow-inactive-timeout {
       description "Interval of inactivity that marks a flow inactive";
       default "60";
       units "seconds";
       type union {
         type string {
           pattern "<.*>|$.*";
         }
         type uint32 {
           range "15 .. 1800";
         }
       }
     }
     leaf flow-active-timeout {
       description "Interval after which an active flow is exported";
       default "1800";
       units "seconds";
       type union {
         type string {
           pattern "<.*>|$.*";
         }
         type uint32 {
           range "60 .. 1800";
         }
       }
     }
     container file {
       description "Configure parameters for dumping sampled packets";
       choice enable-disable {
         case case_1 {
           leaf disable {
             description "Disable sampled packet dumps";
             type empty;
           }
         }
       }
       leaf filename {
         description "Name of file to contain sampled packet dumps";
         type string {
           length "1 .. 1024";
         }
       }
       leaf files {
         description "Maximum number of sampled packet dump files";
         default "10";
         type union {
           type string {
             pattern "<.*>|$.*";
           }
           type uint32 {
             range "2 .. 10000";
           }
         }
       }
       leaf size {
         description "Maximum sample dump file size";
         type string;
       }
       choice world-readable-choice {
         leaf world-readable {
           description "Allow any user to read the sampled dump";
           type empty;
         }
         leaf no-world-readable {
           description "Don't allow any user to read the sampled dump";
           type empty;
         }
       }
       choice stamp-choice {
         leaf stamp {
           description "Timestamp every packet in the dump";
           type empty;
         }
         leaf no-stamp {
           description "Don't timestamp every packet in the dump";
           type empty;
         }
       }
     }
     container port-mirroring {
       description "Configure sending sampled traffic out through an interface";
       presence "enable port-mirroring";
       uses inet_pm_family_output_type;
     }
     list flow-server {
       key name;
       description "Configure sending traffic aggregates in cflowd format";
       max-elements 8;
       uses cflowd_sampling_inet_type;
     }
     container inline-jflow {
       description "Inline processing of sampled packets";
       presence "enable inline-jflow";
       uses packet_export_inline;
     }
     list extension-service {
       key name;
       ordered-by user;
       description "Define the customer specific sampling configuration";
       leaf name {
         description "Customer prefixed sampling service name";
         type string {
           length "1 .. 63";
         }
       }
       uses apply-advanced;
     }
   }
   grouping cflowd_sampling_inet_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       type union {
         type string {
           pattern "<.*>|$.*";
         }
         type uint8 {
           range "0 .. 63";
         }
       }
     }
     leaf forwarding-class {
       description "Forwarding-class for exported jflow packets, applicable only for inline-jflow";
       type string {
         length "1 .. 64";
       }
     }
     leaf routing-instance {
       description "Name of routing instance on which flow collector is reachable";
       type string;
     }
     leaf autonomous-system-type {
       description "Type of autonomous system number to export";
       default "origin";
       type enumeration {
         enum "origin" {
           description "Export origin-AS numbers";
         }
         enum "peer" {
           description "Export peer-AS numbers";
         }
       }
     }
     container aggregation {
       description "Aggregations to perform for exported flows (version 8 only)";
       uses aggregation_type;
     }
     choice local-dump-choice {
       leaf local-dump {
         description "Dump cflowd records to log file before exporting";
         type empty;
       }
       leaf no-local-dump {
         description "Don't dump cflowd records to log file before exporting";
         type empty;
       }
     }
     leaf source-address {
       description "Source IPv4 address for cflowd packets";
       type jt:ipv4addr;
     }
     container version9 {
       presence "enable version9";
       description "Export data in version 9 format";
       uses apply-advanced;
       container template {
         description "Template configuration";
         uses apply-advanced;
         leaf template-name {
           description "Template name";
           type string;
         }
       }
     }
     container version-ipfix {
       presence "enable version-ipfix";
       description "Export data in version ipfix format";
       status deprecated;
       uses apply-advanced;
       container template {
         description "Template configuration";
         uses apply-advanced;
         leaf template-name {
           description "Template name";
           type string;
         }
       }
     }
     leaf version {
       description "Format of exported cflowd aggregates";
       default "5";
       type enumeration {
         enum "5" {
           description "Export cflowd aggregates in version 5 format";
         }
         enum "8" {
           description "Export cflowd aggregates in version 8 format";
         }
         enum "500" {
           description "Export cflowd aggregates in ASN 500 format";
         }
       }
     }
   }
   grouping sampling_instance_inet_output_type {
     description "Configure output options for packet sampling";
     uses apply-advanced;
     leaf aggregate-export-interval {
       description "Interval of exporting aggregate accounting information";
       default "90";
       units "seconds";
       type union {
         type string {
           pattern "<.*>|$.*";
         }
         type uint32 {
           range "90 .. 1800";
         }
       }
     }
     leaf flow-inactive-timeout {
       description "Interval of inactivity that marks a flow inactive";
       default "60";
       units "seconds";
       type union {
         type string {
           pattern "<.*>|$.*";
         }
         type uint32 {
           range "15 .. 1800";
         }
       }
     }
     leaf flow-active-timeout {
       description "Interval after which an active flow is exported";
       default "1800";
       units "seconds";
       type union {
         type string {
           pattern "<.*>|$.*";
         }
         type uint32 {
           range "60 .. 1800";
         }
       }
     }
     list flow-server {
       key name;
       description "Configure sending traffic aggregates in cflowd format";
       max-elements 8;
       uses cflowd_instance_inet_sampling_type;
     }
     container inline-jflow {
       description "Inline processing of sampled packets";
       presence "enable inline-jflow";
       uses packet_export_inline_instance;
     }
     list extension-service {
       key name;
       ordered-by user;
       description "Define the customer specific sampling configuration";
       leaf name {
         description "Customer prefixed sampling service name";
         type string {
           length "1 .. 63";
         }
       }
       uses apply-advanced;
     }
   }
   grouping cflowd_instance_inet_sampling_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       type union {
         type string {
           pattern "<.*>|$.*";
         }
         type uint8 {
           range "0 .. 63";
         }
       }
     }
     leaf forwarding-class {
       description "Forwarding-class for exported jflow packets, applicable only for inline-jflow";
       type string {
         length "1 .. 64";
       }
     }
     leaf routing-instance {
       description "Name of routing instance on which flow collector is reachable";
       type string;
     }
     leaf autonomous-system-type {
       description "Type of autonomous system number to export";
       default "origin";
       type enumeration {
         enum "origin" {
           description "Export origin-AS numbers";
         }
         enum "peer" {
           description "Export peer-AS numbers";
         }
       }
     }
     container aggregation {
       description "Aggregations to perform for exported flows (version 8 only)";
       uses aggregation_type;
     }
     choice local-dump-choice {
       leaf local-dump {
         description "Dump cflowd records to log file before exporting";
         type empty;
       }
       leaf no-local-dump {
         description "Don't dump cflowd records to log file before exporting";
         type empty;
       }
     }
     leaf source-address {
       description "Source IPv4 address for cflowd packets";
       type jt:ipv4addr;
     }
     container version9 {
       presence "enable version9";
       description "Export data in version 9 format";
       uses apply-advanced;
       container template {
         description "Template configuration";
         uses apply-advanced;
         leaf template-name {
           description "Template name";
           type string;
         }
       }
     }
     container version-ipfix {
       presence "enable version-ipfix";
       description "Export data in version ipfix format";
       uses apply-advanced;
       container template {
         description "Template configuration";
         uses apply-advanced;
         leaf template-name {
           description "Template name";
           type string;
         }
       }
     }
     leaf version {
       description "Format of exported cflowd aggregates";
       default "5";
       type enumeration {
         enum "5" {
           description "Export cflowd aggregates in version 5 format";
         }
         enum "8" {
           description "Export cflowd aggregates in version 8 format";
         }
       }
     }
   }
   grouping sampling_instance_input_type {
     description "Configure input options for packet sampling";
     uses apply-advanced;
     leaf rate {
       description "Ratio of packets to be sampled (1 out of N)";
       type union {
         type string {
           pattern "<.*>|$.*";
         }
         type uint32;
       }
     }
     leaf run-length {
       description "Number of samples after initial trigger";
       default "0";
       type union {
         type string {
           pattern "<.*>|$.*";
         }
         type uint32 {
           range "0 .. 20";
         }
       }
     }
     leaf max-packets-per-second {
       description "Threshold of samples per second before dropping";
       default "1000";
       type union {
         type uint16;
         type string {
           pattern "<.*>|$.*";
         }
       }
     }
     leaf maximum-packet-length {
       description "Maximum length of the sampled packet";
       default "0";
       units "bytes";
       type union {
         type string {
           pattern "<.*>|$.*";
         }
         type uint32 {
           range "0 .. 9192";
         }
       }
     }
   }
   grouping sampling_instance_mpls_output_type {
     description "Configure output options for packet sampling";
     uses apply-advanced;
     leaf aggregate-export-interval {
       description "Interval of exporting aggregate accounting information";
       default "90";
       units "seconds";
       type union {
         type string {
           pattern "<.*>|$.*";
         }
         type uint32 {
           range "90 .. 1800";
         }
       }
     }
     leaf flow-inactive-timeout {
       description "Interval of inactivity that marks a flow inactive";
       default "60";
       units "seconds";
       type union {
         type string {
           pattern "<.*>|$.*";
         }
         type uint32 {
           range "15 .. 1800";
         }
       }
     }
     leaf flow-active-timeout {
       description "Interval after which an active flow is exported";
       default "1800";
       units "seconds";
       type union {
         type string {
           pattern "<.*>|$.*";
         }
         type uint32 {
           range "60 .. 1800";
         }
       }
     }
     list flow-server {
       key name;
       description "Configure sending traffic aggregates in cflowd format";
       max-elements 8;
       uses cflowd_instance_mpls_sampling_type;
     }
     container inline-jflow {
       description "Inline processing of sampled packets";
       presence "enable inline-jflow";
       uses packet_export_inline_instance;
     }
   }
   grouping cflowd_instance_mpls_sampling_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       type union {
         type string {
           pattern "<.*>|$.*";
         }
         type uint8 {
           range "0 .. 63";
         }
       }
     }
     leaf forwarding-class {
       description "Forwarding-class for exported jflow packets, applicable only for inline-jflow";
       type string {
         length "1 .. 64";
       }
     }
     leaf routing-instance {
       description "Name of routing instance on which flow collector is reachable";
       type string;
     }
     leaf autonomous-system-type {
       description "Type of autonomous system number to export";
       default "origin";
       type enumeration {
         enum "origin" {
           description "Export origin-AS numbers";
         }
         enum "peer" {
           description "Export peer-AS numbers";
         }
       }
     }
     container aggregation {
       description "Aggregations to perform for exported flows (version 8 only)";
       uses aggregation_type;
     }
     choice local-dump-choice {
       leaf local-dump {
         description "Dump cflowd records to log file before exporting";
         type empty;
       }
       leaf no-local-dump {
         description "Don't dump cflowd records to log file before exporting";
         type empty;
       }
     }
     leaf source-address {
       description "Source IPv4 address for cflowd packets";
       type jt:ipv4addr;
     }
     container version-ipfix {
       presence "enable version-ipfix";
       description "Export data in version ipfix format";
       uses apply-advanced;
       container template {
         description "Template configuration";
         uses apply-advanced;
         leaf template-name {
           description "Template name";
           type string;
         }
       }
     }
   }
   grouping sampling_instance_vpls_output_type {
     description "Configure output options for packet sampling";
     uses apply-advanced;
     list flow-server {
       key name;
       description "Configure sending traffic aggregates in cflowd format";
       max-elements 8;
       uses cflowd_instance_vpls_sampling_type;
     }
     container inline-jflow {
       description "Inline processing of sampled packets";
       presence "enable inline-jflow";
       uses packet_export_inline_instance;
     }
   }
   grouping cflowd_instance_vpls_sampling_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       type union {
         type string {
           pattern "<.*>|$.*";
         }
         type uint8 {
           range "0 .. 63";
         }
       }
     }
     leaf forwarding-class {
       description "Forwarding-class for exported jflow packets, applicable only for inline-jflow";
       type string {
         length "1 .. 64";
       }
     }
     leaf routing-instance {
       description "Name of routing instance on which flow collector is reachable";
       type string;
     }
     container version-ipfix {
       presence "enable version-ipfix";
       description "Export data in version ipfix format";
       uses apply-advanced;
       container template {
         description "Template configuration";
         uses apply-advanced;
         leaf template-name {
           description "Template name";
           type string;
         }
       }
     }
   }
   grouping sampling_output_type {
     description "Configure output options for packet sampling";
     uses apply-advanced;
     leaf aggregate-export-interval {
       description "Interval of exporting aggregate accounting information";
       default "90";
       units "seconds";
       type union {
         type string {
           pattern "<.*>|$.*";
         }
         type uint32 {
           range "90 .. 1800";
         }
       }
     }
     leaf flow-inactive-timeout {
       description "Interval of inactivity that marks a flow inactive";
       default "60";
       units "seconds";
       type union {
         type string {
           pattern "<.*>|$.*";
         }
         type uint32 {
           range "15 .. 1800";
         }
       }
     }
     leaf flow-active-timeout {
       description "Interval after which an active flow is exported";
       default "1800";
       units "seconds";
       type union {
         type string {
           pattern "<.*>|$.*";
         }
         type uint32 {
           range "60 .. 1800";
         }
       }
     }
     container file {
       description "Configure parameters for dumping sampled packets";
       choice enable-disable {
         case case_1 {
           leaf disable {
             description "Disable sampled packet dumps";
             type empty;
           }
         }
       }
       leaf filename {
         description "Name of file to contain sampled packet dumps";
         type string {
           length "1 .. 1024";
         }
       }
       leaf files {
         description "Maximum number of sampled packet dump files";
         default "10";
         type union {
           type string {
             pattern "<.*>|$.*";
           }
           type uint32 {
             range "2 .. 10000";
           }
         }
       }
       leaf size {
         description "Maximum sample dump file size";
         type string;
       }
       choice world-readable-choice {
         leaf world-readable {
           description "Allow any user to read the sampled dump";
           type empty;
         }
         leaf no-world-readable {
           description "Don't allow any user to read the sampled dump";
           type empty;
         }
       }
       choice stamp-choice {
         leaf stamp {
           description "Timestamp every packet in the dump";
           type empty;
         }
         leaf no-stamp {
           description "Don't timestamp every packet in the dump";
           type empty;
         }
       }
     }
     container port-mirroring {
       description "Configure sending sampled traffic out through an interface";
       presence "enable port-mirroring";
       uses inet_pm_family_output_type;
     }
     list flow-server {
       key name;
       description "Configure sending traffic aggregates in cflowd format";
       max-elements 8;
       uses cflowd_sampling_type;
     }
     container inline-jflow {
       description "Inline processing of sampled packets";
       presence "enable inline-jflow";
       uses packet_export_inline;
     }
     list extension-service {
       key name;
       ordered-by user;
       description "Define the customer specific sampling configuration";
       leaf name {
         description "Customer prefixed sampling service name";
         type string {
           length "1 .. 63";
         }
       }
       uses apply-advanced;
     }
   }
   grouping cflowd_sampling_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       type union {
         type string {
           pattern "<.*>|$.*";
         }
         type uint8 {
           range "0 .. 63";
         }
       }
     }
     leaf forwarding-class {
       description "Forwarding-class for exported jflow packets, applicable only for inline-jflow";
       type string {
         length "1 .. 64";
       }
     }
     leaf routing-instance {
       description "Name of routing instance on which flow collector is reachable";
       type string;
     }
     leaf autonomous-system-type {
       description "Type of autonomous system number to export";
       default "origin";
       type enumeration {
         enum "origin" {
           description "Export origin-AS numbers";
         }
         enum "peer" {
           description "Export peer-AS numbers";
         }
       }
     }
     container aggregation {
       description "Aggregations to perform for exported flows (version 8 only)";
       uses aggregation_type;
     }
     choice local-dump-choice {
       leaf local-dump {
         description "Dump cflowd records to log file before exporting";
         type empty;
       }
       leaf no-local-dump {
         description "Don't dump cflowd records to log file before exporting";
         type empty;
       }
     }
     leaf source-address {
       description "Source IPv4 address for cflowd packets";
       type jt:ipv4addr;
     }
     container version9 {
       presence "enable version9";
       description "Export data in version 9 format";
       uses apply-advanced;
       container template {
         description "Template configuration";
         uses apply-advanced;
         leaf template-name {
           description "Template name";
           type string;
         }
       }
     }
     container version-ipfix {
       presence "enable version-ipfix";
       description "Export data in version ipfix format";
       status deprecated;
       uses apply-advanced;
       container template {
         description "Template configuration";
         uses apply-advanced;
         leaf template-name {
           description "Template name";
           type string;
         }
       }
     }
     leaf version {
       description "Format of exported cflowd aggregates";
       default "5";
       type enumeration {
         enum "5" {
           description "Export cflowd aggregates in version 5 format";
         }
         enum "8" {
           description "Export cflowd aggregates in version 8 format";
         }
         enum "500" {
           description "Export cflowd aggregates in ASN 500 format";
         }
       }
     }
   }
   grouping sampling_traceoptions_type {
     description "Configure packet sampling traceoptions";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
   }
   grouping satellite-policy-options {
     uses apply-advanced;
     list extended-ports-template {
       key name;
       ordered-by user;
       description "Extended ports template";
       leaf name {
         type string {
           length "1 .. 32";
         }
       }
       uses apply-advanced;
       list pic {
         key name;
         description "PIC attributes";
         uses satellite-pic-type;
       }
     }
     list port-group-alias {
       key name;
       ordered-by user;
       description "Port group alias";
       leaf name {
         type string {
           length "1 .. 32";
         }
       }
       uses apply-advanced;
       list pic {
         key name;
         ordered-by user;
         description "Satellite PIC information";
         leaf name {
           description "PIC identifier";
           type union {
             type int32;
             type string {
               pattern "<.*>|$.*";
             }
           }
         }
         uses apply-advanced;
         leaf-list port {
           ordered-by user;
           description "Port id or range or all";
           type union {
             type string {
               pattern "<.*>|$.*";
             }
             type uint32 {
               range "0 .. 1024";
             }
           }
         }
       }
     }
     list chassis-group-alias {
       key name;
       ordered-by user;
       description "Chassis group alias";
       leaf name {
         description "Chassis group alias name";
         type string {
           length "1 .. 32";
         }
       }
       uses apply-advanced;
       leaf prefer-primary {
         description "Primary mode chassis will be preferred";
         type empty;
       }
       list chassis-id {
         key name;
         ordered-by user;
         description "List of chassis-ids";
         leaf name {
           description "Chassis ID";
           type union {
             type string {
               pattern "<.*>|$.*";
             }
             type uint32 {
               range "1 .. 255";
             }
           }
         }
         uses apply-advanced;
         container mode {
           description "Mode Primary or Backup";
           uses apply-advanced;
           choice mode-choice {
             case case_1 {
               leaf primary {
                 description "Primary Mode";
                 type empty;
               }
             }
             case case_2 {
               leaf backup {
                 description "Backup Mode";
                 type empty;
               }
             }
           }
         }
         list core-interface {
           key name;
           ordered-by user;
           description "Core interface";
           leaf name {
             description "Core interface name";
             type union {
               type jt:interface-device;
               type string {
                 pattern "<.*>|$.*";
               }
             }
           }
           uses apply-advanced;
         }
       }
     }
     list extended-ports-policy {
       key name;
       ordered-by user;
       description "Define a extended-ports-policy";
       leaf name {
         description "Policy name";
         type string {
           length "1 .. 32";
         }
       }
       uses apply-advanced;
       list term {
         key name;
         ordered-by user;
         description "Policy term";
         leaf name {
           type string {
             length "1 .. 32";
           }
         }
         uses apply-advanced;
         container from {
           description "Condition to match the satellite";
           uses apply-advanced;
           leaf-list product-model {
             ordered-by user;
             description "Product Model Name";
             type string {
               length "1 .. 64";
             }
           }
           leaf extended-ports-template {
             description "Apply extended ports template to satellite matching conditions defined in this term";
             type string;
           }
         }
       }
     }
     list candidate-uplink-port-policy {
       key name;
       ordered-by user;
       description "Define a candidate uplink-port policy";
       leaf name {
         description "Policy name";
         type string {
           length "1 .. 32";
         }
       }
       uses apply-advanced;
       leaf uplink-port-group {
         description "Uplink port group alias name";
         type string;
       }
       leaf minimum-links {
         description "Minimum child links to keep extended-ports UP";
         type union {
           type string {
             pattern "<.*>|$.*";
           }
           type uint16 {
             range "1 .. 32";
           }
         }
       }
       leaf holddown {
         description "Time to hold down after uplink failure";
         units "seconds";
         type union {
           type string {
             pattern "<.*>|$.*";
           }
           type uint32 {
             range "1 .. 600";
           }
         }
       }
       list term {
         key name;
         ordered-by user;
         description "Policy term";
         leaf name {
           type string {
             length "1 .. 32";
           }
         }
         uses apply-advanced;
         container from {
           description "Condition to match the satellite";
           uses apply-advanced;
           leaf-list product-model {
             ordered-by user;
             description "Product Model Name";
             type string {
               length "1 .. 64";
             }
           }
           leaf uplink-port-group {
             description "Uplink port group alias name";
             type string;
           }
           leaf minimum-links {
             description "Minimum child links to keep extended-ports UP";
             type union {
               type string {
                 pattern "<.*>|$.*";
               }
               type uint16 {
                 range "1 .. 32";
               }
             }
           }
           leaf holddown {
             description "Time to hold down after uplink failure";
             units "seconds";
             type union {
               type string {
                 pattern "<.*>|$.*";
               }
               type uint32 {
                 range "1 .. 600";
               }
             }
           }
         }
       }
     }
     list environment-monitoring-policy {
       key name;
       ordered-by user;
       description "Define a environment monitoring policy";
       leaf name {
         description "Policy name";
         type string {
           length "1 .. 32";
         }
       }
       uses apply-advanced;
       container alarm {
         presence "enable alarm";
         description "Policy default alarm policy";
         uses apply-advanced;
         leaf linkdown {
           description "Policy default linkdown alarm";
           type enumeration {
             enum "ignore" {
               description "Ignore ethernet linkdown";
             }
             enum "red" {
               description "Raise major alarm for ethernet linkdown";
             }
             enum "yellow" {
               description "Raise minor alarm for ethernet linkdown";
             }
           }
         }
       }
       list term {
         key name;
         ordered-by user;
         description "Policy term";
         leaf name {
           type string {
             length "1 .. 32";
           }
         }
         uses apply-advanced;
         container from {
           description "Condition to match the satellite";
           uses apply-advanced;
           leaf-list product-model {
             ordered-by user;
             description "Product Model Name";
             type string {
               length "1 .. 64";
             }
           }
           container alarm {
             presence "enable alarm";
             description "Term alarm policy";
             uses apply-advanced;
             leaf linkdown {
               description "Set linkdown alarm";
               type enumeration {
                 enum "ignore" {
                   description "Ignore ethernet linkdown";
                 }
                 enum "red" {
                   description "Raise major alarm for ethernet linkdown";
                 }
                 enum "yellow" {
                   description "Raise minor alarm for ethernet linkdown";
                 }
               }
             }
           }
         }
       }
     }
     list forwarding-policy {
       key name;
       ordered-by user;
       description "Define forwarding policy for extended ports";
       leaf name {
         description "Policy name";
         type string {
           length "1 .. 32";
         }
       }
       uses apply-advanced;
       list port-group-extended {
         key name;
         ordered-by user;
         description "Define a extend port group mapping";
         uses port-extend-type;
       }
       list term {
         key name;
         ordered-by user;
         description "Policy term";
         leaf name {
           type string {
             length "1 .. 32";
           }
         }
         uses apply-advanced;
         container from {
           description "Condition to match the satellite";
           uses apply-advanced;
           leaf-list product-model {
             ordered-by user;
             description "Product Model Name";
             type string {
               length "1 .. 64";
             }
           }
           list port-group-extended {
             key name;
             ordered-by user;
             description "Define a extend port group mapping";
             uses port-extend-type;
           }
         }
       }
     }
   }
   grouping port-extend-type {
     leaf name {
       description "Extended port group alias name policy applied on";
       type string;
     }
     uses apply-advanced;
     leaf filter {
       description "Assign a filter for uplink selection";
       type string;
     }
     container port-group-uplink {
       description "Define a uplink port group mapping";
       uses apply-advanced;
       leaf port-group-uplink-alias {
         description "Uplink port group alias name used for uplink pinning mode";
         type string;
       }
       leaf minimum-links {
         description "Minimum child links to keep extended-ports UP";
         type union {
           type string {
             pattern "<.*>|$.*";
           }
           type uint16 {
             range "1 .. 32";
           }
         }
       }
       leaf holddown {
         description "Time to hold down after uplink failure";
         units "seconds";
         type union {
           type string {
             pattern "<.*>|$.*";
           }
           type uint32 {
             range "1 .. 600";
           }
         }
       }
     }
     container mirror-ingress {
       description "Define a ingress port mirror";
       uses apply-advanced;
       leaf port-group-mirror {
         description "Mirror port group alias name for local port mirroring";
         type string;
       }
     }
     container mirror-egress {
       description "Define a egress port mirror";
       uses apply-advanced;
       leaf port-group-mirror {
         description "Mirror port group alias name for local port mirroring";
         type string;
       }
     }
   }
   grouping satellite-pic-type {
     leaf name {
       description "PIC slot number";
       type union {
         type string {
           pattern "<.*>|$.*";
         }
         type uint32 {
           range "0 .. 4";
         }
       }
     }
     uses apply-advanced;
     list port {
       key name;
       description "Port number";
       uses satellite-pic-port-attr;
     }
     list port-range {
       key "port-range-low port-range-high";
       ordered-by user;
       description "Physical ports to channelize";
       leaf port-range-low {
         description "Port range low number";
         type union {
           type string {
             pattern "<.*>|$.*";
           }
           type uint32 {
             range "0 .. 127";
           }
         }
       }
       leaf port-range-high {
         description "Port range high number";
         type union {
           type string {
             pattern "<.*>|$.*";
           }
           type uint32 {
             range "0 .. 127";
           }
         }
       }
       uses apply-advanced;
       leaf channel-speed {
         description "Port channel speed";
         type enumeration {
           enum "10g" {
             description "Set the port speed to 10G";
           }
           enum "disable-auto-speed-detection" {
             description "Disables automatic speed detection";
           }
         }
       }
     }
   }
   grouping satellite-pic-port-attr {
     leaf name {
       description "Port number";
       type union {
         type string {
           pattern "<.*>|$.*";
         }
         type uint32 {
           range "0 .. 127";
         }
       }
     }
     uses apply-advanced;
     leaf channel-speed {
       description "Port channel speed";
       type enumeration {
         enum "10g" {
           description "Set the port speed to 10G";
         }
         enum "25g" {
           description "Set the port speed to 25G";
         }
         enum "50g" {
           description "Set the port speed to 50G";
         }
         enum "disable-auto-speed-detection" {
           description "Disables automatic speed detection";
         }
       }
     }
   }
   grouping sbl-type {
     description "SBL type";
     uses apply-advanced;
     list profile {
       key name;
       ordered-by user;
       description "SBL profile";
       leaf name {
         description "SBL profile name";
         type string {
           length "1 .. 29";
         }
       }
       uses apply-advanced;
       choice sbl-default-server-choice {
         leaf sbl-default-server {
           description "Default SBL server";
           type empty;
         }
         leaf no-sbl-default-server {
           description "Don't default SBL server";
           type empty;
         }
       }
       leaf spam-action {
         description "Anti-spam actions";
         type enumeration {
           enum "block" {
             description "Block e-mail";
           }
           enum "tag-header" {
             description "Tag header of e-mail";
           }
           enum "tag-subject" {
             description "Tag subject of e-mail";
           }
         }
       }
       leaf custom-tag-string {
         description "Custom tag string";
         type string {
           length "1 .. 512";
         }
       }
       leaf address-whitelist {
         description "Anti-spam whitelist";
         type string;
       }
       leaf address-blacklist {
         description "Anti-spam blacklist";
         type string;
       }
     }
   }
   grouping scheduler_object_type {
     leaf name {
       description "Name of security scheduler";
       type string {
         length "1 .. 63";
       }
     }
     uses apply-advanced;
     leaf description {
       description "Text description of scheduler";
       type string {
         length "1 .. 900";
       }
     }
     list start-date {
       key "start-date stop-date";
       ordered-by user;
       description "Start date and time ([YYYY-]MM-DD.hh:mm)";
       max-elements 2;
       leaf start-date {
         description "Start date and time ([YYYY-]MM-DD.hh:mm)";
         type string {
         }
       }
       leaf stop-date {
         description "Stop date and time ([YYYY-]MM-DD.hh:mm)";
         type string {
         }
       }
       uses apply-advanced;
     }
     container daily {
       description "Everyday; can be overwritten by specific weekday";
       uses daily-object;
     }
     container sunday {
       description "Every Sunday";
       uses daily-object;
     }
     container monday {
       description "Every Monday";
       uses daily-object;
     }
     container tuesday {
       description "Every Tuesday";
       uses daily-object;
     }
     container wednesday {
       description "Every Wednesday";
       uses daily-object;
     }
     container thursday {
       description "Every Thursday";
       uses daily-object;
     }
     container friday {
       description "Every Friday";
       uses daily-object;
     }
     container saturday {
       description "Every Saturday";
       uses daily-object;
     }
   }
   grouping daily-object {
     description "Daily schedule";
     uses apply-advanced;
     choice daily_type {
       case case_1 {
         list start-time {
           key "start-time-value stop-time";
           description "Time range for day";
           max-elements 2;
           leaf start-time-value {
             description "Start time for day (hh:mm)";
             type string {
             }
           }
           leaf stop-time {
             description "Stop time for day (hh:mm)";
             type string {
             }
           }
           uses apply-advanced;
         }
       }
       case case_2 {
         leaf exclude {
           description "Exclude day from week";
           type empty;
         }
       }
       case case_3 {
         leaf all-day {
           description "Include complete day";
           type empty;
         }
       }
     }
   }
   grouping secintel-category-disable {
     description "Security intelligence category";
     leaf name {
       description "Name of security intelligence category";
       type enumeration {
         enum "IPFilter" {
           description "IPFilter";
         }
         enum "GeoIP" {
           description "GeoIP";
         }
         enum "CC" {
           description "Command and control";
         }
         enum "JWAS" {
           description "JWAS";
         }
         enum "Blacklist" {
           description "Blacklist";
         }
         enum "Whitelist" {
           description "Whitelist";
         }
         enum "Infected-Hosts" {
           description "Infected-Hosts";
         }
       }
     }
     uses apply-advanced;
     container disable {
       presence "enable disable";
       description "To disable category for feed update";
     }
   }
   grouping secintel-policy-setting {
     description "Security intelligence policy setting";
     leaf name {
       description "Security intelligence policy name";
       type string {
         length "1 .. 63";
       }
     }
     uses apply-advanced;
     leaf description {
       description "Text description of policy";
       type string {
         length "1 .. 900";
       }
     }
     list category-profiles {
       key name;
       ordered-by user;
       description "Security intelligence category profiles";
       leaf name {
         description "Name of security intelligence category";
         type string;
       }
       uses apply-advanced;
       leaf profile-name {
         description "Name of profile";
         type string;
       }
     }
   }
   grouping secintel-profile-setting {
     description "Security intelligence profile settings";
     leaf name {
       description "Security intelligence profile name";
       type string {
         length "1 .. 63";
       }
     }
     uses apply-advanced;
     leaf description {
       description "Text description of profile";
       type string {
         length "1 .. 900";
       }
     }
     leaf category {
       description "Profile category name";
       type string;
     }
     list rule {
       key name;
       ordered-by user;
       description "Profile rule name";
       uses secintel-profile-rule;
     }
     container default-rule {
       presence "enable default-rule";
       description "Profile default rule";
       uses apply-advanced;
       container then {
         presence "enable then";
         description "Profile default rule action";
         uses apply-advanced;
         container action {
           description "Security intelligence profile action";
           uses apply-advanced;
           choice action {
             case case_1 {
               leaf permit {
                 description "Permit action";
                 type empty;
               }
             }
             case case_2 {
               container block {
                 description "Block action";
                 uses apply-advanced;
                 choice action {
                   case case_1 {
                     container drop {
                       presence "enable drop";
                       description "Drop packet";
                     }
                   }
                   case case_2 {
                     container close {
                       presence "enable close";
                       description "Close session";
                       uses apply-advanced;
                       container http {
                         description "Http content for block action";
                         uses apply-advanced;
                         choice http-choice {
                           case case_1 {
                             leaf file {
                               description "File name for http response to client";
                               type string;
                             }
                           }
                           case case_2 {
                             leaf message {
                               description "Block message to client";
                               type string;
                             }
                           }
                           case case_3 {
                             leaf redirect-url {
                               description "Redirect url to client";
                               type string {
                                 length "1 .. 1023";
                               }
                             }
                           }
                         }
                       }
                     }
                   }
                 }
               }
             }
             case case_3 {
               container recommended {
                 presence "enable recommended";
                 description "Recommended action from feed server";
               }
             }
           }
         }
         choice log-choice {
           leaf log {
             description "Log security intelligence block action";
             type empty;
           }
           leaf no-log {
             description "Don't log security intelligence block action";
             type empty;
           }
         }
       }
     }
   }
   grouping secintel-profile-rule {
     description "Security intelligence profile rule";
     leaf name {
       description "Profile rule name";
       type string {
         length "1 .. 63";
       }
     }
     uses apply-advanced;
     container match {
       description "Profile matching feed name and threat levels";
       uses apply-advanced;
       leaf-list feed-name {
         ordered-by user;
         description "Profile matching feed name";
         type string;
         max-elements 32;
       }
       leaf-list threat-level {
         ordered-by user;
         description "Profile matching threat levels, higher number is more severe";
         type union {
           type uint32;
           type string {
             pattern "<.*>|$.*";
           }
         }
       }
     }
     container then {
       description "Profile action and log";
       uses apply-advanced;
       container action {
         description "Security intelligence profile action";
         uses apply-advanced;
         choice action {
           case case_1 {
             leaf permit {
               description "Permit action";
               type empty;
             }
           }
           case case_2 {
             container block {
               description "Block action";
               uses apply-advanced;
               choice action {
                 case case_1 {
                   container drop {
                     presence "enable drop";
                     description "Drop packet";
                   }
                 }
                 case case_2 {
                   container close {
                     presence "enable close";
                     description "Close session";
                     uses apply-advanced;
                     container http {
                       description "Http content for block action";
                       uses apply-advanced;
                       choice http-choice {
                         case case_1 {
                           leaf file {
                             description "File name for http response to client";
                             type string;
                           }
                         }
                         case case_2 {
                           leaf message {
                             description "Block message to client";
                             type string;
                           }
                         }
                         case case_3 {
                           leaf redirect-url {
                             description "Redirect url to client";
                             type string {
                               length "1 .. 1023";
                             }
                           }
                         }
                       }
                     }
                   }
                 }
               }
             }
           }
           case case_3 {
             container recommended {
               presence "enable recommended";
               description "Recommended action from feed server";
             }
           }
         }
       }
       container log {
         presence "enable log";
         description "Log security intelligence block action";
       }
     }
   }
   grouping secintel-traceoptions {
     description "Security intelligence trace options";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Trace flags";
       leaf name {
         type enumeration {
           enum "all" {
             description "Trace everything";
           }
           enum "blacklist" {
             description "Trace security intelligence Blacklist category";
           }
           enum "cc" {
             description "Trace security intelligence CC category";
           }
           enum "infected-hosts" {
             description "Trace security intelligence Infected-Hosts category";
           }
           enum "control" {
             description "Trace control plane";
           }
           enum "feed" {
             description "Trace feed operation";
           }
           enum "ipc" {
             description "Trace ipc module";
           }
           enum "infrastucture" {
             description "Trace infrastucture functions";
           }
           enum "jwas" {
             description "Trace security intelligence JWAS category";
           }
           enum "plugin" {
             description "Trace security intelligence plugin services";
           }
           enum "whitelist" {
             description "Trace security intelligence Whitelist category";
           }
         }
       }
     }
   }
   grouping secure-wire-type {
     description "Secure-wire cross connection";
     leaf name {
       description "Secure-wire name";
       type string {
         length "1 .. 63";
       }
     }
     uses apply-advanced;
     leaf-list interface {
       description "Secure-wire logical interface";
       type union {
         type jt:interface-unit;
         type string {
           pattern "<.*>|$.*";
         }
       }
     }
   }
   grouping security-authentication-key-chains {
     uses apply-advanced;
     list key-chain {
       key name;
       description "Key chain configuration";
       leaf name {
         description "Name of authentication key chain";
         type string {
         }
       }
       uses apply-advanced;
       leaf description {
         description "Text description of this authentication-key-chain";
         type string {
           length "1 .. 80";
         }
       }
       leaf tolerance {
         description "Clock skew tolerance";
         default "3600";
         units "seconds";
         type union {
           type string {
             pattern "<.*>|$.*";
           }
           type uint32 {
             range "0 .. 4294967295";
           }
         }
       }
       list key {
         key name;
         description "Authentication element configuration";
         leaf name {
           description "Authentication element identifier";
           type union {
             type string {
               pattern "<.*>|$.*";
             }
             type uint32 {
               range "0 .. 63";
             }
           }
         }
         uses apply-advanced;
         leaf secret {
           description "Authentication key";
           type string {
             length "1 .. 126";
           }
         }
         leaf key-name {
           description "Key name in hexadecimal format used for macsec";
           type string {
             length "2 .. 64";
           }
         }
         leaf start-time {
           description "Start time for key transmission (YYYY-MM-DD.HH:MM)";
           type jt:time;
         }
         leaf algorithm {
           description "Authentication algorithm";
           default "md5";
           type enumeration {
             enum "md5" {
               description "Message Digest 5";
             }
             enum "hmac-sha-1" {
               description "Hash-based Message Authentication Code (SHA1) (96 bits)";
             }
           }
         }
         leaf options {
           description "Protocol's transmission encoding format";
           default "basic";
           type enumeration {
             enum "basic" {
               description "Rudimentary encoding format";
             }
             enum "isis-enhanced" {
               description "RFC 5310 based encoding";
             }
           }
         }
       }
     }
   }
   grouping security-dhcpv6-options-type {
     description "Configure DHCPv6 options";
     uses apply-advanced;
     container option-37 {
       presence "enable option-37";
       description "Configure DHCPv6 remote identifier option";
       uses apply-advanced;
       container prefix {
         description "Configure DHCPv6 remote identifier prefix";
         uses apply-advanced;
         leaf host-name {
           description "Prefix router host name to DHCPv6 remote identifier";
           type empty;
         }
         leaf logical-system-name {
           description "Prefix logical system name to DHCPv6 remote identifier";
           type empty;
         }
         leaf routing-instance-name {
           description "Prefix routing instance name to DHCPv6 remote identifier";
           type empty;
         }
         leaf vlan-name {
           description "Prefix vlan name to DHCPv6 remote identifier";
           type empty;
         }
         leaf vlan-id {
           description "Prefix vlan tag to DHCPv6 remote identifier";
           type empty;
         }
       }
       leaf use-interface-mac {
         description "Add incoming interface's MAC address to DHCPv6 remote identifier";
         type empty;
       }
       leaf use-interface-index {
         description "Add interface index to DHCPv6 remote identifier";
         type enumeration {
           enum "logical" {
             description "Use the logical interface index";
           }
           enum "device" {
             description "Use the device interface index";
           }
         }
       }
       leaf use-interface-name {
         description "Add interface name to DHCPv6 remote identifier";
         type enumeration {
           enum "logical" {
             description "Use the logical interface name";
           }
           enum "device" {
             description "Use the device interface name";
           }
         }
       }
       leaf use-interface-description {
         description "Add interface description to DHCPv6 remote identifier";
         type enumeration {
           enum "logical" {
             description "Use the logical interface description";
           }
           enum "device" {
             description "Use the device interface description";
           }
         }
       }
       leaf use-string {
         description "Add custom string to DHCPv6 remote identifier";
         type string;
       }
     }
     container option-18 {
       presence "enable option-18";
       description "Configure DHCPv6 interface identifier option";
       uses apply-advanced;
       container prefix {
         description "Configure DHCPv6 interface identifier prefix";
         uses apply-advanced;
         leaf host-name {
           description "Prefix router host name to DHCPv6 interface identifier";
           type empty;
         }
         leaf logical-system-name {
           description "Prefix logical system name to DHCPv6 interface identifier";
           type empty;
         }
         leaf routing-instance-name {
           description "Prefix routing instance name to DHCPv6 interface identifier";
           type empty;
         }
         leaf vlan-name {
           description "Prefix vlan name to DHCPv6 interface identifier";
           type empty;
         }
         leaf vlan-id {
           description "Prefix vlan tag to DHCPv6 interface identifier";
           type empty;
         }
       }
       leaf use-interface-mac {
         description "Add incoming interface's MAC address to DHCPv6 circuit identifier";
         type empty;
       }
       leaf use-interface-index {
         description "Add interface index to DHCPv6 interface identifier";
         type enumeration {
           enum "logical" {
             description "Use the logical interface index";
           }
           enum "device" {
             description "Use the device interface index";
           }
         }
       }
       leaf use-interface-name {
         description "Add interface name to DHCPv6 remote identifier";
         type enumeration {
           enum "logical" {
             description "Use the logical interface name";
           }
           enum "device" {
             description "Use the device interface name";
           }
         }
       }
       leaf use-interface-description {
         description "Add interface description to DHCPv6 interface identifier";
         type enumeration {
           enum "logical" {
             description "Use the logical interface description";
           }
           enum "device" {
             description "Use the device interface description";
           }
         }
       }
       leaf use-string {
         description "Add custom string to DHCPv6 interface identifier";
         type string;
       }
     }
     container option-16 {
       presence "enable option-16";
       description "Configure DHCPv6 vendor class identifier option. Overwrite if exists";
       uses apply-advanced;
       leaf use-string {
         description "Add custom string to DHCPv6 vendor identifier";
         type string;
       }
     }
     leaf option-79 {
       description "Configure DHCPv6 client link layer address option";
       type empty;
     }
   }
   grouping security-group-vpn {
     uses apply-advanced;
     container member {
       description "Group VPN member configuration";
       uses gvpn-member;
     }
     container server {
       description "Group VPN server configuration";
       uses gvpn-server;
     }
   }
   grouping gvpn-member {
     uses apply-advanced;
     container ike {
       description "Group VPN IKE configuration";
       uses gvpn-member-ike;
     }
     container ipsec {
       description "Group VPN IPsec configuration";
       uses gvpn-member-ipsec-vpn;
     }
   }
   grouping gvpn-member-ike {
     uses apply-advanced;
     container traceoptions {
       description "Trace options for Group VPN Member";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       leaf level {
         description "Level of debugging output";
         default "error";
         type enumeration {
           enum "error" {
             description "Match error conditions";
           }
           enum "warning" {
             description "Match warning messages";
           }
           enum "notice" {
             description "Match conditions that should be handled specially";
           }
           enum "info" {
             description "Match informational messages";
           }
           enum "verbose" {
             description "Match verbose messages";
           }
           enum "all" {
             description "Match all levels";
           }
         }
       }
       list flag {
         key name;
         ordered-by user;
         description "Tracing parameters";
         leaf name {
           type enumeration {
             enum "timer" {
               description "Trace internal timer events";
             }
             enum "routing-socket" {
               description "Trace routing socket messages";
             }
             enum "parse" {
               description "Trace configuration processing";
             }
             enum "config" {
               description "Trace configuration download processing";
             }
             enum "ike" {
               description "Trace IKE module processing";
             }
             enum "policy-manager" {
               description "Trace policy manager processing";
             }
             enum "general" {
               description "Trace general events";
             }
             enum "database" {
               description "Trace security associations database events";
             }
             enum "certificates" {
               description "Trace certificate events";
             }
             enum "snmp" {
               description "Trace SNMP operations";
             }
             enum "thread" {
               description "Trace thread processing";
             }
             enum "high-availability" {
               description "Trace high-availability operations";
             }
             enum "next-hop-tunnels" {
               description "Trace next-hop-tunnels operations";
             }
             enum "all" {
               description "Trace everything";
             }
           }
         }
       }
       container gateway-filter {
         description "Set gateway filter for trace";
         uses apply-advanced;
         leaf local-address {
           description "Use an IP address to identify the local gateway";
           type jt:ipv4addr;
         }
         leaf remote-address {
           description "Use an IP address to identify the remote gateway";
           type jt:ipv4addr;
         }
       }
     }
     list proposal {
       key name;
       ordered-by user;
       description "Define an IKE proposal";
       uses gvpn-member-ike-proposal;
     }
     list policy {
       key name;
       ordered-by user;
       description "Define an IKE policy";
       uses gvpn-ike-policy;
     }
     list gateway {
       key name;
       ordered-by user;
       description "Define an IKE gateway";
       leaf name {
         description "Label for the remote (peer) gateway";
         type string {
           length "1 .. 32";
         }
       }
       uses apply-advanced;
       leaf ike-policy {
         description "Name of the IKE policy";
         type string {
           length "1 .. 32";
         }
       }
       leaf-list server-address {
         ordered-by user;
         description "Server Addresses upto 4";
         type jt:ipv4addr;
         max-elements 4;
       }
       container local-identity {
         description "Set the local IKE identity";
         choice identity-type {
           case case_1 {
             container inet {
               description "Use an IPv4 address";
               uses apply-advanced;
               leaf identity-ipv4 {
                 description "The local IPv4 identity";
                 type jt:ipv4addr;
               }
             }
           }
           case case_2 {
             container hostname {
               description "Use a fully-qualified domain name";
               uses apply-advanced;
               leaf identity-hostname {
                 description "The local hostname";
                 type string;
               }
             }
           }
           case case_3 {
             container user-at-hostname {
               description "Use an e-mail address";
               uses apply-advanced;
               leaf identity-user {
                 description "The local user-FQDN";
                 type string;
               }
             }
           }
         }
       }
       container remote-identity {
         description "Set the remote IKE identity";
         choice identity-type {
           case case_1 {
             container inet {
               description "Use an IPv4 address";
               uses apply-advanced;
               leaf identity-ipv4 {
                 description "The remote IPv4 identity";
                 type jt:ipv4addr;
               }
             }
           }
           case case_2 {
             container hostname {
               description "Use a fully-qualified domain name";
               uses apply-advanced;
               leaf identity-hostname {
                 description "The remote hostname";
                 type string;
               }
             }
           }
           case case_3 {
             container user-at-hostname {
               description "Use an e-mail address";
               uses apply-advanced;
               leaf identity-user {
                 description "The remote user-FQDN";
                 type string;
               }
             }
           }
         }
       }
       leaf local-address {
         description "Local IPv4 address for group member";
         type jt:ipv4addr;
       }
       leaf routing-instance {
         description "Name of routing instance that hosts local address";
         default "default";
         type string;
       }
     }
   }
   grouping gvpn-ike-policy {
     leaf name {
       description "Name of policy";
       type string {
         length "1 .. 32";
       }
     }
     uses apply-advanced;
     leaf mode {
       description "Define the IKE mode for Phase 1";
       default "main";
       type enumeration {
         enum "main" {
           description "Main mode";
         }
         enum "aggressive" {
           description "Aggressive mode";
         }
       }
     }
     leaf description {
       description "Text description of IKE policy";
       type string {
         length "1 .. 80";
       }
     }
     leaf-list proposals {
       ordered-by user;
       description "Name of the proposal";
       type string {
         length "1 .. 32";
       }
     }
     container pre-shared-key {
       description "Define a preshared key";
       choice key-choice {
         case case_1 {
           leaf ascii-text {
             description "Format as text";
             type string {
               length "1 .. 255";
             }
           }
         }
         case case_2 {
           leaf hexadecimal {
             description "Format as hexadecimal";
             type string {
               length "1 .. 255";
             }
           }
         }
       }
     }
   }
   grouping gvpn-member-ike-proposal {
     leaf name {
       description "Name of the IKE proposal";
       type string {
         length "1 .. 32";
       }
     }
     uses apply-advanced;
     leaf description {
       description "Text description of IKE proposal";
       type string {
         length "1 .. 80";
       }
     }
     leaf authentication-method {
       description "Define authentication method";
       type enumeration {
         enum "pre-shared-keys" {
           description "Preshared keys";
         }
       }
     }
     leaf dh-group {
       description "Define Diffie-Hellman group";
       type enumeration {
         enum "group14" {
           description "Diffie-Hellman Group 14";
         }
         enum "group24" {
           description "Diffie-Hellman Group 24";
         }
       }
     }
     leaf authentication-algorithm {
       description "Define authentication algorithm";
       type enumeration {
         enum "sha-256" {
           description "SHA 256-bit authentication algorithm";
         }
         enum "sha-384" {
           description "SHA 384-bit authentication algorithm";
         }
       }
     }
     leaf encryption-algorithm {
       description "Define encryption algorithm";
       type enumeration {
         enum "aes-128-cbc" {
           description "AES-CBC 128-bit encryption algorithm";
         }
         enum "aes-192-cbc" {
           description "AES-CBC 192-bit encryption algorithm";
         }
         enum "aes-256-cbc" {
           description "AES-CBC 256-bit encryption algorithm";
         }
       }
     }
     leaf lifetime-seconds {
       description "Lifetime, in seconds";
       default "180";
       units "seconds";
       type union {
         type string {
           pattern "<.*>|$.*";
         }
         type uint32 {
           range "180 .. 86400";
         }
       }
     }
   }
   grouping gvpn-member-ipsec-vpn {
     uses apply-advanced;
     list vpn {
       key name;
       ordered-by user;
       description "Define an IPSec VPN";
       uses ipsec-gvpn-member-template;
     }
   }
   grouping gvpn-server {
     uses apply-advanced;
     container traceoptions {
       description "Trace options for Group VPN debug";
       uses gvpn-server-traceoptions;
     }
     container ike {
       description "Group VPN IKE configuration";
       uses gvpn-server-ike;
     }
     container ipsec {
       description "Group VPN IPsec configuration";
       uses gvpn-server-ipsec-vpn;
     }
     list group {
       key name;
       ordered-by user;
       description "Define a Group VPN group";
       max-elements 50;
       uses gvpn-server-group-template;
     }
   }
   grouping gvpn-server-group-template {
     description "Configure a Group VPN group";
     leaf name {
       description "Name of the group";
       type string {
         length "1 .. 32";
       }
     }
     uses apply-advanced;
     leaf description {
       description "Text description of Group VPN group";
       type string {
         length "1 .. 80";
       }
     }
     leaf group-id {
       description "Enable Group VPN by defining group id";
       type union {
         type string {
           pattern "<.*>|$.*";
         }
         type uint32 {
           range "1 .. 4294967295";
         }
       }
     }
     leaf member-threshold {
       description "Maximum number of members in this group";
       type union {
         type uint32;
         type string {
           pattern "<.*>|$.*";
         }
       }
     }
     container server-cluster {
       description "Enable server cluster for this group";
       uses gvpn-server-cluster;
     }
     list ike-gateway {
       key name;
       ordered-by user;
       description "Name of the IKE gateway";
       uses gvpn-server-ike-gateway;
     }
     leaf activation-time-delay {
       description "Configure delay in seconds for Group VPN key activation";
       status deprecated;
       default "15";
       type union {
         type string {
           pattern "<.*>|$.*";
         }
         type uint32 {
           range "10 .. 900";
         }
       }
     }
     leaf anti-replay-time-window {
       description "Configure Anti Replay time in milliseconds";
       type union {
         type string {
           pattern "<.*>|$.*";
         }
         type uint32 {
           range "1 .. 60000";
         }
       }
     }
     container server-member-communication {
       description "Configure Server to Member communication parameters";
       uses gvpn-server-member-communication;
     }
     list ipsec-sa {
       key name;
       ordered-by user;
       description "Define a Group VPN group SA";
       uses gvpn-server-group-ipsecsa;
     }
   }
   grouping gvpn-server-cluster {
     description "Server-Cluster for group VPN";
     uses apply-advanced;
     leaf server-role {
       description "Primary or backup server";
       type enumeration {
         enum "root-server" {
           description "Root-server";
         }
         enum "sub-server" {
           description "Sub-server";
         }
       }
     }
     list ike-gateway {
       key name;
       ordered-by user;
       description "Name of the IKE gateway";
       uses gvpn-server-ike-gateway-sc;
     }
     leaf retransmission-period {
       description "Configure retransmission period in seconds Default :10";
       default "10";
       type union {
         type string {
           pattern "<.*>|$.*";
         }
         type uint32 {
           range "2 .. 60";
         }
       }
     }
   }
   grouping gvpn-server-group-ipsecsa {
     description "Configure a Group VPN group SA";
     leaf name {
       description "Name of the SA";
       type string {
         length "1 .. 32";
       }
     }
     uses apply-advanced;
     leaf proposal {
       description "Name of the IPsec proposal";
       type string {
         length "1 .. 32";
       }
     }
     list match-policy {
       key name;
       ordered-by user;
       description "Configure a Group VPN group SA";
       max-elements 10;
       uses gvpn-server-group-ipsecsa-match;
     }
   }
   grouping gvpn-server-group-ipsecsa-match {
     description "Configure a Group VPN group SA policy";
     leaf name {
       description "Name of the policy";
       type string {
         length "1 .. 32";
       }
     }
     uses apply-advanced;
     leaf source {
       description "Specify the source IP address to be matched (0.0.0.0/0 for any)";
       type jt:ipv4prefix-mandatory;
     }
     leaf destination {
       description "Specify the destination IP address to be matched (0.0.0.0/0 for any)";
       type jt:ipv4prefix-mandatory;
     }
     leaf source-port {
       description "Specify the source port to be matched (0 for any)";
       type union {
         type string {
           pattern "<.*>|$.*";
         }
         type uint32 {
           range "0 .. 65535";
         }
       }
     }
     leaf destination-port {
       description "Specify the destination port to be matched (0 for any)";
       type union {
         type string {
           pattern "<.*>|$.*";
         }
         type uint32 {
           range "0 .. 65535";
         }
       }
     }
     leaf protocol {
       description "Specify the protocol number to be matched (0 for any)";
       type union {
         type string {
           pattern "<.*>|$.*";
         }
         type uint32 {
           range "0 .. 254";
         }
       }
     }
   }
   grouping gvpn-server-ike {
     uses apply-advanced;
     list proposal {
       key name;
       ordered-by user;
       description "Define an IKE proposal";
       uses gvpn-server-ike-proposal;
     }
     list policy {
       key name;
       ordered-by user;
       description "Define an IKE policy";
       uses gvpn-ike-policy;
     }
     list gateway {
       key name;
       ordered-by user;
       description "Define an IKE gateway";
       leaf name {
         description "Label for the remote (peer) gateway";
         type string {
           length "1 .. 32";
         }
       }
       uses apply-advanced;
       leaf ike-policy {
         description "Name of the IKE policy";
         type string {
           length "1 .. 32";
         }
       }
       choice remote-identifier {
         case case_1 {
           leaf address {
             description "IP address of peer";
             type string {
               length "1 .. 32";
             }
           }
         }
         case case_2 {
           container dynamic {
             description "Site to site peer with dynamic IP address";
             uses apply-advanced;
             choice remote-id-type {
               case case_1 {
                 leaf hostname {
                   description "Use a fully-qualified domain name";
                   type string;
                 }
               }
               case case_2 {
                 leaf inet {
                   description "Use an IPV4 address to identify the dynamic peer";
                   type jt:ipv4addr;
                 }
               }
               case case_3 {
                 leaf user-at-hostname {
                   description "Use an e-mail address";
                   type string;
                 }
               }
             }
           }
         }
       }
       container dead-peer-detection {
         presence "enable dead-peer-detection";
         description "Enable Dead Peer Detection between group-server-cluster servers";
         uses apply-advanced;
         choice mode {
           case case_1 {
             leaf always-send {
               description "Send probes periodically regardless of incoming and outgoing data traffic ";
               type empty;
             }
           }
         }
         leaf interval {
           description "The time between DPD probe messages  Default :10";
           default "10";
           units "seconds";
           type union {
             type string {
               pattern "<.*>|$.*";
             }
             type uint32 {
               range "10 .. 60";
             }
           }
         }
         leaf threshold {
           description "Maximum number of DPD retransmissions Default :5";
           default "5";
           type union {
             type string {
               pattern "<.*>|$.*";
             }
             type uint32 {
               range "1 .. 5";
             }
           }
         }
       }
       container local-identity {
         description "Set the local IKE identity";
         choice identity-type {
           case case_1 {
             container inet {
               description "Use an IPv4 address";
               uses apply-advanced;
               leaf identity-ipv4 {
                 description "The local IPv4 identity";
                 type jt:ipv4addr;
               }
             }
           }
           case case_2 {
             container hostname {
               description "Use a fully-qualified domain name";
               uses apply-advanced;
               leaf identity-hostname {
                 description "The local hostname";
                 type string;
               }
             }
           }
           case case_3 {
             container user-at-hostname {
               description "Use an e-mail address";
               uses apply-advanced;
               leaf identity-user {
                 description "The local user-FQDN";
                 type string;
               }
             }
           }
         }
       }
       container remote-identity {
         description "Set the remote IKE identity";
         choice identity-type {
           case case_1 {
             container inet {
               description "Use an IPv4 address";
               uses apply-advanced;
               leaf identity-ipv4 {
                 description "The remote IPv4 identity";
                 type jt:ipv4addr;
               }
             }
           }
           case case_2 {
             container hostname {
               description "Use a fully-qualified domain name";
               uses apply-advanced;
               leaf identity-hostname {
                 description "The remote hostname";
                 type string;
               }
             }
           }
           case case_3 {
             container user-at-hostname {
               description "Use an e-mail address";
               uses apply-advanced;
               leaf identity-user {
                 description "The remote user-FQDN";
                 type string;
               }
             }
           }
         }
       }
       leaf local-address {
         description "Local IP address for IKE negotiations";
         type jt:ipaddr;
       }
       leaf routing-instance {
         description "Name of routing instance that hosts local address";
         default "default";
         type string;
       }
     }
   }
   grouping gvpn-server-ike-gateway {
     description "Configure a set of IKE gateways";
     leaf name {
       description "Name of the IKE gateway";
       type string {
         length "1 .. 32";
       }
     }
     uses apply-advanced;
   }
   grouping gvpn-server-ike-gateway-sc {
     description "Configure a set of IKE gateways";
     leaf name {
       description "Name of the IKE gateway";
       type string {
         length "1 .. 32";
       }
     }
     uses apply-advanced;
   }
   grouping gvpn-server-ike-proposal {
     leaf name {
       description "Name of the IKE proposal";
       type string {
         length "1 .. 32";
       }
     }
     uses apply-advanced;
     leaf description {
       description "Text description of IKE proposal";
       type string {
         length "1 .. 80";
       }
     }
     leaf authentication-method {
       description "Define authentication method";
       type enumeration {
         enum "pre-shared-keys" {
           description "Preshared keys";
         }
       }
     }
     leaf authentication-algorithm {
       description "Define authentication algorithm";
       type enumeration {
         enum "sha-256" {
           description "SHA 256-bit authentication algorithm";
         }
         enum "sha-384" {
           description "SHA 384-bit authentication algorithm";
         }
       }
     }
     leaf dh-group {
       description "Define Diffie-Hellman group";
       type enumeration {
         enum "group14" {
           description "Diffie-Hellman Group 14";
         }
         enum "group24" {
           description "Diffie-Hellman Group 24";
         }
       }
     }
     leaf encryption-algorithm {
       description "Define encryption algorithm";
       type enumeration {
         enum "aes-128-cbc" {
           description "AES-CBC 128-bit encryption algorithm";
         }
         enum "aes-192-cbc" {
           description "AES-CBC 192-bit encryption algorithm";
         }
         enum "aes-256-cbc" {
           description "AES-CBC 256-bit encryption algorithm";
         }
       }
     }
   }
   grouping gvpn-server-ipsec-vpn {
     uses apply-advanced;
     list proposal {
       key name;
       ordered-by user;
       description "Define an IPSec proposal";
       uses gvpn-server-ipsec-proposal;
     }
   }
   grouping gvpn-server-ipsec-proposal {
     leaf name {
       description "Name of the IPSec proposal";
       type string {
         length "1 .. 32";
       }
     }
     uses apply-advanced;
     leaf description {
       description "Text description of IPSec proposal";
       type string {
         length "1 .. 80";
       }
     }
     leaf authentication-algorithm {
       description "Define authentication algorithm";
       type enumeration {
         enum "hmac-sha-256-128" {
           description "HMAC-SHA-256-128 authentication algorithm";
         }
       }
     }
     leaf encryption-algorithm {
       description "Define encryption algorithm";
       type enumeration {
         enum "aes-128-cbc" {
           description "AES-CBC 128-bit encryption algorithm";
         }
         enum "aes-192-cbc" {
           description "AES-CBC 192-bit encryption algorithm";
         }
         enum "aes-256-cbc" {
           description "AES-CBC 256-bit encryption algorithm";
         }
       }
     }
     leaf lifetime-seconds {
       description "Lifetime, in seconds";
       units "seconds";
       type union {
         type string {
           pattern "<.*>|$.*";
         }
         type uint32 {
           range "180 .. 86400";
         }
       }
     }
   }
   grouping gvpn-server-member-communication {
     description "Group VPN Server to Member communication";
     uses apply-advanced;
     leaf communication-type {
       description "Define type of server member communication";
       type enumeration {
         enum "unicast" {
           description "Unicast";
         }
       }
     }
     leaf lifetime-seconds {
       description "Configure lifetime in seconds";
       default "3600";
       type union {
         type string {
           pattern "<.*>|$.*";
         }
         type uint32 {
           range "300 .. 86400";
         }
       }
     }
     leaf retransmission-period {
       description "Configure retransmission period in seconds";
       default "10";
       type union {
         type string {
           pattern "<.*>|$.*";
         }
         type uint32 {
           range "2 .. 60";
         }
       }
     }
     leaf number-of-retransmission {
       description "Configure maximum number of retransmission attempts";
       default "2";
       type union {
         type string {
           pattern "<.*>|$.*";
         }
         type uint32 {
           range "0 .. 60";
         }
       }
     }
     leaf heartbeat {
       description "Configure heartbeat period in seconds";
       status deprecated;
       default "300";
       type union {
         type string {
           pattern "<.*>|$.*";
         }
         type uint32 {
           range "60 .. 3600";
         }
       }
     }
     leaf encryption-algorithm {
       description "Define encryption algorithm";
       type enumeration {
         enum "aes-128-cbc" {
           description "AES-CBC 128-bit encryption algorithm";
         }
         enum "aes-192-cbc" {
           description "AES-CBC 192-bit encryption algorithm";
         }
         enum "aes-256-cbc" {
           description "AES-CBC 256-bit encryption algorithm";
         }
       }
     }
     leaf sig-hash-algorithm {
       description "Define sig-hash algorithm";
       type enumeration {
         enum "sha-256" {
           description "SHA 256-bit sig-hash algorithm";
         }
         enum "sha-384" {
           description "SHA 384-bit sig-hash algorithm";
         }
       }
     }
     leaf certificate {
       description "Certificate identifier";
       type string {
       }
     }
   }
   grouping gvpn-server-traceoptions {
     description "Group VPN server tracing options";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing parameters for GKSD";
       leaf name {
         type enumeration {
           enum "timer" {
             description "Trace internal timer events";
           }
           enum "routing-socket" {
             description "Trace routing socket messages";
           }
           enum "parse" {
             description "Trace configuration processing";
           }
           enum "config" {
             description "Trace configuration download processing";
           }
           enum "ike" {
             description "Trace IKE module processing";
           }
           enum "policy-manager" {
             description "Trace policy manager processing";
           }
           enum "general" {
             description "Trace general events";
           }
           enum "database" {
             description "Trace security associations database events";
           }
           enum "certificates" {
             description "Trace certificate events";
           }
           enum "snmp" {
             description "Trace SNMP operations";
           }
           enum "thread" {
             description "Trace thread processing";
           }
           enum "high-availability" {
             description "Trace high-availability operations";
           }
           enum "next-hop-tunnels" {
             description "Trace next-hop-tunnels operations";
           }
           enum "all" {
             description "Trace everything";
           }
         }
       }
     }
     container gateway-filter {
       description "Set gateway filter for trace";
       uses apply-advanced;
       leaf local-address {
         description "Use an IPV4 address to identify the local gateway";
         type jt:ipv4addr;
       }
       leaf remote-address {
         description "Use an IPV4 address to identify the remote gateway";
         type jt:ipv4addr;
       }
     }
   }
   grouping ipsec-gvpn-member-template {
     description "Configure a Group VPN";
     leaf name {
       description "Name of the VPN";
       type string {
         length "1 .. 32";
       }
     }
     uses apply-advanced;
     leaf ike-gateway {
       description "Name of IKE gateway";
       type string {
         length "1 .. 32";
       }
     }
     leaf group-vpn-external-interface {
       description "External interface for Group VPN";
       type union {
         type jt:interface-name;
         type string {
           pattern "<.*>|$.*";
         }
       }
     }
     leaf group {
       description "Enable Group VPN by defining group id";
       type union {
         type string {
           pattern "<.*>|$.*";
         }
         type uint32 {
           range "1 .. 4294967295";
         }
       }
     }
     leaf heartbeat-threshold {
       description "Define heartbeat threshold for Group VPN";
       status deprecated;
       default "3";
       type union {
         type string {
           pattern "<.*>|$.*";
         }
         type uint32 {
           range "0 .. 10";
         }
       }
     }
     leaf recovery-probe {
       description "Enable triggering recovery probe mechanism";
       type empty;
     }
     leaf df-bit {
       description "Specifies how to handle the Don't Fragment bit";
       default "clear";
       type enumeration {
         enum "clear" {
           description "Clear DF bit of outer header";
         }
         enum "set" {
           description "Set DF bit of outer header";
         }
         enum "copy" {
           description "Copy DF bit from inner header";
         }
       }
     }
     container fail-open {
       description "List of fail open rules";
       uses ipsec_gvpn_fail_open_rule_object;
     }
     container exclude {
       description "List of exclude rules";
       uses ipsec_gvpn_exclude_rule_object;
     }
   }
   grouping ipsec_gvpn_exclude_rule_object {
     uses apply-advanced;
     list rule {
       key name;
       ordered-by user;
       description "Define exlude rules upto 10";
       max-elements 10;
       uses ipsec_gvpn_rule_address_object;
     }
   }
   grouping ipsec_gvpn_fail_open_rule_object {
     uses apply-advanced;
     list rule {
       key name;
       ordered-by user;
       description "Define fail open rules upto 10";
       max-elements 10;
       uses ipsec_gvpn_rule_address_object;
     }
   }
   grouping ipsec_gvpn_rule_address_object {
     leaf name {
       description "Rule name";
       type string {
         length "1 .. 63";
       }
     }
     uses apply-advanced;
     container source-address {
       description "Match IP source address";
       presence "enable source-address";
       uses ipsec_gvpn_addr_object;
     }
     container destination-address {
       description "Match IP destination address";
       presence "enable destination-address";
       uses ipsec_gvpn_addr_object;
     }
     leaf application {
       description "Match application";
       type string;
     }
   }
   grouping ipsec_gvpn_addr_object {
     uses apply-advanced;
     leaf address {
       description "Prefix to match";
       type jt:ipv4prefix-only;
     }
   }
   grouping security-ike {
     uses apply-advanced;
     container traceoptions {
       description "Trace options for IPSec key management";
       uses security-traceoptions;
     }
     container respond-bad-spi {
       presence "enable respond-bad-spi";
       description "Respond to IPSec packets with bad SPI values";
       leaf max-responses {
         description "Maximum number of times to respond";
         default "5";
         type union {
           type string {
             pattern "<.*>|$.*";
           }
           type uint32 {
             range "1 .. 30";
           }
         }
       }
     }
     list proposal {
       key name;
       ordered-by user;
       description "Define an IKE proposal";
       uses ike-proposal;
     }
     list policy {
       key name;
       ordered-by user;
       description "Define an IKE policy";
       uses ike-policy;
     }
     list gateway {
       key name;
       ordered-by user;
       description "Define an IKE gateway";
       leaf name {
         description "Label for the remote (peer) gateway";
         type string {
           length "1 .. 32";
         }
       }
       uses apply-advanced;
       leaf ike-policy {
         description "Name of the IKE policy";
         type string {
           length "1 .. 32";
         }
       }
       choice remote-identifier {
         case case_1 {
           leaf-list address {
             ordered-by user;
             description "Addresses or hostnames of peer:1 primary, upto 4 backups";
             type string;
           }
         }
         case case_2 {
           container dynamic {
             description "Site to site peer with dynamic IP address";
             uses apply-advanced;
             choice remote-id-type {
               case case_1 {
                 container distinguished-name {
                   presence "enable distinguished-name";
                   description "Use a distinguished name: ";
                   uses apply-advanced;
                   choice name-type {
                     case case_1 {
                       leaf container {
                         description "Specify the container string";
                         type string;
                       }
                     }
                     case case_2 {
                       leaf wildcard {
                         description "Specify the wildcard string";
                         type string;
                       }
                     }
                   }
                 }
               }
               case case_2 {
                 leaf hostname {
                   description "Use a fully-qualified domain name";
                   type string;
                 }
               }
               case case_3 {
                 leaf inet {
                   description "Use an IPV4 address to identify the dynamic peer";
                   type jt:ipv4addr;
                 }
               }
               case case_4 {
                 leaf inet6 {
                   description "Use an IPV6 address to identify the dynamic peer";
                   type jt:ipv6addr;
                 }
               }
               case case_5 {
                 leaf user-at-hostname {
                   description "Use an e-mail address";
                   type string;
                 }
               }
             }
             leaf connections-limit {
               description "Maximum number of users connected to gateway";
               type union {
                 type uint32;
                 type string {
                   pattern "<.*>|$.*";
                 }
               }
             }
             leaf ike-user-type {
               description "Type of the IKE ID";
               type enumeration {
                 enum "group-ike-id" {
                   description "Email address or FQDN shared as IKED ID by multiple users";
                 }
                 enum "shared-ike-id" {
                   description "Email address shared as IKED ID by multiple users";
                 }
               }
             }
             leaf reject-duplicate-connection {
               description "Reject new connection from duplicate IKE-id";
               type empty;
             }
           }
         }
       }
       container dead-peer-detection {
         presence "enable dead-peer-detection";
         description "Enable Dead Peer Detection ";
         uses apply-advanced;
         choice mode {
           case case_1 {
             leaf optimized {
               description "Send probes only when there is outgoing and no incoming data traffic - RFC3706 (Default mode)";
               type empty;
             }
           }
           case case_2 {
             leaf probe-idle-tunnel {
               description "Send probes same as in optimized mode and also when there is no outgoing & incoming data traffic";
               type empty;
             }
           }
           case case_3 {
             leaf always-send {
               description "Send probes periodically regardless of incoming and outgoing data traffic ";
               type empty;
             }
           }
         }
         leaf interval {
           description "The time between DPD probe messages  Default :10";
           default "10";
           units "seconds";
           type union {
             type string {
               pattern "<.*>|$.*";
             }
             type uint32 {
               range "2 .. 60";
             }
           }
         }
         leaf threshold {
           description "Maximum number of DPD retransmissions Default :5";
           default "5";
           type union {
             type string {
               pattern "<.*>|$.*";
             }
             type uint32 {
               range "1 .. 5";
             }
           }
         }
       }
       leaf no-nat-traversal {
         description "Disable IPSec NAT traversal";
         type empty;
       }
       leaf nat-keepalive {
         description "Interval at which to send NAT keepalives";
         default "20";
         units "seconds";
         type union {
           type string {
             pattern "<.*>|$.*";
           }
           type uint32 {
             range "1 .. 300";
           }
         }
       }
       container local-identity {
         description "Set the local IKE identity";
         choice identity-type {
           case case_1 {
             container inet {
               description "Use an IPv4 address";
               uses apply-advanced;
               leaf identity-ipv4 {
                 description "The local IPv4 identity";
                 type jt:ipv4addr;
               }
             }
           }
           case case_2 {
             container inet6 {
               description "Use an IPv6 address";
               uses apply-advanced;
               leaf identity-ipv6 {
                 description "The local IPv6 identity";
                 type jt:ipv6addr;
               }
             }
           }
           case case_3 {
             container hostname {
               description "Use a fully-qualified domain name";
               uses apply-advanced;
               leaf identity-hostname {
                 description "The local hostname";
                 type string;
               }
             }
           }
           case case_4 {
             container user-at-hostname {
               description "Use an e-mail address";
               uses apply-advanced;
               leaf identity-user {
                 description "The local user-FQDN";
                 type string;
               }
             }
           }
           case case_5 {
             leaf distinguished-name {
               description "Use a distinguished name specified in local certificate";
               type empty;
             }
           }
           case case_6 {
             container key-id {
               description "Key ID identification values in ASCII string";
               uses apply-advanced;
               leaf string-key-id {
                 description "Key ID in ASCII string";
                 type string {
                   length "1 .. 127";
                 }
               }
             }
           }
         }
       }
       container remote-identity {
         description "Set the remote IKE identity";
         choice identity-type {
           case case_1 {
             container inet {
               description "Use an IPv4 address";
               uses apply-advanced;
               leaf identity-ipv4 {
                 description "The remote IPv4 identity";
                 type jt:ipv4addr;
               }
             }
           }
           case case_2 {
             container inet6 {
               description "Use an IPv6 address";
               uses apply-advanced;
               leaf identity-ipv6 {
                 description "The remote IPv6 identity";
                 type jt:ipv6addr;
               }
             }
           }
           case case_3 {
             container hostname {
               description "Use a fully-qualified domain name";
               uses apply-advanced;
               leaf identity-hostname {
                 description "The remote hostname";
                 type string;
               }
             }
           }
           case case_4 {
             container user-at-hostname {
               description "Use an e-mail address";
               uses apply-advanced;
               leaf identity-user {
                 description "The remote user-FQDN";
                 type string;
               }
             }
           }
           case case_5 {
             container distinguished-name {
               presence "enable distinguished-name";
               description "Use a distinguished name: ";
               uses apply-advanced;
               leaf container {
                 description "Specify the container string";
                 type string;
               }
               leaf wildcard {
                 description "Specify the wildcard string";
                 type string;
               }
             }
           }
           case case_6 {
             container key-id {
               description "Key ID identification values in string";
               uses apply-advanced;
               leaf string-key-id {
                 description "Key ID in ASCII string";
                 type string {
                   length "1 .. 127";
                 }
               }
             }
           }
         }
       }
       leaf external-interface {
         description "External interface for IKE negotiations";
         type union {
           type jt:interface-unit;
           type string {
             pattern "<.*>|$.*";
           }
         }
       }
       leaf local-address {
         description "Local IP address for IKE negotiations";
         type jt:ipaddr;
       }
       container aaa {
         description "Use extended authentication";
         uses apply-advanced;
         leaf access-profile {
           description "Access profile that contains authentication information";
           type string;
         }
         container client {
           description "AAA client info for authentication";
           leaf username {
             description "AAA client username with 1 to 128 characters";
             type string {
               length "1 .. 128";
             }
           }
           leaf password {
             description "AAA client password with 1 to 128 characters";
             type string {
               length "1 .. 128";
             }
           }
         }
       }
       container xauth {
         description "Use extended authentication";
         status deprecated;
         uses apply-advanced;
         leaf access-profile {
           description "Access profile that contains authentication information";
           type string;
         }
         container client {
           description "Xauth client info for authentication";
           leaf username {
             description "XAuth client username with 1 to 128 characters";
             type string {
               length "1 .. 128";
             }
           }
           leaf password {
             description "XAuth client password with 1 to 128 characters";
             type string {
               length "1 .. 128";
             }
           }
         }
       }
       leaf general-ikeid {
         description "Accept peer IKE-ID in general";
         type empty;
       }
       container advpn {
         description "Enable Auto Discovery VPN";
         presence "enable advpn";
         uses advpn-suggester-partner;
       }
       leaf version {
         description "Negotiate using either IKE v1 or IKE v2 protocol";
         default "v1-only";
         type enumeration {
           enum "v1-only" {
             description "The connection must be initiated using IKE version 1";
           }
           enum "v2-only" {
             description "The connection must be initiated using IKE version 2";
           }
         }
       }
       container fragmentation {
         description "IKEv2 fragmentation configuration";
         uses apply-advanced;
         leaf disable {
           description "Disable IKEv2 fragmentation";
           type empty;
         }
         leaf size {
           description "Default 576 bytes for ipv4 and 1280 bytes for ipv6";
           type union {
             type string {
               pattern "<.*>|$.*";
             }
             type uint32 {
               range "570 .. 1320";
             }
           }
         }
       }
       leaf tcp-encap-profile {
         description "Ike over tcp profile name";
         type string;
       }
     }
   }
   grouping advpn-suggester-partner {
     description "Configure ADVPN Suggester Partner";
     uses apply-advanced;
     container suggester {
       presence "enable suggester";
       description "Configure Shortcut Suggester parameters";
       uses apply-advanced;
       leaf disable {
         description "Disable Suggester capability";
         type empty;
       }
     }
     container partner {
       presence "enable partner";
       description "Configure Shortcut Partner parameters";
       uses apply-advanced;
       leaf connection-limit {
         description "Maximum number of shortcut connections (default: varies per platform)";
         type union {
           type uint32;
           type string {
             pattern "<.*>|$.*";
           }
         }
       }
       leaf idle-time {
         description "The duration (in sec) after which shortcut is torn down (default: 300 sec)";
         default "300";
         units "seconds";
         type union {
           type string {
             pattern "<.*>|$.*";
           }
           type uint32 {
             range "60 .. 86400";
           }
         }
       }
       leaf idle-threshold {
         description "The packet rate below which shortcut is torn down (default: 5 packets/sec)";
         default "5";
         type union {
           type string {
             pattern "<.*>|$.*";
           }
           type uint32 {
             range "3 .. 5000";
           }
         }
       }
       leaf disable {
         description "Disable Partner capability";
         type empty;
       }
     }
   }
   grouping ike-policy {
     leaf name {
       description "Name of policy";
       type string {
         length "1 .. 32";
       }
     }
     uses apply-advanced;
     leaf mode {
       description "Define the IKE mode for Phase 1";
       default "main";
       type enumeration {
         enum "main" {
           description "Main mode";
         }
         enum "aggressive" {
           description "Aggressive mode";
         }
       }
     }
     leaf reauth-frequency {
       description "Re-auth Peer after reauth-frequency times hard lifetime. (0-100) Default:0=Disabled";
       default "0";
       type union {
         type string {
           pattern "<.*>|$.*";
         }
         type uint32 {
           range "0 .. 100";
         }
       }
     }
     leaf description {
       description "Text description of IKE policy";
       type string {
         length "1 .. 80";
       }
     }
     leaf-list proposals {
       ordered-by user;
       description "Name of the proposal";
       type string {
         length "1 .. 32";
       }
     }
     container certificate {
       description "Certificate configuration";
       uses apply-advanced;
       leaf local-certificate {
         description "Local certificate identifier";
         type string {
         }
       }
       container trusted-ca {
         description "Specify the CA to use";
         choice ca {
           case case_1 {
             leaf ca-index {
               description "Index of the preferred CA to use";
               status deprecated;
               type union {
                 type uint32;
                 type string {
                   pattern "<.*>|$.*";
                 }
               }
             }
           }
           case case_2 {
             leaf use-all {
               description "Use all configured CAs";
               status deprecated;
               type empty;
             }
           }
           case case_3 {
             leaf ca-profile {
               description "Name of the preferred CA to use";
               type string;
             }
           }
           case case_4 {
             leaf trusted-ca-group {
               description "Name of the preferred CA group to use";
               type string;
             }
           }
         }
       }
       leaf peer-certificate-type {
         description "Preferred type of certificate from peer";
         default "x509-signature";
         type enumeration {
           enum "pkcs7" {
             description "PKCS7 encoding";
           }
           enum "x509-signature" {
             description "X509 signature encoding";
           }
         }
       }
       leaf-list policy-oids {
         ordered-by user;
         description "Certificate policy object identifiers (maximum 5)";
         type string {
           length "1 .. 63";
         }
         max-elements 5;
       }
     }
     leaf proposal-set {
       description "Types of default IKE proposal-set";
       type enumeration {
         enum "basic" {
           description "IKE proposal-set for basic";
         }
         enum "compatible" {
           description "IKE proposal-set for compatible";
         }
         enum "standard" {
           description "IKE proposal-set for standard";
         }
         enum "suiteb-gcm-128" {
           description "IKE proposal-set for Suite-B-GCM-128";
         }
         enum "suiteb-gcm-256" {
           description "IKE proposal-set for Suite-B-GCM-256";
         }
       }
     }
     container pre-shared-key {
       description "Define a preshared key";
       choice key-choice {
         case case_1 {
           leaf ascii-text {
             description "Format as text";
             type string {
               length "1 .. 255";
             }
           }
         }
         case case_2 {
           leaf hexadecimal {
             description "Format as hexadecimal";
             type string {
               length "1 .. 255";
             }
           }
         }
       }
     }
   }
   grouping ike-proposal {
     leaf name {
       description "Name of the IKE proposal";
       type string {
         length "1 .. 32";
       }
     }
     uses apply-advanced;
     leaf description {
       description "Text description of IKE proposal";
       type string {
         length "1 .. 80";
       }
     }
     leaf authentication-method {
       description "Define authentication method";
       type enumeration {
         enum "pre-shared-keys" {
           description "Preshared keys";
         }
         enum "rsa-signatures" {
           description "RSA signatures";
         }
         enum "dsa-signatures" {
           description "DSA signatures";
         }
         enum "ecdsa-signatures-256" {
           description "ECDSA signatures (256 bit modulus)";
         }
         enum "ecdsa-signatures-384" {
           description "ECDSA signatures (384 bit modulus)";
         }
       }
     }
     leaf dh-group {
       description "Define Diffie-Hellman group";
       type enumeration {
         enum "group1" {
           description "Diffie-Hellman Group 1";
         }
         enum "group2" {
           description "Diffie-Hellman Group 2";
         }
         enum "group5" {
           description "Diffie-Hellman Group 5";
         }
         enum "group14" {
           description "Diffie-Hellman Group 14";
         }
         enum "group15" {
           description "Diffie-Hellman Group 15";
         }
         enum "group16" {
           description "Diffie-Hellman Group 16";
         }
         enum "group19" {
           description "Diffie-Hellman Group 19";
         }
         enum "group20" {
           description "Diffie-Hellman Group 20";
         }
         enum "group24" {
           description "Diffie-Hellman Group 24";
         }
       }
     }
     leaf authentication-algorithm {
       description "Define authentication algorithm";
       type enumeration {
         enum "md5" {
           description "MD5 authentication algorithm";
         }
         enum "sha1" {
           description "SHA1 authentication algorithm";
         }
         enum "sha-256" {
           description "SHA 256-bit authentication algorithm";
         }
         enum "sha-384" {
           description "SHA 384-bit authentication algorithm";
         }
       }
     }
     leaf encryption-algorithm {
       description "Define encryption algorithm";
       type enumeration {
         enum "des-cbc" {
           description "DES-CBC encryption algorithm";
         }
         enum "3des-cbc" {
           description "3DES-CBC encryption algorithm";
         }
         enum "aes-128-cbc" {
           description "AES-CBC 128-bit encryption algorithm";
         }
         enum "aes-192-cbc" {
           description "AES-CBC 192-bit encryption algorithm";
         }
         enum "aes-256-cbc" {
           description "AES-CBC 256-bit encryption algorithm";
         }
         enum "aes-128-gcm" {
           description "AES-GCM 128-bit encryption algorithm";
         }
         enum "aes-256-gcm" {
           description "AES-GCM 256-bit encryption algorithm";
         }
       }
     }
     leaf lifetime-seconds {
       description "Lifetime, in seconds";
       units "seconds";
       type union {
         type string {
           pattern "<.*>|$.*";
         }
         type uint32 {
           range "180 .. 86400";
         }
       }
     }
   }
   grouping security-ipsec-policies {
     uses apply-advanced;
     list from-zone {
       key "from-zone-name to-zone";
       ordered-by user;
       description "Define ipsec policy context";
       uses security-ipsec-policy;
     }
   }
   grouping security-ipsec-policy {
     leaf from-zone-name {
       description "Incoming zone";
       type string {
         length "1 .. 63";
       }
     }
     leaf to-zone {
       description "Outgoing zone";
       type string {
         length "1 .. 63";
       }
     }
     uses apply-advanced;
     leaf ipsec-group-vpn {
       description "Group VPN name";
       type string {
         length "1 .. 32";
       }
     }
   }
   grouping security-ipsec-vpn {
     uses apply-advanced;
     container internal {
       presence "enable internal";
       description "Define an IPSec SA for internal RE-RE communication";
       uses apply-advanced;
       container security-association {
         description "Define an IPsec security association";
         presence "enable security-association";
         uses ipsec-internal-sa;
       }
     }
     container traceoptions {
       description "Trace options for IPSec data-plane debug";
       uses ipsec-traceoptions;
     }
     container vpn-monitor-options {
       description "Global options for VPN liveliness monitoring";
       presence "enable vpn-monitor-options";
       uses ipsec-vpn-monitor;
     }
     list proposal {
       key name;
       ordered-by user;
       description "Define an IPSec proposal";
       uses ipsec-proposal;
     }
     list policy {
       key name;
       ordered-by user;
       description "Define an IPSec policy";
       uses ipsec-policy;
     }
     list vpn {
       key name;
       ordered-by user;
       description "Define an IPSec VPN";
       uses ipsec-vpn-template;
     }
     list security-association {
       key name;
       ordered-by user;
       description "Define a manual control plane SA ";
       uses ipsec-sa;
     }
   }
   grouping ipsec-internal-sa {
     uses apply-advanced;
     container manual {
       description "Define a manual security association";
       uses apply-advanced;
       container encryption {
         description "Define encryption parameters";
         uses apply-advanced;
         leaf algorithm {
           description "Define encryption algorithm";
           type enumeration {
             enum "3des-cbc" {
               description "3DES-CBC encryption algorithm";
             }
             enum "aes-128-cbc" {
               description "AES-CBC 128-bit encryption algorithm";
             }
           }
         }
         leaf ike-ha-link-encryption {
           description "Enable HA link encryption IKE internal messages";
           type enumeration {
             enum "enable" {
               description "Enable HA link encryption IKE internal messages";
             }
           }
         }
         container key {
           description "Define an encryption key";
           choice key-choice {
             case case_1 {
               leaf ascii-text {
                 description "Format as text";
                 type jt:unreadable;
               }
             }
           }
         }
       }
     }
   }
   grouping ipsec-policy {
     leaf name {
       description "Name of the IPSec policy";
       type string {
         length "1 .. 32";
       }
     }
     uses apply-advanced;
     leaf description {
       description "Text description of IPSec policy";
       type string {
         length "1 .. 80";
       }
     }
     container perfect-forward-secrecy {
       description "Define perfect forward secrecy";
       uses apply-advanced;
       leaf keys {
         description "Define Diffie-Hellman group";
         type enumeration {
           enum "group1" {
             description "Diffie-Hellman Group 1";
           }
           enum "group2" {
             description "Diffie-Hellman Group 2";
           }
           enum "group5" {
             description "Diffie-Hellman Group 5";
           }
           enum "group14" {
             description "Diffie-Hellman Group 14";
           }
           enum "group15" {
             description "Diffie-Hellman Group 15";
           }
           enum "group16" {
             description "Diffie-Hellman Group 16";
           }
           enum "group19" {
             description "Diffie-Hellman Group 19";
           }
           enum "group20" {
             description "Diffie-Hellman Group 20";
           }
           enum "group24" {
             description "Diffie-Hellman Group 24";
           }
         }
       }
     }
     leaf-list proposals {
       ordered-by user;
       description "Name of the proposal";
       type string {
         length "1 .. 32";
       }
     }
     leaf proposal-set {
       description "Types of default IPSEC proposal-set";
       type enumeration {
         enum "basic" {
           description "IPSEC basic proposal-set";
         }
         enum "compatible" {
           description "IPSEC compatible proposal-set";
         }
         enum "standard" {
           description "IPSEC standard proposal-set";
         }
         enum "suiteb-gcm-128" {
           description "IPSec proposal-set for Suite-B-GCM-128";
         }
         enum "suiteb-gcm-256" {
           description "IPSec proposal-set for Suite-B-GCM-256";
         }
         enum "prime-128" {
           description "IPSec proposal-set for PRIME-128";
         }
         enum "prime-256" {
           description "IPSec proposal-set for PRIME-256";
         }
       }
     }
   }
   grouping ipsec-proposal {
     leaf name {
       description "Name of the IPSec proposal";
       type string {
         length "1 .. 32";
       }
     }
     uses apply-advanced;
     leaf description {
       description "Text description of IPSec proposal";
       type string {
         length "1 .. 80";
       }
     }
     leaf protocol {
       description "Define an IPSec protocol for the proposal";
       type enumeration {
         enum "ah" {
           description "Authentication header";
         }
         enum "esp" {
           description "Encapsulated Security Payload header";
         }
       }
     }
     leaf authentication-algorithm {
       description "Define authentication algorithm";
       type enumeration {
         enum "hmac-md5-96" {
           description "HMAC-MD5-96 authentication algorithm";
         }
         enum "hmac-sha1-96" {
           description "HMAC-SHA1-96 authentication algorithm";
         }
         enum "hmac-sha-256-128" {
           description "HMAC-SHA-256-128 authentication algorithm";
         }
         enum "hmac-sha-256-96" {
           description "HMAC-SHA-256-96 authentication algorithm (non-RFC compliant)";
         }
       }
     }
     leaf encryption-algorithm {
       description "Define encryption algorithm";
       type enumeration {
         enum "des-cbc" {
           description "DES-CBC encryption algorithm";
         }
         enum "3des-cbc" {
           description "3DES-CBC encryption algorithm";
         }
         enum "aes-128-cbc" {
           description "AES-CBC 128-bit encryption algorithm";
         }
         enum "aes-192-cbc" {
           description "AES-CBC 192-bit encryption algorithm";
         }
         enum "aes-256-cbc" {
           description "AES-CBC 256-bit encryption algorithm";
         }
         enum "aes-128-gcm" {
           description "AES-GCM 128-bit encryption algorithm";
         }
         enum "aes-192-gcm" {
           description "AES-GCM 192-bit encryption algorithm";
         }
         enum "aes-256-gcm" {
           description "AES-GCM 256-bit encryption algorithm";
         }
       }
     }
     leaf lifetime-seconds {
       description "Lifetime, in seconds";
       units "seconds";
       type union {
         type string {
           pattern "<.*>|$.*";
         }
         type uint32 {
           range "180 .. 86400";
         }
       }
     }
     leaf lifetime-kilobytes {
       description "Lifetime, in kilobytes";
       units "kilobytes";
       type union {
         type string {
           pattern "<.*>|$.*";
         }
         type uint32 {
           range "64 .. 4294967294";
         }
       }
     }
   }
   grouping ipsec-sa {
     leaf name {
       description "Name of IPSec security association";
       type string {
         length "1 .. 32";
       }
     }
     uses apply-advanced;
     leaf description {
       description "Text description of security association";
       type string {
         length "1 .. 80";
       }
     }
     leaf mode {
       description "Define security association mode";
       default "transport";
       type enumeration {
         enum "transport" {
           description "Transport mode";
         }
       }
     }
     choice sa_choice {
       case case_1 {
         container manual {
           description "Define a manual security association";
           uses security-association-manual;
         }
       }
     }
   }
   grouping ipsec-traceoptions {
     description "Data-plane IPSec tracing options";
     uses apply-advanced;
     list flag {
       key name;
       ordered-by user;
       description "Events to include in data-plane IPSec trace output";
       leaf name {
         type enumeration {
           enum "packet-processing" {
             description "Trace data packet processing events";
           }
           enum "packet-drops" {
             description "Trace packet drops";
           }
           enum "security-associations" {
             description "Trace security association management events";
           }
           enum "next-hop-tunnel-binding" {
             description "Trace next-hop tunnel binding events";
           }
           enum "all" {
             description "Trace with all flags enabled";
           }
         }
       }
     }
   }
   grouping ipsec-vpn-monitor {
     description "Configure VPN monitoring";
     uses apply-advanced;
     leaf interval {
       description "Monitor interval in seconds";
       default "10";
       units "seconds";
       type union {
         type string {
           pattern "<.*>|$.*";
         }
         type uint32 {
           range "2 .. 3600";
         }
       }
     }
     leaf threshold {
       description "Number of consecutive failures to determine connectivity";
       default "10";
       type union {
         type string {
           pattern "<.*>|$.*";
         }
         type uint32 {
           range "1 .. 65536";
         }
       }
     }
   }
   grouping ipsec-vpn-template {
     description "Configure an IPSec VPN";
     leaf name {
       description "Name of the VPN";
       type string {
         length "1 .. 32";
       }
     }
     uses apply-advanced;
     leaf bind-interface {
       description "Bind to tunnel interface (route-based VPN)";
       type union {
         type jt:interface-name;
         type string {
           pattern "<.*>|$.*";
         }
       }
     }
     leaf df-bit {
       description "Specifies how to handle the Don't Fragment bit";
       type enumeration {
         enum "clear" {
           description "Clear DF bit of outer header";
         }
         enum "set" {
           description "Set DF bit of outer header";
         }
         enum "copy" {
           description "Copy DF bit from inner header";
         }
       }
     }
     container multi-sa {
       presence "enable multi-sa";
       description "Negotiate multiple SAs based on configuration choice";
       uses apply-advanced;
       choice sa_map {
         case case_1 {
           list forwarding-class {
             key name;
             ordered-by user;
             leaf name {
               description "Name of forwarding classes";
               type string {
                 length "1 .. 32";
               }
             }
             uses apply-advanced;
           }
         }
       }
     }
     leaf copy-outer-dscp {
       description "Enable copying outer IP header DSCP and ECN to inner IP header";
       type empty;
     }
     container vpn-monitor {
       description "Monitor VPN liveliness";
       presence "enable vpn-monitor";
       uses ipsec-template-monitor;
     }
     choice negotiation {
       case case_1 {
         container manual {
           description "Define a manual security association";
           uses apply-advanced;
           leaf gateway {
             description "Define the IPSec peer";
             type jt:hostname;
           }
           leaf external-interface {
             description "External interface for the security association";
             type union {
               type jt:interface-unit;
               type string {
                 pattern "<.*>|$.*";
               }
             }
           }
           leaf protocol {
             description "Define an IPSec protocol for the security association";
             type enumeration {
               enum "ah" {
                 description "Authentication header";
               }
               enum "esp" {
                 description "Encapsulated Security Payload header";
               }
             }
           }
           leaf spi {
             description "Define security parameter index";
             type union {
               type string {
                 pattern "<.*>|$.*";
               }
               type uint32 {
                 range "256 .. 16639";
               }
             }
           }
           container authentication {
             description "Define authentication parameters";
             uses apply-advanced;
             leaf algorithm {
               description "Define authentication algorithm";
               type enumeration {
                 enum "hmac-md5-96" {
                   description "HMAC-MD5-96 authentication algorithm";
                 }
                 enum "hmac-sha1-96" {
                   description "HMAC-SHA1-96 authentication algorithm";
                 }
                 enum "hmac-sha-256-128" {
                   description "HMAC-SHA-256-128 authentication algorithm";
                 }
                 enum "hmac-sha-256-96" {
                   description "HMAC-SHA-256-96 authentication algorithm (non-RFC compliant)";
                 }
               }
             }
             container key {
               description "Define an authentication key";
               choice key-choice {
                 case case_1 {
                   leaf ascii-text {
                     description "Format as text";
                     type string {
                       length "1 .. 255";
                     }
                   }
                 }
                 case case_2 {
                   leaf hexadecimal {
                     description "Format as hexadecimal";
                     type string {
                       length "1 .. 255";
                     }
                   }
                 }
               }
             }
           }
           container encryption {
             description "Define encryption parameters";
             uses apply-advanced;
             leaf algorithm {
               description "Define encryption algorithm";
               type enumeration {
                 enum "des-cbc" {
                   description "DES-CBC encryption algorithm";
                 }
                 enum "3des-cbc" {
                   description "3DES-CBC encryption algorithm";
                 }
                 enum "aes-128-cbc" {
                   description "AES-CBC 128-bit encryption algorithm";
                 }
                 enum "aes-192-cbc" {
                   description "AES-CBC 192-bit encryption algorithm";
                 }
                 enum "aes-256-cbc" {
                   description "AES-CBC 256-bit encryption algorithm";
                 }
                 enum "aes-128-gcm" {
                   description "AES-GCM 128-bit encryption algorithm";
                 }
                 enum "aes-256-gcm" {
                   description "AES-GCM 256-bit encryption algorithm";
                 }
               }
             }
             container key {
               description "Define an encryption key";
               choice key-choice {
                 case case_1 {
                   leaf ascii-text {
                     description "Format as text";
                     type string {
                       length "1 .. 255";
                     }
                   }
                 }
                 case case_2 {
                   leaf hexadecimal {
                     description "Format as hexadecimal";
                     type string {
                       length "1 .. 255";
                     }
                   }
                 }
               }
             }
           }
         }
       }
       case case_2 {
         container ike {
           description "Define an IKE-keyed IPSec vpn";
           uses apply-advanced;
           leaf gateway {
             description "Name of remote gateway";
             type string {
               length "1 .. 32";
             }
           }
           leaf idle-time {
             description "Idle time to delete SA";
             units "seconds";
             type union {
               type string {
                 pattern "<.*>|$.*";
               }
               type uint32 {
                 range "60 .. 999999";
               }
             }
           }
           leaf no-anti-replay {
             description "Disable the anti-replay check";
             type empty;
           }
           container proxy-identity {
             description "IPSec proxy-id to use in IKE negotiations";
             presence "enable proxy-identity";
             uses ipsec-template-proxy-id;
           }
           leaf ipsec-policy {
             description "Name of the IPSec policy";
             type string {
               length "1 .. 32";
             }
           }
           leaf install-interval {
             description "Delay installation of rekeyed outbound SAs on initiator";
             default "1";
             units "seconds";
             type union {
               type string {
                 pattern "<.*>|$.*";
               }
               type uint32 {
                 range "0 .. 10";
               }
             }
           }
         }
       }
     }
     list traffic-selector {
       key name;
       ordered-by user;
       description "Traffic selector";
       max-elements 200;
       leaf name {
         description "Name of traffic selector";
         type string {
           length "1 .. 31";
         }
       }
       uses apply-advanced;
       leaf local-ip {
         description "IP address of local traffic-selector";
         type jt:ipprefix-mandatory;
       }
       leaf remote-ip {
         description "IP address of remote traffic-selector";
         type jt:ipprefix-mandatory;
       }
     }
     leaf establish-tunnels {
       description "Define the criteria to establish tunnels";
       default "on-traffic";
       type enumeration {
         enum "immediately" {
           description "Establish tunnels immediately";
         }
         enum "on-traffic" {
           description "Establish tunnels on traffic";
         }
       }
     }
     container udp-encapsulate {
       presence "enable udp-encapsulate";
       description "UDP encapsulation of IPsec data traffic";
       leaf dest-port {
         description "UDP destination port";
         default "4565";
         type union {
           type string {
             pattern "<.*>|$.*";
           }
           type uint32 {
             range "1025 .. 65536";
           }
         }
       }
     }
   }
   grouping ipsec-template-monitor {
     description "Configure VPN monitoring";
     uses apply-advanced;
     leaf optimized {
       description "Optimize for scalability";
       type empty;
     }
     leaf source-interface {
       description "Source interface for monitor message";
       type union {
         type jt:interface-unit;
         type string {
           pattern "<.*>|$.*";
         }
       }
     }
     leaf destination-ip {
       description "Destination IP addres for monitor message";
       type jt:ipaddr;
     }
     container verify-path {
       presence "enable verify-path";
       description "Verify IPSec path using vpn-monitor before bring up st0 state";
       uses apply-advanced;
       leaf destination-ip {
         description "Destination IP addres for verify IPSec path";
         type jt:ipaddr;
       }
       leaf packet-size {
         description "Size of the packet";
         default "64";
         type union {
           type string {
             pattern "<.*>|$.*";
           }
           type uint32 {
             range "64 .. 1350";
           }
         }
       }
     }
   }
   grouping ipsec-template-proxy-id {
     description "Proxy identity settings";
     uses apply-advanced;
     leaf local {
       description "Local IP address/prefix length";
       type jt:ipprefix-mandatory;
     }
     leaf remote {
       description "Remote IP address/prefix length";
       type jt:ipprefix-mandatory;
     }
     leaf service {
       description "Name of serivce that passes through, any enables all services";
       type string {
         length "1 .. 32";
       }
     }
   }
   grouping security-association-manual {
     uses apply-advanced;
     list direction {
       key name;
       ordered-by user;
       description "Define the direction of the security association";
       leaf name {
         type enumeration {
           enum "bidirectional" {
             description "Bidirectional security association";
           }
         }
       }
       uses apply-advanced;
       leaf protocol {
         description "Define an IPSec protocol for the security association";
         type enumeration {
           enum "ah" {
             description "Authentication header";
           }
           enum "esp" {
             description "Encapsulated Security Payload header";
           }
         }
       }
       leaf spi {
         description "Define security parameter index";
         type union {
           type string {
             pattern "<.*>|$.*";
           }
           type uint32 {
             range "256 .. 16639";
           }
         }
       }
       container authentication {
         description "Define authentication parameters";
         uses apply-advanced;
         leaf algorithm {
           description "Define authentication algorithm";
           type enumeration {
             enum "hmac-md5-96" {
               description "HMAC-MD5-96 authentication algorithm";
             }
             enum "hmac-sha1-96" {
               description "HMAC-SHA1-96 authentication algorithm";
             }
           }
         }
         container key {
           description "Define an authentication key";
           choice key-choice {
             case case_1 {
               leaf ascii-text {
                 description "Format as text";
                 type string {
                   length "1 .. 255";
                 }
               }
             }
             case case_2 {
               leaf hexadecimal {
                 description "Format as hexadecimal";
                 type string {
                   length "1 .. 255";
                 }
               }
             }
           }
         }
       }
       container encryption {
         description "Define encryption parameters";
         uses apply-advanced;
         leaf algorithm {
           description "Define encryption algorithm";
           type enumeration {
             enum "des-cbc" {
               description "DES-CBC encryption algorithm";
             }
             enum "3des-cbc" {
               description "3DES-CBC encryption algorithm";
             }
           }
         }
         container key {
           description "Define an encryption key";
           choice key-choice {
             case case_1 {
               leaf ascii-text {
                 description "Format as text";
                 type string {
                   length "1 .. 255";
                 }
               }
             }
             case case_2 {
               leaf hexadecimal {
                 description "Format as hexadecimal";
                 type string {
                   length "1 .. 255";
                 }
               }
             }
           }
         }
       }
     }
   }
   grouping security-macsec {
     uses apply-advanced;
     container traceoptions {
       description "Tracing options for debugging protocol operation";
       presence "enable traceoptions";
       uses macsec-trace-options;
     }
     list connectivity-association {
       key name;
       ordered-by user;
       description "Configure connectivity association properties";
       leaf name {
         description "Connectivity association name";
         type string {
           length "1 .. 32";
         }
       }
       uses apply-advanced;
       leaf security-mode {
         description "Connectivity association mode";
         type enumeration {
           enum "dynamic" {
             description "Dynamic connectivity and secure association mode (MKA and dot1x)";
           }
           enum "static-sak" {
             description "Static secure association key mode (no MKA)";
           }
           enum "static-cak" {
             description "Static connectivity association key mode (MKA and Pre-shared key)";
           }
         }
       }
       list secure-channel {
         key name;
         ordered-by user;
         description "Configure secure channel properties";
         leaf name {
           description "Secure channel name";
           type string;
         }
         uses apply-advanced;
         container id {
           description "Secure channel identifier";
           uses apply-advanced;
           leaf mac-address {
             description "MAC addresses";
             type jt:mac-addr;
           }
           leaf port-id {
             description "Port identifier";
             type union {
               type string {
                 pattern "<.*>|$.*";
               }
               type uint32 {
                 range "1 .. 65535";
               }
             }
           }
         }
         leaf direction {
           description "Secure channel direction";
           type enumeration {
             enum "inbound" {
             }
             enum "outbound" {
             }
           }
         }
         leaf encryption {
           description "Enable Encryption";
           type empty;
         }
         leaf offset {
           description "Confidentiality offset";
           type enumeration {
             enum "0" {
               description "Confidentiality protected for all octets of MACSec PDU data";
             }
             enum "30" {
               description "Confidentiality not protected for initial 30 octets of MACSec PDU data";
             }
             enum "50" {
               description "Confidentiality not protected for initial 50 octets of MACSec PDU data";
             }
           }
         }
         leaf include-sci {
           description "Include secure channel identifier in MAC Security PDU";
           type empty;
         }
         list security-association {
           key name;
           ordered-by user;
           description "Security association";
           leaf name {
             description "Security association number";
             type union {
               type string {
                 pattern "<.*>|$.*";
               }
               type uint32 {
                 range "0 .. 3";
               }
             }
           }
           uses apply-advanced;
           leaf key {
             description "Security association key in hexadecimal format of length 32";
             type string {
               length 32;
             }
           }
         }
       }
       container mka {
         presence "enable mka";
         description "Configure MAC Security Key Agreement protocol properties";
         uses apply-advanced;
         leaf transmit-interval {
           description "Configure MKA periodic transmit interval";
           default "7000";
           units "milliseconds";
           type union {
             type string {
               pattern "<.*>|$.*";
             }
             type uint32 {
               range "2000 .. 10000";
             }
           }
         }
         leaf bounded-delay {
           description "Configure Bounded Hello Time";
           type empty;
         }
         leaf key-server-priority {
           description "Configure MKA key server priority";
           default "16";
           type union {
             type string {
               pattern "<.*>|$.*";
             }
             type uint32 {
               range "0 .. 255";
             }
           }
         }
         leaf must-secure {
           description "Allow only secure dot1x traffic";
           type empty;
         }
         leaf should-secure {
           description "Configure fail open mode for MKA protocol";
           type empty;
         }
         leaf eapol-address {
           description "Configure EAPOL destination group address";
           default "pae";
           type string;
         }
       }
       container replay-protect {
         description "Configure replay protection";
         uses apply-advanced;
         leaf replay-window-size {
           description "Configure replay protection window size";
           units "packets";
           type union {
             type string {
               pattern "<.*>|$.*";
             }
             type uint32 {
               range "0 .. 65535";
             }
           }
         }
       }
       leaf no-encryption {
         description "Disable encryption";
         type empty;
       }
       leaf offset {
         description "Confidentiality offset";
         default "0";
         type enumeration {
           enum "0" {
             description "Confidentiality provided for all octets of data";
           }
           enum "30" {
             description "Confidentiality not provided for initial 30 octets of data";
           }
           enum "50" {
             description "Confidentiality not provided for initial 50 octets of data";
           }
         }
       }
       leaf include-sci {
         description "Include secure channel identifier in MAC Security PDU";
         type empty;
       }
       container pre-shared-key {
         presence "enable pre-shared-key";
         description "Configure pre-shared connectivity association key";
         uses apply-advanced;
         leaf ckn {
           description "Connectivity association key name in hexadecimal format";
           type string {
             length "2 .. 64";
           }
         }
         leaf cak {
           description "Connectivity association key in hexadecimal format (max_length = 64)";
           type string {
             length "1 .. 64";
           }
         }
       }
       leaf pre-shared-key-chain {
         description "Pre-shared key chain name for connectivity association";
         type string {
         }
       }
       list exclude-protocol {
         key name;
         ordered-by user;
         description "Configure protocols to exclude from MAC Security";
         leaf name {
           type enumeration {
             enum "cdp" {
               description "Cisco Discovery Protocol";
             }
             enum "lldp" {
               description "Link Level Discovery Protocol";
             }
             enum "lacp" {
               description "Link Aggregation Control Protocol";
             }
           }
         }
       }
     }
     list interfaces {
       key name;
       description "Interfaces on which macsec configuration is applied";
       leaf name {
         type union {
           type jt:interface-device;
           type string {
             pattern "<.*>|$.*";
           }
         }
       }
       uses apply-advanced;
       leaf connectivity-association {
         description "Connectivity association name";
         type string;
       }
       leaf aes-gcm-revert-flag {
         description "Flag to fall back to previous AES_GCM_256
           cipher suite implementation";
         type empty;
       }
       container traceoptions {
         description "Tracing options of MKA protocol";
         presence "enable traceoptions";
         uses mka-trace-options;
       }
     }
     list cluster-control-port {
       key name;
       description "Cluster control port on which macsec configuration is applied";
       leaf name {
         description "Port identifier";
         type union {
           type string {
             pattern "<.*>|$.*";
           }
           type uint32 {
             range "0 .. 1";
           }
         }
       }
       uses apply-advanced;
       leaf connectivity-association {
         description "Connectivity association name";
         type string;
       }
       container traceoptions {
         description "Tracing options of MKA protocol";
         presence "enable traceoptions";
         uses mka-trace-options;
       }
     }
     list cluster-data-port {
       key name;
       description "Cluster data port on which macsec configuration is applied";
       leaf name {
         type union {
           type jt:interface-device;
           type string {
             pattern "<.*>|$.*";
           }
         }
       }
       uses apply-advanced;
       leaf connectivity-association {
         description "Connectivity association name";
         type string;
       }
       container traceoptions {
         description "Tracing options of MKA protocol";
         presence "enable traceoptions";
         uses mka-trace-options;
       }
     }
   }
   grouping macsec-trace-options {
     description "Trace options for MACSec Protocol";
     uses apply-advanced;
     container file {
       description "Trace file options";
       leaf filename {
         description "Name of file in which to write trace information";
         type string {
           length "1 .. 1024";
         }
       }
       leaf replace {
         description "Replace trace file rather than appending to it";
         status deprecated;
         type empty;
       }
       leaf size {
         description "Maximum trace file size";
         type string;
       }
       leaf files {
         description "Maximum number of trace files";
         default "10";
         type union {
           type string {
             pattern "<.*>|$.*";
           }
           type uint32 {
             range "2 .. 1000";
           }
         }
       }
       leaf no-stamp {
         description "Do not timestamp trace file";
         status deprecated;
         type empty;
       }
       choice world-readable-choice {
         leaf world-readable {
           description "Allow any user to read the log file";
           type empty;
         }
         leaf no-world-readable {
           description "Don't allow any user to read the log file";
           type empty;
         }
       }
     }
     list flag {
       key name;
       ordered-by user;
       description "Tracing parameters";
       leaf name {
         type enumeration {
           enum "config" {
             description "Trace configuration messages";
           }
           enum "debug" {
             description "Trace debug messages";
           }
           enum "normal" {
             description "Trace normal messages";
           }
           enum "all" {
             description "Trace all";
           }
         }
       }
     }
   }
   grouping mka-trace-options {
     description "Trace options for MKA protocol";
     uses apply-advanced;
     container file {
       description "Trace file options";
       leaf filename {
         description "Name of file in which to write trace information";
         type string {
           length "1 .. 1024";
         }
       }
       leaf replace {
         description "Replace trace file rather than appending to it";
         status deprecated;
         type empty;
       }
       leaf size {
         description "Maximum trace file size";
         type string;
       }
       leaf files {
         description "Maximum number of trace files";
         default "10";
         type union {
           type string {
             pattern "<.*>|$.*";
           }
           type uint32 {
             range "2 .. 1000";
           }
         }
       }
       leaf no-stamp {
         description "Do not timestamp trace file";
         status deprecated;
         type empty;
       }
       choice world-readable-choice {
         leaf world-readable {
           description "Allow any user to read the log file";
           type empty;
         }
         leaf no-world-readable {
           description "Don't allow any user to read the log file";
           type empty;
         }
       }
     }
     list flag {
       key name;
       ordered-by user;
       description "Tracing parameters";
       leaf name {
         type enumeration {
           enum "mka-packets" {
             description "Trace MKA input and output packets";
           }
           enum "state" {
             description "Trace MKA state information";
           }
           enum "to-secy" {
             description "Trace MKA to SecY state changes";
           }
           enum "keys" {
             description "Trace key creation/generation information";
           }
           enum "normal" {
             description "Trace normal events";
           }
           enum "all" {
             description "Trace all";
           }
         }
       }
     }
   }
   grouping security-option-82-type {
     description "DHCP option-82 processing";
     uses apply-advanced;
     container circuit-id {
       presence "enable circuit-id";
       description "Configure DHCP option 82 circuit id";
       uses apply-advanced;
       container prefix {
         description "Configure DHCP option 82 circuit id prefix";
         uses apply-advanced;
         leaf host-name {
           description "Add router host name to DHCP option-82 circuit id";
           type empty;
         }
         leaf logical-system-name {
           description "Add logical system name to DHCP option-82 circuit id";
           type empty;
         }
         leaf routing-instance-name {
           description "Add routing instance name to DHCP option-82 circuit id";
           type empty;
         }
       }
       leaf use-interface-description {
         description "Use interface description instead of circuit identifier";
         type enumeration {
           enum "logical" {
             description "Use the logical interface description";
           }
           enum "device" {
             description "Use the device interface description";
           }
         }
       }
       leaf use-vlan-id {
         description "Use VLAN id instead of name";
         type empty;
       }
     }
     container remote-id {
       presence "enable remote-id";
       description "Configure DHCP option 82 remote id";
       uses apply-advanced;
       leaf host-name {
         description "Add router host name to DHCP option-82 remote id";
         type empty;
       }
       leaf use-interface-description {
         description "Use interface description instead of interface name";
         type enumeration {
           enum "logical" {
             description "Use the logical interface description";
           }
           enum "device" {
             description "Use the device interface description";
           }
         }
       }
       leaf use-string {
         description "Use raw string instead of the default remote id";
         type string;
       }
       leaf mac {
         description "Add chassis MAC Address to DHCP option-82 remote id";
         type empty;
       }
     }
     container vendor-id {
       presence "enable vendor-id";
       description "Configure DHCP option 82 vendor id";
       uses apply-advanced;
       leaf use-string {
         description "Use raw string instead of the default vendor id";
         default "Juniper Networks";
         type string;
       }
     }
   }
   grouping security-pki {
     uses apply-advanced;
     list ca-profile {
       key name;
       ordered-by user;
       description "Certificate authority profile configuration";
       leaf name {
         description "Name of certificate authority profile";
         type string {
           length "1 .. 32";
         }
       }
       uses apply-advanced;
       leaf ca-identity {
         description "Certificate authority identifier";
         type string;
       }
       leaf source-address {
         description "Use specified address as source address";
         type jt:ipaddr;
       }
       leaf proxy-profile {
         description "Use specified proxy server";
         type string;
       }
       leaf routing-instance {
         description "Use specified routing instance";
         type string;
       }
       container enrollment {
         description "Enrollment parameters for certificate authority";
         uses apply-advanced;
         leaf url {
           description "Enrollment URL of certificate authority";
           type string;
         }
         leaf retry {
           description "Number of enrollment retry attempts before aborting";
           default "1000";
           type union {
             type string {
               pattern "<.*>|$.*";
             }
             type uint32 {
               range "0 .. 1080";
             }
           }
         }
         leaf retry-interval {
           description "Interval in seconds between the enrollment retries";
           default "600";
           type union {
             type string {
               pattern "<.*>|$.*";
             }
             type uint32 {
               range "0 .. 3600";
             }
           }
         }
       }
       container revocation-check {
         description "Method for checking certificate revocations";
         uses apply-advanced;
         choice revocation-check-options {
           case case_1 {
             leaf use-crl {
               description "Use CRL for revocation check";
               type empty;
             }
           }
           case case_2 {
             leaf use-ocsp {
               description "Use OCSP for revocation check";
               type empty;
             }
           }
           case case_3 {
             leaf disable {
               description "Disable revocation check";
               type empty;
             }
           }
         }
         container ocsp {
           presence "enable ocsp";
           description "Online Certificate Status Protocol (OCSP) configuration";
           uses apply-advanced;
           list url {
             key name;
             ordered-by user;
             leaf name {
               description "HTTP URL for OCSP access location";
               type string {
                 length "1 .. 500";
               }
             }
             uses apply-advanced;
           }
           leaf nonce-payload {
             description "Include nonce payload in OCSP requests";
             type enumeration {
               enum "enable" {
                 description "Send nonce paylod in OCSP request";
               }
               enum "disable" {
                 description "Do not send nonce payload in OCSP request";
               }
             }
           }
           leaf disable-responder-revocation-check {
             description "Disable OCSP responder certificate revocation check";
             type empty;
           }
           leaf accept-unknown-status {
             description "Accept certificates with unknown status";
             type empty;
           }
           container connection-failure {
             presence "enable connection-failure";
             description "Actions on failure to connect to OCSP Responder";
             uses apply-advanced;
             choice connection-failure-options {
               case case_1 {
                 leaf fallback-crl {
                   description "Use CRL for revocation check";
                   type empty;
                 }
               }
               case case_2 {
                 leaf disable {
                   description "Disable OCSP check on connection failure";
                   type empty;
                 }
               }
             }
           }
         }
         container crl {
           description "Certificate revocation list configuration";
           uses apply-advanced;
           container disable {
             leaf on-download-failure {
               description "Check revocation status with existing CRL file if present, otherwise skip. This feature must be enabled for manual CRL download.";
               type empty;
             }
           }
           list url {
             key name;
             ordered-by user;
             leaf name {
               description "URL of CRL distribution point for certificate authority";
               type string {
                 length "1 .. 500";
               }
             }
             uses apply-advanced;
             leaf password {
               description "Password for authentication with the server";
               type jt:unreadable;
             }
           }
           leaf refresh-interval {
             description "CRL refresh interval";
             units "hours";
             type union {
               type string {
                 pattern "<.*>|$.*";
               }
               type uint32 {
                 range "0 .. 8784";
               }
             }
           }
         }
       }
       container administrator {
         description "Administrator information";
         uses apply-advanced;
         leaf email-address {
           description "Administrator e-mail to which to send certificate requests";
           type string;
         }
       }
     }
     list trusted-ca-group {
       key name;
       ordered-by user;
       description "Trusted Certificate Authority group configuration";
       leaf name {
         description "Name of the trusted CA group";
         type string {
           length "1 .. 63";
         }
       }
       uses apply-advanced;
       leaf-list ca-profiles {
         ordered-by user;
         description "Name of the CA profiles (maximum 20)";
         type string {
           length "1 .. 63";
         }
         max-elements 20;
       }
     }
     container auto-re-enrollment {
       description "Auto re-enroll of certificate";
       uses apply-advanced;
       container cmpv2 {
         presence "enable cmpv2";
         description "CMPv2 auto re-enrollment configuration";
         uses apply-advanced;
         list certificate-id {
           key name;
           ordered-by user;
           description "CMPv2 auto re-enrollment configuration for certificate-id";
           leaf name {
             description "Certificate identifier that needs auto re-enrollment";
             type string {
             }
           }
           uses apply-advanced;
           leaf ca-profile-name {
             description "Name of certificate authority profile";
             type string {
             }
           }
           leaf re-enroll-trigger-time-percentage {
             description "Re-enrollment trigger time before expiration as percentage";
             type union {
               type string {
                 pattern "<.*>|$.*";
               }
               type uint32 {
                 range "1 .. 99";
               }
             }
           }
           leaf re-generate-keypair {
             description "Generate new key-pair for auto-re-enrollment";
             type empty;
           }
         }
       }
       container scep {
         presence "enable scep";
         description "SCEP auto re-enrollment configuration";
         uses apply-advanced;
         list certificate-id {
           key name;
           ordered-by user;
           description "SCEP auto re-enrollment configuration for certificate-id";
           leaf name {
             description "Certificate identifier that needs auto re-enrollment";
             type string {
             }
           }
           uses apply-advanced;
           leaf ca-profile-name {
             description "Name of certificate authority profile";
             type string {
             }
           }
           leaf re-generate-keypair {
             description "Generate new key-pair for auto-re-enrollment";
             type empty;
           }
           leaf re-enroll-trigger-time-percentage {
             description "Re-enrollment trigger time before expiration as percentage";
             type union {
               type string {
                 pattern "<.*>|$.*";
               }
               type uint32 {
                 range "1 .. 99";
               }
             }
           }
           leaf challenge-password {
             description "Password used by CA for enrollment and revocation";
             type jt:unreadable;
           }
           container scep-encryption-algorithm {
             presence "enable scep-encryption-algorithm";
             description "SCEP encryption algorithm";
             uses apply-advanced;
             choice scep-encryption-algorithm-options {
               case case_1 {
                 leaf des {
                   description "Use DES as SCEP encryption algorithm";
                   type empty;
                 }
               }
               case case_2 {
                 leaf des3 {
                   description "Use DES3 as SCEP encryption algorithm";
                   type empty;
                 }
               }
             }
           }
           container scep-digest-algorithm {
             presence "enable scep-digest-algorithm";
             description "SCEP digest algorithm";
             uses apply-advanced;
             choice scep-digest-algorithm-options {
               case case_1 {
                 leaf md5 {
                   description "Use MD5 as SCEP digest algorithm";
                   type empty;
                 }
               }
               case case_2 {
                 leaf sha1 {
                   description "Use SHA1 as SCEP digest algorithm";
                   type empty;
                 }
               }
             }
           }
         }
       }
       list certificate-id {
         key name;
         ordered-by user;
         description "Auto re-enrollment configuration for certificate-id";
         leaf name {
           description "Certificate identifier that needs auto re-enrollment";
           type string {
           }
         }
         uses apply-advanced;
         leaf ca-profile-name {
           description "Name of certificate authority profile";
           type string {
           }
         }
         leaf re-generate-keypair {
           description "Generate new key-pair for auto-re-enrollment";
           type empty;
         }
         leaf re-enroll-trigger-time-percentage {
           description "Re-enrollment trigger time before expiration as percentage";
           type union {
             type string {
               pattern "<.*>|$.*";
             }
             type uint32 {
               range "1 .. 99";
             }
           }
         }
         leaf challenge-password {
           description "Password used by CA for enrollment and revocation";
           type jt:unreadable;
         }
         container scep-encryption-algorithm {
           presence "enable scep-encryption-algorithm";
           description "SCEP encryption algorithm";
           uses apply-advanced;
           choice scep-encryption-algorithm-options {
             case case_1 {
               leaf des {
                 description "Use DES as SCEP encryption algorithm";
                 type empty;
               }
             }
             case case_2 {
               leaf des3 {
                 description "Use DES3 as SCEP encryption algorithm";
                 type empty;
               }
             }
           }
         }
         container scep-digest-algorithm {
           presence "enable scep-digest-algorithm";
           description "SCEP digest algorithm";
           uses apply-advanced;
           choice scep-digest-algorithm-options {
             case case_1 {
               leaf md5 {
                 description "Use MD5 as SCEP digest algorithm";
                 type empty;
               }
             }
             case case_2 {
               leaf sha1 {
                 description "Use SHA1 as SCEP digest algorithm";
                 type empty;
               }
             }
           }
         }
       }
     }
     container traceoptions {
       description "PKI trace options";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing parameters";
         leaf name {
           type enumeration {
             enum "certificate-verification" {
               description "PKI certificate verification tracing";
             }
             enum "online-crl-check" {
               description "PKI online crl tracing";
             }
             enum "enrollment" {
               description "PKI certificate enrollment tracing";
             }
             enum "all" {
               description "Trace with all flags enabled";
             }
           }
         }
       }
     }
   }
   grouping security-traceoptions {
     description "Trace options for key management process";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf rate-limit {
       description "Limit the incoming rate of trace messages";
       default "0";
       type union {
         type string {
           pattern "<.*>|$.*";
         }
         type uint32 {
           range "0 .. 4294967295";
         }
       }
     }
     container filter {
       description "Filter parameters for IKE traceoptions";
       uses apply-advanced;
       leaf fpc {
         description "FPC slot number";
         type union {
           type string {
             pattern "<.*>|$.*";
           }
           type uint32;
         }
       }
       leaf pic {
         description "PIC slot number";
         type union {
           type string {
             pattern "<.*>|$.*";
           }
           type uint32;
         }
       }
     }
     list flag {
       key name;
       ordered-by user;
       description "Tracing parameters for IKE";
       leaf name {
         type enumeration {
           enum "timer" {
             description "Trace internal timer events";
           }
           enum "routing-socket" {
             description "Trace routing socket messages";
           }
           enum "parse" {
             description "Trace configuration processing";
           }
           enum "config" {
             description "Trace configuration download processing";
           }
           enum "ike" {
             description "Trace IKE module processing";
           }
           enum "policy-manager" {
             description "Trace policy manager processing";
           }
           enum "general" {
             description "Trace general events";
           }
           enum "database" {
             description "Trace security associations database events";
           }
           enum "certificates" {
             description "Trace certificate events";
           }
           enum "snmp" {
             description "Trace SNMP operations";
           }
           enum "thread" {
             description "Trace thread processing";
           }
           enum "high-availability" {
             description "Trace high-availability operations";
           }
           enum "next-hop-tunnels" {
             description "Trace next-hop-tunnels operations";
           }
           enum "all" {
             description "Trace everything";
           }
         }
       }
     }
   }
   grouping security-zone-type {
     description "Security zone";
     leaf name {
       description "Name of the zone";
       type string {
         length "1 .. 63";
       }
     }
     uses apply-advanced;
     leaf description {
       description "Text description of zone";
       type string {
         length "1 .. 900";
       }
     }
     leaf tcp-rst {
       description "Send RST for NON-SYN packet not matching TCP session";
       type empty;
     }
     container address-book {
       description "Address book entries";
       uses address-book-type;
     }
     leaf screen {
       description "Name of ids option object applied to the zone";
       type string {
         length "1 .. 32";
       }
     }
     container host-inbound-traffic {
       description "Allowed system services & protocols";
       uses zone_host_inbound_traffic_t;
     }
     list interfaces {
       key name;
       ordered-by user;
       description "Interfaces that are part of this zone";
       uses zone-interface-list-type;
     }
     leaf application-tracking {
       description "Enable Application tracking support for this zone";
       type empty;
     }
     leaf source-identity-log {
       description "Show user and group info in session log for this zone";
       type empty;
     }
     container advance-policy-based-routing-profile {
       description "Enable Advance Policy Based Routing on this zone";
       uses apply-advanced;
       leaf profile {
         description "Advance policy based routing profile name";
         type string {
           length "1 .. 63";
         }
       }
     }
     leaf enable-reverse-reroute {
       description "Enable Reverse route lookup when there is change in ingress interface";
       type empty;
     }
   }
   grouping address-book-type {
     description "Configure security address book for the zone";
     uses apply-advanced;
     list address {
       key name;
       ordered-by user;
       description "Define a security address";
       uses address_type;
     }
     list address-set {
       key name;
       ordered-by user;
       description "Define a security address set";
       uses address_set_type;
     }
   }
   grouping server {
     description "Server settings";
     uses apply-advanced;
     leaf host {
       description "Server host IP address or string host name";
       type string;
     }
     leaf port {
       description "Server port";
       type union {
         type string {
           pattern "<.*>|$.*";
         }
         type uint32 {
           range "1024 .. 65535";
         }
       }
     }
     leaf routing-instance {
       description "Routing instance name";
       type string;
     }
   }
   grouping server-bulk-leasequery-type {
     description "Allow bulk leasequery";
     uses apply-advanced;
     leaf max-connections {
       description "Max TCP connections allowed at a time";
       default "3";
       type union {
         type string {
           pattern "<.*>|$.*";
         }
         type uint32 {
           range "1 .. 10";
         }
       }
     }
     leaf timeout {
       description "Timeout for blocked connection";
       default "120";
       units "seconds";
       type union {
         type string {
           pattern "<.*>|$.*";
         }
         type uint32 {
           range "1 .. 1000";
         }
       }
     }
     leaf max-empty-replies {
       description "Maximum number of empty replies for a connection";
       default "5";
       units "seconds";
       type union {
         type string {
           pattern "<.*>|$.*";
         }
         type uint32 {
           range "1 .. 100";
         }
       }
     }
     leaf restricted-requestor {
       description "Allow bulk leasequery only from restricted requestors";
       type empty;
     }
   }
   grouping server-group-type {
     uses apply-advanced;
     list server-group {
       key name;
       ordered-by user;
       description "One or more server groups";
       leaf name {
         description "Server group name";
         type string {
           length "1 .. 64";
         }
       }
       uses apply-advanced;
       list address {
         key name;
         ordered-by user;
         description "IP Address of one or more DHCP servers";
         leaf name {
           description "IP Address of DHCP server";
           type jt:ipaddr;
         }
         uses apply-advanced;
       }
     }
   }
   grouping server-leasequery-type {
     description "Allow leasequery";
     uses apply-advanced;
     leaf restricted-requestor {
       description "Allow leasequery only from restricted requestors";
       type empty;
     }
   }
   grouping server-match-action-choice {
     uses apply-advanced;
     choice v4-action-choice {
       case case_1 {
         leaf forward-only {
           description "Forward without subscriber services";
           type empty;
         }
       }
       case case_2 {
         leaf create-relay-entry {
           description "Create relay entry and allow subscriber services";
           type empty;
         }
       }
     }
   }
   grouping server-match-v6-ascii-hex {
     uses apply-advanced;
     list ascii {
       key name;
       description "ASCII string";
       leaf name {
         description "ASCII string";
         type string {
           length "1 .. 256";
         }
       }
       uses apply-advanced;
       choice server-match-action-choice {
         case case_1 {
           leaf forward-only {
             description "Forward without subscriber services when a match is made";
             type empty;
           }
         }
         case case_2 {
           leaf create-relay-entry {
             description "Create relay entry and allow subscriber services";
             type empty;
           }
         }
       }
     }
     list hexadecimal {
       key name;
       description "Hexadecimal string";
       leaf name {
         description "Hexadecimal string";
         type string {
           length "1 .. 512";
         }
       }
       uses apply-advanced;
       choice server-match-action-choice {
         case case_1 {
           leaf forward-only {
             description "Forward without subscriber services when a match is made";
             type empty;
           }
         }
         case case_2 {
           leaf create-relay-entry {
             description "Create relay entry and allow subscriber services";
             type empty;
           }
         }
       }
     }
   }
   grouping server-v6-option-ascii-hex {
     uses apply-advanced;
     list ascii {
       key name;
       description "ASCII string";
       leaf name {
         description "ASCII string";
         type string {
           length "1 .. 256";
         }
       }
       uses apply-advanced;
     }
     list hexadecimal {
       key name;
       description "Hexadecimal string";
       leaf name {
         description "Hexadecimal string";
         type string {
           length "1 .. 512";
         }
       }
       uses apply-advanced;
     }
   }
   grouping session_timeout_type {
     uses apply-advanced;
     leaf tcp {
       description "Timeout value for tcp sessions";
       units "seconds";
       type union {
         type string {
           pattern "<.*>|$.*";
         }
         type uint32 {
           range "4 .. 86400";
         }
       }
     }
     leaf udp {
       description "Timeout value for udp sessions";
       units "seconds";
       type union {
         type string {
           pattern "<.*>|$.*";
         }
         type uint32 {
           range "4 .. 86400";
         }
       }
     }
     leaf ospf {
       description "Timeout value for ospf sessions";
       units "seconds";
       type union {
         type string {
           pattern "<.*>|$.*";
         }
         type uint32 {
           range "4 .. 86400";
         }
       }
     }
     leaf icmp {
       description "Timeout value for icmp sessions";
       units "seconds";
       type union {
         type string {
           pattern "<.*>|$.*";
         }
         type uint32 {
           range "4 .. 86400";
         }
       }
     }
     leaf icmp6 {
       description "Timeout value for icmp6 sessions";
       units "seconds";
       type union {
         type string {
           pattern "<.*>|$.*";
         }
         type uint32 {
           range "4 .. 86400";
         }
       }
     }
     leaf others {
       description "Timeout value for other sessions";
       units "seconds";
       type union {
         type string {
           pattern "<.*>|$.*";
         }
         type uint32 {
           range "4 .. 86400";
         }
       }
     }
   }
   grouping sla_policy_type {
     leaf name {
       description "APBR policy name";
       type string {
         length "1 .. 63";
       }
     }
     uses apply-advanced;
     leaf description {
       description "Text description of policy";
       type string {
         length "1 .. 900";
       }
     }
     container match {
       description "Specify sla policy match-criteria";
       uses apply-advanced;
       choice source-address_choice {
         case case_1 {
           leaf-list source-address {
             ordered-by user;
             type string;
           }
         }
       }
       choice destination-address_choice {
         case case_1 {
           leaf-list destination-address {
             ordered-by user;
             type string;
           }
         }
       }
       leaf source-address-excluded {
         description "Exclude source addresses";
         type empty;
       }
       leaf destination-address-excluded {
         description "Exclude destination addresses";
         type empty;
       }
       choice application_type_choice {
         case case_1 {
           leaf-list application {
             ordered-by user;
             description "Specify application or application-set name to match";
             type string {
               length "1 .. 63";
             }
           }
         }
       }
     }
     container then {
       description "Specify policy action to take when packet match criteria";
       uses apply-advanced;
       choice action {
         case case_1 {
           container application-services {
             description "Application Services";
             uses sla_application_services_type;
           }
         }
       }
     }
     leaf scheduler-name {
       description "Name of scheduler";
       type string {
         length "1 .. 63";
       }
     }
   }
   grouping sla_application_services_type {
     description "Application Services";
     uses apply-advanced;
     leaf advance-policy-based-routing-profile {
       description "Specify APBR profile name";
       type string {
         length "1 .. 63";
       }
     }
   }
   grouping softwires-object {
     description "Configure softwire feature";
     uses apply-advanced;
     list softwire-name {
       key name;
       description "Configure softwire object";
       uses softwire-option-type;
     }
     container traceoptions {
       description "Trace options for Network Security DS-Lite";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing parameters";
         leaf name {
           type enumeration {
             enum "configuration" {
               description "Trace configuration events";
             }
             enum "flow" {
               description "Trace flow events";
             }
             enum "all" {
               description "Trace everything";
             }
           }
         }
       }
     }
     list rule-set {
       key name;
       ordered-by user;
       description "Define a softwire rule set";
       uses sw-rule-set-object;
     }
   }
   grouping softwire-option-type {
     description "Configure softwire object";
     leaf name {
       description "DS-Lite/Softwire object name";
       type string {
         length "1 .. 23";
       }
     }
     uses apply-advanced;
     leaf softwire-concentrator {
       description "Concentrator address";
       type jt:ipaddr;
     }
     leaf softwire-type {
       description "Softwire-type";
       default "IPv4-in-IPv6";
       type enumeration {
         enum "IPv4-in-IPv6" {
           description "Ipv4-in-IPv6";
         }
         enum "v6rd" {
           description "V6rd";
         }
       }
     }
     leaf ipv4-prefix {
       description "6rd customer edge IPV4 prefix";
       type jt:ipv4prefix;
     }
     leaf v6rd-prefix {
       description "6rd domain's IPV6 prefix";
       type jt:ipv6prefix;
     }
     leaf mtu-v4 {
       description "MTU for the softwire tunnel";
       type union {
         type string {
           pattern "<.*>|$.*";
         }
         type uint32 {
           range "576 .. 9192";
         }
       }
     }
   }
   grouping sophos-scan-options {
     description "Anti-virus scan options";
     uses apply-advanced;
     choice uri-check-choice {
       leaf uri-check {
         description "Anti-virus uri-check";
         type empty;
       }
       leaf no-uri-check {
         description "Don't anti-virus uri-check";
         type empty;
       }
     }
     leaf content-size-limit {
       description "Content size limit";
       type string;
     }
     leaf timeout {
       description "Scan engine timeout";
       units "seconds";
       type union {
         type string {
           pattern "<.*>|$.*";
         }
         type uint32 {
           range "1 .. 1800";
         }
       }
     }
   }
   grouping source_address_filter_list_items {
     leaf address {
       description "IP address or hostname";
       type jt:ipprefix;
     }
     leaf choice-ident {
       type enumeration {
         enum "exact" {
         }
         enum "longer" {
         }
         enum "orlonger" {
         }
         enum "upto" {
         }
         enum "through" {
         }
         enum "prefix-length-range" {
         }
         enum "apply-advanced" {
         }
         enum "metric" {
         }
         enum "metric2" {
         }
         enum "metric3" {
         }
         enum "metric4" {
         }
         enum "tag" {
         }
         enum "tag2" {
         }
         enum "preference" {
         }
         enum "preference2" {
         }
         enum "color" {
         }
         enum "color2" {
         }
         enum "local-preference" {
         }
         enum "priority" {
         }
         enum "prefix-segment" {
         }
         enum "label-allocation" {
         }
         enum "add-path" {
         }
         enum "validation-state" {
         }
         enum "origin" {
         }
         enum "aigp-originate" {
         }
         enum "aigp-adjust" {
         }
         enum "community" {
         }
         enum "damping" {
         }
         enum "aggregate-bandwidth" {
         }
         enum "limit-bandwidth" {
         }
         enum "no-entropy-label-capability" {
         }
         enum "as-path-prepend" {
         }
         enum "as-path-expand" {
         }
         enum "next-hop" {
         }
         enum "install-nexthop" {
         }
         enum "trace" {
         }
         enum "external" {
         }
         enum "load-balance" {
         }
         enum "no-route-localize" {
         }
         enum "install-to-fib" {
         }
         enum "analyze" {
         }
         enum "class" {
         }
         enum "destination-class" {
         }
         enum "source-class" {
         }
         enum "forwarding-class" {
         }
         enum "map-to-interface" {
         }
         enum "ssm-source" {
         }
         enum "p2mp-lsp-root" {
         }
         enum "cos-next-hop-map" {
         }
         enum "dynamic-tunnel-attributes" {
         }
         enum "selected-mldp-egress" {
         }
         enum "mhop-bfd-port" {
         }
         enum "no-backup" {
         }
         enum "default-action" {
         }
         enum "next" {
         }
         enum "accept_reject" {
         }
         enum "bgp-output-queue-priority" {
         }
         enum "multipath-resolve" {
         }
         enum "label-allocation-fallback-reject" {
         }
       }
     }
     leaf choice-value {
       type string;
     }
     uses apply-advanced;
     container metric {
       description "Metric value";
       uses apply-advanced;
       choice metric_action {
         case case_1 {
           leaf metric {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
         case case_4 {
           container igp {
             presence "enable igp";
             description "Track the IGP metric (BGP only)";
             leaf metric_offset {
               description "Metric offset for MED";
               type union {
                 type int32;
                 type string {
                   pattern "<.*>|$.*";
                 }
               }
             }
           }
         }
         case case_5 {
           container minimum-igp {
             presence "enable minimum-igp";
             description "Track the minimum IGP metric (BGP only)";
             leaf metric_offset {
               description "Metric offset for MED";
               type union {
                 type int32;
                 type string {
                   pattern "<.*>|$.*";
                 }
               }
             }
           }
         }
         case case_6 {
           container expression {
             description "Calculate value based on route metric and metric2";
             uses metric_expression_type;
           }
         }
         case case_7 {
           leaf aigp {
             description "Use aigp, if it exists, to set the IGP metric";
             type empty;
           }
         }
       }
     }
     container metric2 {
       description "Metric value 2";
       uses apply-advanced;
       choice metric_action {
         case case_1 {
           leaf metric2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric3 {
       description "Metric value 3";
       uses apply-advanced;
       choice metric_action {
         case case_1 {
           leaf metric3 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container metric4 {
       description "Metric value 4";
       uses apply-advanced;
       choice metric_action {
         case case_1 {
           leaf metric4 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag {
       description "Tag string";
       uses apply-advanced;
       choice metric_action {
         case case_1 {
           leaf tag {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container tag2 {
       description "Tag string 2";
       uses apply-advanced;
       choice metric_action {
         case case_1 {
           leaf tag2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference {
       description "Preference value";
       uses apply-advanced;
       choice metric_action {
         case case_1 {
           leaf preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container preference2 {
       description "Preference value 2";
       uses apply-advanced;
       choice metric_action {
         case case_1 {
           leaf preference2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color {
       description "Color (preference) value";
       uses apply-advanced;
       choice metric_action {
         case case_1 {
           leaf color {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container color2 {
       description "Color (preference) value 2";
       uses apply-advanced;
       choice metric_action {
         case case_1 {
           leaf color2 {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     container local-preference {
       description "Local preference associated with a route";
       uses apply-advanced;
       choice metric_action {
         case case_1 {
           leaf local-preference {
             type union {
               type uint32;
               type string {
                 pattern "<.*>|$.*";
               }
             }
           }
         }
         case case_2 {
           leaf add {
             description "Add constant to attribute";
             type union {
               type uint32;
               type string {
                 pattern "<.*>|$.*";
               }
             }
           }
         }
         case case_3 {
           leaf subtract {
             description "Subtract constant from attribute";
             type union {
               type uint32;
               type string {
                 pattern "<.*>|$.*";
               }
             }
           }
         }
       }
     }
     leaf priority {
       description "Set priority for route installation";
       type enumeration {
         enum "high" {
           description "Set priority to high";
         }
         enum "medium" {
           description "Set priority to medium";
         }
         enum "low" {
           description "Set priority to low";
         }
       }
     }
     container prefix-segment {
       description "Set prefix segment attributes";
       leaf index {
         description "Set prefix segment index ";
         type union {
           type string {
             pattern "<.*>|$.*";
           }
           type uint32 {
             range "0 .. 199999";
           }
         }
       }
       leaf node-segment {
         description "Set node segment flag for this prefix segment";
         type empty;
       }
     }
     leaf label-allocation {
       description "Set label allocation mode";
       type enumeration {
         enum "per-table" {
           description "Set per-table label allocation mode";
         }
         enum "per-nexthop" {
           description "Set per-nexthop label allocation mode";
         }
         enum "per-table-localize" {
           description "Set per-table-localize label allocation mode";
         }
       }
     }
     container add-path {
       description "Set BGP add-path attributes";
       leaf send-count {
         description "Number of add-paths sent";
         type union {
           type string {
             pattern "<.*>|$.*";
           }
           type uint32 {
             range "2 .. 64";
           }
         }
       }
     }
     leaf validation-state {
       description "Set validation-state of a route";
       type enumeration {
         enum "valid" {
           description "Set validaton-state to valid";
         }
         enum "invalid" {
           description "Set validation-state to invalid";
         }
         enum "unknown" {
           description "Set validation-state to unknown";
         }
       }
     }
     leaf origin {
       description "BGP path origin";
       type enumeration {
         enum "igp" {
           description "Path originated in the local IGP";
         }
         enum "egp" {
           description "Path originated in another AS";
         }
         enum "incomplete" {
           description "Path was learned by some other means";
         }
       }
     }
     container aigp-originate {
       presence "enable aigp-originate";
       description "Originate a BGP AIGP attribute";
       leaf distance {
         description "AIGP distance";
         type union {
           type uint32;
           type string {
             pattern "<.*>|$.*";
           }
         }
       }
     }
     container aigp-adjust {
       description "Adjust a BGP AIGP attribute";
       choice math-op {
         case case_1 {
           leaf add {
             type empty;
           }
         }
         case case_2 {
           leaf subtract {
             type empty;
           }
         }
         case case_3 {
           leaf multiply {
             type empty;
           }
         }
         case case_4 {
           leaf divide {
             type empty;
           }
         }
       }
       choice adjust-value {
         case case_1 {
           leaf user-value {
             description "Adjustment value";
             type union {
               type uint64;
               type string {
                 pattern "<.*>|$.*";
               }
             }
           }
         }
         case case_2 {
           leaf distance-to-protocol-nexthop {
             description "Metric2";
             type empty;
           }
         }
       }
     }
     list community {
       key "choice-ident choice-value community-name";
       ordered-by user;
       description "BGP community properties associated with a route";
       leaf choice-ident {
         type enumeration {
           enum "equal-literal" {
           }
           enum "set" {
           }
           enum "plus-literal" {
           }
           enum "add" {
           }
           enum "minus-literal" {
           }
           enum "delete" {
           }
           enum "community-name" {
           }
         }
       }
       leaf choice-value {
         type string;
       }
       leaf community-name {
         description "Name to identify a BGP community";
         type string;
       }
     }
     leaf damping {
       description "Define BGP route flap damping parameters";
       type string;
     }
     leaf aggregate-bandwidth {
       description "Advertise aggregate outbound link bandwidth";
       type empty;
     }
     leaf limit-bandwidth {
       description "Limit advertised aggregate outbound link bandwidth";
       type union {
         type string {
           pattern "<.*>|$.*";
         }
         type uint32 {
           range "0 .. 4294967295";
         }
       }
     }
     leaf no-entropy-label-capability {
       description "Don't advertise entropy label capability";
       type empty;
     }
     leaf as-path-prepend {
       description "Prepend AS numbers to an AS path (BGP only)";
       type string;
     }
     container as-path-expand {
       description "Prepend AS numbers prior to adding local-as (BGP only)";
       choice aspath_exp_value {
         case case_1 {
           container last-as {
             presence "enable last-as";
             description "Prepend last AS";
             leaf count {
               description "Repeat count";
               type union {
                 type string {
                   pattern "<.*>|$.*";
                 }
                 type uint32 {
                   range "1 .. 32";
                 }
               }
             }
           }
         }
         case case_2 {
           leaf aspath {
             description "AS path string";
             type string;
           }
         }
       }
     }
     container next-hop {
       description "Set the address of the next-hop router";
       choice nexthop_value {
         case case_1 {
           leaf self {
             description "Use a local address as the next-hop address";
             type empty;
           }
         }
         case case_2 {
           leaf peer-address {
             description "Use the remote peer address as the next-hop address";
             type empty;
           }
         }
         case case_3 {
           leaf address {
             description "Next-hop address";
             type jt:ipaddr;
           }
         }
         case case_4 {
           leaf reject {
             description "Use a reject next hop";
             type empty;
           }
         }
         case case_5 {
           leaf discard {
             description "Use a discard next hop";
             type empty;
           }
         }
         case case_6 {
           leaf next-table {
             description "Perform a forwarding lookup in the specified table";
             type string;
           }
         }
       }
     }
     container install-nexthop {
       description "Choose the next hop to be used for forwarding";
       leaf strict {
         description "Do not use any other available next hops";
         type empty;
       }
       choice nexthop-value {
         case case_1 {
           leaf-list lsp {
             ordered-by user;
             description "Next-hop LSP name";
             type string;
           }
         }
         case case_2 {
           leaf-list lsp-regex {
             ordered-by user;
             description "Next-hop LSP name regular expression";
             type string;
           }
         }
         case case_3 {
           leaf-list static-lsp {
             ordered-by user;
             description "Next-hop static LSP name";
             type string;
           }
         }
         case case_4 {
           leaf-list static-lsp-regex {
             ordered-by user;
             description "Next-hop static LSP name regular expression";
             type string;
           }
         }
       }
       container except {
         description "Do not choose to install matching next hops";
         uses apply-advanced;
         choice nexthop-value {
           case case_1 {
             leaf-list lsp {
               ordered-by user;
               description "Next-hop LSP name";
               type string;
             }
           }
           case case_2 {
             leaf-list lsp-regex {
               ordered-by user;
               description "Next-hop LSP name regular expression";
               type string;
             }
           }
           case case_3 {
             leaf-list static-lsp {
               ordered-by user;
               description "Next-hop static LSP name";
               type string;
             }
           }
           case case_4 {
             leaf-list static-lsp-regex {
               ordered-by user;
               description "Next-hop static LSP name regular expression";
               type string;
             }
           }
         }
       }
     }
     leaf trace {
       description "Log matches to a trace file";
       type empty;
     }
     container external {
       presence "enable external";
       description "External route";
       uses apply-advanced;
       leaf type {
         description "OSPF external metric type";
         type union {
           type string {
             pattern "<.*>|$.*";
           }
           type int32 {
             range "1 .. 2";
           }
         }
       }
       leaf nssa-only {
         description "Clear P-bit on lsa type 7";
         type empty;
       }
     }
     container load-balance {
       description "Type of load balancing in forwarding table";
       choice load_balance_type {
         case case_1 {
           leaf per-packet {
             description "Load balance on a per-packet basis";
             type empty;
           }
         }
         case case_2 {
         }
         case case_3 {
         }
         case case_4 {
           leaf consistent-hash {
             description "Give a prefix consistent load-balancing";
             type empty;
           }
         }
         case case_5 {
         }
         case case_6 {
         }
       }
     }
     leaf analyze {
       description "Send to registered controllers for analysis";
       type empty;
     }
     leaf class {
       description "Set class-of-service parameters";
       type string;
     }
     leaf destination-class {
       description "Set destination class in forwarding table";
       type string;
     }
     leaf source-class {
       description "Set source class in forwarding table";
       type string;
     }
     leaf forwarding-class {
       description "Set source or destination class in forwarding table";
       type string;
     }
     container map-to-interface {
       description "Set output logical interface";
       choice map_to_interface_value {
         case case_1 {
           leaf self {
             description "Map the interface to itself";
             type empty;
           }
         }
         case case_2 {
           leaf interface {
             description "Output logical interface";
             type union {
               type jt:interface-name;
               type string {
                 pattern "<.*>|$.*";
               }
             }
           }
         }
       }
     }
     leaf-list ssm-source {
       ordered-by user;
       description "List of Sources for SSM mapping";
       type jt:ipaddr;
     }
     container p2mp-lsp-root {
       description "P2mp lsp root address";
       uses apply-advanced;
       leaf address {
         description "Ipv4 root address";
         type jt:ipv4addr;
       }
     }
     leaf cos-next-hop-map {
       description "Set CoS-based next-hop map in forwarding table";
       type string;
     }
     leaf dynamic-tunnel-attributes {
       description "Choose the dynamic tunnel attributes used for forwarding";
       type string;
     }
     leaf selected-mldp-egress {
       description "This node should act as egress node for MLDP inband signalling";
       type empty;
     }
     leaf mhop-bfd-port {
       description "Use port number 4784 for MPLS-BFD as per RFC5884";
       type empty;
     }
     leaf no-backup {
       description "This prefix should not have backup";
       type empty;
     }
     leaf default-action {
       description "Set default policy action";
       type enumeration {
         enum "accept" {
           description "Accept a route";
         }
         enum "reject" {
           description "Reject a route";
         }
       }
     }
     leaf next {
       description "Skip to next policy or term";
       type enumeration {
         enum "policy" {
           description "Skip to next policy filter";
         }
         enum "term" {
           description "Skip to next term in a policy filter";
         }
       }
     }
     choice accept_reject {
       case case_1 {
         leaf accept {
           description "Accept a route";
           type empty;
         }
       }
       case case_2 {
         leaf reject {
           description "Reject a route";
           type empty;
         }
       }
     }
     container bgp-output-queue-priority {
       description "Set the BGP Update output queue priority.";
       choice class {
         case case_1 {
           leaf priority {
             description "Output queue priority; higher is better";
             type union {
               type string {
                 pattern "<.*>|$.*";
               }
               type uint32 {
                 range "1 .. 16";
               }
             }
           }
         }
         case case_2 {
           leaf expedited {
             description "Expedited queue; highest priority";
             type empty;
           }
         }
       }
     }
     leaf multipath-resolve {
       description "Use all paths for resolution over this prefix";
       type empty;
     }
     leaf label-allocation-fallback-reject {
       description "Suppress prefix export when label allocation fails";
       type empty;
     }
   }
   grouping srd-ev-action-object {
     description "Action to be taken on the occurence if defined events";
     uses apply-advanced;
     leaf mship-actions {
       description "Mastership related actions";
       type enumeration {
         enum "acquire-mastership" {
           description "Attempt to acquire mastership";
         }
         enum "release-mastership" {
           description "Attempt to release mastership";
         }
         enum "release-mastership-force" {
           description "Attempt to release mastership";
         }
         enum "release-mastership-if-standby-clear" {
           description "Attempt to release mastership if standby has no warning";
         }
         enum "broadcast-warning" {
           description "Attempt to release mastership";
         }
       }
     }
     list add-static-route {
       key name;
       ordered-by user;
       description "Add a static route in the specified routing table";
       max-elements 1;
       uses srd-route-add-object;
     }
     list delete-static-route {
       key name;
       ordered-by user;
       description "Delete a static route in the specified routing table";
       max-elements 1;
       uses srd-route-delete-object;
     }
   }
   grouping srd-route-add-object {
     description "Route details";
     leaf name {
       description " Destination route address with prefix length";
       type jt:ipv4prefix-mandatory;
     }
     uses apply-advanced;
     choice next-hop-details {
       case case_1 {
         leaf next-hop {
           description "Next-hop (interface) to destination";
           type string;
         }
       }
       case case_2 {
         leaf receive {
           description "Install a receive route for the destination";
           type empty;
         }
       }
     }
     leaf routing-instance {
       description "Routing instance where the route should be added";
       type string;
     }
   }
   grouping srd-route-delete-object {
     description "Route details";
     leaf name {
       description "Destination route address with prefix length";
       type jt:ipv4prefix-mandatory;
     }
     uses apply-advanced;
     leaf routing-instance {
       description "Routing instance where the route should be added";
       type string;
     }
   }
   grouping ssg-destination-nat-object {
     uses apply-advanced;
     list pool {
       key name;
       ordered-by user;
       description "Define a destination address pool";
       leaf name {
         description "Pool name";
         type string {
           length "1 .. 31";
         }
       }
       uses apply-advanced;
       leaf description {
         description "Text description of pool";
         type string {
           length "1 .. 900";
         }
       }
       container routing-instance {
         description "Routing instance";
         uses apply-advanced;
         choice ri-name-choice {
           case case_1 {
             leaf default {
               description "Default routing-instance";
               type empty;
             }
           }
           case case_2 {
             leaf ri-name {
               description "Routing-instance name";
               type string {
               }
             }
           }
         }
       }
       container address {
         description "Add address or address range to pool";
         leaf ipaddr {
           description "IPv4 or IPv6 address or address range";
           type jt:ipprefix;
         }
         choice range-port-choice {
           case case_1 {
             container to {
               description "Upper limit of address range";
               uses apply-advanced;
               leaf ipaddr {
                 description "IPv4 or IPv6 upper limit of address range";
                 type jt:ipprefix;
               }
             }
           }
           case case_2 {
             leaf port {
               description "Specify the port value";
               type union {
                 type uint16;
                 type string {
                   pattern "<.*>|$.*";
                 }
               }
             }
           }
         }
       }
     }
     list port-forwarding {
       key name;
       ordered-by user;
       description "Define a port-forwarding mapping pool";
       leaf name {
         description "Port Forwarding mapping name";
         type string {
           length "1 .. 31";
         }
       }
       uses apply-advanced;
       leaf description {
         description "Text description of port forwarding mapping";
         type string {
           length "1 .. 900";
         }
       }
       list destined-port {
         key "port translated-port";
         ordered-by user;
         description "Port forwarding mappings";
         max-elements 32;
         leaf port {
           description "Destination port";
           type union {
             type string {
               pattern "<.*>|$.*";
             }
             type uint16 {
               range "1 .. 65535";
             }
           }
         }
         leaf translated-port {
           description "Translated port";
           type union {
             type string {
               pattern "<.*>|$.*";
             }
             type uint16 {
               range "1 .. 65535";
             }
           }
         }
       }
     }
     list rule-set {
       key name;
       ordered-by user;
       description "Configurate a set of rules";
       leaf name {
         description "Rule-set name";
         type string {
           length "1 .. 31";
         }
       }
       uses apply-advanced;
       leaf description {
         description "Text description of rule set";
         type string {
           length "1 .. 900";
         }
       }
       container from {
         description "Where is the traffic from";
         choice from-context-choice {
           case case_1 {
             leaf-list routing-instance {
               description "Source routing instance list";
               type string;
               max-elements 8;
             }
           }
           case case_2 {
             leaf-list zone {
               description "Source zone list";
               type string;
               max-elements 8;
             }
           }
           case case_3 {
             leaf-list interface {
               description "Source interface list";
               type union {
                 type jt:interface-name;
                 type string {
                   pattern "<.*>|$.*";
                 }
               }
               max-elements 8;
             }
           }
         }
       }
       list rule {
         key name;
         ordered-by user;
         description "Destination NAT rule";
         uses dest-nat-rule-object;
       }
       leaf match-direction {
         description "Match direction";
         type enumeration {
           enum "input" {
             description "Match on input to interface";
           }
           enum "output" {
             description "Match on output from interface";
           }
         }
       }
     }
   }
   grouping dest-nat-rule-object {
     leaf name {
       description "Rule name";
       type string {
         length "1 .. 31";
       }
     }
     uses apply-advanced;
     leaf description {
       description "Text description of rule";
       type string {
         length "1 .. 900";
       }
     }
     container dest-nat-rule-match {
       description "Specify Destination NAT rule match criteria";
       uses apply-advanced;
       leaf-list source-address {
         ordered-by user;
         description "Source address";
         type string;
         max-elements 8;
       }
       leaf-list source-address-name {
         ordered-by user;
         description "Address/address-set from address book";
         type string;
         max-elements 8;
       }
       choice dst-choice {
         case case_1 {
           container destination-address {
             description "Destination address";
             choice dst-addr-choice {
               case case_1 {
                 leaf dst-addr {
                   description "IPv4 or IPv6 destination address";
                   type jt:ipprefix;
                 }
               }
               case case_2 {
                 leaf any-unicast {
                   description "Match any unicast address";
                   type empty;
                 }
               }
             }
           }
         }
         case case_2 {
           container destination-address-name {
             description "Address from address book";
             leaf dst-addr-name {
               description "Address from address book";
               type string {
                 length "1 .. 63";
               }
             }
           }
         }
       }
       list destination-port {
         key name;
         ordered-by user;
         description "Destination port";
         max-elements 8;
         leaf name {
           description "Port or lower limit of port range";
           type union {
             type uint16;
             type string {
               pattern "<.*>|$.*";
             }
           }
         }
         container to {
           description "Port range upper limit";
           uses apply-advanced;
           leaf high {
             description "Upper limit of port range";
             type union {
               type uint16;
               type string {
                 pattern "<.*>|$.*";
               }
             }
           }
         }
       }
       leaf-list protocol {
         ordered-by user;
         description "IP Protocol";
         type string;
         max-elements 4;
       }
       leaf-list application {
         ordered-by user;
         type string;
       }
     }
     container then {
       description "Then action";
       uses apply-advanced;
       container destination-nat {
         description "Destination NAT action";
         uses apply-advanced;
         choice action {
           case case_1 {
             leaf off {
               description "No action";
               type empty;
             }
           }
           case case_2 {
             container pool {
               description "Use Destination NAT pool";
               uses apply-advanced;
               leaf pool-name {
                 description "Name of Destination NAT pool";
                 type string {
                   length "1 .. 31";
                 }
               }
             }
           }
           case case_3 {
             leaf destination-prefix {
               description "Destination prefix to be used for NAT64 and 464 translation type";
               type jt:ipprefix-only;
             }
           }
         }
         container port-forwarding-mappings {
           description "Use Destination NAT port forwarding mapping pool";
           uses apply-advanced;
           leaf pf-name {
             description "Name of Port forwarding mappings";
             type string {
               length "1 .. 31";
             }
           }
         }
         container rule-session-count-alarm {
           description "Config rule-session-count-alarm to destination rule";
           uses nat-rule-session-count-alarm-object;
         }
       }
       leaf syslog {
         description "System log information about the packet";
         type empty;
       }
     }
   }
   grouping nat-rule-session-count-alarm-object {
     uses apply-advanced;
     leaf raise-threshold {
       description "Raise threshold for rule session count alarm";
       type union {
         type string {
           pattern "<.*>|$.*";
         }
         type uint32 {
           range "1 .. 4294967295";
         }
       }
     }
     leaf clear-threshold {
       description "Clear threshold for session count hit alarm";
       type union {
         type string {
           pattern "<.*>|$.*";
         }
         type uint32 {
           range "1 .. 4294967295";
         }
       }
     }
   }
   grouping ssg-proxy-arp-object {
     uses apply-advanced;
     list interface {
       key name;
       ordered-by user;
       description "Interface with proxy arp configured";
       uses ssg-interface-object;
     }
   }
   grouping ssg-interface-object {
     leaf name {
       description "Interface name";
       type union {
         type jt:interface-name;
         type string {
           pattern "<.*>|$.*";
         }
       }
     }
     uses apply-advanced;
     list address {
       key name;
       ordered-by user;
       description "Proxy ARP address";
       leaf name {
         description "Address or address range";
         type jt:ipv4prefix;
       }
       container to {
         description "Upper limit of address range";
         uses apply-advanced;
         leaf ipaddr {
           description "Upper limit of address range";
           type jt:ipv4prefix;
         }
       }
     }
   }
   grouping ssg-proxy-ndp-object {
     uses apply-advanced;
     list interface {
       key name;
       ordered-by user;
       description "Interface with proxy arp configured";
       uses ssg-proxy-ndp-interface-object;
     }
   }
   grouping ssg-proxy-ndp-interface-object {
     leaf name {
       description "Interface name";
       type union {
         type jt:interface-name;
         type string {
           pattern "<.*>|$.*";
         }
       }
     }
     uses apply-advanced;
     list address {
       key name;
       ordered-by user;
       description "Proxy ndp address";
       leaf name {
         description "Address or address range";
         type jt:ipv6prefix;
       }
       container to {
         description "Upper limit of address range";
         uses apply-advanced;
         leaf ipv6addr {
           description "Upper limit of address range";
           type jt:ipv6addr;
         }
       }
     }
   }
   grouping ssg-source-nat-object {
     uses apply-advanced;
     list pool {
       key name;
       ordered-by user;
       description "Define a source address pool";
       leaf name {
         description "Pool name";
         type string {
           length "1 .. 31";
         }
       }
       uses apply-advanced;
       leaf description {
         description "Text description of pool";
         type string {
           length "1 .. 900";
         }
       }
       container routing-instance {
         description "Routing instance";
         uses apply-advanced;
         leaf ri-name {
           description "Routing instance name";
           type string {
           }
         }
       }
       list address {
         key name;
         ordered-by user;
         description "Add address to pool";
         max-elements 8;
         leaf name {
           description "IPv4 or IPv6 address or address range";
           type jt:ipprefix;
         }
         container to {
           description "Upper limit of address range";
           uses apply-advanced;
           leaf ipaddr {
             description "IPv4 or IPv6 upper limit of address range";
             type jt:ipprefix;
           }
         }
       }
       container host-address-base {
         description "The base of host address";
         leaf ipaddr {
           description "IPv4 or IPv6 base address";
           type jt:ipprefix;
         }
       }
       container port {
         description "Config port attribute to pool";
         uses apply-advanced;
         choice port-choice {
           case case_1 {
             leaf no-translation {
               description "Do not perform port translation";
               type empty;
             }
           }
           case case_2 {
             container range {
               description "Port range";
               uses apply-advanced;
               leaf low {
                 description "Lower limit of port range";
                 type union {
                   type string {
                     pattern "<.*>|$.*";
                   }
                   type uint16 {
                     range "1024 .. 65535";
                   }
                 }
               }
               container to {
                 description "Port range upper limit";
                 uses apply-advanced;
                 leaf high {
                   description "Upper limit of port range";
                   type union {
                     type string {
                       pattern "<.*>|$.*";
                     }
                     type uint16 {
                       range "1024 .. 65535";
                     }
                   }
                 }
               }
               container twin-port {
                 description "Twin port range";
                 uses apply-advanced;
                 leaf low {
                   description "Lower limit of twin port range";
                   type union {
                     type string {
                       pattern "<.*>|$.*";
                     }
                     type uint16 {
                       range "63488 .. 65535";
                     }
                   }
                 }
                 container to {
                   description "Twin port range upper limit";
                   uses apply-advanced;
                   leaf high {
                     description "Upper limit of twin port range";
                     type union {
                       type string {
                         pattern "<.*>|$.*";
                       }
                       type uint16 {
                         range "63488 .. 65535";
                       }
                     }
                   }
                 }
               }
             }
           }
         }
         leaf port-overloading-factor {
           description "Port overloading factor for each IP";
           type union {
             type string {
               pattern "<.*>|$.*";
             }
             type uint16 {
               range "2 .. 32";
             }
           }
         }
         container block-allocation {
           description "Port block allocation";
           presence "enable block-allocation";
           uses block-allocation-object;
         }
         container deterministic {
           description "Deterministic nat allocation";
           presence "enable deterministic";
           uses deterministic-object;
         }
         leaf preserve-parity {
           description "Allocate port as the same parity as incoming port";
           type empty;
         }
         leaf preserve-range {
           description "Allocate port from the same port range as incoming port";
           type empty;
         }
         container automatic {
           description "Port assignment";
           uses apply-advanced;
           choice port-assign-choice {
             case case_1 {
               leaf random-allocation {
                 description "Allocate port randomly";
                 type empty;
               }
             }
             case case_2 {
               leaf round-robin {
                 description "Allocate port by round-robin";
                 type empty;
               }
             }
           }
         }
       }
       container overflow-pool {
         description "Specify an overflow pool";
         choice overflow-pool-choice {
           case case_1 {
             leaf pool-name {
               description "Name of source address pool";
               type string {
                 length "1 .. 31";
               }
             }
           }
           case case_2 {
             leaf interface {
               description "Allow interface pool to support overflow";
               type empty;
             }
           }
         }
       }
       leaf address-shared {
         description "Allow multiple hosts to share an externel address";
         type empty;
       }
       container address-pooling {
         description "Specify the address-pooling behavior";
         choice pooling-choice {
           case case_1 {
             leaf paired {
               description "Allow address-pooling paired for a source pool with port translation";
               type empty;
             }
           }
           case case_2 {
             leaf no-paired {
               description "Allow address-pooling no-paired for a source pool without port translation";
               type empty;
             }
           }
         }
       }
       container address-persistent {
         description "Specify the address-persistent behavior";
         container subscriber {
           description "Configure address persistent for subscriber";
           leaf ipv6-prefix-length {
             description "Ipv6 prefix length for address persistent";
             type union {
               type string {
                 pattern "<.*>|$.*";
               }
               type uint16 {
                 range "8 .. 128";
               }
             }
           }
         }
       }
       container pool-utilization-alarm {
         description "Config pool-utilization-alarm to pool";
         uses source-nat-pool-utilization-alarm-object;
       }
       leaf ei-mapping-timeout {
         description "Endpoint-independent mapping timeout";
         units "second";
         type union {
           type string {
             pattern "<.*>|$.*";
           }
           type uint32 {
             range "120 .. 86400";
           }
         }
       }
       leaf mapping-timeout {
         description "Address-pooling paired and endpoint-independent mapping timeout";
         units "second";
         type union {
           type string {
             pattern "<.*>|$.*";
           }
           type uint32 {
             range "120 .. 86400";
           }
         }
       }
       leaf limit-ports-per-host {
         description "Number of ports allocated per host";
         type union {
           type string {
             pattern "<.*>|$.*";
           }
           type uint16 {
             range "2 .. 65535";
           }
         }
       }
     }
     leaf address-persistent {
       description "Allow source address to maintain same translation";
       type empty;
     }
     leaf session-persistence-scan {
       description "Allow source to maintain session when session scan";
       type empty;
     }
     leaf session-drop-hold-down {
       description "Session drop hold down time";
       type union {
         type string {
           pattern "<.*>|$.*";
         }
         type uint16 {
           range "30 .. 28800";
         }
       }
     }
     container pool-utilization-alarm {
       description "Configure pool utilization alarm";
       uses source-nat-pool-utilization-alarm-object;
     }
     container port-randomization {
       description "Configure Source NAT port randomization";
       choice enable-disable {
         case case_1 {
           leaf disable {
             description "Disable Source NAT port randomization";
             type empty;
           }
         }
       }
     }
     container port-round-robin {
       description "Configure Source NAT port randomization";
       choice enable-disable {
         case case_1 {
           leaf disable {
             description "Disable Source NAT port randomization";
             type empty;
           }
         }
       }
     }
     leaf port-scaling-enlargement {
       description "Configure source port scaling to 2.4G only for NGSPC";
       type empty;
     }
     leaf pool-distribution {
       description "Configure Source pool distribution, the APPCP bottleneck of NAT CPS can be alleviated.";
       type empty;
     }
     container pool-default-port-range {
       description "Configure Source NAT default port range";
       leaf low {
         description "Lower limit of port range";
         type union {
           type string {
             pattern "<.*>|$.*";
           }
           type uint16;
         }
       }
       container to {
         description "Port range upper limit";
         uses apply-advanced;
         leaf high {
           description "Upper limit of port range";
           type union {
             type string {
               pattern "<.*>|$.*";
             }
             type uint16;
           }
         }
       }
     }
     container pool-default-twin-port-range {
       description "Configure Source NAT default twin port range";
       leaf low {
         description "Lower limit of twin port range";
         type union {
           type string {
             pattern "<.*>|$.*";
           }
           type uint16 {
             range "63488 .. 65535";
           }
         }
       }
       container to {
         description "Twin port range upper limit";
         uses apply-advanced;
         leaf high {
           description "Upper limit of twin port range";
           type union {
             type string {
               pattern "<.*>|$.*";
             }
             type uint16 {
               range "63488 .. 65535";
             }
           }
         }
       }
     }
     container interface {
       description "Configure interface port overloading for persistent NAT";
       uses apply-advanced;
       choice interface-choice {
         case case_1 {
           container port-overloading {
             description "Configure port overloading";
             leaf off {
               description "Turn off interface port over-loading";
               type empty;
             }
           }
         }
         case case_2 {
           leaf port-overloading-factor {
             description "Port overloading factor for interface NAT";
             type union {
               type uint16;
               type string {
                 pattern "<.*>|$.*";
               }
             }
           }
         }
       }
     }
     list rule-set {
       key name;
       ordered-by user;
       description "Configurate a set of rules";
       leaf name {
         description "Rule-set name";
         type string {
           length "1 .. 31";
         }
       }
       uses apply-advanced;
       leaf description {
         description "Text description of rule set";
         type string {
           length "1 .. 900";
         }
       }
       container from {
         description "Where is the traffic from";
         choice from-context-choice {
           case case_1 {
             leaf-list routing-instance {
               description "Source routing instance list";
               type string;
               max-elements 8;
             }
           }
           case case_2 {
             leaf-list zone {
               description "Source zone list";
               type string;
               max-elements 8;
             }
           }
           case case_3 {
             leaf-list interface {
               description "Source interface list";
               type union {
                 type jt:interface-name;
                 type string {
                   pattern "<.*>|$.*";
                 }
               }
               max-elements 8;
             }
           }
         }
       }
       container to {
         description "Where is the traffic to";
         choice from-context-choice {
           case case_1 {
             leaf-list routing-instance {
               description "Destination routing instance list";
               type string;
               max-elements 8;
             }
           }
           case case_2 {
             leaf-list zone {
               description "Destination zone list";
               type string;
               max-elements 8;
             }
           }
           case case_3 {
             leaf-list interface {
               description "Destination interface list";
               type union {
                 type jt:interface-name;
                 type string {
                   pattern "<.*>|$.*";
                 }
               }
               max-elements 8;
             }
           }
         }
       }
       list rule {
         key name;
         ordered-by user;
         description "Source NAT rule";
         uses src-nat-rule-object;
       }
       leaf match-direction {
         description "Match direction";
         type enumeration {
           enum "input" {
             description "Match on input to interface";
           }
           enum "output" {
             description "Match on output from interface";
           }
         }
       }
     }
   }
   grouping block-allocation-object {
     description "Port block allocation";
     uses apply-advanced;
     leaf block-size {
       description "Block size";
       type union {
         type string {
           pattern "<.*>|$.*";
         }
         type uint16;
       }
     }
     leaf maximum-blocks-per-host {
       description "Maximum block number per host";
       type union {
         type string {
           pattern "<.*>|$.*";
         }
         type uint16 {
           range "1 .. 512";
         }
       }
     }
     leaf active-block-timeout {
       description "Active block timeout interval";
       type union {
         type string {
           pattern "<.*>|$.*";
         }
         type uint32;
       }
     }
     leaf interim-logging-interval {
       description "Interim Logging interval";
       type union {
         type string {
           pattern "<.*>|$.*";
         }
         type uint32 {
           range "1800 .. 86400";
         }
       }
     }
     leaf last-block-recycle-timeout {
       description "Last Block recycle timeout interval";
       type union {
         type string {
           pattern "<.*>|$.*";
         }
         type uint32 {
           range "120 .. 864000";
         }
       }
     }
     container log {
       description "Configure port block log";
       choice enable-disable {
         case case_1 {
           leaf disable {
             description "Disable PBA port block log";
             type empty;
           }
         }
       }
     }
   }
   grouping deterministic-object {
     description "Deterministic nat allocation";
     uses apply-advanced;
     leaf block-size {
       description "Block size";
       type union {
         type string {
           pattern "<.*>|$.*";
         }
         type uint16;
       }
     }
     leaf det-nat-configuration-log-interval {
       description "Deterministic nat configuration logging interval";
       type union {
         type string {
           pattern "<.*>|$.*";
         }
         type uint32 {
           range "1800 .. 86400";
         }
       }
     }
     container host {
       description "Host address";
       leaf-list address {
         ordered-by user;
         description "Host ip address";
         type jt:ipprefix;
         max-elements 8;
       }
       leaf-list address-name {
         ordered-by user;
         description "Host address/address-set from address book";
         type string;
         max-elements 8;
       }
     }
     leaf include-boundary-addresses {
       description "Include network and broadcast in 'match' source address";
       type empty;
     }
   }
   grouping source-nat-pool-utilization-alarm-object {
     uses apply-advanced;
     leaf raise-threshold {
       description "Raise threshold for pool utilization alarm";
       type union {
         type string {
           pattern "<.*>|$.*";
         }
         type uint16 {
           range "50 .. 100";
         }
       }
     }
     leaf clear-threshold {
       description "Clear threshold for pool utilization alarm";
       type union {
         type string {
           pattern "<.*>|$.*";
         }
         type uint16 {
           range "40 .. 100";
         }
       }
     }
   }
   grouping src-nat-rule-object {
     leaf name {
       description "Source NAT Rule name";
       type string {
         length "1 .. 31";
       }
     }
     uses apply-advanced;
     leaf description {
       description "Text description of rule";
       type string {
         length "1 .. 900";
       }
     }
     container src-nat-rule-match {
       description "Specify Source NAT rule match criteria";
       uses apply-advanced;
       leaf-list source-address {
         ordered-by user;
         description "Source address";
         type string;
         max-elements 8;
       }
       leaf-list source-address-name {
         ordered-by user;
         description "Address/address-set from address book";
         type string;
         max-elements 8;
       }
       list source-port {
         key name;
         ordered-by user;
         description "Source port";
         max-elements 8;
         leaf name {
           description "Port or lower limit of port range";
           type union {
             type uint16;
             type string {
               pattern "<.*>|$.*";
             }
           }
         }
         container to {
           description "Port range upper limit";
           uses apply-advanced;
           leaf high {
             description "Upper limit of port range";
             type union {
               type uint16;
               type string {
                 pattern "<.*>|$.*";
               }
             }
           }
         }
       }
       leaf-list destination-address {
         ordered-by user;
         description "Destination address";
         type string;
         max-elements 8;
       }
       leaf-list destination-address-name {
         ordered-by user;
         description "Address/address-set from address book";
         type string;
         max-elements 8;
       }
       list destination-port {
         key name;
         ordered-by user;
         description "Destination port";
         max-elements 8;
         leaf name {
           description "Port or lower limit of port range";
           type union {
             type uint16;
             type string {
               pattern "<.*>|$.*";
             }
           }
         }
         container to {
           description "Port range upper limit";
           uses apply-advanced;
           leaf high {
             description "Upper limit of port range";
             type union {
               type uint16;
               type string {
                 pattern "<.*>|$.*";
               }
             }
           }
         }
       }
       leaf-list protocol {
         ordered-by user;
         description "IP Protocol";
         type string;
         max-elements 4;
       }
       leaf-list application {
         ordered-by user;
         type string;
       }
     }
     container then {
       description "Then action";
       uses apply-advanced;
       container source-nat {
         description "Source NAT action";
         uses apply-advanced;
         choice action {
           case case_1 {
             leaf off {
               description "No action";
               type empty;
             }
           }
           case case_2 {
             container pool {
               description "Use Source NAT pool";
               uses apply-advanced;
               leaf pool-name {
                 description "Name of Source NAT pool";
                 type string {
                   length "1 .. 31";
                 }
               }
               container persistent-nat {
                 description "Persistent NAT info";
                 presence "enable persistent-nat";
                 uses persistent-nat-object;
               }
             }
           }
           case case_3 {
             container interface {
               presence "enable interface";
               description "Use egress interface address";
               uses apply-advanced;
               container persistent-nat {
                 description "Persistent NAT info";
                 presence "enable persistent-nat";
                 uses persistent-nat-object;
               }
             }
           }
         }
         leaf clat-prefix {
           description "An IPv6 prefix to be used for XLAT464 and prefix length can only be 32/40/48/56/64/96";
           type jt:ipprefix-only;
         }
         container rule-session-count-alarm {
           description "Config rule-session-count-alarm to source rule";
           uses nat-rule-session-count-alarm-object;
         }
         container mapping-type {
           description "Source nat mapping type";
           leaf endpoint-independent {
             description "Endpoint independent mapping";
             type empty;
           }
         }
         container secure-nat-mapping {
           description "Mapping options for enhanced security";
           leaf eif-flow-limit {
             description "Number of inbound flows to be allowed for a EIF mapping";
             type union {
               type string {
                 pattern "<.*>|$.*";
               }
               type uint16 {
                 range "0 .. 65534";
               }
             }
           }
           container mapping-refresh {
             description "Enable timer refresh option";
             choice refresh-choice {
               case case_1 {
                 leaf inbound {
                   description "Enable timer refresh for inbound connections only";
                   type empty;
                 }
               }
               case case_2 {
                 leaf outbound {
                   description "Enable timer refresh for outbound connections only";
                   type empty;
                 }
               }
               case case_3 {
                 leaf inbound-outbound {
                   description "Enable timer refresh for inbound & outbound connections";
                   type empty;
                 }
               }
             }
           }
         }
         container filtering-type {
           description "Source NAT filtering type";
           uses apply-advanced;
           container endpoint-independent {
             presence "enable endpoint-independent";
             description "Endpoint independent filtering";
             uses apply-advanced;
             list prefix-list {
               key name;
               ordered-by user;
               description "One or more named lists of source prefixes to match";
               leaf name {
                 description "Name of prefix list to match against";
                 type string {
                   length "1 .. 63";
                 }
               }
               leaf except {
                 description "Name of prefix list not to match against";
                 type empty;
               }
             }
           }
         }
       }
       leaf syslog {
         description "System log information about the packet";
         type empty;
       }
     }
   }
   grouping persistent-nat-object {
     uses apply-advanced;
     container permit {
       description "Persistent NAT permit configure";
       choice persistent-nat-type-choice {
         case case_1 {
           leaf any-remote-host {
             description "Permit any remote host";
             type empty;
           }
         }
         case case_2 {
           leaf target-host {
             description "Permit target host";
             type empty;
           }
         }
         case case_3 {
           leaf target-host-port {
             description "Permit target host port";
             type empty;
           }
         }
       }
     }
     leaf address-mapping {
       description "Address-to-address mapping";
       type empty;
     }
     leaf inactivity-timeout {
       description "Inactivity timeout value";
       type union {
         type string {
           pattern "<.*>|$.*";
         }
         type uint16 {
           range "60 .. 7200";
         }
       }
     }
     leaf max-session-number {
       description "The maximum session number value";
       type union {
         type string {
           pattern "<.*>|$.*";
         }
         type uint32 {
           range "8 .. 65536";
         }
       }
     }
   }
   grouping ssg-static-nat-object {
     uses apply-advanced;
     list rule-set {
       key name;
       ordered-by user;
       description "Configurate a set of rules";
       leaf name {
         description "Rule-set name";
         type string {
           length "1 .. 31";
         }
       }
       uses apply-advanced;
       leaf description {
         description "Text description of rule set";
         type string {
           length "1 .. 900";
         }
       }
       container from {
         description "Where is the traffic from";
         choice from-context-choice {
           case case_1 {
             leaf-list routing-instance {
               description "Source routing instance list";
               type string;
               max-elements 8;
             }
           }
           case case_2 {
             leaf-list zone {
               description "Source zone list";
               type string;
               max-elements 8;
             }
           }
           case case_3 {
             leaf-list interface {
               description "Source interface list";
               type union {
                 type jt:interface-name;
                 type string {
                   pattern "<.*>|$.*";
                 }
               }
               max-elements 8;
             }
           }
         }
       }
       list rule {
         key name;
         ordered-by user;
         description "Static NAT rule";
         uses static-nat-rule-object;
       }
     }
   }
   grouping static-nat-rule-object {
     leaf name {
       description "Static Rule name";
       type string {
         length "1 .. 31";
       }
     }
     uses apply-advanced;
     leaf description {
       description "Text description of rule";
       type string {
         length "1 .. 900";
       }
     }
     container static-nat-rule-match {
       description "Specify Static NAT rule match criteria";
       uses apply-advanced;
       leaf-list source-address {
         ordered-by user;
         description "Source address";
         type jt:ipprefix;
         max-elements 8;
       }
       leaf-list source-address-name {
         ordered-by user;
         description "Address from address book";
         type string;
         max-elements 8;
       }
       list source-port {
         key name;
         ordered-by user;
         description "Source port";
         max-elements 8;
         leaf name {
           description "Port or lower limit of port range";
           type union {
             type uint16;
             type string {
               pattern "<.*>|$.*";
             }
           }
         }
         container to {
           description "Port range upper limit";
           uses apply-advanced;
           leaf high {
             description "Upper limit of port range";
             type union {
               type uint16;
               type string {
                 pattern "<.*>|$.*";
               }
             }
           }
         }
       }
       choice dst-choice {
         case case_1 {
           container destination-address {
             description "Destination address";
             leaf dst-addr {
               description "IPv4 or IPv6 Destination address prefix";
               type jt:ipprefix;
             }
           }
         }
         case case_2 {
           container destination-address-name {
             description "Address from address book";
             leaf dst-addr-name {
               description "Address from address book";
               type string {
                 length "1 .. 63";
               }
             }
           }
         }
       }
       container destination-port {
         description "Destination port";
         leaf low {
           description "Port or lower limit of port range";
           type union {
             type uint16;
             type string {
               pattern "<.*>|$.*";
             }
           }
         }
         container to {
           description "Port range upper limit";
           uses apply-advanced;
           leaf high {
             description "Upper limit of port range";
             type union {
               type uint16;
               type string {
                 pattern "<.*>|$.*";
               }
             }
           }
         }
       }
     }
     container then {
       description "Then action";
       uses apply-advanced;
       container static-nat {
         description "Static NAT action";
         uses apply-advanced;
         choice prefix-choice {
           case case_1 {
             container inet {
               presence "enable inet";
               description "Translated to IPv4 address";
               uses apply-advanced;
               leaf routing-instance {
                 description "Routing instance";
                 type string;
               }
             }
           }
           case case_2 {
             container prefix {
               description "Address prefix";
               uses apply-advanced;
               leaf addr-prefix {
                 description "IPv4 or IPv6 address prefix value";
                 type jt:ipprefix;
               }
               container mapped-port {
                 description "Mapped port";
                 uses static-nat-rule-mapped-port-object;
               }
               leaf routing-instance {
                 description "Routing instance";
                 type string;
               }
             }
           }
           case case_3 {
             container prefix-name {
               description "Address from address book";
               uses apply-advanced;
               leaf addr-prefix-name {
                 description "Address from address book";
                 type string {
                   length "1 .. 63";
                 }
               }
               container mapped-port {
                 description "Mapped port";
                 uses static-nat-rule-mapped-port-object;
               }
               leaf routing-instance {
                 description "Routing instance";
                 type string;
               }
             }
           }
           case case_4 {
             container nptv6-prefix {
               description "NPTv6 address prefix, the longest prefix will be supported is /64";
               uses apply-advanced;
               leaf addr-prefix {
                 description "IPv6 address prefix value, the longest prefix will be supported is /64";
                 type jt:ipprefix;
               }
               leaf routing-instance {
                 description "Routing instance";
                 type string;
               }
             }
           }
           case case_5 {
             container nptv6-prefix-name {
               description "NPTv6 address from address book";
               uses apply-advanced;
               leaf addr-prefix-name {
                 description "IPv6 address from address book";
                 type string {
                   length "1 .. 63";
                 }
               }
               leaf routing-instance {
                 description "Routing instance";
                 type string;
               }
             }
           }
         }
         container rule-session-count-alarm {
           description "Config rule-session-count-alarm to static rule";
           uses nat-rule-session-count-alarm-object;
         }
       }
     }
   }
   grouping static-nat-rule-mapped-port-object {
     uses apply-advanced;
     leaf low {
       description "Port or lower limit of port range";
       type union {
         type uint16;
         type string {
           pattern "<.*>|$.*";
         }
       }
     }
     container to {
       description "Port range upper limit";
       uses apply-advanced;
       leaf high {
         description "Upper limit of port range";
         type union {
           type uint16;
           type string {
             pattern "<.*>|$.*";
           }
         }
       }
     }
   }
   grouping stp-interface {
     leaf name {
       type string;
     }
     uses apply-advanced;
     leaf priority {
       description "Interface priority (in increments of 16 - 0,16,..240)";
       type union {
         type string {
           pattern "<.*>|$.*";
         }
         type uint16 {
           range "0 .. 255";
         }
       }
     }
     leaf cost {
       description "Cost of the interface";
       type union {
         type string {
           pattern "<.*>|$.*";
         }
         type uint32 {
           range "1 .. 200000000";
         }
       }
     }
     leaf mode {
       description "Interface mode (P2P or shared)";
       type enumeration {
         enum "point-to-point" {
           description "Interface mode is point-to-point";
         }
         enum "shared" {
           description "Interface mode is shared";
         }
       }
     }
     leaf edge {
       description "Port is an edge port";
       type empty;
     }
     leaf access-trunk {
       description "Send/Receive untagged RSTP BPDUs on this interface";
       type empty;
     }
     container bpdu-timeout-action {
       presence "enable bpdu-timeout-action";
       description "Define action on BPDU expiry (Loop Protect)";
       uses apply-advanced;
       leaf block {
         description "Block the interface";
         type empty;
       }
       leaf alarm {
         description "Generate an alarm";
         type empty;
       }
     }
     leaf no-root-port {
       description "Do not allow the interface to become root (Root Protect)";
       type empty;
     }
     leaf disable {
       description "Disable Spanning Tree on port";
       type empty;
     }
   }
   grouping stp-trace-options {
     description "Trace options for Spanning Tree Protocol";
     uses apply-advanced;
     container file {
       description "Trace file options";
       leaf filename {
         description "Name of file in which to write trace information";
         type string {
           length "1 .. 1024";
         }
       }
       leaf replace {
         description "Replace trace file rather than appending to it";
         status deprecated;
         type empty;
       }
       leaf size {
         description "Maximum trace file size";
         type string;
       }
       leaf files {
         description "Maximum number of trace files";
         default "10";
         type union {
           type string {
             pattern "<.*>|$.*";
           }
           type uint32 {
             range "2 .. 1000";
           }
         }
       }
       leaf no-stamp {
         description "Do not timestamp trace file";
         status deprecated;
         type empty;
       }
       choice world-readable-choice {
         leaf world-readable {
           description "Allow any user to read the log file";
           type empty;
         }
         leaf no-world-readable {
           description "Don't allow any user to read the log file";
           type empty;
         }
       }
     }
     list flag {
       key name;
       ordered-by user;
       description "Tracing parameters";
       leaf name {
         type enumeration {
           enum "events" {
             description "Trace events to the protocol state machine";
           }
           enum "bpdu" {
             description "Trace BPDU reception and transmission";
           }
           enum "timers" {
             description "Trace protocol timers";
           }
           enum "port-information-state-machine" {
             description "Trace port information state machine";
           }
           enum "port-receive-state-machine" {
             description "Trace port receive state machine";
           }
           enum "port-role-select-state-machine" {
             description "Trace port role selection state machine";
           }
           enum "port-role-transit-state-machine" {
             description "Trace port role transit state machine";
           }
           enum "port-state-transit-state-machine" {
             description "Trace port state transit state machine";
           }
           enum "port-migration-state-machine" {
             description "Trace port migration state machine";
           }
           enum "port-transmit-state-machine" {
             description "Trace port transmit state machine";
           }
           enum "topology-change-state-machine" {
             description "Trace topology change state machine";
           }
           enum "bridge-detection-state-machine" {
             description "Trace Bridge detection state machine";
           }
           enum "state-machine-variables" {
             description "Trace when state machine variables change";
           }
           enum "ppmd" {
             description "Trace state and events for ppmd process";
           }
           enum "all-failures" {
             description "Trace all failure conditions";
           }
           enum "all" {
             description "Trace all";
           }
         }
       }
       leaf disable {
         description "Disable this trace flag";
         type empty;
       }
     }
   }
   grouping subscription-type {
     uses apply-advanced;
     leaf link-subscription {
       description "Link bandwidth percentage for RSVP reservation";
       default "100";
       type string;
     }
     leaf ct0 {
       description "Subscription percentage for traffic class 0";
       default "100";
       type string;
     }
     leaf ct1 {
       description "Subscription percentage for traffic class 1";
       default "100";
       type string;
     }
     leaf ct2 {
       description "Subscription percentage for traffic class 2";
       default "100";
       type string;
     }
     leaf ct3 {
       description "Subscription percentage for traffic class 3";
       default "100";
       type string;
     }
   }
   grouping sw-rule-set-object {
     leaf name {
       description "Define Rule Set name";
       type string {
         length "1 .. 63";
       }
     }
     uses apply-advanced;
     list rule {
       key name;
       ordered-by user;
       description "Define a rule term";
       leaf name {
         description "Rule name";
         type string {
           length "1 .. 63";
         }
       }
       uses apply-advanced;
       container then {
         description "Action to take if the condition is matched";
         uses apply-advanced;
         choice designation {
           case case_1 {
             leaf v6rd {
               description "Apply 6rd softwire";
               type string {
                 length "1 .. 63";
               }
             }
           }
         }
       }
     }
     leaf match-direction {
       description "Match direction";
       type enumeration {
         enum "input" {
           description "Match on input to interface";
         }
         enum "output" {
           description "Match on output from interface";
         }
       }
     }
   }
   grouping system-id-ip-map {
     leaf name {
       type jt:mac-unicast;
     }
     uses apply-advanced;
     leaf ip-address {
       description "Peer ID (IP Address)";
       type jt:ipv4prefix;
     }
   }
   grouping te-class-object {
     leaf traffic-class {
       description "Traffic class";
       type enumeration {
         enum "ct0" {
           description "Traffic class 0";
         }
         enum "ct1" {
           description "Traffic class 1";
         }
         enum "ct2" {
           description "Traffic class 2";
         }
         enum "ct3" {
           description "Traffic class 3";
         }
       }
     }
     leaf priority {
       description "Preemption priority for this class";
       type union {
         type string {
           pattern "<.*>|$.*";
         }
         type uint32 {
           range "0 .. 7";
         }
       }
     }
   }
   grouping term_object {
     leaf name {
       description "Term name";
       type string {
         length "1 .. 63";
       }
     }
     leaf alg {
       description "Application Layer Gateway";
       type enumeration {
         enum "bootp" {
           description "Bootstrap protocol";
         }
         enum "dce-rpc" {
           description "DCE RPC";
         }
         enum "dce-rpc-portmap" {
           description "DCE RPC portmap";
         }
         enum "dns" {
           description "Domain Name Service";
         }
         enum "exec" {
           description "Remote Execution Protocol";
         }
         enum "ftp" {
           description "File Transfer Protocol";
         }
         enum "ftp-data" {
           description "File Transfer Protocol Data Session";
         }
         enum "gprs-gtp-c" {
           description "GPRS Tunneling Control Plane";
         }
         enum "gprs-gtp-u" {
           description "GPRS Tunneling User Plane";
         }
         enum "gprs-gtp-v0" {
           description "GPRS Tunneling Version 0";
         }
         enum "gprs-sctp" {
           description "GPRS Stream Control Protocol";
         }
         enum "h323" {
           description "H.323";
         }
         enum "icmp" {
           description "ICMP";
         }
         enum "icmpv6" {
           description "ICMPv6";
         }
         enum "ignore" {
           description "Ignore application type";
         }
         enum "iiop" {
           description "Internet Inter-ORB Protocol";
         }
         enum "ike-esp-nat" {
           description "IKE/ESP with NAT";
         }
         enum "ip" {
           description "IP";
         }
         enum "login" {
           description "Login";
         }
         enum "mgcp-ca" {
           description "MGCP-CA";
         }
         enum "mgcp-ua" {
           description "MGCP-UA";
         }
         enum "ms-rpc" {
           description "Microsoft RPC";
         }
         enum "netbios" {
           description "NetBIOS";
         }
         enum "netshow" {
           description "NetShow";
         }
         enum "none" {
           description "None";
         }
         enum "pptp" {
           description "Point-to-Point Tunneling Protocol";
         }
         enum "q931" {
           description "Q.931";
         }
         enum "ras" {
           description "RAS";
         }
         enum "realaudio" {
           description "RealAudio";
         }
         enum "rpc" {
           description "RPC";
         }
         enum "rpc-portmap" {
           description "RPC portmap";
         }
         enum "rsh" {
           description "Remote Shell";
         }
         enum "rtsp" {
           description "Real Time Streaming Protocol";
         }
         enum "sccp" {
           description "Skinny Client Control Protocol";
         }
         enum "sip" {
           description "Session Initiation Protocol";
         }
         enum "shell" {
           description "Shell";
         }
         enum "snmp" {
           description "SNMP";
         }
         enum "sqlnet" {
           description "SQLNet";
         }
         enum "sqlnet-v2" {
           description "Oracle SQL*Net Version 2";
         }
         enum "sun-rpc" {
           description "Sun Microsystems RPC";
         }
         enum "talk" {
           description "Talk Program";
         }
         enum "tftp" {
           description "Trivial File Transfer Protocol";
         }
         enum "traceroute" {
           description "Traceroute";
         }
         enum "http" {
           description "Hypertext Transfer Protocol";
         }
         enum "winframe" {
           description "WinFrame";
         }
         enum "https" {
           description "Hypertext Transfer Protocol";
         }
         enum "imap" {
           description "Internet Mail Access Protocol";
         }
         enum "smtp" {
           description "Simple Mail Transfer Protocol";
         }
         enum "ssh" {
           description "Secure Shell Protocol";
         }
         enum "telnet" {
           description "Telnet Protocol";
         }
         enum "twamp" {
           description "Two Way Active Meaurement Protocol";
         }
       }
     }
     leaf protocol {
       description "Match IP protocol type";
       type string;
     }
     leaf source-port {
       description "Match TCP/UDP source port";
       type string;
     }
     leaf destination-port {
       description "Match TCP/UDP destination port";
       type string;
     }
     leaf icmp-type {
       description "Match ICMP message type";
       type string;
     }
     leaf icmp-code {
       description "Match ICMP message code";
       type string;
     }
     leaf icmp6-type {
       description "Match ICMP6 message type";
       type string;
     }
     leaf icmp6-code {
       description "Match ICMP6 message code";
       type string;
     }
     leaf rpc-program-number {
       description "Match range of RPC program numbers";
       type string {
       }
     }
     leaf uuid {
       description "Match universal unique identifier for DCE RPC objects";
       type string {
       }
     }
     leaf inactivity-timeout {
       description "Application-specific inactivity timeout";
       units "seconds";
       type string;
     }
   }
   grouping three-color-policer-type {
     description "Three-color policer";
     leaf name {
       description "Policer name";
       type string {
       }
     }
     uses apply-advanced;
     leaf filter-specific {
       description "Three color policer is filter-specific";
       type empty;
     }
     leaf physical-interface-policer {
       description "Policer is physical interface policer";
       type empty;
     }
     container action {
       description "Action for three-color policer";
       uses apply-advanced;
       list loss-priority {
         key name;
         ordered-by user;
         description "Loss priority for packet";
         uses three-color-policer-action;
       }
     }
     choice rate-type-choice {
       case case_1 {
         container single-rate {
           description "Single-rate policer";
           uses apply-advanced;
           choice mode-choice {
             case case_1 {
               leaf color-blind {
                 description "Color-blind mode";
                 type empty;
               }
             }
             case case_2 {
               leaf color-aware {
                 description "Color-aware mode";
                 type empty;
               }
             }
           }
           leaf committed-information-rate {
             description "Bandwidth allowed for committed traffic";
             units "bits per second";
             type string;
           }
           leaf committed-burst-size {
             description "Burst size allowed for committed traffic";
             units "bytes";
             type string;
           }
           leaf excess-burst-size {
             description "Burst size allowed for excess traffic";
             units "bytes";
             type string;
           }
         }
       }
       case case_2 {
       }
       case case_3 {
         container two-rate {
           presence "enable two-rate";
           description "Two-rate policer";
           uses apply-advanced;
           choice mode-choice {
             case case_1 {
               leaf color-blind {
                 description "Color-blind mode";
                 type empty;
               }
             }
             case case_2 {
               leaf color-aware {
                 description "Color-aware mode";
                 type empty;
               }
             }
           }
           leaf committed-information-rate {
             description "Bandwidth allowed for committed traffic";
             units "bits per second";
             type string;
           }
           leaf committed-burst-size {
             description "Burst size allowed for committed traffic  ";
             units "bytes";
             type string;
           }
           leaf peak-information-rate {
             description "Bandwidth allowed for peak traffic";
             units "bits per second";
             type string;
           }
           leaf peak-burst-size {
             description "Burst size allowed for peak traffic  ";
             units "bytes";
             type string;
           }
           container aggregate-policing {
             presence "enable aggregate-policing";
             description "Configure Aggregate Policer";
             uses apply-advanced;
             list policer {
               key name;
               ordered-by user;
               description "Two-color policer to be used as aggregate";
               max-elements 1;
               leaf name {
                 description "Name of two-color policer to use to aggregate police";
                 type string;
               }
               uses apply-advanced;
               leaf aggregate-sharing-mode {
                 description "Hierarchical Metering model";
                 type enumeration {
                   enum "hybrid" {
                     description "Child policer CIR rates are guaranteed rates and PIR rate are peak rates for member flow";
                   }
                 }
               }
             }
           }
         }
       }
       case case_4 {
       }
     }
   }
   grouping three-color-policer-action {
     description "Action for three-color policer";
     leaf name {
       description "Loss priority for packet";
       type enumeration {
         enum "high" {
           description "High loss priority";
         }
       }
     }
     uses apply-advanced;
     container then {
       description "Action to take if the rate limits are exceeded";
       uses apply-advanced;
       leaf discard {
         description "Discard the packet";
         type empty;
       }
     }
   }
   grouping tunable-object {
     leaf name {
       type string;
     }
     uses apply-advanced;
     leaf tunable-value {
       description "Protocol tunable value";
       type union {
         type uint32;
         type string {
           pattern "<.*>|$.*";
         }
       }
     }
   }
   grouping tunnel_end_point {
     description "Define a tunnel end point";
     leaf name {
       description "Tunnel end-point identifier (ASCII string)";
       type string {
       }
     }
     uses apply-advanced;
     choice l3-protocol {
       case case_1 {
         container ipv6 {
           presence "enable ipv6";
           description "Enter an IPv6 tunnel";
           uses apply-advanced;
           leaf source-address {
             description "Tunnel source address";
             type jt:ipv6addr;
           }
           leaf destination-address {
             description "Tunnel destination address";
             type jt:ipv6prefix;
           }
         }
       }
       case case_2 {
         container ipv4 {
           presence "enable ipv4";
           description "Enter an IPv4 tunnel";
           uses apply-advanced;
           leaf source-address {
             description "Tunnel source address";
             type jt:ipv4addr;
           }
           leaf destination-address {
             description "Tunnel destination address";
             type jt:ipv4prefix;
           }
         }
       }
     }
     choice tunnel-protocol {
       case case_1 {
         container gre {
           presence "enable gre";
           description "Tunnel is GRE";
           uses apply-advanced;
           leaf key {
             description "Key for authentication";
             type union {
               type uint32;
               type string {
                 pattern "<.*>|$.*";
               }
             }
           }
         }
       }
       case case_2 {
         container gre-in-udp {
           presence "enable gre-in-udp";
           description "Tunnel is GRE-in-UDP";
           uses apply-advanced;
           leaf source-port {
             description "UDP source port";
             type union {
               type string {
                 pattern "<.*>|$.*";
               }
               type uint32 {
                 range "0 .. 65535";
               }
             }
           }
           leaf destination-port {
             description "UDP destination port";
             type union {
               type string {
                 pattern "<.*>|$.*";
               }
               type uint32 {
                 range "0 .. 65535";
               }
             }
           }
           leaf key {
             description "GRE key for authentication";
             type union {
               type uint32;
               type string {
                 pattern "<.*>|$.*";
               }
             }
           }
         }
       }
     }
   }
   grouping tunnel_type {
     description "Tunnel packets";
     uses apply-advanced;
     choice ipsec-vpn-choice {
       case case_1 {
         leaf ipsec-vpn {
           description "Enable VPN with name";
           type string {
             length "1 .. 63";
           }
         }
       }
       case case_2 {
         leaf ipsec-group-vpn {
           description "Enable dynamic IPSEC group with name";
           status deprecated;
           type string {
             length "1 .. 63";
           }
         }
       }
     }
     leaf pair-policy {
       description "Policy in the reverse direction, to form a pair";
       type string {
         length "1 .. 63";
       }
     }
   }
   grouping url-list-type {
     description "Configure url-list object";
     leaf name {
       description "Configure name of url-list object";
       type string {
         length "1 .. 29";
       }
     }
     uses apply-advanced;
     leaf-list value {
       ordered-by user;
       description "Configure value of url-list object";
       type string {
         length "1 .. 256";
       }
     }
   }
   grouping utm-apppxy-traceoptions {
     description "Traceoptions for utm application proxy process";
     uses apply-advanced;
     list flag {
       key name;
       ordered-by user;
       description "Tracing parameters for utm application proxy";
       leaf name {
         description "Tracing parameters for utm application proxy flag name";
         type enumeration {
           enum "abort" {
             description "Trace application-proxy session abort";
           }
           enum "application-objects" {
             description "Trace application-proxy objects information";
           }
           enum "utm-realtime" {
             description "Trace application-proxy realtime-thread information";
           }
           enum "anti-virus" {
             description "Trace anti-virus information";
           }
           enum "basic" {
             description "Trace application-proxy basic information";
           }
           enum "buffer" {
             description "Trace application-proxy data buffer information";
           }
           enum "detail" {
             description "Trace application-proxy detailed information";
           }
           enum "ftp-data" {
             description "Trace FTP data connection information";
           }
           enum "ftp-control" {
             description "Trace FTP control connection information";
           }
           enum "http" {
             description "Trace HTTP protocol information";
           }
           enum "imap" {
             description "Trace IMAP protocol information";
           }
           enum "memory" {
             description "Trace memory usage";
           }
           enum "parser" {
             description "Trace protocol parser";
           }
           enum "pfe" {
             description "Trace communication with PFE";
           }
           enum "pop3" {
             description "Trace POP3 protocol information";
           }
           enum "queue" {
             description "Trace queue information";
           }
           enum "smtp" {
             description "Trace SMTP protocol information";
           }
           enum "tcp" {
             description "Trace TCP level information";
           }
           enum "timer" {
             description "Trace timer processing";
           }
           enum "connection-rating" {
             description "Trace connection rating information";
           }
           enum "mime" {
             description "Trace MIME parser information";
           }
           enum "regex-engine" {
             description "Trace Pattern Match Engine (PME) information";
           }
           enum "sophos-anti-virus" {
             description "Trace anti-virus sophos engine information";
           }
           enum "all" {
             description "Enable all application-proxy trace options";
           }
         }
       }
     }
   }
   grouping utm-ipc-traceoptions {
     description "Traceoptions for utm IPC";
     uses apply-advanced;
     list flag {
       key name;
       ordered-by user;
       description "Traceoptions for utm IPC flag";
       leaf name {
         description "Trace options for utm IPC flag name";
         type enumeration {
           enum "basic" {
             description "Trace basic IPC related information";
           }
           enum "detail" {
             description "Trace detail IPC related information";
           }
           enum "connection-manager" {
             description "Trace IPC connection manager";
           }
           enum "connection-status" {
             description "Trace IPC connection status";
           }
           enum "pfe" {
             description "Trace communication with pfe";
           }
           enum "utm-realtime" {
             description "Trace IPC realtime-thread information";
           }
           enum "all" {
             description "Enable all IPC trace options";
           }
         }
       }
     }
   }
   grouping utm-traceoptions {
     description "Trace options for utm process";
     uses apply-advanced;
     list flag {
       key name;
       ordered-by user;
       description "Tracing UTM information";
       leaf name {
         description "Flag name";
         type enumeration {
           enum "cli" {
             description "Trace CLI";
           }
           enum "daemon" {
             description "Trace daemon information";
           }
           enum "ipc" {
             description "Trace IPC information";
           }
           enum "pfe" {
             description "Trace pfe information";
           }
           enum "all" {
             description "Enable all utm trace options";
           }
         }
       }
     }
   }
   grouping v6-relay-option-interface-id-type {
     description "Interface ID processing";
     uses apply-advanced;
     container prefix {
       description "Add prefix to circuit/interface-id or remote-id";
       uses apply-advanced;
       leaf host-name {
         description "Add router host name to circuit / interface-id or remote-id";
         type empty;
       }
       leaf logical-system-name {
         description "Add logical system name to circuit / interface-id or remote-id";
         type empty;
       }
       leaf routing-instance-name {
         description "Add routing instance name to circuit / interface-id or remote-id";
         type empty;
       }
     }
     leaf use-interface-description {
       description "Use interface description instead of circuit identifier";
       type enumeration {
         enum "logical" {
           description "Use the logical interface description";
         }
         enum "device" {
           description "Use the device interface description";
         }
       }
     }
     leaf use-vlan-id {
       description "Use VLAN id instead of name";
       type empty;
     }
     leaf no-vlan-interface-name {
       description "Not include vlan or interface name";
       type empty;
     }
     leaf include-irb-and-l2 {
       description "Include IRB and L2 interface name";
       type empty;
     }
     container use-option-82 {
       description "Use option-82 circuit-id for interface-id";
       presence "enable use-option-82";
       uses v6-relay-option-cid-rid-action;
     }
     container keep-incoming-interface-id {
       description "Keep incoming interface identifier";
       presence "enable keep-incoming-interface-id";
       uses v6-relay-option-cid-rid-action;
     }
   }
   grouping v6-relay-option-cid-rid-action {
     uses apply-advanced;
     leaf strict {
       description "Drop packet if id not present";
       type empty;
     }
   }
   grouping v6-relay-option-remote-id-type {
     description "Remote ID processing";
     uses apply-advanced;
     container prefix {
       description "Add prefix to circuit/interface-id or remote-id";
       uses apply-advanced;
       leaf host-name {
         description "Add router host name to circuit / interface-id or remote-id";
         type empty;
       }
       leaf logical-system-name {
         description "Add logical system name to circuit / interface-id or remote-id";
         type empty;
       }
       leaf routing-instance-name {
         description "Add routing instance name to circuit / interface-id or remote-id";
         type empty;
       }
     }
     leaf use-interface-description {
       description "Use interface description instead of circuit identifier";
       type enumeration {
         enum "logical" {
           description "Use the logical interface description";
         }
         enum "device" {
           description "Use the device interface description";
         }
       }
     }
     leaf use-vlan-id {
       description "Use VLAN id instead of name";
       type empty;
     }
     leaf no-vlan-interface-name {
       description "Not include vlan or interface name";
       type empty;
     }
     leaf include-irb-and-l2 {
       description "Include IRB and L2 interface name";
       type empty;
     }
     container use-option-82 {
       description "Use option-82 remote-id for v6 remote-id";
       presence "enable use-option-82";
       uses v6-relay-option-cid-rid-action;
     }
     leaf keep-incoming-remote-id {
       description "Keep incoming remote identifier";
       type empty;
     }
   }
   grouping v6-server-group-type {
     uses apply-advanced;
     list server-group {
       key name;
       ordered-by user;
       description "One or more server groups";
       leaf name {
         description "DHCPv6 Server group name";
         type string {
           length "1 .. 64";
         }
       }
       uses apply-advanced;
       list address {
         key name;
         ordered-by user;
         description "IP Address of one or more DHCP servers";
         max-elements 32;
         leaf name {
           description "IP Address of DHCP server";
           type jt:ipaddr;
         }
         uses apply-advanced;
       }
     }
   }
   grouping vendor-object {
     leaf name {
       description "Values for vendor field";
       type string;
     }
     uses apply-advanced;
     leaf product-name {
       description "Values for product field";
       type string;
     }
   }
   grouping version9-template {
     description "One or more version 9 templates for flow monitoring";
     leaf name {
       description "Name of template";
       type string;
     }
     uses apply-advanced;
     leaf flow-active-timeout {
       description "Interval after which active flow is exported";
       default "60";
       type union {
         type string {
           pattern "<.*>|$.*";
         }
         type uint32 {
           range "10 .. 600";
         }
       }
     }
     leaf flow-inactive-timeout {
       description "Period of inactivity that marks a flow inactive";
       default "60";
       type union {
         type string {
           pattern "<.*>|$.*";
         }
         type uint32 {
           range "10 .. 600";
         }
       }
     }
     leaf template-id {
       description "Template id";
       type union {
         type string {
           pattern "<.*>|$.*";
         }
         type uint32 {
           range "1024 .. 65535";
         }
       }
     }
     leaf option-template-id {
       description "Options template id";
       type union {
         type string {
           pattern "<.*>|$.*";
         }
         type uint32 {
           range "1024 .. 65535";
         }
       }
     }
     leaf source-id {
       description "Source Id";
       default "0";
       type union {
         type string {
           pattern "<.*>|$.*";
         }
         type uint32 {
           range "0 .. 255";
         }
       }
     }
     container nexthop-learning {
       description "Nexthop learning parameter. Valid ONLY for INLINE-JFLOW";
       uses apply-advanced;
       choice enable-disable {
         case case_1 {
           leaf enable {
             description "Enable nexthop learning";
             type empty;
           }
         }
         case case_2 {
           leaf disable {
             description "Disable nexthop learning";
             type empty;
           }
         }
       }
     }
     container template-refresh-rate {
       presence "enable template-refresh-rate";
       description "Template refresh rate";
       uses apply-advanced;
       leaf packets {
         description "In number of packets";
         default "4800";
         type union {
           type string {
             pattern "<.*>|$.*";
           }
           type uint32 {
             range "1 .. 480000";
           }
         }
       }
       leaf seconds {
         description "In number of seconds";
         type union {
           type string {
             pattern "<.*>|$.*";
           }
           type uint32 {
             range "10 .. 600";
           }
         }
       }
     }
     container option-refresh-rate {
       presence "enable option-refresh-rate";
       description "Option template refresh rate";
       uses apply-advanced;
       leaf packets {
         description "In number of packets";
         default "4800";
         type union {
           type string {
             pattern "<.*>|$.*";
           }
           type uint32 {
             range "1 .. 480000";
           }
         }
       }
       leaf seconds {
         description "In number of seconds";
         type union {
           type string {
             pattern "<.*>|$.*";
           }
           type uint32 {
             range "10 .. 600";
           }
         }
       }
     }
     choice template-types {
       case case_1 {
       }
       case case_2 {
       }
       case case_3 {
         container ipv6-template {
           presence "enable ipv6-template";
           description "IPv6 template configuration";
           uses apply-advanced;
           list export-extension {
             key name;
             ordered-by user;
             description "IPv6 template configuration with extra fields added to the template";
             leaf name {
               type enumeration {
                 enum "flow-dir" {
                   description "Applicationid field type";
                 }
                 enum "app-id" {
                   description "Applicationid field type";
                 }
               }
             }
             uses apply-advanced;
           }
           container nexthop-options {
             presence "enable nexthop-options";
             description "Additional information retrieved from nexthop";
             uses apply-advanced;
             choice nexthop-types {
               case case_1 {
                 container mpls {
                   presence "enable mpls";
                   description "MPLS information retrieved from nexthop";
                   uses apply-advanced;
                   leaf-list label-position {
                     ordered-by user;
                     description "One or more MPLS label positions";
                     type union {
                       type string {
                         pattern "<.*>|$.*";
                       }
                       type uint8 {
                         range "1 .. 3";
                       }
                     }
                     max-elements 3;
                   }
                 }
               }
             }
           }
         }
       }
       case case_4 {
         container peer-as-billing-template {
           presence "enable peer-as-billing-template";
           description "Peer AS billing template configuration";
         }
       }
       case case_5 {
         container ipv4-template {
           presence "enable ipv4-template";
           description "IPv4 template configuration";
           uses apply-advanced;
           list export-extension {
             key name;
             ordered-by user;
             description "IPv4 template configuration with extra fields added to the template";
             leaf name {
               type enumeration {
                 enum "flow-dir" {
                   description "Applicationid field type";
                 }
                 enum "app-id" {
                   description "Applicationid field type";
                 }
               }
             }
             uses apply-advanced;
           }
         }
       }
       case case_6 {
       }
       case case_7 {
       }
     }
     container tunnel-observation {
       description "Tunnel observation";
       uses apply-advanced;
       leaf ipv4 {
         description "IPv4";
         type empty;
       }
       leaf ipv6 {
         description "IPv6";
         type empty;
       }
     }
     container flow-key {
       description "Flow key for the template. Valid ONLY for INLINE-JFLOW";
       uses apply-advanced;
       leaf flow-direction {
         description "Include flow direction";
         type empty;
       }
       leaf vlan-id {
         description "Include vlan ID";
         type empty;
       }
       leaf output-interface {
         description "Include output interface";
         type empty;
       }
     }
   }
   grouping vlan-policy {
     description "Virtual LAN";
     leaf name {
       description "VLAN id";
       type string;
     }
     uses apply-advanced;
     container policy {
       description "Attach policy";
       uses apply-advanced;
       leaf policy-name {
         description "Router Advertisement Guard policy name";
         type string;
       }
       choice policy-type {
         case case_1 {
           leaf stateful {
             description "Stateful router advertisement guard";
             type empty;
           }
         }
         case case_2 {
           leaf stateless {
             description "Stateless router advertisement guard";
             type empty;
           }
         }
       }
     }
   }
   grouping vlan-types {
     description "Virtual LAN";
     leaf name {
       description "VLAN name";
       type string {
         length "2 .. 64";
       }
     }
     uses apply-advanced;
     leaf description {
       description "Text description of VLANs";
       type string {
       }
     }
     choice vlan-identifier-choice {
       case case_1 {
         leaf vlan-id {
           description "IEEE 802.1q VLAN identifier for VLAN";
           type string;
         }
       }
       case case_2 {
         leaf-list vlan-id-list {
           description "Create VLAN for each of the vlan-id specified in the vlan-id-list";
           type jt:vlan-range;
         }
       }
       case case_3 {
         container vlan-tags {
           presence "enable vlan-tags";
           description "IEEE 802.1q VLAN tags for VLANs";
           leaf outer {
             description "[tpid.]vlan-id, tpid format is 0xNNNN and is optional";
             type string {
             }
           }
           leaf inner {
             description "[tpid.]vlan-id, tpid format is 0xNNNN and is optional";
             type string {
             }
           }
         }
       }
     }
     list interface {
       key name;
       ordered-by user;
       description "Interface name for this VLAN";
       leaf name {
         type string;
       }
       uses apply-advanced;
     }
     leaf l3-interface {
       description "L3 interface name for this vlans";
       type union {
         type jt:interface-unit;
         type string {
           pattern "<.*>|$.*";
         }
       }
     }
     leaf no-local-switching {
       description "Disable local switching within CE-facing interfaces";
       type empty;
     }
     container forwarding-options {
       description "Forwarding options configuration";
       uses juniper-ethernet-switching-forwarding-options;
     }
     container multicast-snooping-options {
       description "Multicast snooping option configuration";
       uses juniper-multicast-snooping-options;
     }
     container switch-options {
       description "VLANs switch-options configuration";
       uses juniper-protocols-vlan;
     }
     leaf domain-type {
       description "Type of VLANs SVLAN/DVLAN";
       type enumeration {
         enum "bridge" {
           description "Forwarding instance";
         }
       }
     }
     leaf no-irb-layer-2-copy {
       description "Disable transmission of layer-2 copy of packets of IRB routing-interface";
       type empty;
     }
     leaf service-id {
       description "Service id required if VLAN is of type MC-AE, and vlan-id all or vlan-id none or vlan-tags is configured";
       type union {
         type string {
           pattern "<.*>|$.*";
         }
         type uint32 {
           range "1 .. 65535";
         }
       }
     }
     leaf mcae-mac-synchronize {
       description "Enable IRB MAC synchronization in this VLAN";
       type empty;
     }
     leaf mcae-mac-flush {
       description "Enable IRB MAC flush in a/s mode for this VLAN on MCAE link up";
       type empty;
     }
     leaf private-vlan {
       description "Type of secondary vlan for private vlan";
       type enumeration {
         enum "isolated" {
           description "Isolated vlan";
         }
         enum "community" {
           description "Community vlan";
         }
       }
     }
     leaf isolated-vlan {
       description "VLAN id or name";
       type string {
       }
     }
     leaf-list community-vlans {
       ordered-by user;
       description "List of VLAN id or name";
       type string;
     }
     container vxlan {
       uses apply-advanced;
       leaf ovsdb-managed {
         description "Bridge-domain is managed remotely via VXLAN OVSDB Controller";
         type empty;
       }
       leaf vni {
         description "VXLAN identifier";
         type union {
           type string {
             pattern "<.*>|$.*";
           }
           type uint32 {
             range "0 .. 16777214";
           }
         }
       }
       leaf multicast-group {
         description "Multicast group registered for VXLAN segment";
         type jt:ipv4addr;
       }
       leaf encapsulate-inner-vlan {
         description "Retain inner VLAN in the packet";
         type empty;
       }
       leaf decapsulate-accept-inner-vlan {
         description "Accept VXLAN packets with inner VLAN";
         type empty;
       }
       leaf unreachable-vtep-aging-timer {
         description "Unreachable VXLAN tunnel endpoint removal timer";
         units "seconds";
         type union {
           type string {
             pattern "<.*>|$.*";
           }
           type uint16 {
             range "300 .. 1800";
           }
         }
       }
     }
   }
   grouping juniper-ethernet-switching-forwarding-options {
     uses apply-advanced;
     container filter {
       description "Filtering for ethernet switching forwarding table";
       uses apply-advanced;
       leaf input {
         description "Name of input filter to apply for forwarded packets";
         type string;
       }
     }
     container flood {
       description "Filtering for ethernet switching flood table";
       uses apply-advanced;
       leaf input {
         description "Name of input filter to apply for ethernet switching flood packets";
         type string;
       }
     }
     container dhcp-relay {
       description "Dynamic Host Configuration Protocol relay configuration";
       status deprecated;
       uses jdhcp-relay-type;
     }
     container dhcp-security {
       description "DHCP access security configuration";
       presence "enable dhcp-security";
       uses jdhcp-security-type;
     }
   }
   grouping juniper-protocols-vlan {
     description "VLANs switch-options configuration";
     uses apply-advanced;
     container mac-table-size {
       description "Size of MAC address forwarding table";
       uses apply-advanced;
       leaf limit {
         description "Maximum number of MAC addresses";
         type union {
           type string {
             pattern "<.*>|$.*";
           }
           type uint32;
         }
       }
       leaf packet-action {
         description "Action when MAC limit is reached";
         type enumeration {
           enum "none" {
             description "Forward the packet";
           }
           enum "drop" {
             description "Drop packets and do not learn. Default is forward";
           }
         }
       }
     }
     container mac-ip-table-size {
       description "Size of MAC+IP bindings table";
       uses apply-advanced;
       leaf limit {
         description "Maximum number of MAC+IP bindings";
         type union {
           type string {
             pattern "<.*>|$.*";
           }
           type uint32;
         }
       }
     }
     container interface-mac-limit {
       description "Maximum MAC address learned per interface";
       uses apply-advanced;
       leaf limit {
         description "Maximum number of MAC addresses per interface";
         type union {
           type string {
             pattern "<.*>|$.*";
           }
           type uint32;
         }
       }
       leaf packet-action {
         description "Action when MAC limit is reached";
         type enumeration {
           enum "none" {
             description "Forward the packet";
           }
           enum "drop" {
             description "Drop packets and do not learn. Default is forward";
           }
           enum "log" {
             description "Do not drop the packet but generate an alarm, an SNMP trap or a system log entry";
           }
           enum "shutdown" {
             description "Disable the interface and generate an alarm, an SNMP trap or a system log entry";
           }
           enum "drop-and-log" {
             description "Drop the packet and generate an alarm, an SNMP trap or a system log entry";
           }
         }
       }
     }
     container interface-mac-ip-limit {
       description "Maximum number of MAC+IP bindings learned on the interface";
       uses apply-advanced;
       leaf limit {
         description "Maximum number of MAC+IP bindings per interface";
         type union {
           type string {
             pattern "<.*>|$.*";
           }
           type uint32;
         }
       }
     }
     leaf mac-table-aging-time {
       description "Delay for discarding MAC address if no updates are received";
       units "seconds";
       type union {
         type string {
           pattern "<.*>|$.*";
         }
         type uint32;
       }
     }
     leaf no-mac-learning {
       description "Disable dynamic MAC address learning";
       type empty;
     }
     leaf no-normalization {
       description "Disable vlan id normalization for interfaces";
       type empty;
     }
     leaf mac-statistics {
       description "Enable MAC address statistics";
       type empty;
     }
     container static-rvtep-mac {
       description "Configure Static MAC and remote VxLAN tunnel endpoint entries";
       uses apply-advanced;
       list mac {
         key "mac_addr remote-vtep";
         description "Unicast MAC address";
         leaf mac_addr {
           type jt:mac-unicast;
         }
         leaf remote-vtep {
           description "Configure static remote VXLAN tunnel endpoints";
           type jt:ipaddr;
         }
       }
     }
     list interface {
       key name;
       ordered-by user;
       description "Interface that connect this site to the VPN";
       leaf name {
         description "Interface name";
         type union {
           type jt:interface-name;
           type string {
             pattern "<.*>|$.*";
           }
         }
       }
       uses apply-advanced;
       container interface-mac-limit {
         description "Maximum number of MAC addresses learned on the interface";
         uses apply-advanced;
         leaf limit {
           description "Maximum number of MAC addresses per interface";
           type union {
             type string {
               pattern "<.*>|$.*";
             }
             type uint32;
           }
         }
         leaf disable {
           description "Disable interface for interface-mac-limit";
           type empty;
         }
         leaf packet-action {
           description "Action when MAC limit is reached";
           type enumeration {
             enum "none" {
               description "Forward the packet";
             }
             enum "drop" {
               description "Drop packets and do not learn. Default is forward";
             }
             enum "log" {
               description "Do not drop the packet but generate an alarm, an SNMP trap or a system log entry";
             }
             enum "shutdown" {
               description "Disable the interface and generate an alarm, an SNMP trap or a system log entry";
             }
             enum "drop-and-log" {
               description "Drop the packet and generate an alarm, an SNMP trap or a system log entry";
             }
           }
         }
       }
       container vpws-service-id {
         presence "enable vpws-service-id";
         description "Service-id for EVPN VPWS routing instance";
         uses apply-advanced;
         leaf local {
           description "Local EVPN VPWS service id";
           type union {
             type string {
               pattern "<.*>|$.*";
             }
             type uint32 {
               range "1 .. 16777215";
             }
           }
         }
         leaf remote {
           description "Remote EVPN VPWS service id";
           type union {
             type string {
               pattern "<.*>|$.*";
             }
             type uint32 {
               range "1 .. 16777215";
             }
           }
         }
       }
       leaf protect-interface {
         description "Name of protect interface";
         type union {
           type jt:interface-name;
           type string {
             pattern "<.*>|$.*";
           }
         }
       }
       leaf action-priority {
         description "Blocking priority of this interface on mac move detection";
         type union {
           type string {
             pattern "<.*>|$.*";
           }
           type uint32 {
             range "0 .. 8";
           }
         }
       }
       leaf remote-site-id {
         description "Site identifier associated with this interface";
         type union {
           type string {
             pattern "<.*>|$.*";
           }
           type uint32 {
             range "1 .. 65534";
           }
         }
       }
       leaf target-attachment-identifier {
         description "FEC 129 VPWS target attachment identifier";
         type string {
         }
       }
       leaf flow-label-transmit {
         description "Advertise capability to push Flow Label in transmit direction to remote PE";
         type empty;
       }
       leaf flow-label-receive {
         description "Advertise capability to push Flow Label in receive direction to remote PE";
         type empty;
       }
       leaf encapsulation-type {
         description "Encapsulation type for VPN";
         type enumeration {
           enum "atm-aal5" {
             description "ATM AAL/5 encapsulation";
           }
           enum "atm-cell" {
             description "ATM port promiscuous mode cell encapsulation";
           }
           enum "atm-cell-port-mode" {
             description "ATM port promiscuous mode cell encapsulation";
           }
           enum "atm-cell-vp-mode" {
             description "ATM VP promiscuous mode cell encapsulation";
           }
           enum "atm-cell-vc-mode" {
             description "ATM non-promiscuous cell encapsulation";
           }
           enum "frame-relay" {
             description "Frame Relay encapsulation";
           }
           enum "ppp" {
             description "PPP encapsulation";
           }
           enum "cisco-hdlc" {
             description "Cisco-compatible HDLC encapsulation";
           }
           enum "ethernet-vlan" {
             description "Ethernet VLAN encapsulation";
           }
           enum "ethernet" {
             description "Ethernet encapsulation";
           }
           enum "interworking" {
             description "Layer 2.5 interworking VPN";
           }
           enum "frame-relay-port-mode" {
             description "Frame Relay port mode encapsulation";
           }
           enum "satop-t1" {
             description "SATOP-T1 based Layer 2 VPN";
           }
           enum "satop-e1" {
             description "SATOP-E1 based Layer 2 VPN";
           }
           enum "satop-t3" {
             description "SATOP-T3 based Layer 2 VPN";
           }
           enum "satop-e3" {
             description "SATOP-E3 based Layer 2 VPN";
           }
           enum "cesop" {
             description "CESOP based Layer 2 VPN";
           }
         }
       }
       leaf ignore-encapsulation-mismatch {
         description "Allow different encapsulation types on local and remote end";
         type empty;
       }
       leaf mtu {
         description "MTU to be advertised to the remote end";
         type union {
           type string {
             pattern "<.*>|$.*";
           }
           type uint16 {
             range "512 .. 65535";
           }
         }
       }
       leaf ignore-mtu-mismatch {
         description "Allow different MTU values on local and remote end";
         type empty;
       }
       choice cword {
         case case_1 {
           leaf control-word {
             description "Adds control-word to the Layer 2 encapsulation";
             type empty;
           }
         }
         case case_2 {
           leaf no-control-word {
             description "Disables control-word to the Layer 2 encapsulation";
             type empty;
           }
         }
       }
       leaf pseudowire-status-tlv {
         description "Send pseudowire status TLV";
         type empty;
       }
       container oam {
         description "OAM Configuration for VPN";
         uses apply-advanced;
         leaf ping-interval {
           description "Time interval between ping messages";
           default "60";
           units "seconds";
           type union {
             type string {
               pattern "<.*>|$.*";
             }
             type uint16 {
               range "30 .. 3600";
             }
           }
         }
         leaf ping-multiplier {
           description "Number of ping reply missed before declaring BFD down";
           type union {
             type string {
               pattern "<.*>|$.*";
             }
             type uint8 {
               range "1 .. 5";
             }
           }
         }
         container bfd-liveness-detection {
           description "Bidirectional Forwarding Detection (BFD) options";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
         }
       }
       leaf community {
         description "Community associated with this interface";
         type string;
       }
       list static-mac {
         key name;
         ordered-by user;
         description "Static MAC addresses assigned to this interface";
         leaf name {
           description "MAC address";
           type jt:mac-addr;
         }
         uses apply-advanced;
         list vlan-id {
           key name;
           ordered-by user;
           description "VLAN ID of learning VLAN";
           leaf name {
             description "Learning VLAN";
             type union {
               type string {
                 pattern "<.*>|$.*";
               }
               type uint32 {
                 range "0 .. 4094";
               }
             }
           }
           uses apply-advanced;
         }
       }
       container interface-mac-ip-limit {
         description "Maximum number of MAC+IP bindings learned on the interface";
         uses apply-advanced;
         leaf limit {
           description "Maximum number of MAC+IP bindings per interface";
           type union {
             type string {
               pattern "<.*>|$.*";
             }
             type uint32;
           }
         }
       }
       leaf no-mac-learning {
         description "Disable dynamic MAC address learning";
         type empty;
       }
       leaf mac-pinning {
         description "Enable MAC pinning";
         type empty;
       }
       leaf description {
         description "Text description";
         type string;
       }
       leaf persistent-learning {
         description "Enable persistent MAC learning on this interface";
         type empty;
       }
     }
   }
   grouping vlan_map {
     description "IEEE 802.1q Virtual LAN (VLAN) Tag mapping";
     uses apply-advanced;
     choice operation_choices {
       case case_1 {
         leaf push {
           description "Push a VLAN tag";
           type empty;
         }
       }
       case case_2 {
         leaf swap {
           description "Swap a VLAN tag";
           type empty;
         }
       }
       case case_3 {
         leaf pop {
           description "Pop a VLAN tag";
           type empty;
         }
       }
       case case_4 {
         leaf push-push {
           description "Push two VLAN tags";
           type empty;
         }
       }
       case case_5 {
         leaf swap-push {
           description "Swap VLAN tag and push a new VLAN tag";
           type empty;
         }
       }
       case case_6 {
         leaf swap-swap {
           description "Swap both outer and inner VLAN tags";
           type empty;
         }
       }
       case case_7 {
         leaf pop-swap {
           description "Pop outer VLAN tag and swap inner VLAN tag";
           type empty;
         }
       }
       case case_8 {
         leaf pop-pop {
           description "Pop both outer and inner VLAN tags";
           type empty;
         }
       }
     }
     leaf tag-protocol-id {
       description "IEEE 802.1q Tag Protocol Identifier to rewrite";
       type string {
       }
     }
     leaf inner-tag-protocol-id {
       description "IEEE 802.1q Tag Protocol ID to rewrite for inner tag";
       type string;
     }
     leaf vlan-id {
       description "VLAN ID to rewrite";
       type string;
     }
     leaf inner-vlan-id {
       description "VLAN ID to rewrite for inner tag";
       type string;
     }
   }
   grouping vpls_filter {
     description "Define an VPLS firewall filter";
     leaf name {
       description "Filter name";
       type string {
       }
     }
     uses apply-advanced;
     leaf-list accounting-profile {
       ordered-by user;
       description "Accounting profile name";
       type string;
     }
     leaf interface-specific {
       description "Defined counters are interface specific";
       type empty;
     }
     leaf physical-interface-filter {
       description "Filter is physical interface filter";
       type empty;
     }
     list term {
       key name;
       ordered-by user;
       description "Define a firewall term";
       leaf name {
         description "Term name";
         type string {
         }
       }
       uses apply-advanced;
       leaf filter {
         description "Filter to include";
         type string {
         }
       }
       container from {
         description "Define match criteria";
         uses apply-advanced;
         choice interface-group_choice {
           case case_1 {
             leaf-list interface-group {
               ordered-by user;
               description "Range of values";
               type string;
             }
           }
           case case_2 {
             leaf-list interface-group-except {
               ordered-by user;
               description "Range of values";
               type string;
             }
           }
         }
         choice ether-type_choice {
           case case_1 {
             leaf-list ether-type {
               ordered-by user;
               type string;
             }
           }
           case case_2 {
             leaf-list ether-type-except {
               ordered-by user;
               type string;
             }
           }
         }
         choice vlan-ether-type_choice {
           case case_1 {
             leaf-list vlan-ether-type {
               ordered-by user;
               type string;
             }
           }
           case case_2 {
             leaf-list vlan-ether-type-except {
               ordered-by user;
               type string;
             }
           }
         }
         list destination-mac-address {
           key name;
           ordered-by user;
           description "Destination MAC address";
           uses firewall_mac_addr_object;
         }
         list source-mac-address {
           key name;
           ordered-by user;
           description "Source MAC address";
           uses firewall_mac_addr_object;
         }
         choice forwarding-class_choice {
           case case_1 {
             leaf-list forwarding-class {
               ordered-by user;
               description "String name";
               type string {
               }
             }
           }
           case case_2 {
             leaf-list forwarding-class-except {
               ordered-by user;
               description "String name";
               type string {
               }
             }
           }
         }
         choice loss-priority_choice {
           case case_1 {
           }
           case case_2 {
           }
         }
         choice learn-vlan-id_choice {
           case case_1 {
           }
           case case_2 {
           }
         }
         choice learn-vlan-1p-priority_choice {
           case case_1 {
           }
           case case_2 {
           }
         }
         choice user-vlan-id_choice {
           case case_1 {
           }
           case case_2 {
           }
         }
         choice user-vlan-1p-priority_choice {
           case case_1 {
           }
           case case_2 {
           }
         }
         choice learn-vlan-dei_choice {
           case case_1 {
           }
           case case_2 {
           }
         }
         choice traffic-type_choice {
           case case_1 {
           }
           case case_2 {
           }
         }
         choice ip-protocol_choice {
           case case_1 {
           }
           case case_2 {
           }
         }
         choice dscp_choice {
           case case_1 {
           }
           case case_2 {
           }
         }
         choice ip-precedence_choice {
           case case_1 {
           }
           case case_2 {
           }
         }
         choice source-port_choice {
           case case_1 {
           }
           case case_2 {
           }
         }
         choice destination-port_choice {
           case case_1 {
           }
           case case_2 {
           }
         }
         choice port_choice {
           case case_1 {
           }
           case case_2 {
           }
         }
         choice icmp-type_choice {
           case case_1 {
           }
           case case_2 {
           }
         }
         choice icmp-code_choice {
           case case_1 {
           }
           case case_2 {
           }
         }
         list interface {
           key name;
           ordered-by user;
           description "Match interface name";
           uses match_interface_object;
         }
         list interface-set {
           key name;
           ordered-by user;
           description "Match interface in set";
           uses match_interface_set_object;
         }
         choice ipv6-next-header_choice {
           case case_1 {
           }
           case case_2 {
           }
         }
         choice ipv6-payload-protocol_choice {
           case case_1 {
           }
           case case_2 {
           }
         }
         choice ipv6-traffic-class_choice {
           case case_1 {
           }
           case case_2 {
           }
         }
         choice policy-map_choice {
           case case_1 {
             leaf-list policy-map {
               ordered-by user;
               description "String name";
               type string {
                 length "1 .. 64";
               }
             }
           }
           case case_2 {
             leaf-list policy-map-except {
               ordered-by user;
               description "String name";
               type string {
                 length "1 .. 64";
               }
             }
           }
         }
       }
       container then {
         description "Action to take if the 'from' condition is matched";
         uses apply-advanced;
         choice policer-choice {
           case case_1 {
             leaf policer {
               description "Name of policer to use to rate-limit traffic";
               type string {
               }
             }
           }
           case case_2 {
             container three-color-policer {
               description "Police the packet using a three-color-policer";
               uses apply-advanced;
               choice type-choice {
                 case case_1 {
                   leaf single-rate {
                     description "Name of single-rate three-color policer to use to rate-limit traffic";
                     type string {
                     }
                   }
                 }
                 case case_2 {
                   leaf single-packet-rate {
                     description "Name of single-packet-rate three-color policer to use to rate-limit traffic";
                     type string {
                     }
                   }
                 }
                 case case_3 {
                   leaf two-rate {
                     description "Name of two-rate three-color policer to use to rate-limit traffic";
                     type string {
                     }
                   }
                 }
                 case case_4 {
                   leaf two-packet-rate {
                     description "Name of two-packet-rate three-color policer to use to rate-limit traffic";
                     type string {
                     }
                   }
                 }
               }
             }
           }
           case case_3 {
           }
         }
         choice policy-map-choice {
           case case_1 {
             leaf clear-policy-map {
               description "Clear the policy marking";
               type empty;
             }
           }
           case case_2 {
             leaf policy-map {
               description "Policy map action";
               type string {
               }
             }
           }
         }
         leaf count {
           description "Count the packet in the named counter";
           type string {
           }
         }
         leaf loss-priority {
           description "Packet's loss priority";
           type enumeration {
             enum "low" {
               description "Loss priority low";
             }
             enum "high" {
               description "Loss priority high";
             }
             enum "medium-low" {
               description "Loss priority medium-low";
             }
             enum "medium-high" {
               description "Loss priority medium-high";
             }
           }
         }
         leaf forwarding-class {
           description "Classify packet to forwarding class";
           type string {
           }
         }
         choice designation {
           case case_1 {
             leaf accept {
               description "Accept the packet";
               type empty;
             }
           }
           case case_2 {
             leaf discard {
               description "Discard the packet";
               type empty;
             }
           }
           case case_3 {
             leaf next {
               description "Continue to next term in a filter";
               type enumeration {
                 enum "term" {
                   description "Continue to next term in a filter";
                 }
               }
             }
           }
         }
         leaf port-mirror-instance {
           description "Port-mirror the packet to specified instance";
           type string {
           }
         }
         leaf port-mirror {
           description "Port-mirror the packet";
           type empty;
         }
       }
     }
   }
   grouping vrrp-group {
     description "Virtual Router Redundancy Protocol group";
     leaf name {
       description "Identifier for VRRP group";
       type union {
         type string {
           pattern "<.*>|$.*";
         }
         type uint32 {
           range "0 .. 255";
         }
       }
     }
     uses apply-advanced;
     choice address {
       case case_1 {
         leaf-list virtual-address {
           ordered-by user;
           description "One or more virtual IPv4 addresses";
           type jt:ipv4addr;
         }
       }
       case case_2 {
         leaf-list virtual-inet6-address {
           ordered-by user;
           description "One or more virtual inet6 addresses";
           type jt:ipv6addr;
         }
       }
     }
     leaf virtual-link-local-address {
       description "Virtual link-local addresses";
       type jt:ipv6addr;
     }
     leaf priority {
       description "Virtual router election priority";
       type union {
         type string {
           pattern "<.*>|$.*";
         }
         type uint32 {
           range "0 .. 255";
         }
       }
     }
     leaf preferred {
       description "Preferred group on subnet";
       type empty;
     }
     choice advertisement_type {
       case case_1 {
         leaf advertise-interval {
           description "Advertisement interval";
           units "seconds";
           type union {
             type string {
               pattern "<.*>|$.*";
             }
             type uint32 {
               range "1 .. 255";
             }
           }
         }
       }
       case case_2 {
         leaf fast-interval {
           description "Fast advertisement interval";
           units "milliseconds";
           type union {
             type string {
               pattern "<.*>|$.*";
             }
             type uint32 {
               range "10 .. 40950";
             }
           }
         }
       }
       case case_3 {
         leaf inet6-advertise-interval {
           description "Inet6 advertisement interval";
           units "milliseconds";
           type union {
             type string {
               pattern "<.*>|$.*";
             }
             type uint32 {
               range "100 .. 40000";
             }
           }
         }
       }
     }
     choice preempt_type {
       case case_1 {
         container preempt {
           presence "enable preempt";
           description "Allow preemption";
           uses apply-advanced;
           leaf hold-time {
             description "Preemption hold time";
             units "seconds";
             type union {
               type string {
                 pattern "<.*>|$.*";
               }
               type uint32 {
                 range "0 .. 3600";
               }
             }
           }
         }
       }
       case case_2 {
         leaf no-preempt {
           description "Don't allow preemption";
           type empty;
         }
       }
     }
     choice accept_type {
       case case_1 {
         leaf accept-data {
           description "Accept packets destined for virtual IP address";
           type empty;
         }
       }
       case case_2 {
         leaf no-accept-data {
           description "Don't accept packets destined for virtual IP address";
           type empty;
         }
       }
     }
     leaf authentication-type {
       description "Authentication type";
       type enumeration {
         enum "md5" {
           description "HMAC-MD5-96";
         }
         enum "simple" {
           description "Simple password";
         }
       }
     }
     leaf authentication-key {
       description "Authentication key";
       type jt:unreadable;
     }
     container track {
       description "Interfaces to track for VRRP group";
       uses apply-advanced;
       leaf priority-hold-time {
         description "Priority hold time";
         units "seconds";
         type union {
           type string {
             pattern "<.*>|$.*";
           }
           type uint32 {
             range "0 .. 3600";
           }
         }
       }
       list interface {
         key name;
         ordered-by user;
         description "Interface to track in VRRP group";
         leaf name {
           description "Name of interface";
           type union {
             type jt:interface-unit;
             type string {
               pattern "<.*>|$.*";
             }
           }
         }
         uses apply-advanced;
         list bandwidth-threshold {
           key name;
           description "Track bandwidth of interface";
           leaf name {
             description "Interface speed below which priority cost is incurred";
             units "bits per second";
             type string;
           }
           leaf priority-cost {
             description "Value subtracted from priority when bandwidth is below threshold";
             type union {
               type string {
                 pattern "<.*>|$.*";
               }
               type uint32 {
                 range "1 .. 254";
               }
             }
           }
         }
         leaf priority-cost {
           description "Value to subtract from priority when interface is down";
           type union {
             type string {
               pattern "<.*>|$.*";
             }
             type uint32 {
               range "1 .. 254";
             }
           }
         }
       }
       list route {
         key "route_address routing-instance";
         ordered-by user;
         description "Route to track in VRRP group";
         leaf route_address {
           description "Route address";
           type jt:ipprefix-mandatory;
         }
         leaf routing-instance {
           description "Routing instance to which route belongs, or 'default'";
           type string {
           }
         }
         leaf priority-cost {
           description "Value to subtract from priority when route is down";
           type union {
             type string {
               pattern "<.*>|$.*";
             }
             type uint32 {
               range "1 .. 254";
             }
           }
         }
       }
     }
     container vrrp-inherit-from {
       description "VRRP group to follow for this VRRP group";
       uses apply-advanced;
       leaf active-interface {
         description "Interface name of VRRP active group";
         type union {
           type jt:interface-unit;
           type string {
             pattern "<.*>|$.*";
           }
         }
       }
       leaf active-group {
         description "Identifier for VRRP active group";
         type union {
           type string {
             pattern "<.*>|$.*";
           }
           type uint32 {
             range "0 .. 255";
           }
         }
       }
     }
     leaf advertisements-threshold {
       description "Number of vrrp advertisements missed before declaring master down";
       type union {
         type string {
           pattern "<.*>|$.*";
         }
         type uint32 {
           range "1 .. 15";
         }
       }
     }
   }
   grouping web-filtering-block-message {
     description "Web filtering block message settings";
     uses apply-advanced;
     leaf type {
       description "Type of block message desired";
       type enumeration {
         enum "custom-redirect-url" {
           description "Custom redirect URL server";
         }
       }
     }
     leaf url {
       description "URL of block message";
       type string {
         length "1 .. 1024";
       }
     }
   }
   grouping web-filtering-fallback-setting {
     description "Web-filtering fallback settings";
     uses apply-advanced;
     leaf default {
       description "Fallback default settings";
       type enumeration {
         enum "log-and-permit" {
         }
         enum "block" {
         }
       }
     }
     leaf server-connectivity {
       description "Fallback action when device cannot connect to server";
       type enumeration {
         enum "log-and-permit" {
         }
         enum "block" {
         }
       }
     }
     leaf timeout {
       description "Fallback action when connection to server timeout";
       type enumeration {
         enum "log-and-permit" {
         }
         enum "block" {
         }
       }
     }
     leaf too-many-requests {
       description "Fallback action when requests exceed the limit of engine";
       type enumeration {
         enum "log-and-permit" {
         }
         enum "block" {
         }
       }
     }
   }
   grouping web-filtering-quarantine-message {
     description "Web filtering quarantine message settings";
     uses apply-advanced;
     leaf type {
       description "Type of quarantine message desired";
       type enumeration {
         enum "custom-redirect-url" {
           description "Custom redirect URL server";
         }
       }
     }
     leaf url {
       description "URL of quarantine message";
       type string {
         length "1 .. 1024";
       }
     }
   }
   grouping web-filtering-traceoptions {
     description "Trace options for web-filtering feature";
     uses apply-advanced;
     list flag {
       key name;
       ordered-by user;
       description "Trace options for web-filtering feature trace flag";
       leaf name {
         description "Trace options for web-filtering feature trace flag name";
         type enumeration {
           enum "basic" {
             description "Trace web-filtering module generic basic information";
           }
           enum "session-manager" {
             description "Trace session management information";
           }
           enum "heartbeat" {
             description "Trace connectivity information with web-filter server";
           }
           enum "packet" {
             description "Trace packet information from session management";
           }
           enum "profile" {
             description "Trace profile config information";
           }
           enum "requests" {
             description "Trace requests sent to web-filter server";
           }
           enum "response" {
             description "Trace response received from web-filter server";
           }
           enum "socket" {
             description "Trace communication socket with web-filter server";
           }
           enum "timer" {
             description "Trace aging information for requests sent to server";
           }
           enum "ipc" {
             description "Trace communication events with PFE";
           }
           enum "cache" {
             description "Trace category cache operations";
           }
           enum "enhanced" {
             description "Trace Juniper enhanced web-filtering operations";
           }
           enum "all" {
             description "Enable trace all anti-virus trace options";
           }
         }
       }
     }
   }
   grouping webfilter-feature {
     description "Web-filtering feature settings";
     uses apply-advanced;
     container surf-control-integrated {
       description "Configure web-filtering surf-control integrated engine";
       status deprecated;
       uses surf-control-integrated-type;
     }
     container websense-redirect {
       description "Configure web-filtering websense redirect engine";
       uses websense-type;
     }
     container juniper-local {
       description "Configure web-filtering juniper local engine";
       uses juniper-local-type;
     }
     container juniper-enhanced {
       description "Configure web-filtering juniper enhanced engine";
       uses juniper-enhanced-type;
     }
   }
   grouping juniper-enhanced-type {
     description "Juniper Enhanced";
     uses apply-advanced;
     list profile {
       key name;
       ordered-by user;
       description "Juniper enhanced profile";
       leaf name {
         description "Juniper enhanced profile name";
         type string {
           length "1 .. 29";
         }
       }
       uses apply-advanced;
       leaf base-filter {
         description "Juniper base filter";
         type string;
       }
       list category {
         key name;
         ordered-by user;
         description "Juniper enhanced category";
         uses juniper-enhanced-category-type;
       }
       container site-reputation-action {
         description "Juniper enhanced site reputation action";
         presence "enable site-reputation-action";
         uses juniper-enhanced-site-reputation-setting;
       }
       leaf default {
         description "Juniper enhanced profile default";
         type enumeration {
           enum "permit" {
             description "Permit action";
           }
           enum "block" {
             description "Block action";
           }
           enum "log-and-permit" {
             description "Log and permit action";
           }
           enum "quarantine" {
             description "Quarantine action";
           }
         }
       }
       leaf custom-block-message {
         description "Juniper enhanced custom block message sent to HTTP client";
         type string {
           length "1 .. 512";
         }
       }
       leaf quarantine-custom-message {
         description "Juniper enhanced quarantine custom message";
         type string {
           length "1 .. 512";
         }
       }
       container fallback-settings {
         description "Juniper enhanced fallback settings";
         presence "enable fallback-settings";
         uses web-filtering-fallback-setting;
       }
       leaf timeout {
         description "Juniper enhanced timeout";
         units "seconds";
         type union {
           type string {
             pattern "<.*>|$.*";
           }
           type uint32;
         }
       }
       leaf no-safe-search {
         description "Do not perform safe-search for Juniper enhanced protocol";
         type empty;
       }
       container block-message {
         description "Juniper enhanced block message settings";
         presence "enable block-message";
         uses web-filtering-block-message;
       }
       container quarantine-message {
         description "Juniper enhanced quarantine message settings";
         presence "enable quarantine-message";
         uses web-filtering-quarantine-message;
       }
     }
   }
   grouping juniper-local-type {
     description "Juniper local";
     uses apply-advanced;
     list profile {
       key name;
       ordered-by user;
       description "Juniper local profile";
       leaf name {
         description "Juniper local profile name";
         type string {
           length "1 .. 29";
         }
       }
       uses apply-advanced;
       leaf default {
         description "Juniper local profile default";
         type enumeration {
           enum "permit" {
             description "Permit action";
           }
           enum "block" {
             description "Block action";
           }
           enum "log-and-permit" {
             description "Log and permit action";
           }
         }
       }
       list category {
         key name;
         ordered-by user;
         description "Custom category";
         uses custom-category-type;
       }
       leaf custom-block-message {
         description "Juniper local custom block message";
         type string {
           length "1 .. 512";
         }
       }
       leaf quarantine-custom-message {
         description "Juniper local quarantine custom message";
         type string {
           length "1 .. 512";
         }
       }
       container block-message {
         description "Juniper local block message settings";
         presence "enable block-message";
         uses web-filtering-block-message;
       }
       container quarantine-message {
         description "Juniper local quarantine message settings";
         presence "enable quarantine-message";
         uses web-filtering-quarantine-message;
       }
       container fallback-settings {
         description "Juniper local fallback settings";
         presence "enable fallback-settings";
         uses web-filtering-fallback-setting;
       }
       leaf timeout {
         description "Juniper local timeout";
         units "seconds";
         type union {
           type string {
             pattern "<.*>|$.*";
           }
           type uint32 {
             range "1 .. 1800";
           }
         }
       }
     }
   }
   grouping surf-control-integrated-type {
     description "Surf control integrated";
     uses apply-advanced;
     container cache {
       presence "enable cache";
       uses apply-advanced;
       leaf timeout {
         description "Surf control integrated cache timeout";
         default "1440";
         units "minutes";
         type union {
           type string {
             pattern "<.*>|$.*";
           }
           type uint32 {
             range "1 .. 1800";
           }
         }
       }
       leaf size {
         description "Surf control integrated cache size";
         default "1024";
         units "kilobytes";
         type string;
       }
     }
     container server {
       description "Surf control server";
       presence "enable server";
       uses server;
     }
     list profile {
       key name;
       ordered-by user;
       description "Surf control integrated profile";
       leaf name {
         description "Surf control integrated profile name";
         type string {
           length "1 .. 29";
         }
       }
       uses apply-advanced;
       list category {
         key name;
         ordered-by user;
         description "Surf control integrated category";
         uses surf-control-integrated-category-type;
       }
       leaf default {
         description "Surf control integrated profile default";
         type enumeration {
           enum "permit" {
             description "Permit action";
           }
           enum "block" {
             description "Block action";
           }
           enum "log-and-permit" {
             description "Log and permit action";
           }
         }
       }
       leaf custom-block-message {
         description "Surf control integrated custom block message";
         type string {
           length "1 .. 512";
         }
       }
       container fallback-settings {
         description "Surf control integrated fallback settings";
         presence "enable fallback-settings";
         uses web-filtering-fallback-setting;
       }
       leaf timeout {
         description "Surf control integrated timeout";
         default "15";
         units "seconds";
         type union {
           type string {
             pattern "<.*>|$.*";
           }
           type uint32 {
             range "1 .. 1800";
           }
         }
       }
     }
   }
   grouping surf-control-integrated-category-type {
     description "Surf control integrated category type";
     leaf name {
       description "Surf control integrated category type name";
       type string {
         length "1 .. 59";
       }
     }
     uses apply-advanced;
     leaf action {
       description "Surf control integrated category type action";
       type enumeration {
         enum "permit" {
           description "Permit action";
         }
         enum "block" {
           description "Block action";
         }
         enum "log-and-permit" {
           description "Log and permit action";
         }
       }
     }
   }
   grouping websense-type {
     description "Websense redirect";
     uses apply-advanced;
     list profile {
       key name;
       ordered-by user;
       description "Websense redirect profile";
       leaf name {
         description "Websense redirect profile name";
         type string {
           length "1 .. 29";
         }
       }
       uses apply-advanced;
       container server {
         description "Websense redirect server";
         presence "enable server";
         uses server;
       }
       list category {
         key name;
         ordered-by user;
         description "Custom category";
         uses custom-category-type;
       }
       leaf custom-block-message {
         description "Websense redirect custom block message";
         type string {
           length "1 .. 512";
         }
       }
       leaf quarantine-custom-message {
         description "Websense redirect quarantine custom message";
         type string {
           length "1 .. 512";
         }
       }
       container block-message {
         description "Websense redirect block message settings";
         presence "enable block-message";
         uses web-filtering-block-message;
       }
       container quarantine-message {
         description "Websense redirect quarantine message settings";
         presence "enable quarantine-message";
         uses web-filtering-quarantine-message;
       }
       container fallback-settings {
         description "Websense redirect fallback settings";
         presence "enable fallback-settings";
         uses web-filtering-fallback-setting;
       }
       leaf timeout {
         description "Websense redirect timeout";
         units "seconds";
         type union {
           type string {
             pattern "<.*>|$.*";
           }
           type uint32 {
             range "1 .. 1800";
           }
         }
       }
       leaf sockets {
         description "Websense redirect sockets number";
         type union {
           type string {
             pattern "<.*>|$.*";
           }
           type uint32 {
             range "1 .. 32";
           }
         }
       }
       leaf account {
         description "Websense redirect account";
         type string {
           length "1 .. 28";
         }
       }
     }
   }
   grouping wildcard-address-type {
     description "Wildcard address and mask";
     leaf name {
       description "Numeric IPv4 wildcard address with in the form of a.d.d.r/netmask";
       type string {
         length "1 .. 63";
       }
     }
     uses apply-advanced;
   }
   grouping write-option-82-type {
     uses apply-advanced;
   }
   grouping zone-interface-list-type {
     description "Logical interfaces in this zone";
     leaf name {
       description "Logical interface";
       type union {
         type jt:interface-name;
         type string {
           pattern "<.*>|$.*";
         }
       }
     }
     uses apply-advanced;
     container host-inbound-traffic {
       uses interface_host_inbound_traffic_t;
     }
   }
   grouping interface_host_inbound_traffic_t {
     uses apply-advanced;
     list system-services {
       key name;
       ordered-by user;
       description "Type of incoming system-service traffic to accept";
       uses interface-system-services-object-type;
     }
     list protocols {
       key name;
       ordered-by user;
       description "Protocol type of incoming traffic to accept";
       uses host-inbound-protocols-object-type;
     }
   }
   grouping host-inbound-protocols-object-type {
     description "Protocol type of incoming traffic to accept";
     leaf name {
       description "Protocol name";
       type enumeration {
         enum "all" {
           description "All protocols";
         }
         enum "bfd" {
           description "Bidirectional Forwarding Detection";
         }
         enum "bgp" {
           description "Border Gateway Protocol";
         }
         enum "dvmrp" {
           description "Distance Vector Multicast Routing Protocol";
         }
         enum "igmp" {
           description "Internet Group Management Protocol";
         }
         enum "ldp" {
           description "Label Distribution Protocol";
         }
         enum "msdp" {
           description "Multicast Source Discovery Protocol";
         }
         enum "ndp" {
           description "IPv6 Neighbor Discovery Protocol";
         }
         enum "nhrp" {
           description "Next Hop Resolution Protocol";
         }
         enum "ospf" {
           description "Open Shortest Path First";
         }
         enum "ospf3" {
           description "Open Shortest Path First version 3";
         }
         enum "pgm" {
           description "Pragmatic General Multicast";
         }
         enum "pim" {
           description "Protocol Independent Multicast";
         }
         enum "rip" {
           description "Routing Information Protocol";
         }
         enum "ripng" {
           description "Routing Information Protocol next generation";
         }
         enum "router-discovery" {
           description "Router Discovery";
         }
         enum "rsvp" {
           description "Resource Reservation Protocol";
         }
         enum "sap" {
           description "Session Announcement Protocol";
         }
         enum "vrrp" {
           description "Virtual Router Redundancy Protocol";
         }
       }
     }
     uses apply-advanced;
     leaf except {
       description "Protocol type of incoming traffic to disallow";
       type empty;
     }
   }
   grouping interface-system-services-object-type {
     description "Type of incoming system-service traffic to accept";
     leaf name {
       type enumeration {
         enum "all" {
           description "All system services";
         }
         enum "bootp" {
           description "Bootp and dhcp relay-agent service";
         }
         enum "dhcp" {
           description "Dynamic Host Configuration Protocol";
         }
         enum "dhcpv6" {
           description "Enable Dynamic Host Configuration Protocol for IPv6";
         }
         enum "dns" {
           description "DNS service";
         }
         enum "finger" {
           description "Finger service";
         }
         enum "ftp" {
           description "FTP";
         }
         enum "ident-reset" {
           description "Send back TCP RST to IDENT request for port 113";
         }
         enum "http" {
           description "Web management service using HTTP";
         }
         enum "https" {
           description "Web management service using HTTP secured by SSL";
         }
         enum "ike" {
           description "Internet Key Exchange";
         }
         enum "netconf" {
           description "NETCONF service";
         }
         enum "ping" {
           description "Internet Control Message Protocol echo requests";
         }
         enum "rlogin" {
           description "Rlogin service";
         }
         enum "reverse-telnet" {
           description "Reverse telnet service";
         }
         enum "reverse-ssh" {
           description "Reverse SSH service";
         }
         enum "rpm" {
           description "Real-time performance monitoring";
         }
         enum "rsh" {
           description "Rsh service";
         }
         enum "snmp" {
           description "Simple Network Management Protocol service";
         }
         enum "snmp-trap" {
           description "Simple Network Management Protocol traps";
         }
         enum "ssh" {
           description "SSH service";
         }
         enum "telnet" {
           description "Telnet service";
         }
         enum "traceroute" {
           description "Traceroute service";
         }
         enum "xnm-ssl" {
           description "JUNOScript API service over SSL";
         }
         enum "xnm-clear-text" {
           description "JUNOScript API for unencrypted traffic over TCP";
         }
         enum "tftp" {
           description "TFTP";
         }
         enum "lsping" {
           description "Label Switched Path ping service";
         }
         enum "ntp" {
           description "Network Time Protocol service";
         }
         enum "sip" {
           description "Enable Session Initiation Protocol service";
         }
         enum "r2cp" {
           description "Enable Radio-Router Control Protocol service";
         }
         enum "webapi-clear-text" {
           description "Webapi service using http";
         }
         enum "webapi-ssl" {
           description "Webapi service using HTTP secured by SSL";
         }
         enum "tcp-encap" {
           description "Tcp encapsulation service";
         }
         enum "appqoe" {
           description "APPQOE active probe servie";
         }
         enum "any-service" {
           description "Enable services on entire port range";
         }
       }
     }
     uses apply-advanced;
     leaf except {
       description "Type of incoming system-service traffic to disallow";
       type empty;
     }
   }
   grouping zone_host_inbound_traffic_t {
     uses apply-advanced;
     list system-services {
       key name;
       ordered-by user;
       description "Type of incoming system-service traffic to accept";
       uses zone-system-services-object-type;
     }
     list protocols {
       key name;
       ordered-by user;
       description "Protocol type of incoming traffic to accept";
       uses host-inbound-protocols-object-type;
     }
   }
   grouping zone-system-services-object-type {
     description "Type of incoming system-service traffic to accept";
     leaf name {
       type enumeration {
         enum "all" {
           description "All system services";
         }
         enum "bootp" {
           description "Bootp and dhcp relay-agent service";
         }
         enum "dhcp" {
           description "Dynamic Host Configuration Protocol";
         }
         enum "dhcpv6" {
           description "Enable Dynamic Host Configuration Protocol for IPv6";
         }
         enum "dns" {
           description "DNS service";
         }
         enum "finger" {
           description "Finger service";
         }
         enum "ftp" {
           description "FTP";
         }
         enum "ident-reset" {
           description "Send back TCP RST to IDENT request for port 113";
         }
         enum "http" {
           description "Web management service using HTTP";
         }
         enum "https" {
           description "Web management service using HTTP secured by SSL";
         }
         enum "ike" {
           description "Internet Key Exchange";
         }
         enum "netconf" {
           description "NETCONF service";
         }
         enum "ping" {
           description "Internet Control Message Protocol echo requests";
         }
         enum "rlogin" {
           description "Rlogin service";
         }
         enum "reverse-telnet" {
           description "Reverse telnet service";
         }
         enum "reverse-ssh" {
           description "Reverse SSH service";
         }
         enum "rpm" {
           description "Real-time performance monitoring";
         }
         enum "rsh" {
           description "Rsh service";
         }
         enum "snmp" {
           description "Simple Network Management Protocol service";
         }
         enum "snmp-trap" {
           description "Simple Network Management Protocol traps";
         }
         enum "ssh" {
           description "SSH service";
         }
         enum "telnet" {
           description "Telnet service";
         }
         enum "traceroute" {
           description "Traceroute service";
         }
         enum "xnm-ssl" {
           description "JUNOScript API service over SSL";
         }
         enum "xnm-clear-text" {
           description "JUNOScript API for unencrypted traffic over TCP";
         }
         enum "tftp" {
           description "TFTP";
         }
         enum "lsping" {
           description "Label Switched Path ping service";
         }
         enum "ntp" {
           description "Network Time Protocol service";
         }
         enum "sip" {
           description "Enable Session Initiation Protocol service";
         }
         enum "r2cp" {
           description "Enable Radio-Router Control Protocol service";
         }
         enum "webapi-clear-text" {
           description "Webapi service using http";
         }
         enum "webapi-ssl" {
           description "Webapi service using HTTP secured by SSL";
         }
         enum "tcp-encap" {
           description "Tcp encapsulation service";
         }
         enum "appqoe" {
           description "APPQOE active probe servie";
         }
         enum "any-service" {
           description "Enable services on entire port range";
         }
       }
     }
     uses apply-advanced;
     leaf except {
       description "Type of incoming system-service traffic to disallow";
       type empty;
     }
   }
 }
