/*
 * Copyright (c) 2019 Juniper Networks, Inc.
 * All rights reserved.
 */
 module junos-es-conf-applications {
   namespace "http://yang.juniper.net/junos-es/conf/applications";

   prefix jc-applications;

   import junos-common-ddl-extensions {
     prefix junos;
   }

   import junos-common-types {
     prefix jt;
   }

   import junos-es-conf-root {
     prefix jc;
   }

   organization "Juniper Networks, Inc.";

   contact "yang-support@juniper.net";

   description "Junos applications configuration module";

   revision 2019-01-01 {
     description "Junos: 18.4R3.3";
   }

   augment /jc:configuration {
     uses applications-group;
   }
   augment /jc:configuration/jc:groups {
     uses applications-group;
   }
   grouping applications-group {
     container applications {
       description "Define applications by protocol characteristics";
       uses apply-advanced;
       list application {
         key name;
         ordered-by user;
         description "Define an application";
         uses application_object;
       }
       list application-set {
         key name;
         ordered-by user;
         description "Define an application set";
         uses application_set_object;
       }
     }
   }
   grouping application_object {
     leaf name {
       description "Application name";
       type string {
         length "1 .. 63";
         junos:posix-pattern "^[[:alnum:]][[:alnum:]_-]*$";
         junos:pattern-message "Must be a string beginning with a number or letter and consisting of letters, numbers, dashes and underscores.";
       }
     }
     uses apply-advanced;
     leaf description {
       description "Text description of application";
       type string {
         length "1 .. 900";
         junos:posix-pattern "^[^&<>\n]+$";
         junos:pattern-message "Must be a string excluding '&', '<', '>' and '\n'";
       }
     }
     list term {
       key name;
       ordered-by user;
       description "Define individual application protocols";
       max-elements 8;
       uses term_object;
     }
     leaf application-protocol {
       description "Application protocol type";
       type enumeration {
         enum "bootp" {
           description "Bootstrap protocol";
         }
         enum "dce-rpc" {
           description "DCE RPC";
         }
         enum "dce-rpc-portmap" {
           description "DCE RPC portmap";
         }
         enum "dns" {
           description "Domain Name Service";
         }
         enum "exec" {
           description "Remote Execution Protocol";
         }
         enum "ftp" {
           description "File Transfer Protocol";
         }
         enum "ftp-data" {
           description "File Transfer Protocol Data Session";
         }
         enum "gprs-gtp-c" {
           description "GPRS Tunneling Control Plane";
         }
         enum "gprs-gtp-u" {
           description "GPRS Tunneling User Plane";
         }
         enum "gprs-gtp-v0" {
           description "GPRS Tunneling Version 0";
         }
         enum "gprs-sctp" {
           description "GPRS Stream Control Protocol";
         }
         enum "h323" {
           description "H.323";
         }
         enum "icmp" {
           description "ICMP";
         }
         enum "icmpv6" {
           description "ICMPv6";
         }
         enum "ignore" {
           description "Ignore application type";
         }
         enum "iiop" {
           description "Internet Inter-ORB Protocol";
         }
         enum "ike-esp-nat" {
           description "IKE/ESP with NAT";
         }
         enum "ip" {
           description "IP";
         }
         enum "login" {
           description "Login";
         }
         enum "mgcp-ca" {
           description "MGCP-CA";
         }
         enum "mgcp-ua" {
           description "MGCP-UA";
         }
         enum "ms-rpc" {
           description "Microsoft RPC";
         }
         enum "netbios" {
           description "NetBIOS";
         }
         enum "netshow" {
           description "NetShow";
         }
         enum "none" {
           description "None";
         }
         enum "pptp" {
           description "Point-to-Point Tunneling Protocol";
         }
         enum "q931" {
           description "Q.931";
         }
         enum "ras" {
           description "RAS";
         }
         enum "realaudio" {
           description "RealAudio";
         }
         enum "rpc" {
           description "RPC";
         }
         enum "rpc-portmap" {
           description "RPC portmap";
         }
         enum "rsh" {
           description "Remote Shell";
         }
         enum "rtsp" {
           description "Real Time Streaming Protocol";
         }
         enum "sccp" {
           description "Skinny Client Control Protocol";
         }
         enum "sip" {
           description "Session Initiation Protocol";
         }
         enum "shell" {
           description "Shell";
         }
         enum "snmp" {
           description "SNMP";
         }
         enum "sqlnet" {
           description "SQLNet";
         }
         enum "sqlnet-v2" {
           description "Oracle SQL*Net Version 2";
         }
         enum "sun-rpc" {
           description "Sun Microsystems RPC";
         }
         enum "talk" {
           description "Talk Program";
         }
         enum "tftp" {
           description "Trivial File Transfer Protocol";
         }
         enum "traceroute" {
           description "Traceroute";
         }
         enum "http" {
           description "Hypertext Transfer Protocol";
         }
         enum "winframe" {
           description "WinFrame";
         }
         enum "https" {
           description "Hypertext Transfer Protocol";
         }
         enum "imap" {
           description "Internet Mail Access Protocol";
         }
         enum "smtp" {
           description "Simple Mail Transfer Protocol";
         }
         enum "ssh" {
           description "Secure Shell Protocol";
         }
         enum "telnet" {
           description "Telnet Protocol";
         }
         enum "twamp" {
           description "Two Way Active Meaurement Protocol";
         }
       }
     }
     leaf protocol {
       description "Match IP protocol type";
       type string;
     }
     leaf source-port {
       description "Match TCP/UDP source port";
       type string;
     }
     leaf destination-port {
       description "Match TCP/UDP destination port";
       type string;
     }
     leaf ether-type {
       description "Match ether type";
       type string {
         junos:posix-pattern "^(0[Xx][0-9A-Fa-f]{4})$|^([0-9A-Fa-f]{4})$";
         junos:pattern-message "Ether-type should be in hex - (example: 0x8906)";
       }
     }
     leaf icmp-type {
       description "Match ICMP message type";
       type string;
     }
     leaf icmp6-type {
       description "Match ICMP6 message type";
       type string;
     }
     leaf icmp-code {
       description "Match ICMP message code";
       type string;
     }
     leaf icmp6-code {
       description "Match ICMP6 message code";
       type string;
     }
     leaf rpc-program-number {
       description "Match range of RPC program numbers";
       type string {
         junos:posix-pattern "^(0|[1-9][0-9]{0,9})(-(0|[1-9][0-9]{0,9}))?$";
         junos:pattern-message "Value must be an integer or a range of integers";
       }
     }
     leaf uuid {
       description "Match universal unique identifier for DCE RPC objects";
       type string {
         junos:posix-pattern "^[[:xdigit:]]{8}-[[:xdigit:]]{4}-[[:xdigit:]]{4}-[[:xdigit:]]{4}-[[:xdigit:]]{12}$";
         junos:pattern-message "Value must be of the form xxxxxxxx-xxxx-xxxx-xxxx-xxxxxxxxxxxx";
       }
     }
     leaf inactivity-timeout {
       description "Application-specific inactivity timeout";
       units "seconds";
       type string;
     }
     choice dns-choice {
       case case_1 {
         leaf do-not-translate-AAAA-query-to-A-query {
           description "Knob to control the translation of AAAA query to A query";
           junos:must "(\".. application-protocol dns\")";
           junos:must-message "Application protocol must be DNS";
           type empty;
         }
       }
       case case_2 {
         leaf do-not-translate-A-query-to-AAAA-query {
           description "Knob to control the translation of A query to AAAA query";
           junos:must "(\".. application-protocol dns\")";
           junos:must-message "Application protocol must be DNS";
           type empty;
         }
       }
     }
   }
   grouping application_set_object {
     leaf name {
       description "Application set name";
       type string {
         length "1 .. 63";
         junos:posix-pattern "^[[:alnum:]][[:alnum:]_-]*$";
         junos:pattern-message "Must be a string beginning with a number or letter and consisting of letters, numbers, dashes and underscores.";
       }
     }
     uses apply-advanced;
     leaf description {
       description "Text description of application set";
       type string {
         length "1 .. 900";
         junos:posix-pattern "^[^&<>\n]+$";
         junos:pattern-message "Must be a string excluding '&', '<', '>' and '\n'";
       }
     }
     list application {
       key name;
       ordered-by user;
       description "Application to be included in the set";
       leaf name {
         description "Application name";
         type string {
           length "1 .. 63";
           junos:posix-pattern "^[[:alnum:]][[:alnum:]_-]*$";
           junos:pattern-message "Must be a string beginning with a number or letter and consisting of letters, numbers, dashes and underscores.";
         }
       }
       uses apply-advanced;
     }
     list application-set {
       key name;
       ordered-by user;
       description "Define an application-set";
       leaf name {
         description "Define an application-set name";
         type string {
           length "1 .. 63";
           junos:posix-pattern "^[[:alnum:]][[:alnum:]_-]*$";
           junos:pattern-message "Must be a string beginning with a number or letter and consisting of letters, numbers, dashes and underscores.";
         }
       }
       uses apply-advanced;
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping macro-data-type {
     leaf name {
       description "Keyword part of the keyword-value pair";
       type string;
     }
     leaf value {
       description "Value part of the keyword-value pair";
       type string;
     }
   }
   grouping term_object {
     leaf name {
       description "Term name";
       type string {
         length "1 .. 63";
         junos:posix-pattern "^[[:alnum:]][[:alnum:]_-]*$";
         junos:pattern-message "Must be a string beginning with a number or letter and consisting of letters, numbers, dashes and underscores.";
       }
     }
     leaf alg {
       description "Application Layer Gateway";
       type enumeration {
         enum "bootp" {
           description "Bootstrap protocol";
         }
         enum "dce-rpc" {
           description "DCE RPC";
         }
         enum "dce-rpc-portmap" {
           description "DCE RPC portmap";
         }
         enum "dns" {
           description "Domain Name Service";
         }
         enum "exec" {
           description "Remote Execution Protocol";
         }
         enum "ftp" {
           description "File Transfer Protocol";
         }
         enum "ftp-data" {
           description "File Transfer Protocol Data Session";
         }
         enum "gprs-gtp-c" {
           description "GPRS Tunneling Control Plane";
         }
         enum "gprs-gtp-u" {
           description "GPRS Tunneling User Plane";
         }
         enum "gprs-gtp-v0" {
           description "GPRS Tunneling Version 0";
         }
         enum "gprs-sctp" {
           description "GPRS Stream Control Protocol";
         }
         enum "h323" {
           description "H.323";
         }
         enum "icmp" {
           description "ICMP";
         }
         enum "icmpv6" {
           description "ICMPv6";
         }
         enum "ignore" {
           description "Ignore application type";
         }
         enum "iiop" {
           description "Internet Inter-ORB Protocol";
         }
         enum "ike-esp-nat" {
           description "IKE/ESP with NAT";
         }
         enum "ip" {
           description "IP";
         }
         enum "login" {
           description "Login";
         }
         enum "mgcp-ca" {
           description "MGCP-CA";
         }
         enum "mgcp-ua" {
           description "MGCP-UA";
         }
         enum "ms-rpc" {
           description "Microsoft RPC";
         }
         enum "netbios" {
           description "NetBIOS";
         }
         enum "netshow" {
           description "NetShow";
         }
         enum "none" {
           description "None";
         }
         enum "pptp" {
           description "Point-to-Point Tunneling Protocol";
         }
         enum "q931" {
           description "Q.931";
         }
         enum "ras" {
           description "RAS";
         }
         enum "realaudio" {
           description "RealAudio";
         }
         enum "rpc" {
           description "RPC";
         }
         enum "rpc-portmap" {
           description "RPC portmap";
         }
         enum "rsh" {
           description "Remote Shell";
         }
         enum "rtsp" {
           description "Real Time Streaming Protocol";
         }
         enum "sccp" {
           description "Skinny Client Control Protocol";
         }
         enum "sip" {
           description "Session Initiation Protocol";
         }
         enum "shell" {
           description "Shell";
         }
         enum "snmp" {
           description "SNMP";
         }
         enum "sqlnet" {
           description "SQLNet";
         }
         enum "sqlnet-v2" {
           description "Oracle SQL*Net Version 2";
         }
         enum "sun-rpc" {
           description "Sun Microsystems RPC";
         }
         enum "talk" {
           description "Talk Program";
         }
         enum "tftp" {
           description "Trivial File Transfer Protocol";
         }
         enum "traceroute" {
           description "Traceroute";
         }
         enum "http" {
           description "Hypertext Transfer Protocol";
         }
         enum "winframe" {
           description "WinFrame";
         }
         enum "https" {
           description "Hypertext Transfer Protocol";
         }
         enum "imap" {
           description "Internet Mail Access Protocol";
         }
         enum "smtp" {
           description "Simple Mail Transfer Protocol";
         }
         enum "ssh" {
           description "Secure Shell Protocol";
         }
         enum "telnet" {
           description "Telnet Protocol";
         }
         enum "twamp" {
           description "Two Way Active Meaurement Protocol";
         }
       }
     }
     leaf protocol {
       description "Match IP protocol type";
       type string;
     }
     leaf source-port {
       description "Match TCP/UDP source port";
       type string;
     }
     leaf destination-port {
       description "Match TCP/UDP destination port";
       type string;
     }
     leaf icmp-type {
       description "Match ICMP message type";
       type string;
     }
     leaf icmp-code {
       description "Match ICMP message code";
       type string;
     }
     leaf icmp6-type {
       description "Match ICMP6 message type";
       type string;
     }
     leaf icmp6-code {
       description "Match ICMP6 message code";
       type string;
     }
     leaf rpc-program-number {
       description "Match range of RPC program numbers";
       type string {
         junos:posix-pattern "^(0|[1-9][0-9]{0,9})(-(0|[1-9][0-9]{0,9}))?$";
         junos:pattern-message "Value must be an integer or a range of integers";
       }
     }
     leaf uuid {
       description "Match universal unique identifier for DCE RPC objects";
       type string {
         junos:posix-pattern "^[[:xdigit:]]{8}-[[:xdigit:]]{4}-[[:xdigit:]]{4}-[[:xdigit:]]{4}-[[:xdigit:]]{12}$";
         junos:pattern-message "Value must be of the form xxxxxxxx-xxxx-xxxx-xxxx-xxxxxxxxxxxx";
       }
     }
     leaf inactivity-timeout {
       description "Application-specific inactivity timeout";
       units "seconds";
       type string;
     }
   }
 }
