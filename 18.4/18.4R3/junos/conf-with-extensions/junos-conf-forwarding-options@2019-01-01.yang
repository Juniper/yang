/*
 * Copyright (c) 2019 Juniper Networks, Inc.
 * All rights reserved.
 */
 module junos-conf-forwarding-options {
   namespace "http://yang.juniper.net/junos/conf/forwarding-options";

   prefix jc-forwarding-options;

   import junos-common-ddl-extensions {
     prefix junos;
   }

   import junos-common-types {
     prefix jt;
   }

   import junos-conf-root {
     prefix jc;
   }

   organization "Juniper Networks, Inc.";

   contact "yang-support@juniper.net";

   description "Junos forwarding-options configuration module";

   revision 2019-01-01 {
     description "Junos: 18.4R3.3";
   }

   augment /jc:configuration {
     uses forwarding-options-group;
   }
   augment /jc:configuration/jc:groups {
     uses forwarding-options-group;
   }
   grouping forwarding-options-group {
     container forwarding-options {
       description "Configure options to control packet forwarding";
       uses juniper-forwarding-options;
     }
   }
   grouping juniper-forwarding-options {
     uses apply-advanced;
     list storm-control-profiles {
       key name;
       description "Storm control profile for this instance";
       leaf name {
         description "Storm control profile name";
         junos:must "(\"forwarding-options storm-control-profiles $$ all\")";
         junos:must-message "Only aggregate profiles supported";
         type string {
           length "1 .. 127";
         }
       }
       uses apply-advanced;
       container all {
         presence "enable all";
         description "For all BUM traffic";
         uses apply-advanced;
         choice bandwidth {
           case case_1 {
             leaf bandwidth-percentage {
               description "Percentage of link bandwidth";
               type union {
                 type string {
                   pattern "<.*>|$.*";
                 }
                 type uint32 {
                   range "1 .. 100";
                 }
               }
             }
           }
           case case_2 {
             leaf bandwidth-level {
               description "Link bandwidth";
               units "kbps";
               type union {
                 type string {
                   pattern "<.*>|$.*";
                 }
                 type uint32;
               }
             }
           }
         }
         leaf burst-size {
           description "Burst size";
           units "bytes";
           type union {
             type string {
               pattern "<.*>|$.*";
             }
             type uint32 {
               range "1500 .. 100000000";
             }
           }
         }
         leaf no-broadcast {
           description "Disable broadcast storm control";
           type empty;
         }
         leaf no-unknown-unicast {
           description "Disable unknown unicast storm control";
           type empty;
         }
         choice no-multicast-choices {
           case case_1 {
             leaf no-multicast {
               description "Disable multicast storm control";
               type empty;
             }
           }
           case case_2 {
             leaf no-registered-multicast {
               description "Disable registered multicast storm control";
               type empty;
             }
           }
           case case_3 {
             leaf no-unregistered-multicast {
               description "Disable unregistered multicast storm control";
               type empty;
             }
           }
         }
       }
       leaf action-shutdown {
         description "Disable port for excessive storm control errors";
         type empty;
       }
     }
     choice sampling-or-packet-capture {
       case case_1 {
         container sampling {
           description "Statistical traffic sampling options";
           uses juniper-sampling-options;
         }
       }
       case case_2 {
         container packet-capture {
           description "Packet capture options";
           uses juniper-packet-capture-options;
         }
       }
     }
     list monitoring {
       key name;
       description "Configure lawful interception of traffic";
       uses juniper-monitoring-options;
     }
     list accounting {
       key name;
       description "Configure accounting of traffic";
       uses juniper-packet-accounting-options;
     }
     list analyzer {
       key name;
       description "Analyzer options";
       uses smpl-analyzer-type;
     }
     container port-mirroring {
       description "Configure port mirroring of traffic";
       uses juniper-port-mirror-options;
     }
     container multicast-replication {
       description "Set mode of multicast replication";
       uses apply-advanced;
       leaf ingress {
         description "Complete ingress replication";
         junos:must "(\"chassis network-services enhanced-ip\")";
         junos:must-message "Enhanced IP must be configured for using multicast-replication features";
         type empty;
       }
       leaf local-latency-fairness {
         description "Complete parallel replication";
         junos:must "(\"chassis network-services enhanced-ip\")";
         junos:must-message "Enhanced IP must be configured for using multicast-replication features";
         type empty;
       }
       container evpn {
         description "EVPN IRB multicast related options";
         uses apply-advanced;
         leaf irb {
           type enumeration {
             enum "local-only" {
               description "Multicast forward in local-only mode";
             }
             enum "local-remote" {
               description "Multicast forward in local-remote mode";
             }
           }
         }
         leaf smet-nexthop-limit {
           description "Flood traffic to all egress when count goes above limit";
           type union {
             type string {
               pattern "<.*>|$.*";
             }
             type uint32 {
               range "10000 .. 40000";
             }
           }
         }
       }
     }
     container load-balance {
       description "Configure load-balancing attributes on the forwarding path";
       uses apply-advanced;
       container indexed-load-balance {
         presence "enable indexed-load-balance";
         description "Use indexed permuted next hop lists for unilist and aggregate next hops";
         uses apply-advanced;
       }
       container per-flow {
         uses apply-advanced;
         leaf hash-seed {
           description "Enable per flow seed value on packet forwarding engine";
           type empty;
         }
       }
       container per-prefix {
         presence "enable per-prefix";
         uses apply-advanced;
         leaf hash-seed {
           description "Specifies per-router input value for per-prefix load-balancing hash function";
           default "0";
           type union {
             type string {
               pattern "<.*>|$.*";
             }
             type uint16 {
               range "0 .. 65534";
             }
           }
         }
       }
     }
     container hash-key {
       description "Select data used in the hash key";
       uses junos_hash_key;
     }
     container local-bias {
       presence "enable local-bias";
       description "Turn on local bias functionality";
       uses apply-advanced;
       leaf disable {
         description "Disable local-bias";
         type empty;
       }
     }
     container enhanced-hash-key {
       description "Select data used in the hash key for Enhanced IP Forwarding Engines";
       uses apply-advanced;
       container hash-mode {
         description "Hashing mode";
         uses apply-advanced;
         choice instance {
           case case_1 {
             leaf layer2-header {
               description "Only layer2 header fields are considered for hashing";
               type empty;
             }
           }
           case case_2 {
             leaf layer2-payload {
               description "Only layer2 payload fields are considered for hashing";
               type empty;
             }
           }
           case case_3 {
             leaf gtp-header-offset {
               description "Gtp header first byte offset";
               type union {
                 type uint8;
                 type string {
                   pattern "<.*>|$.*";
                 }
               }
             }
           }
         }
       }
       container hash-parameters {
         description "Set traffic hashing parameters";
         uses apply-advanced;
         container ecmp {
           description "Configure hashing parameters for ECMP Traffic";
           uses apply-advanced;
           leaf offset {
             description "Set hashing offset for ECMP Traffic";
             type union {
               type string {
                 pattern "<.*>|$.*";
               }
               type uint32 {
                 range "0 .. 199";
               }
             }
           }
           leaf preprocess {
             description "Enable/Disable the preprocess parameter for ECMP traffic";
             type empty;
           }
           container function {
             description "Configure hash functions for ECMP traffic";
             uses apply-advanced;
             choice instance {
               case case_1 {
                 leaf crc16-bisync {
                   description "Use CRC16-BISYNC function for ECMP traffic rcvd on xe";
                   type empty;
                 }
               }
               case case_2 {
                 leaf crc16-ccitt {
                   description "Use CRC16-CCITT function for ECMP traffic rcvd on xe";
                   type empty;
                 }
               }
               case case_3 {
                 leaf crc32-hi {
                   description "Use CRC32-HI function for ECMP traffic rcvd on xe";
                   type empty;
                 }
               }
               case case_4 {
                 leaf crc32-lo {
                   description "Use CRC32-LO function for ECMP traffic rcvd on xe";
                   type empty;
                 }
               }
             }
           }
         }
         container lag {
           description "Configure hashing parameters for LAG Traffic";
           uses apply-advanced;
           leaf offset {
             description "Set hashing offset for LAG Traffic";
             type union {
               type string {
                 pattern "<.*>|$.*";
               }
               type uint32 {
                 range "0 .. 4294967295";
               }
             }
           }
           leaf preprocess {
             description "Enable/Disable the preprocess parameter for LAG traffic";
             type empty;
           }
           container function {
             description "Configure hash functions for LAG traffic";
             uses apply-advanced;
             choice instance {
               case case_1 {
                 leaf crc16-bisync {
                   description "Use CRC16-BISYNC function for LAG traffic rcvd on xe";
                   type empty;
                 }
               }
               case case_2 {
                 leaf crc16-ccitt {
                   description "Use CRC16-CCITT function for LAG traffic rcvd on xe";
                   type empty;
                 }
               }
               case case_3 {
                 leaf crc32-hi {
                   description "Use CRC32-HI function for LAG traffic rcvd on xe";
                   type empty;
                 }
               }
               case case_4 {
                 leaf crc32-lo {
                   description "Use CRC32-LO function for LAG traffic rcvd on xe";
                   type empty;
                 }
               }
             }
           }
         }
       }
       container hash-seed {
         presence "enable hash-seed";
         description "Hash seed";
         uses apply-advanced;
         leaf seed-value {
           description "Hash seed value";
           type union {
             type string {
               pattern "<.*>|$.*";
             }
             type uint32 {
               range "0 .. 4294967295";
             }
           }
         }
       }
       container mpls {
         description "Configure mpls fields";
         uses apply-advanced;
         leaf no-incoming-port {
           description "Exclude incoming port from the hash key";
           type empty;
         }
         leaf no-incoming-device {
           description "Exclude incoming device from the hash key";
           type empty;
         }
       }
       container layer2 {
         description "Configure layer2 fields";
         uses apply-advanced;
         leaf no-incoming-port {
           description "Exclude incoming port from the hash key";
           type empty;
         }
         leaf no-incoming-device {
           description "Exclude incoming device from the hash key";
           type empty;
         }
         leaf no-source-mac-address {
           description "Exclude source MAC address from the hash key";
           type empty;
         }
         leaf no-destination-mac-address {
           description "Exclude destination MAC address from the hash key";
           type empty;
         }
         leaf no-ether-type {
           description "Exclude ether type from the hash key";
           type empty;
         }
         leaf vlan-id {
           description "Include incoming vlan-id in hash key";
           type empty;
         }
       }
       container inet {
         description "Configure inet4 fields";
         uses apply-advanced;
         leaf no-incoming-port {
           description "Exclude incoming port from the hash key";
           type empty;
         }
         leaf no-incoming-device {
           description "Exclude incoming device from the hash key";
           type empty;
         }
         leaf no-l4-source-port {
           description "Exclude l4 source port from the hash key";
           type empty;
         }
         leaf no-l4-destination-port {
           description "Exclude l4 dest port from the hash key";
           type empty;
         }
         leaf no-protocol {
           description "Exclude protocol from the hash key";
           type empty;
         }
         leaf no-ipv4-source-address {
           description "Exclude IPv4 source address";
           type empty;
         }
         leaf no-ipv4-destination-address {
           description "Exclude IPv4 destination address";
           type empty;
         }
         leaf vlan-id {
           description "Include incoming vlan-id in hash key";
           type empty;
         }
       }
       container inet6 {
         description "Configure inet6 fields";
         uses apply-advanced;
         leaf no-incoming-port {
           description "Exclude incoming port from the hash key";
           type empty;
         }
         leaf no-incoming-device {
           description "Exclude incoming device from the hash key";
           type empty;
         }
         leaf no-l4-source-port {
           description "Exclude l4 source port from the hash key";
           type empty;
         }
         leaf no-l4-destination-port {
           description "Exclude l4 dest port from the hash key";
           type empty;
         }
         leaf no-next-header {
           description "Exclude next header from the hash key";
           type empty;
         }
         leaf no-ipv6-source-address {
           description "Exclude IPv6 source address";
           type empty;
         }
         leaf no-ipv6-destination-address {
           description "Exclude IPv6 destination address";
           type empty;
         }
         leaf vlan-id {
           description "Include vlan-id in hash key";
           type empty;
         }
       }
       leaf no-mpls {
         description "Disable mpls in hash key";
         type empty;
       }
       container gre {
         description "Configure for GRE ";
         uses apply-advanced;
         leaf key {
           description "Include key in hash key";
           type empty;
         }
         leaf protocol {
           description "Include protocol in hash key";
           type empty;
         }
       }
       container services-loadbalancing {
         description "Select key to load balance across service PICs";
         uses apply-advanced;
         container family {
           description "Protocol family";
           container inet {
             description "IPv4 protocol family";
             uses apply-advanced;
             container layer-3-services {
               description "Include Layer 3 (IP) data in the hash key";
               uses apply-advanced;
               leaf source-address {
                 description "Include IP source address in the hash key";
                 type empty;
               }
               leaf destination-address {
                 description "Include IP destination address in the hash key";
                 type empty;
               }
               leaf incoming-interface-index {
                 description "Include incoming interface index in the hash key";
                 type empty;
               }
             }
           }
           container inet6 {
             description "IPv6 protocol family";
             uses apply-advanced;
             container layer-3-services {
               description "Include Layer 3 (IP) data in the hash key";
               uses apply-advanced;
               leaf source-address {
                 description "Include IP source address in the hash key";
                 type empty;
               }
               leaf destination-address {
                 description "Include IP destination address in the hash key";
                 type empty;
               }
               leaf incoming-interface-index {
                 description "Include incoming interface index in the hash key";
                 type empty;
               }
               leaf src-prefix-len {
                 description "Enhanced hash key inet6 source prefix length";
                 default "127";
                 units "bits";
                 type union {
                   type string {
                     pattern "<.*>|$.*";
                   }
                   type uint32 {
                     range "56 .. 127";
                   }
                 }
               }
             }
           }
         }
       }
       container source-destination-only-loadbalancing {
         description "Configure key for source/destination-ip-only load balancing";
         uses apply-advanced;
         container family {
           description "Protocol family";
           container inet {
             description "IPv4 protocol family";
             uses apply-advanced;
             leaf prefix-length {
               description "Source/Destination Only Load-Balancing inet prefix length";
               default "32";
               units "bits";
               type union {
                 type string {
                   pattern "<.*>|$.*";
                 }
                 type uint32 {
                   range "1 .. 32";
                 }
               }
             }
           }
           container inet6 {
             description "IPv6 protocol family";
             uses apply-advanced;
             leaf prefix-length {
               description "Source/Destination Only Load-Balancing inet6 prefix length";
               default "128";
               units "bits";
               type union {
                 type string {
                   pattern "<.*>|$.*";
                 }
                 type uint32 {
                   range "1 .. 128";
                 }
               }
             }
           }
         }
       }
       container family {
         description "Protocol family";
         container inet {
           description "IPv4 protocol family";
           uses apply-advanced;
           leaf incoming-interface-index {
             description "Include incoming interface index in the hash key";
             type empty;
           }
           leaf no-destination-port {
             description "Omit IP destination port in the hash key";
             type empty;
           }
           leaf no-source-port {
             description "Omit IP source port in the hash key";
             type empty;
           }
           leaf type-of-service {
             description "Include TOS byte in the hash key";
             type empty;
           }
           leaf gtp-tunnel-endpoint-identifier {
             description "Include TEID in the hash key for GTP-U packets";
             type empty;
           }
           leaf l2tp-tunnel-session-identifier {
             description "Include TID SID in the hash key for L2TP packets";
             type empty;
           }
           leaf session-id {
             description "Include session ID in the enhanced hash key";
             type empty;
           }
         }
         container inet6 {
           description "IPv6 protocol family";
           uses apply-advanced;
           leaf incoming-interface-index {
             description "Include incoming interface index in the hash key";
             type empty;
           }
           leaf traffic-class {
             description "Include Traffic Class byte in the hash key";
             type empty;
           }
           leaf no-destination-port {
             description "Omit IP destination port in the hash key";
             type empty;
           }
           leaf no-source-port {
             description "Omit IP source port in the hash key";
             type empty;
           }
           leaf gtp-tunnel-endpoint-identifier {
             description "Include TEID in the hash key for GTP-U packets";
             type empty;
           }
           leaf no-flow-label {
             description "Omit Flow label in the hash key";
             type empty;
           }
         }
         container mpls {
           description "MPLS protocol family";
           uses apply-advanced;
           leaf label-1-exp {
             description "Include EXP of first MPLS label from the hash key";
             type empty;
           }
           leaf incoming-interface-index {
             description "Include incoming interface index in the hash key";
             type empty;
           }
           choice pseudowire_option {
             case case_1 {
               leaf no-ether-pseudowire {
                 description "Omit IP payload over ethernet PW from the hash-key";
                 type empty;
               }
             }
             case case_2 {
               container ether-pseudowire {
                 description "Load-balance IP over ethernet PW";
                 leaf zero-control-word {
                   description "Parse zero control word in packet header";
                   type empty;
                 }
               }
             }
           }
           leaf no-payload {
             description "Omit MPLS payload data from the hash key";
             type empty;
           }
         }
         container multiservice {
           description "Multiservice protocol (bridged/CCC/VPLS) family";
           uses apply-advanced;
           leaf incoming-interface-index {
             description "Include incoming interface index in hash key";
             type empty;
           }
           leaf outer-priority {
             description "Include Outer 802.1 Priority bits in the hash key";
             type empty;
           }
           leaf no-payload {
             description "Omit payload data from the hash key";
             type empty;
           }
           leaf no-mac-addresses {
             description "Omit source and destination MAC addresses from the hash key";
             type empty;
           }
         }
       }
       container hash-function {
         description "Configure hash functions";
         uses apply-advanced;
         choice instance {
           case case_1 {
             leaf CRC16-CCITT {
               description "16-bit CRC16 using CCITT polynomial";
               type empty;
             }
           }
           case case_2 {
             leaf CRC16 {
               description "16-bit CRC16 calculated using the BISYNC polynomial";
               type empty;
             }
           }
           case case_3 {
             leaf CRC16XOR1 {
               description "Upper 8 bits BISYNC CRC16 and 8 bit XOR1";
               type empty;
             }
           }
           case case_4 {
             leaf CRC16XOR2 {
               description "Upper 8 bit BISYNC CRC16 and 8 bit XOR2";
               type empty;
             }
           }
           case case_5 {
             leaf CRC16XOR4 {
               description "Upper 8 bit BISYNC CRC16 and 8 bit XOR4";
               type empty;
             }
           }
           case case_6 {
             leaf CRC16XOR8 {
               description "Upper 8 bit BISYNC CRC16 and 8 bit XOR8";
               type empty;
             }
           }
           case case_7 {
             leaf CRC32HI {
               description "16 LSBs of computed CRC32";
               type empty;
             }
           }
           case case_8 {
             leaf CRC32LO {
               description "16 MSBs of computed CRC32";
               type empty;
             }
           }
           case case_9 {
           }
           case case_10 {
           }
           case case_11 {
           }
           case case_12 {
           }
         }
       }
       leaf symmetric {
         description "Enable symmetric load-balancing";
         type empty;
       }
     }
     container next-hop {
       description "Next hop throttle";
       uses apply-advanced;
     }
     container multicast {
       description "Multicast resolve and mismatch rate";
       uses apply-advanced;
       leaf resolve-rate {
         description "Multicast resolve rate";
         units "per second";
         type union {
           type string {
             pattern "<.*>|$.*";
           }
           type uint32 {
             range "100 .. 1000";
           }
         }
       }
       leaf mismatch-rate {
         description "Multicast interface mismatch rate";
         units "per second";
         type union {
           type string {
             pattern "<.*>|$.*";
           }
           type uint32 {
             range "50 .. 1000";
           }
         }
       }
       container policer {
         presence "enable policer";
         uses apply-advanced;
         leaf bandwidth-limit {
           description "Bandwidth limit";
           units "bits per second";
           type string;
         }
         leaf burst-size-limit {
           description "Burst size limit";
           units "bytes";
           type string;
         }
       }
     }
     container rpf-loose-mode-discard {
       description "Configure rpf loose mode behavior";
       uses apply-advanced;
       container family {
         description "Protocol family";
         uses apply-advanced;
         leaf inet {
           description "Configure rpf loose mode behavior for IPv4";
           type empty;
         }
         leaf inet6 {
           description "Configure rpf loose mode behavior for IPv6";
           type empty;
         }
       }
     }
     leaf l2circuit-control-passthrough {
       description "Configure passthrough for control protocol packets on L2 Circuit";
       type empty;
     }
     container explicit-null-cos {
       presence "enable explicit-null-cos";
       description "Configure to use MPLS explicit null exp for COS classification";
       uses apply-advanced;
       leaf inet {
         description "Include family inet";
         type empty;
       }
       leaf inet6 {
         description "Include family inet6";
         type empty;
       }
     }
     container helpers {
       description "Port forwarding configuration";
       uses apply-advanced;
       container traceoptions {
         description "Trace options for helper";
         uses apply-advanced;
         leaf no-remote-trace {
           description "Disable remote tracing";
           junos:must "(\"system tracing\")";
           junos:must-message "'no-remote-trace' is valid only when [system tracing] is configured";
           type empty;
         }
         container file {
           description "Trace file information";
           leaf filename {
             description "Name of file in which to write trace information";
             type string {
               length "1 .. 1024";
               junos:posix-pattern "![/ %]";
               junos:pattern-message "Must not contain '/', % or a space";
             }
           }
           leaf size {
             description "Maximum trace file size";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         leaf level {
           description "Level of debugging output";
           default "error";
           type enumeration {
             enum "error" {
               description "Match error conditions";
             }
             enum "warning" {
               description "Match warning messages";
             }
             enum "notice" {
               description "Match conditions that should be handled specially";
             }
             enum "info" {
               description "Match informational messages";
             }
             enum "verbose" {
               description "Match verbose messages";
             }
             enum "all" {
               description "Match all levels";
             }
           }
         }
         list flag {
           key name;
           ordered-by user;
           description "Area of UDP forwarding helper process on which to enable debugging output";
           leaf name {
             type enumeration {
               enum "trace" {
                 description "Trace tracing code";
               }
               enum "address" {
                 description "Trace address management code";
               }
               enum "main" {
                 description "Trace main loop code";
               }
               enum "config" {
                 description "Trace configuration code";
               }
               enum "ifdb" {
                 description "Trace interface database code";
               }
               enum "io" {
                 description "Trace I/O code";
               }
               enum "rtsock" {
                 description "Trace routing socket code";
               }
               enum "ui" {
                 description "Trace user interface code";
               }
               enum "util" {
                 description "Trace miscellaneous utility code";
               }
               enum "gencfg" {
                 description "Trace fud gencfg message";
               }
               enum "domain" {
                 description "Trace DNS service-specific code";
               }
               enum "tftp" {
                 description "Trace TFTP service-specific code";
               }
               enum "bootp" {
                 description "Trace BOOTP/DHCP service-specific code";
               }
               enum "port" {
                 description "Trace arbitrary protocol code";
               }
               enum "if-rtsdb" {
                 description "Trace interface hierarchy rtsdb";
               }
               enum "all" {
                 description "Trace all areas of code";
               }
             }
           }
         }
       }
       container rtsdb-client-traceoptions {
         presence "enable rtsdb-client-traceoptions";
         description "SHM rtsock database client library trace options";
         status deprecated;
         uses apply-advanced;
         container if-rtsdb {
           presence "enable if-rtsdb";
           description "Trace interface hierarchy rtsdb";
           uses apply-advanced;
           list flag {
             key name;
             ordered-by user;
             description "Tracing parameters";
             leaf name {
               type enumeration {
                 enum "init" {
                   description "Trace initialization";
                 }
                 enum "routing-socket" {
                   description "Trace routing socket messages";
                 }
                 enum "map" {
                   description "Trace shared memory mapping";
                 }
                 enum "all" {
                   description "Trace all";
                 }
               }
             }
             leaf disable {
               description "Disable this trace flag";
               type empty;
             }
           }
         }
       }
       container domain {
         description "Incoming DNS request forwarding configuration";
         uses apply-advanced;
         leaf description {
           description "Text description of server";
           type string;
         }
         container server {
           description "Server information";
           leaf address {
             description "Name or address of server to which to forward";
             type jt:ipv4addr;
           }
           choice instance {
             case case_1 {
               container logical-system {
                 description "Logical system of server to which to forward";
                 leaf logical-system-name {
                   description "Name of logical system";
                   junos:must "(\"logical-systems $$\")";
                   junos:must-message "referenced logical system must be defined";
                   type string {
                     junos:posix-pattern "^[a-zA-Z0-9_-]{1,63}$";
                     junos:pattern-message "Logical-system name is a string consisting of up to 63 letters, numbers, dashes and underscores";
                   }
                 }
                 leaf routing-instance {
                   description "Routing instance of server to which to forward";
                   type union {
                     type string {
                       pattern "default";
                     }
                     type string {
                       junos:posix-pattern "!^((__.*__)|(all)|(.*[ ].*)|(\"\")|(.{129,}))$";
                       junos:pattern-message "Must be a non-reserved string of 128 characters or less with no spaces.";
                     }
                   }
                 }
               }
             }
             case case_2 {
               leaf routing-instance {
                 description "Routing instance of server to which to forward";
                 junos:must "(\"routing-instances $$\")";
                 junos:must-message "referenced routing instance must be defined";
                 type union {
                   type string {
                     pattern "default";
                   }
                   type string {
                     junos:posix-pattern "!^((__.*__)|(all)|(.*[ ].*)|(\"\")|(.{129,}))$";
                     junos:pattern-message "Must be a non-reserved string of 128 characters or less with no spaces.";
                   }
                 }
               }
             }
           }
         }
         list interface {
           key name;
           ordered-by user;
           description "Incoming DNS request forwarding interface configuration";
           leaf name {
             description "Name of interface or group of interfaces";
             type union {
               type jt:interface-wildcard;
               type string {
                 pattern "<.*>|$.*";
               }
             }
           }
           uses apply-advanced;
           leaf no-listen {
             description "Do not listen on this interface";
             type empty;
           }
           leaf broadcast {
             description "If the layer 2 interface is unknown then broadcast";
             type empty;
           }
           leaf description {
             description "Text description of server";
             type string;
           }
           container server {
             description "Server information";
             leaf address {
               description "Name or address of server to which to forward";
               type jt:ipv4addr;
             }
             choice instance {
               case case_1 {
                 container logical-system {
                   description "Logical system of server to which to forward";
                   leaf logical-system-name {
                     description "Name of logical system";
                     junos:must "(\"logical-systems $$\")";
                     junos:must-message "referenced logical system must be defined";
                     type string {
                       junos:posix-pattern "^[a-zA-Z0-9_-]{1,63}$";
                       junos:pattern-message "Logical-system name is a string consisting of up to 63 letters, numbers, dashes and underscores";
                     }
                   }
                   leaf routing-instance {
                     description "Routing instance of server to which to forward";
                     type union {
                       type string {
                         pattern "default";
                       }
                       type string {
                         junos:posix-pattern "!^((__.*__)|(all)|(.*[ ].*)|(\"\")|(.{129,}))$";
                         junos:pattern-message "Must be a non-reserved string of 128 characters or less with no spaces.";
                       }
                     }
                   }
                 }
               }
               case case_2 {
                 leaf routing-instance {
                   description "Routing instance of server to which to forward";
                   junos:must "(\"routing-instances $$\")";
                   junos:must-message "referenced routing instance must be defined";
                   type union {
                     type string {
                       pattern "default";
                     }
                     type string {
                       junos:posix-pattern "!^((__.*__)|(all)|(.*[ ].*)|(\"\")|(.{129,}))$";
                       junos:pattern-message "Must be a non-reserved string of 128 characters or less with no spaces.";
                     }
                   }
                 }
               }
             }
           }
         }
       }
       container tftp {
         description "Incoming TFTP request forwarding configuration";
         uses apply-advanced;
         leaf description {
           description "Text description of server";
           type string;
         }
         container server {
           description "Server information";
           leaf address {
             description "Name or address of server to which to forward";
             type jt:ipv4addr;
           }
           choice instance {
             case case_1 {
               container logical-system {
                 description "Logical system of server to which to forward";
                 leaf logical-system-name {
                   description "Name of logical system";
                   junos:must "(\"logical-systems $$\")";
                   junos:must-message "referenced logical system must be defined";
                   type string {
                     junos:posix-pattern "^[a-zA-Z0-9_-]{1,63}$";
                     junos:pattern-message "Logical-system name is a string consisting of up to 63 letters, numbers, dashes and underscores";
                   }
                 }
                 leaf routing-instance {
                   description "Routing instance of server to which to forward";
                   type union {
                     type string {
                       pattern "default";
                     }
                     type string {
                       junos:posix-pattern "!^((__.*__)|(all)|(.*[ ].*)|(\"\")|(.{129,}))$";
                       junos:pattern-message "Must be a non-reserved string of 128 characters or less with no spaces.";
                     }
                   }
                 }
               }
             }
             case case_2 {
               leaf routing-instance {
                 description "Routing instance of server to which to forward";
                 junos:must "(\"routing-instances $$\")";
                 junos:must-message "referenced routing instance must be defined";
                 type union {
                   type string {
                     pattern "default";
                   }
                   type string {
                     junos:posix-pattern "!^((__.*__)|(all)|(.*[ ].*)|(\"\")|(.{129,}))$";
                     junos:pattern-message "Must be a non-reserved string of 128 characters or less with no spaces.";
                   }
                 }
               }
             }
           }
         }
         list interface {
           key name;
           ordered-by user;
           description "Incoming TFTP request forwarding interface configuration";
           leaf name {
             description "Name of interface or group of interfaces";
             type union {
               type jt:interface-wildcard;
               type string {
                 pattern "<.*>|$.*";
               }
             }
           }
           uses apply-advanced;
           leaf no-listen {
             description "Do not listen on this interface";
             type empty;
           }
           leaf broadcast {
             description "If the layer 2 interface is unknown then broadcast";
             type empty;
           }
           leaf description {
             description "Text description of server";
             type string;
           }
           container server {
             description "Server information";
             leaf address {
               description "Name or address of server to which to forward";
               type jt:ipv4addr;
             }
             choice instance {
               case case_1 {
                 container logical-system {
                   description "Logical system of server to which to forward";
                   leaf logical-system-name {
                     description "Name of logical system";
                     junos:must "(\"logical-systems $$\")";
                     junos:must-message "referenced logical system must be defined";
                     type string {
                       junos:posix-pattern "^[a-zA-Z0-9_-]{1,63}$";
                       junos:pattern-message "Logical-system name is a string consisting of up to 63 letters, numbers, dashes and underscores";
                     }
                   }
                   leaf routing-instance {
                     description "Routing instance of server to which to forward";
                     type union {
                       type string {
                         pattern "default";
                       }
                       type string {
                         junos:posix-pattern "!^((__.*__)|(all)|(.*[ ].*)|(\"\")|(.{129,}))$";
                         junos:pattern-message "Must be a non-reserved string of 128 characters or less with no spaces.";
                       }
                     }
                   }
                 }
               }
               case case_2 {
                 leaf routing-instance {
                   description "Routing instance of server to which to forward";
                   junos:must "(\"routing-instances $$\")";
                   junos:must-message "referenced routing instance must be defined";
                   type union {
                     type string {
                       pattern "default";
                     }
                     type string {
                       junos:posix-pattern "!^((__.*__)|(all)|(.*[ ].*)|(\"\")|(.{129,}))$";
                       junos:pattern-message "Must be a non-reserved string of 128 characters or less with no spaces.";
                     }
                   }
                 }
               }
             }
           }
         }
       }
       container bootp {
         junos:must "(!(\"system autoinstallation\"))";
         junos:must-message "incompatible with 'system autoinstallation'";
         description "Incoming BOOTP/DHCP request forwarding configuration";
         uses apply-advanced;
         leaf relay-agent-option {
           description "Use DHCP Relay Agent option in relayed BOOTP/DHCP messages";
           type empty;
         }
         leaf description {
           description "Text description of servers";
           type string;
         }
         list server {
           key name;
           ordered-by user;
           description "Server information";
           leaf name {
             description "Name or address of servers to which to forward";
             type jt:ipv4addr;
           }
           uses apply-advanced;
           list logical-system {
             key name;
             ordered-by user;
             description "Logical system of server to which to forward";
             leaf name {
               description "Name of logical system";
               junos:must "(\"logical-systems $$\")";
               junos:must-message "referenced logical system must be defined";
               type string {
                 junos:posix-pattern "^[a-zA-Z0-9_-]{1,63}$";
                 junos:pattern-message "Logical-system name is a string consisting of up to 63 letters, numbers, dashes and underscores";
               }
             }
             leaf-list routing-instance {
               ordered-by user;
               description "Routing instance of server to which to forward";
               type string;
             }
           }
           leaf-list routing-instance {
             ordered-by user;
             description "Routing instance of server to which to forward";
             type string;
           }
         }
         leaf maximum-hop-count {
           description "Maximum number of hops per packet";
           default "4";
           type union {
             type string {
               pattern "<.*>|$.*";
             }
             type uint32 {
               range "1 .. 16";
             }
           }
         }
         leaf minimum-wait-time {
           description "Minimum number of seconds before requests are forwarded";
           default "0";
           type union {
             type string {
               pattern "<.*>|$.*";
             }
             type uint32 {
               range "0 .. 30000";
             }
           }
         }
         leaf client-response-ttl {
           description "IP time-to-live value to set in responses to client";
           type union {
             type string {
               pattern "<.*>|$.*";
             }
             type uint32 {
               range "1 .. 255";
             }
           }
         }
         leaf vpn {
           description "Enable vpn encryption ";
           type empty;
         }
         leaf apply-secondary-as-giaddr {
           description "Enable DHCP relay to use secondary gateway ip on all interfaces";
           type empty;
         }
         list interface {
           key name;
           ordered-by user;
           description "Incoming BOOTP/DHCP request forwarding interface configuration";
           leaf name {
             description "Name of interface or group of interfaces";
             type union {
               type jt:interface-wildcard;
               type string {
                 pattern "<.*>|$.*";
               }
             }
           }
           uses apply-advanced;
           leaf no-listen {
             description "Do not listen on this interface";
             type empty;
           }
           leaf broadcast {
             description "If the layer 2 interface is unknown then broadcast";
             type empty;
           }
           leaf description {
             description "Text description of servers";
             type string;
           }
           list server {
             key name;
             ordered-by user;
             description "Server information";
             leaf name {
               description "Name or address of servers to which to forward";
               type jt:ipv4addr;
             }
             uses apply-advanced;
             list logical-system {
               key name;
               ordered-by user;
               description "Logical system of server to which to forward";
               leaf name {
                 description "Name of logical system";
                 junos:must "(\"logical-systems $$\")";
                 junos:must-message "referenced logical system must be defined";
                 type string {
                   junos:posix-pattern "^[a-zA-Z0-9_-]{1,63}$";
                   junos:pattern-message "Logical-system name is a string consisting of up to 63 letters, numbers, dashes and underscores";
                 }
               }
               leaf-list routing-instance {
                 ordered-by user;
                 description "Routing instance of server to which to forward";
                 type string;
               }
             }
             leaf-list routing-instance {
               ordered-by user;
               description "Routing instance of server to which to forward";
               type string;
             }
           }
           leaf maximum-hop-count {
             description "Maximum number of hops per packet";
             default "4";
             type union {
               type string {
                 pattern "<.*>|$.*";
               }
               type uint32 {
                 range "1 .. 16";
               }
             }
           }
           leaf minimum-wait-time {
             description "Minimum number of seconds before requests are forwarded";
             default "0";
             type union {
               type string {
                 pattern "<.*>|$.*";
               }
               type uint32 {
                 range "0 .. 30000";
               }
             }
           }
           leaf client-response-ttl {
             description "IP time-to-live value to set in responses to client";
             type union {
               type string {
                 pattern "<.*>|$.*";
               }
               type uint32 {
                 range "1 .. 255";
               }
             }
           }
           leaf vpn {
             description "Enable vpn encryption ";
             type empty;
           }
           leaf apply-secondary-as-giaddr {
             description "Enable DHCP relay to use secondary gateway ip on this interface";
             type empty;
           }
         }
       }
       list port {
         key name;
         ordered-by user;
         description "Incoming arbitrary protocol request forwarding configuration";
         leaf name {
           description "Port number of the protocol to listen";
           type union {
             type string {
               pattern "<.*>|$.*";
             }
             type uint32 {
               range "1 .. 65535";
             }
           }
         }
         uses apply-advanced;
         leaf description {
           description "Text description of server";
           type string;
         }
         list server {
           key name;
           ordered-by user;
           description "Server information";
           leaf name {
             description "Name or address of server to which to forward";
             type jt:ipv4addr;
           }
           uses apply-advanced;
           choice instance {
             case case_1 {
               container logical-system {
                 description "Logical system of server to which to forward";
                 leaf logical-system-name {
                   description "Name of logical system";
                   junos:must "(\"logical-systems $$\")";
                   junos:must-message "referenced logical system must be defined";
                   type string {
                     junos:posix-pattern "^[a-zA-Z0-9_-]{1,63}$";
                     junos:pattern-message "Logical-system name is a string consisting of up to 63 letters, numbers, dashes and underscores";
                   }
                 }
                 leaf routing-instance {
                   description "Routing instance of server to which to forward";
                   type union {
                     type string {
                       pattern "default";
                     }
                     type string {
                       junos:posix-pattern "!^((__.*__)|(all)|(.*[ ].*)|(\"\")|(.{129,}))$";
                       junos:pattern-message "Must be a non-reserved string of 128 characters or less with no spaces.";
                     }
                   }
                 }
               }
             }
             case case_2 {
               leaf routing-instance {
                 description "Routing instance of server to which to forward";
                 junos:must "(\"routing-instances $$\")";
                 junos:must-message "referenced routing instance must be defined";
                 type union {
                   type string {
                     pattern "default";
                   }
                   type string {
                     junos:posix-pattern "!^((__.*__)|(all)|(.*[ ].*)|(\"\")|(.{129,}))$";
                     junos:pattern-message "Must be a non-reserved string of 128 characters or less with no spaces.";
                   }
                 }
               }
             }
           }
         }
         list interface {
           key name;
           ordered-by user;
           description "Incoming request forwarding interface configuration";
           leaf name {
             description "Name of interface or group of interfaces";
             type union {
               type jt:interface-wildcard;
               type string {
                 pattern "<.*>|$.*";
               }
             }
           }
           uses apply-advanced;
           leaf no-listen {
             description "Do not listen on this interface";
             type empty;
           }
           leaf broadcast {
             description "If the layer 2 interface is unknown then broadcast";
             type empty;
           }
           leaf description {
             description "Text description of server";
             type string;
           }
           list server {
             key name;
             ordered-by user;
             description "Server information";
             leaf name {
               description "Name or address of server to which to forward";
               type jt:ipv4addr;
             }
             uses apply-advanced;
             choice instance {
               case case_1 {
                 container logical-system {
                   description "Logical system of server to which to forward";
                   leaf logical-system-name {
                     description "Name of logical system";
                     junos:must "(\"logical-systems $$\")";
                     junos:must-message "referenced logical system must be defined";
                     type string {
                       junos:posix-pattern "^[a-zA-Z0-9_-]{1,63}$";
                       junos:pattern-message "Logical-system name is a string consisting of up to 63 letters, numbers, dashes and underscores";
                     }
                   }
                   leaf routing-instance {
                     description "Routing instance of server to which to forward";
                     type union {
                       type string {
                         pattern "default";
                       }
                       type string {
                         junos:posix-pattern "!^((__.*__)|(all)|(.*[ ].*)|(\"\")|(.{129,}))$";
                         junos:pattern-message "Must be a non-reserved string of 128 characters or less with no spaces.";
                       }
                     }
                   }
                 }
               }
               case case_2 {
                 leaf routing-instance {
                   description "Routing instance of server to which to forward";
                   junos:must "(\"routing-instances $$\")";
                   junos:must-message "referenced routing instance must be defined";
                   type union {
                     type string {
                       pattern "default";
                     }
                     type string {
                       junos:posix-pattern "!^((__.*__)|(all)|(.*[ ].*)|(\"\")|(.{129,}))$";
                       junos:pattern-message "Must be a non-reserved string of 128 characters or less with no spaces.";
                     }
                   }
                 }
               }
             }
           }
         }
       }
     }
     container family {
       description "Protocol family";
       container inet {
         description "IPv4 parameters";
         uses apply-advanced;
         container filter {
           description "Filtering for forwarding table";
           uses apply-advanced;
           leaf input {
             description "Name of input filter to apply for forwarded packets";
             type string;
           }
           leaf output {
             description "Name of output filter to apply for forwarded packets";
             type string;
           }
         }
       }
       container inet6 {
         description "IPv6 parameters";
         uses apply-advanced;
         container filter {
           description "Filtering for forwarding table";
           uses apply-advanced;
           leaf input {
             description "Name of input filter to apply for forwarded packets";
             type string;
           }
           leaf output {
             description "Name of output filter to apply for forwarded packets";
             type string;
           }
         }
         leaf route-accounting {
           description "Enable IPv6 route accounting";
           type empty;
         }
         leaf source-checking {
           description "Discard IPv6 packet when source address type is unspecified, loopback, multicast or link-local ";
           type empty;
         }
       }
       container mpls {
         description "MPLS parameters";
         uses apply-advanced;
         container filter {
           description "Filtering for forwarding table";
           uses apply-advanced;
           leaf input {
             description "Name of input filter to apply for forwarded packets";
             type string;
           }
           leaf output {
             description "Name of output filter to apply for forwarded packets";
             type string;
           }
         }
       }
       container vpls {
         description "VPLS parameters";
         uses apply-advanced;
         container filter {
           description "Filtering for VPLS DMAC forwarding table";
           uses apply-advanced;
           leaf input {
             description "Name of input filter to apply for forwarded packets";
             type string;
           }
         }
         container flood {
           description "Filtering for VPLS flood table";
           uses apply-advanced;
           leaf input {
             description "Name of input filter to apply for VPLS flood packets";
             type string;
           }
         }
       }
       container evpn {
         description "EVPN parameters";
         uses apply-advanced;
         container filter {
           description "Filtering for EVPN DMAC forwarding table";
           uses apply-advanced;
           leaf input {
             description "Name of input filter to apply for forwarded packets";
             type string;
           }
         }
         container flood {
           description "Filtering for EVPN flood table";
           uses apply-advanced;
           leaf input {
             description "Name of input filter to apply for EVPN flood packets";
             type string;
           }
         }
       }
     }
     list next-hop-group {
       key name;
       description "Next hop group forwarding option";
       uses juniper-next-hop-group-options;
     }
     container dhcp-relay {
       description "Dynamic Host Configuration Protocol relay configuration";
       junos:must "(!(\"system services dhcp\"))";
       junos:must-message "Incompatible with 'set system services dhcp'";
       junos:must "(!(\".. .. instance-type virtual-switch\"))";
       junos:must-message "forwarding-options dhcp-relay incompatible with routing-instances instance-type virtual-switch'";
       uses jdhcp-relay-type;
     }
     choice load-balance-label-capability-choice {
       leaf load-balance-label-capability {
         description "Load balance label capability";
         type empty;
       }
       leaf no-load-balance-label-capability {
         description "Don't load balance label capability";
         type empty;
       }
     }
     leaf fast-reroute-priority {
       description "Fast-reroute repair priority";
       junos:must "(\".. .. instance-type vpls\")";
       junos:must-message "'fast-reroute-priority' configuration can only be used for 'instance-type vpls'";
       type enumeration {
         enum "low" {
           description "Set priority to low";
         }
         enum "medium" {
           description "Set priority to medium";
         }
         enum "high" {
           description "Set priority to high";
         }
       }
     }
     list ip-options-protocol-queue {
       key name;
       ordered-by user;
       description "IP Options protocol logical queue parameters";
       leaf name {
         description "Protocol name";
         type string;
       }
       uses apply-advanced;
       leaf protocol-id {
         description "Protocol Identifier";
         type union {
           type string {
             pattern "<.*>|$.*";
           }
           type uint8 {
             range "1 .. 254";
           }
         }
       }
       leaf queue-depth {
         description "Size of the protocol logical options queue";
         type union {
           type string {
             pattern "<.*>|$.*";
           }
           type uint32 {
             range "1 .. 807";
           }
         }
       }
     }
     leaf link-layer-broadcast-inet-check {
       description "Enable destination mac and destination ip address check";
       type empty;
     }
     choice hyper-mode-choice {
       leaf hyper-mode {
         description "Enable hyper mode";
         type empty;
       }
       leaf no-hyper-mode {
         description "Don't enable hyper mode";
         type empty;
       }
     }
     container access-security {
       description "Access security configuration";
       uses jdhcp-access-security-type;
     }
     list forwarding-sandbox {
       key name;
       description "Create forwarding sandbox";
       max-elements 8;
       uses juniper-forwarding-sandbox-options;
     }
     container satellite {
       description "Satellite forwarding options";
       uses apply-advanced;
       container traceoptions {
         description "Global tracing options for satellite control plane";
         uses apply-advanced;
         leaf no-remote-trace {
           description "Disable remote tracing";
           junos:must "(\"system tracing\")";
           junos:must-message "'no-remote-trace' is valid only when [system tracing] is configured";
           type empty;
         }
         container file {
           description "Trace file information";
           leaf filename {
             description "Name of file in which to write trace information";
             type string {
               length "1 .. 1024";
               junos:posix-pattern "![/ %]";
               junos:pattern-message "Must not contain '/', % or a space";
             }
           }
           leaf size {
             description "Maximum trace file size";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           ordered-by user;
           description "Tracing parameters";
           leaf name {
             type enumeration {
               enum "all" {
                 description "Trace everything";
               }
               enum "bd" {
                 description "Trace BD events";
               }
               enum "config-internal" {
                 description "Trace configuration internals";
               }
               enum "interface" {
                 description "Trace interface events";
               }
               enum "interface-vlan" {
                 description "Trace IFBD events";
               }
               enum "ipc" {
                 description "Trace internal IPC messages";
               }
               enum "kernel" {
                 description "Trace Kernel messages";
               }
               enum "krt" {
                 description "Trace communication over routing socket";
               }
               enum "mac" {
                 description "Trace MAC events ";
               }
               enum "nh" {
                 description "Trace NH events";
               }
               enum "normal" {
                 description "Trace normal events";
               }
               enum "parse" {
                 description "Trace configuration parsing";
               }
               enum "stp" {
                 description "Trace STP events";
               }
               enum "task" {
                 description "Trace task processing";
               }
               enum "timer" {
                 description "Trace task timer processing";
               }
               enum "firewall" {
                 description "Trace firewall processing";
               }
               enum "l3" {
                 description "Trace Layer-3 processing";
               }
               enum "fip-snooping" {
                 description "Trace FIP-Snooping processing";
               }
             }
           }
         }
       }
       leaf local-replication {
         description "Enable satellite multicast replication";
         type empty;
       }
       list fpc {
         key name;
         leaf name {
           description "Satellite slot identifier";
           type union {
             type string {
               pattern "<.*>|$.*";
             }
             type uint32 {
               range "65 .. 254";
             }
           }
         }
         uses apply-advanced;
         choice local-switching-mode-choice {
           case case_1 {
             container local-switching {
               presence "enable local-switching";
               description "Enable local-switching on Satellite device";
               uses apply-advanced;
               leaf l3 {
                 description "Enable L3 local switching on the Satellite device";
                 type empty;
               }
             }
           }
           case case_2 {
             container selective-vlan-switching {
               description "Enable selective-vlan-switching on Satellite device";
               uses apply-advanced;
               leaf routing-instance {
                 description "Associated Routing instance name";
                 type string {
                   junos:posix-pattern "!^((__.*__)|(all)|(.*[ ].*)|(\"\")|(.{129,}))$";
                   junos:pattern-message "Must be a non-reserved string of 128 characters or less with no spaces.";
                 }
               }
             }
           }
         }
       }
       container vlan-auto-sense {
         description "Vlan-auto-sense attributes provisioning";
         uses apply-advanced;
         leaf expiry-time {
           description "Expiry time (in seconds) after last MAC aged out";
           default "600";
           units "seconds";
           type union {
             type string {
               pattern "<.*>|$.*";
             }
             type uint32 {
               range "30 .. 3600";
             }
           }
         }
       }
       container analyzer-vlan {
         description "Output VLAN for Analyzer";
         uses apply-advanced;
         leaf vlan-name {
           description "Name of the analyzer VLAN";
           type string;
         }
       }
       choice disable-heartbeat-choice {
         leaf disable-heartbeat {
           description "Disable heartbeat between Aggregation and Satellite";
           type empty;
         }
         leaf no-disable-heartbeat {
           description "Don't disable heartbeat between Aggregation and Satellite";
           type empty;
         }
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping jdhcp-access-security-type {
     description "Access security configuration";
     uses apply-advanced;
     container slaac-snooping {
       description "Stateless address auto configuration options";
       uses slaacd-config-type;
     }
     container router-advertisement-guard {
       presence "enable router-advertisement-guard";
       description "Router Advertisement Guard Configuration";
       uses apply-advanced;
       list policy {
         key name;
         ordered-by user;
         description "Router Advertisement Guard policy";
         leaf name {
           description "Router Advertisement Guard policy name";
           type string {
             length "1 .. 64";
           }
         }
         uses apply-advanced;
         container discard {
           description "Discard parameters";
           uses apply-advanced;
           leaf source-ip-address-list {
             description "IPv6 Source address list name";
             type string;
           }
           leaf source-mac-address-list {
             description "Source mac address list name";
             type string;
           }
           leaf prefix-list-name {
             description "Prefix-list Name";
             type string;
           }
         }
         container accept {
           description "Accept parameters";
           uses apply-advanced;
           container match-list {
             description "List of parameters to check";
             uses apply-advanced;
             leaf source-ip-address-list {
               description "IPv6 Source address list name";
               type string;
             }
             leaf source-mac-address-list {
               description "Source mac address list name";
               type string;
             }
             leaf prefix-list-name {
               description "Prefix-list Name";
               type string;
             }
             leaf match-criteria {
               description "Match Criteria";
               type enumeration {
                 enum "match-all" {
                   description "A match from every list";
                 }
                 enum "match-any" {
                   description "A match from any list";
                 }
               }
             }
           }
           container match-options {
             presence "enable match-options";
             description "List of Options to check";
             uses apply-advanced;
             container hop-limit {
               description "Hop limit";
               uses apply-advanced;
               leaf maximum {
                 description "Maximum hop limit";
                 type union {
                   type string {
                     pattern "<.*>|$.*";
                   }
                   type uint32 {
                     range "1 .. 255";
                   }
                 }
               }
               leaf minimum {
                 description "Minimum hop limit";
                 type union {
                   type string {
                     pattern "<.*>|$.*";
                   }
                   type uint32 {
                     range "1 .. 255";
                   }
                 }
               }
             }
             container route-preference {
               description "Accept route preference";
               uses apply-advanced;
               leaf maximum {
                 description "Maximum route preference";
                 type enumeration {
                   enum "low" {
                     description "Route preference low";
                   }
                   enum "medium" {
                     description "Route preference medium";
                   }
                   enum "high" {
                     description "Route preference high";
                   }
                 }
               }
             }
             leaf managed-config-flag {
               description "Check Managed config flag";
               type empty;
             }
             leaf other-config-flag {
               description "Check Other config flag";
               type empty;
             }
           }
         }
       }
       container interface {
         description "RA Guard config on Interface";
         uses apply-advanced;
         list intf-config {
           key name;
           description "Interface Configuration";
           uses interface-policy;
         }
       }
       container vlans {
         description "RA Guard config on Vlan";
         uses apply-advanced;
         list vlan-config {
           key name;
           description "Virtual LAN Configuration";
           uses vlan-policy;
         }
       }
     }
   }
   grouping interface-policy {
     description "Interface Name";
     leaf name {
       description "Interface Name";
       type union {
         type jt:interface-name;
         type string {
           pattern "<.*>|$.*";
         }
       }
     }
     uses apply-advanced;
     container policy {
       description "Attach policy";
       uses apply-advanced;
       leaf policy-name {
         description "Router Advertisement Guard policy name";
         type string;
       }
       choice policy-type {
         case case_1 {
           leaf stateful {
             description "Stateful router advertisement guard";
             type empty;
           }
         }
         case case_2 {
           leaf stateless {
             description "Stateless router advertisement guard";
             type empty;
           }
         }
       }
     }
     container mark-interface {
       description "Mark interface";
       uses apply-advanced;
       choice mark-intf-type {
         case case_1 {
           leaf trusted {
             description "Mark interface trusted";
             junos:must "(!(\".. .. policy\"))";
             junos:must-message "Trusted interfaces cannot have policy attached";
             type empty;
           }
         }
         case case_2 {
           leaf block {
             description "Block router-advertisement";
             junos:must "(!(\".. .. policy\"))";
             junos:must-message "Blocked interfaces cannot have policy attached";
             type empty;
           }
         }
       }
     }
   }
   grouping jdhcp-relay-type {
     description "Dynamic Host Configuration Protocol relay configuration";
     uses apply-advanced;
     container traceoptions {
       description "DHCP relay trace options";
       status deprecated;
       junos:must "(!(\"forwarding-options helpers bootp\"))";
       junos:must-message "Incompatible with 'forwarding-options helpers bootp'";
       junos:must "(!(\"system services dhcp\"))";
       junos:must-message "Incompatible with 'set system services dhcp'";
       uses jdhcp-traceoptions-type;
     }
     container persistent-storage {
       description "Trigger to enable flat file storage";
       leaf automatic {
         description "Trigger automatically";
         type empty;
       }
     }
     leaf duplicate-clients-on-interface {
       description "Allow duplicate clients on different interfaces in a subnet";
       status deprecated;
       type empty;
     }
     container duplicate-clients-in-subnet {
       description "Allow duplicate clients in a subnet";
       junos:must "(!(\".. duplicate-clients-on-interface\"))";
       junos:must-message "Cannot specify duplicate-clients-in-subnet with duplicate-clients-on-interface";
       uses jdhcp-duplicate-clients-in-subnet-type;
     }
     container interface-traceoptions {
       description "DHCP relay interface trace options";
       status deprecated;
       uses jdhcp-interface-traceoptions-type;
     }
     container dhcpv6 {
       description "DHCPv6 configuration";
       uses dhcpv6-relay-type;
     }
     leaf arp-inspection {
       description "Enable Dynamic ARP Inspection";
       type empty;
     }
     container forward-snooped-clients {
       junos:must "((!(\".. forward-only\") && (!(\".. forward-only-replies\") && !(any \".. group <*> forward-only\"))))";
       junos:must-message "forward-only and forward-only-replies cannot be configured when forward-snooped-clients is configured";
       description "Forward snooped (unicast) packets";
       choice interface-type {
         case case_1 {
           leaf configured-interfaces {
             description "Forward snooped (unicast) packets on configured interfaces";
             type empty;
           }
         }
         case case_2 {
           leaf non-configured-interfaces {
             description "Forward snooped (unicast) packets on non-configured interfaces";
             type empty;
           }
         }
         case case_3 {
           leaf all-interfaces {
             description "Forward snooped (unicast) packets on configured and non-configured interfaces";
             type empty;
           }
         }
       }
     }
     container authentication {
       description "DHCP authentication";
       junos:must "(!(\"forwarding-options helpers bootp\"))";
       junos:must-message "'authentication' statement cannot be included along with 'forwarding-options helpers bootp' statement";
       uses authentication-type;
     }
     container liveness-detection {
       description "DHCP client liveness detection processing";
       junos:must "(!(\"forwarding-options helpers bootp\"))";
       junos:must-message "'liveness-detection' statement cannot be included along with 'forwarding-options helpers bootp' statement";
       uses dhcp-liveness-detection-type;
     }
     container dynamic-profile {
       description "Dynamic profile to use";
       junos:must "(!(\"forwarding-options helpers bootp\"))";
       junos:must-message "'dynamic-profile' statement cannot be included along with 'forwarding-options helpers bootp' statement";
       uses dynamic-profile-type;
     }
     leaf service-profile {
       description "Dynamic profile to use for default service activation";
       type string {
         length "1 .. 128";
       }
     }
     leaf access-profile {
       description "Access profile to use for AAA services";
       junos:must "(\"access profile $$\")";
       junos:must-message "Matching access profile must be defined";
       junos:must "(!(\"forwarding-options helpers bootp\"))";
       junos:must-message "'access-profile' statement cannot be included along with 'forwarding-options helpers bootp' statement";
       type string {
         length "1 .. 128";
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container overrides {
       description "DHCP override processing";
       presence "enable overrides";
       junos:must "(!(\"forwarding-options helpers bootp\"))";
       junos:must-message "'overrides' statement cannot be included along with 'forwarding-options helpers bootp' statement";
       uses override-type;
     }
     container relay-option {
       description "DHCP option processing";
       presence "enable relay-option";
       junos:must "((!(\".. relay-option-60\") && !(any \".. group <*> relay-option-60\")))";
       junos:must-message "Cannot specify relay-option-60 with relay-option";
       uses dhcp-generic-v4-option;
     }
     container server-match {
       description "Server match processing";
       uses apply-advanced;
       container default-action {
         description "Server match default action";
         presence "enable default-action";
         uses server-match-action-choice;
       }
       list address {
         key name;
         ordered-by user;
         description "Server address";
         leaf name {
           description "Server address for matching";
           type jt:ipv4prefix;
         }
         uses apply-advanced;
         choice server-match-action-choice {
           case case_1 {
             leaf forward-only {
               description "Forward without subscriber services when a match is made";
               type empty;
             }
           }
           case case_2 {
             leaf create-relay-entry {
               description "Create relay entry and allow subscriber services";
               type empty;
             }
           }
         }
       }
     }
     container relay-option-60 {
       description "DHCP option-60 processing";
       presence "enable relay-option-60";
       status deprecated;
       junos:must "(!(\"forwarding-options helpers bootp\"))";
       junos:must-message "'relay-option-60' statement cannot be included along with 'forwarding-options helpers bootp' statement";
       junos:must "((!(\".. relay-option\") && !(any \".. group <*> relay-option\")))";
       junos:must-message "Cannot specify relay-option with relay-option-60 ";
       uses relay-option-60-type-top;
     }
     container relay-option-82 {
       description "DHCP option-82 processing";
       presence "enable relay-option-82";
       junos:must "(!(\"forwarding-options helpers bootp\"))";
       junos:must-message "'relay-option-82' statement cannot be included along with 'forwarding-options helpers bootp' statement";
       uses relay-option-82-type;
     }
     container forward-only {
       description "Forward DHCP packets without creating binding";
       presence "enable forward-only";
       junos:must "(!(\"forwarding-options helpers bootp\"))";
       junos:must-message "'forward-only' statement cannot be included along with 'forwarding-options helpers bootp' statement";
       uses forward-only-to-rc-type;
     }
     leaf description {
       description "Text description of servers";
       type string;
     }
     leaf maximum-hop-count {
       description "Maximum number of hops per packet";
       type union {
         type string {
           pattern "<.*>|$.*";
         }
         type uint32 {
           range "1 .. 16";
         }
       }
     }
     leaf minimum-wait-time {
       description "Minimum number of seconds before requests are forwarded";
       type union {
         type string {
           pattern "<.*>|$.*";
         }
         type uint32 {
           range "0 .. 30000";
         }
       }
     }
     leaf client-response-ttl {
       description "IP time-to-live value to set in responses to client";
       type union {
         type string {
           pattern "<.*>|$.*";
         }
         type uint32 {
           range "1 .. 255";
         }
       }
     }
     leaf source-ip-change {
       description "Use address of egress interface as source ip";
       type empty;
     }
     leaf forward-only-replies {
       description "Forward-only replies from server to appropriate logical-system:routing-instance based on options";
       type empty;
     }
     container server-group {
       description "Define a DHCP server group";
       junos:must "(!(\"forwarding-options helpers bootp\"))";
       junos:must-message "'server-group' statement cannot be included along with 'forwarding-options helpers bootp' statement";
       uses server-group-type;
     }
     container active-server-group {
       description "Name of DHCP server group";
       uses dhcpv4-gbl-active-sg-type;
     }
     container route-suppression {
       description "Suppress access-internal and/or destination route addition";
       junos:must "(!(\".. liveness-detection method layer2-liveness-detection\"))";
       junos:must-message "Cannot specify route-suppression with liveness-detection method layer2-liveness-detection";
       junos:must "(!(\".. overrides no-arp\"))";
       junos:must-message "Cannot specify route-suppression with overrides no-arp";
       uses dhcp-route-suppression-type;
     }
     list group {
       key name;
       ordered-by user;
       description "Define a DHCP group";
       junos:must "(!(\"forwarding-options helpers bootp\"))";
       junos:must-message "'group' statement cannot be included along with 'forwarding-options helpers bootp' statement";
       uses dhcp-group;
     }
     list dual-stack-group {
       key name;
       description "Define a DHCP dual stack group";
       uses dhcp-dual-stack-group;
     }
     leaf no-snoop {
       description "Do not snoop DHCP packets";
       junos:must "(!(\"legacy-snooping\"))";
       junos:must-message "'no-snoop' statement cannot be included along with 'legacy-snooping' statement";
       type empty;
     }
     leaf server-response-time {
       description "Number of seconds in a period of activity between the last server response and an unaswered request";
       default "0";
       type union {
         type uint32;
         type string {
           pattern "<.*>|$.*";
         }
       }
     }
     container lease-time-validation {
       presence "enable lease-time-validation";
       description "Configure lease time violation validation";
       uses apply-advanced;
       leaf lease-time-threshold {
         description "Threshold for lease time violation in seconds";
         units "seconds";
         type union {
           type string {
             pattern "<.*>|$.*";
           }
           type uint32 {
             range "60 .. 2147483647";
           }
         }
       }
       container violation-action {
         description "Lease time validation violation action";
         leaf drop {
           description "Drop dhcpv4 offer and ack packets";
           type empty;
         }
       }
     }
     container leasequery {
       description "DHCP leasequery configuration";
       presence "enable leasequery";
       junos:must "(\".. overrides always-write-option-82\")";
       junos:must-message "Must configure [overrides always-write-option-82] to overwrite circuit-id";
       junos:must "((\".. relay-option-82 circuit-id\" && (!(\".. relay-option-82 circuit-id use-interface-description\") && !(\".. relay-option-82 circuit-id require-interface-description\"))))";
       junos:must-message "Must configure [relay-option-82 circuit-id] without description to insert circuit-id";
       uses relay-leasequery-type;
     }
     container bulk-leasequery {
       description "DHCP bulk leasequery configuration";
       presence "enable bulk-leasequery";
       junos:must "(\".. overrides always-write-option-82\")";
       junos:must-message "Must configure [overrides always-write-option-82] to overwrite circuit-id";
       junos:must "((\".. relay-option-82 circuit-id\" && (!(\".. relay-option-82 circuit-id use-interface-description\") && !(\".. relay-option-82 circuit-id require-interface-description\"))))";
       junos:must-message "Must configure [relay-option-82 circuit-id] without description to insert circuit-id";
       uses relay-bulk-leasequery-v4-type;
     }
     container remote-id-mismatch {
       description "DHCP client remote-id mismatch";
       presence "enable remote-id-mismatch";
       uses dhcp-remote-id-mismatch-type;
     }
   }
   grouping authentication-type {
     description "DHCP authentication";
     uses apply-advanced;
     leaf password {
       description "Username password to use";
       type string {
         length "1 .. 64";
       }
     }
     container username-include {
       description "Add username options";
       uses apply-advanced;
       leaf delimiter {
         description "Change delimiter/separator character";
         type string {
           length 1;
         }
       }
       leaf domain-name {
         description "Add domain name";
         type string {
           length "1 .. 64";
         }
       }
       leaf user-prefix {
         description "Add user defined prefix";
         type string {
           length "1 .. 64";
         }
       }
       leaf mac-address {
         description "Include MAC address";
         type empty;
       }
       container option-82 {
         presence "enable option-82";
         description "Include option 82";
         leaf circuit-id {
           description "Include option 82 circuit-id (sub option 1)";
           type empty;
         }
         leaf remote-id {
           description "Include option 82 remote-id (sub option 2)";
           type empty;
         }
       }
       leaf logical-system-name {
         description "Include logical system name";
         type empty;
       }
       leaf routing-instance-name {
         description "Include routing instance name";
         type empty;
       }
       leaf option-60 {
         description "Include option 60";
         type empty;
       }
       leaf circuit-type {
         description "Include circuit type";
         type empty;
       }
       leaf interface-name {
         description "Include interface name";
         type empty;
       }
       leaf interface-description {
         description "Include interface description";
         type enumeration {
           enum "device" {
             description "Add the device interface description";
           }
           enum "logical" {
             description "Add the logical interface description";
           }
         }
       }
       leaf vlan-tags {
         description "Include the vlan tag(s)";
         type empty;
       }
     }
   }
   grouping dhcp-dual-stack-group {
     description "DHCP dual stack groups";
     leaf name {
       description "Dual stack group name";
       type string {
         length "1 .. 64";
         junos:posix-pattern "^[A-Za-z0-9][_0-9A-Za-z-]*$";
         junos:pattern-message "Must be a non-reserved string of 64 characters or less";
       }
     }
     uses apply-advanced;
     container authentication {
       description "DHCP authentication";
       uses dual-stack-authentication-type;
     }
     leaf service-profile {
       description "Dynamic profile to use for default service activation";
       type string {
         length "1 .. 128";
       }
     }
     leaf access-profile {
       description "Access profile to be used for jdhcpd";
       type string {
         length "1 .. 128";
       }
     }
     container dynamic-profile {
       description "Dynamic profile to use";
       uses dynamic-profile-type;
     }
     container liveness-detection {
       description "DHCP client liveness detection processing";
       uses dhcp-liveness-detection-dualstack-type;
     }
     container relay-agent-interface-id {
       description "Interface-id option processing";
       presence "enable relay-agent-interface-id";
       uses v6-relay-option-interface-id-type;
     }
     container relay-agent-remote-id {
       description "Remote-id option processing";
       presence "enable relay-agent-remote-id";
       uses v6-relay-option-remote-id-type;
     }
     container classification-key {
       description "Classification key for identifying dual stack household";
       junos:must "(\".. dynamic-profile\")";
       junos:must-message "dynamic profile configuration in dual-stack-group is must for configuring classification-type";
       uses classification-types;
     }
     leaf dual-stack-interface-client-limit {
       description "Limit the number of client allowed on an interface";
       type union {
         type string {
           pattern "<.*>|$.*";
         }
         type uint32 {
           range "1 .. 500000";
         }
       }
     }
     container protocol-master {
       description "Select family as protocol master";
       uses jdhcp-dual-stack-protocol-mstr-type;
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
   }
   grouping classification-types {
     description "Different mechanisms to identify a single household";
     uses apply-advanced;
     leaf mac-address {
       description "MAC address of client";
       type empty;
     }
     leaf circuit-id {
       description "Circuit-id as key";
       type empty;
     }
     leaf remote-id {
       description "Remote-id as key";
       type empty;
     }
   }
   grouping dhcp-generic-v4-option {
     description "Generic DHCP options processing";
     uses apply-advanced;
     leaf option-number {
       description "Option number";
       status deprecated;
       type enumeration {
         enum "60" {
           description "Option 60";
           status deprecated;
         }
         enum "77" {
           description "Option 77";
           status deprecated;
         }
       }
     }
     container equals {
       description "Generic option equals";
       status deprecated;
       uses relay-v4-option-ascii-hex;
     }
     container default-action {
       description "Generic option default action";
       status deprecated;
       uses dhcp-v4-option-default-action;
     }
     container starts-with {
       description "Generic option starts with";
       status deprecated;
       uses relay-v4-option-ascii-hex;
     }
     container option-60 {
       description "Add option 60 processing";
       presence "enable option-60";
       junos:must "(!(\"option-number\"))";
       junos:must-message "Cannot specify option-60  with option-number";
       uses dhcp-generic-v4-option-type;
     }
     container option-77 {
       description "Add option 77 processing";
       presence "enable option-77";
       junos:must "(!(\"option-number\"))";
       junos:must-message "Cannot specify option-77  with option-number";
       uses dhcp-generic-v4-option-type;
     }
     list option-order {
       key name;
       ordered-by user;
       description "Options precedence order";
       junos:must "(!(\"option-number\"))";
       junos:must-message "Cannot specify option-order  with option-number";
       leaf name {
         description "Option number";
         type enumeration {
           enum "60" {
             description "Option 60";
           }
           enum "77" {
             description "Option 77";
           }
         }
       }
       uses apply-advanced;
     }
   }
   grouping dhcp-generic-v4-option-type {
     uses apply-advanced;
     container equals {
       description "Generic option equals";
       uses relay-v4-option-ascii-hex;
     }
     container default-action {
       description "Generic option default action";
       uses dhcp-v4-option-default-action;
     }
     container starts-with {
       description "Generic option starts with";
       uses relay-v4-option-ascii-hex;
     }
   }
   grouping dhcp-group {
     description "DHCP groups";
     leaf name {
       description "Group name";
       type string {
         length "1 .. 64";
         junos:posix-pattern "^[A-Za-z0-9][_0-9A-Za-z-]*$";
         junos:pattern-message "Must be a non-reserved string of 64 characters or less";
       }
     }
     uses apply-advanced;
     container active-server-group {
       description "Name of DHCP server group";
       uses dhcpv4-gp-active-sg-type;
     }
     container authentication {
       description "DHCP authentication";
       uses authentication-type;
     }
     container liveness-detection {
       description "DHCP client liveness detection processing";
       uses dhcp-liveness-detection-type;
     }
     container dynamic-profile {
       description "Dynamic profile to use";
       uses dynamic-profile-type;
     }
     leaf service-profile {
       description "Dynamic profile to use for default service activation";
       type string {
         length "1 .. 128";
       }
     }
     leaf access-profile {
       description "Access profile to use for AAA services";
       junos:must "(\"access profile $$\")";
       junos:must-message "Matching access profile must be defined";
       type string {
         length "1 .. 128";
       }
     }
     container overrides {
       description "DHCP override processing";
       presence "enable overrides";
       uses override-type;
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container server-match {
       description "Server match processing";
       uses apply-advanced;
       container default-action {
         description "Server match default action";
         presence "enable default-action";
         uses server-match-action-choice;
       }
       list address {
         key name;
         ordered-by user;
         description "Server address";
         leaf name {
           description "Server address for matching";
           type jt:ipv4prefix;
         }
         uses apply-advanced;
         choice server-match-action-choice {
           case case_1 {
             leaf forward-only {
               description "Forward without subscriber services when a match is made";
               type empty;
             }
           }
           case case_2 {
             leaf create-relay-entry {
               description "Create relay entry and allow subscriber services";
               type empty;
             }
           }
         }
       }
     }
     container relay-option {
       description "DHCP option processing";
       presence "enable relay-option";
       junos:must "((!(\".. relay-option-60\") && !(\".. .. relay-option-60\")))";
       junos:must-message "Cannot specify relay-option-60 with relay-option";
       uses dhcp-generic-v4-option;
     }
     container relay-option-60 {
       description "DHCP option-60 processing";
       presence "enable relay-option-60";
       status deprecated;
       junos:must "((!(\".. relay-option\") && !(\".. .. relay-option\")))";
       junos:must-message "Cannot specify relay-option with relay-option-60";
       uses relay-option-60-type-group;
     }
     container relay-option-82 {
       description "DHCP option-82 processing";
       presence "enable relay-option-82";
       uses relay-option-82-type;
     }
     container forward-only {
       description "Forward DHCP packets without creating binding";
       presence "enable forward-only";
       uses forward-only-to-rc-type;
     }
     container route-suppression {
       description "Suppress access-internal and/or destination route addition";
       junos:must "(!(\".. liveness-detection method layer2-liveness-detection\"))";
       junos:must-message "Cannot specify route-suppression with liveness-detection method layer2-liveness-detection";
       junos:must "((!(\".. overrides no-arp\") && !(\".. .. overrides no-arp\")))";
       junos:must-message "Cannot specify route-suppression with overrides no-arp";
       uses dhcp-route-suppression-type;
     }
     leaf description {
       description "Text description of servers";
       type string;
     }
     leaf maximum-hop-count {
       description "Maximum number of hops per packet";
       type union {
         type string {
           pattern "<.*>|$.*";
         }
         type uint32 {
           range "1 .. 16";
         }
       }
     }
     leaf minimum-wait-time {
       description "Minimum number of seconds before requests are forwarded";
       type union {
         type string {
           pattern "<.*>|$.*";
         }
         type uint32 {
           range "0 .. 30000";
         }
       }
     }
     leaf client-response-ttl {
       description "IP time-to-live value to set in responses to client";
       type union {
         type string {
           pattern "<.*>|$.*";
         }
         type uint32 {
           range "1 .. 255";
         }
       }
     }
     leaf source-ip-change {
       description "Use address of egress interface as source ip";
       type empty;
     }
     list interface {
       key name;
       description "One or more interfaces";
       leaf name {
         description "Interface name";
         type union {
           type jt:interface-name;
           type string {
             pattern "<.*>|$.*";
           }
         }
       }
       uses apply-advanced;
       leaf upto {
         description "Interface up to";
         type union {
           type jt:interface-name;
           type string {
             pattern "<.*>|$.*";
           }
         }
       }
       leaf exclude {
         description "Exclude this interface range";
         type empty;
       }
       leaf trace {
         description "Enable tracing for this interface";
         junos:must "(!(\".. exclude\"))";
         junos:must-message "Cannot specify tracing with exclude";
         type empty;
       }
       container overrides {
         description "DHCP override processing";
         junos:must "(!(\".. exclude\"))";
         junos:must-message "Cannot specify overrides with exclude";
         uses override-type;
       }
       container dynamic-profile {
         description "Dynamic profile to use";
         junos:must "(!(\".. exclude\"))";
         junos:must-message "Cannot specify overrides with exclude";
         uses dynamic-profile-type;
       }
       leaf service-profile {
         description "Dynamic profile to use for default service activation";
         type string {
           length "1 .. 128";
         }
       }
       leaf access-profile {
         description "Access profile to use for AAA services";
         junos:must "(\"access profile $$\")";
         junos:must-message "Matching access profile must be defined";
         junos:must "(!(\".. exclude\"))";
         junos:must-message "Cannot specify overrides with exclude";
         type string {
           length "1 .. 128";
         }
       }
       container short-cycle-protection {
         description "Short cycle lockout configuration";
         leaf lockout-min-time {
           description "Short cycle lockout time in seconds";
           type union {
             type string {
               pattern "<.*>|$.*";
             }
             type uint32 {
               range "1 .. 86400";
             }
           }
         }
         leaf lockout-max-time {
           description "Short cycle lockout time in seconds";
           type union {
             type string {
               pattern "<.*>|$.*";
             }
             type uint32 {
               range "1 .. 86400";
             }
           }
         }
       }
     }
     container remote-id-mismatch {
       description "DHCP client remote-id mismatch";
       presence "enable remote-id-mismatch";
       uses dhcp-remote-id-mismatch-type;
     }
     container lease-time-validation {
       presence "enable lease-time-validation";
       description "Configure lease time violation validation";
       uses apply-advanced;
       leaf lease-time-threshold {
         description "Threshold for lease time violation in seconds";
         units "seconds";
         type union {
           type string {
             pattern "<.*>|$.*";
           }
           type uint32 {
             range "60 .. 2147483647";
           }
         }
       }
       container violation-action {
         description "Lease time validation violation action";
         leaf drop {
           description "Drop dhcpv4 offer and ack packets";
           type empty;
         }
       }
     }
   }
   grouping dhcp-liveness-detection-dualstack-type {
     description "DHCP client liveness detection processing";
     uses apply-advanced;
     container failure-action {
       description "Liveness detection failure action options";
       uses dhcp-liveness-detection-failure-action-type;
     }
     container method {
       description "Liveness detection method options";
       uses apply-advanced;
       choice method-choice {
         case case_1 {
           container layer2-liveness-detection {
             description "Address resolution options";
             junos:must "((!(\".. .. route-suppression\") && (!(\".. .. .. route-suppression\") && !(\".. .. .. .. route-suppression\"))))";
             junos:must-message "Method not allowed with route-suppression enabled";
             uses dhcp-arp-nud-liveness-detection-type;
           }
         }
       }
     }
   }
   grouping dhcp-arp-nud-liveness-detection-type {
     description "Address Resolution detection options";
     uses apply-advanced;
     leaf transmit-interval {
       description "Transmit interval for address resolution";
       default "300";
       units "seconds";
       type union {
         type string {
           pattern "<.*>|$.*";
         }
         type uint32 {
           range "300 .. 1800";
         }
       }
     }
     leaf max-consecutive-retries {
       description "Retry attempts";
       default "3";
       type union {
         type string {
           pattern "<.*>|$.*";
         }
         type uint32 {
           range "3 .. 6";
         }
       }
     }
   }
   grouping dhcp-liveness-detection-failure-action-type {
     description "Liveness detection failure action options";
     uses apply-advanced;
     choice failure-action-type {
       case case_1 {
         leaf clear-binding {
           description "Clear the client binding";
           type empty;
         }
       }
       case case_2 {
         leaf clear-binding-if-interface-up {
           description "Clear the client binding only if the incoming interface is up";
           type empty;
         }
       }
       case case_3 {
         leaf log-only {
           description "Maintain the client binding and log the failure event";
           type empty;
         }
       }
     }
   }
   grouping dhcp-liveness-detection-type {
     description "DHCP client liveness detection processing";
     uses apply-advanced;
     container failure-action {
       description "Liveness detection failure action options";
       uses dhcp-liveness-detection-failure-action-type;
     }
     container method {
       description "Liveness detection method options";
       uses apply-advanced;
       choice method-choice {
         case case_1 {
           container bfd {
             description "Bidirectional Forwarding Detection (BFD) options";
             uses dhcp-bfd-liveness-detection-type;
           }
         }
         case case_2 {
           container layer2-liveness-detection {
             description "Address resolution options";
             junos:must "((!(\".. .. route-suppression\") && (!(\".. .. .. route-suppression\") && !(\".. .. .. .. route-suppression\"))))";
             junos:must-message "Method not allowed with route-suppression enabled";
             uses dhcp-arp-nud-liveness-detection-type;
           }
         }
       }
     }
   }
   grouping dhcp-bfd-liveness-detection-type {
     description "Bidirectional Forwarding Detection (BFD) options";
     uses apply-advanced;
     leaf version {
       description "BFD protocol version number";
       default "automatic";
       type enumeration {
         enum "0" {
           description "BFD version 0 (deprecated)";
         }
         enum "1" {
           description "BFD version 1";
         }
         enum "automatic" {
           description "Choose BFD version automatically";
         }
       }
     }
     leaf minimum-interval {
       description "Minimum transmit and receive interval";
       units "milliseconds";
       type union {
         type string {
           pattern "<.*>|$.*";
         }
         type uint32 {
           range "30000 .. 255000";
         }
       }
     }
     leaf minimum-transmit-interval {
       description "Minimum transmit interval";
       status deprecated;
       units "milliseconds";
       type union {
         type string {
           pattern "<.*>|$.*";
         }
         type uint32 {
           range "30000 .. 255000";
         }
       }
     }
     leaf minimum-receive-interval {
       description "Minimum receive interval";
       units "milliseconds";
       type union {
         type string {
           pattern "<.*>|$.*";
         }
         type uint32 {
           range "30000 .. 255000";
         }
       }
     }
     leaf multiplier {
       description "Detection time multiplier";
       default "3";
       type union {
         type string {
           pattern "<.*>|$.*";
         }
         type uint32 {
           range "1 .. 255";
         }
       }
     }
     choice adaptation-choice {
       case case_1 {
         leaf no-adaptation {
           description "Disable adaptation";
           type empty;
         }
       }
     }
     container transmit-interval {
       description "Transmit-interval options";
       uses apply-advanced;
       leaf minimum-interval {
         description "Minimum transmit interval";
         units "milliseconds";
         type union {
           type string {
             pattern "<.*>|$.*";
           }
           type uint32 {
             range "30000 .. 255000";
           }
         }
       }
       leaf threshold {
         description "High transmit interval triggering a trap";
         units "milliseconds";
         type union {
           type uint32;
           type string {
             pattern "<.*>|$.*";
           }
         }
       }
     }
     container detection-time {
       description "Detection-time options";
       uses apply-advanced;
       leaf threshold {
         description "High detection-time triggering a trap";
         units "milliseconds";
         type union {
           type uint32;
           type string {
             pattern "<.*>|$.*";
           }
         }
       }
     }
     leaf session-mode {
       description "BFD single-hop or multihop session-mode";
       default "automatic";
       type enumeration {
         enum "automatic" {
           description "Choose session-mode automatically";
         }
         enum "single-hop" {
           description "Use single-hop";
         }
         enum "multihop" {
           description "Use multihop";
         }
       }
     }
     leaf holddown-interval {
       description "Time to hold the session-UP notification to the client";
       default "0";
       units "milliseconds";
       type union {
         type string {
           pattern "<.*>|$.*";
         }
         type uint32 {
           range "0 .. 255000";
         }
       }
     }
   }
   grouping dhcp-remote-id-mismatch-type {
     description "DHCP client remote-id-mismatch processing";
     uses apply-advanced;
     leaf disconnect {
       description "Disconnect session on remote-id mismatch";
       type empty;
     }
   }
   grouping dhcp-route-suppression-type {
     uses apply-advanced;
     choice dhcp-route-suppression-choice {
       case case_1 {
         leaf access-internal {
           description "Suppress access-internal and destination route addition";
           type empty;
         }
       }
       case case_2 {
         leaf destination {
           description "Suppress destination route addition";
           type empty;
         }
       }
     }
   }
   grouping dhcp-v4-option-default-action {
     description "Default action";
     uses apply-advanced;
     choice server-group-choice {
       case case_1 {
         leaf relay-server-group {
           description "Name of DHCP relay server group when match is made";
           junos:must "((\".. .. .. .. .. .. server-group $$\" || (\".. .. .. .. .. server-group $$\" || (\".. .. .. .. server-group $$\" || \".. .. .. server-group $$\"))))";
           junos:must-message "Referenced group must be defined under [edit forwarding dhcp-relay server-group]";
           type string {
             length "1 .. 64";
           }
         }
       }
       case case_2 {
         leaf local-server-group {
           description "Name of DHCP local server group when match is made";
           junos:must "((\".. .. .. .. .. .. .. .. system services dhcp-local-server group $$\" || (\".. .. .. .. .. .. .. system services dhcp-local-server group $$\" || (\".. .. .. .. .. .. system services dhcp-local-server group $$\" || \".. .. .. .. .. system services dhcp-local-server group $$\"))))";
           junos:must-message "Referenced group must be defined under [edit system services dhcp-local-server group]";
           type string {
             length "1 .. 64";
           }
         }
       }
       case case_3 {
         leaf drop {
           description "Discard when a match is made";
           type empty;
         }
       }
       case case_4 {
         leaf forward-only {
           description "Forward without subscriber services when a match is made";
           type empty;
         }
       }
     }
   }
   grouping dhcpv4-gbl-active-sg-type {
     leaf active-server-group {
       description "Name of DHCP server group";
       junos:must "(\".. .. server-group $$\")";
       junos:must-message "Referenced group must be defined under [edit forwarding-options dhcp-relay server-group]";
       type string {
         length "1 .. 64";
       }
     }
     leaf allow-server-change {
       description "Accept DHCP-ACK from any server in this group";
       type empty;
     }
   }
   grouping dhcpv4-gp-active-sg-type {
     leaf active-server-group {
       description "Name of DHCP server group";
       junos:must "(\".. .. .. server-group $$\")";
       junos:must-message "Referenced group must be defined under [edit forwarding-options dhcp-relay server-group]";
       type string {
         length "1 .. 64";
       }
     }
     leaf allow-server-change {
       description "Accept DHCP-ACK from any server in this group";
       type empty;
     }
   }
   grouping dhcpv6-relay-type {
     description "DHCPv6 relay configuration";
     uses apply-advanced;
     container authentication {
       description "DHCPv6 authentication";
       uses dhcpv6-authentication-type;
     }
     container persistent-storage {
       description "Trigger to enable flat file storage";
       leaf automatic {
         description "Trigger automatically";
         type empty;
       }
     }
     container liveness-detection {
       description "DHCPv6 client liveness detection processing";
       uses dhcpv6-liveness-detection-type;
     }
     container dynamic-profile {
       description "Dynamic profile to use";
       uses dynamic-profile-type;
     }
     leaf service-profile {
       description "Dynamic profile to use for default service activation";
       type string {
         length "1 .. 128";
       }
     }
     leaf access-profile {
       description "Access profile to use for AAA services";
       junos:must "(\"access profile $$\")";
       junos:must-message "Matching access profile must be defined";
       type string {
         length "1 .. 128";
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container overrides {
       description "DHCPv6 override processing";
       presence "enable overrides";
       uses dhcpv6-override-relay-type;
     }
     container relay-option {
       description "DHCPv6 option processing";
       presence "enable relay-option";
       uses dhcp-generic-v6-option;
     }
     container server-match {
       description "Server match processing";
       uses apply-advanced;
       container default-action {
         description "Server match default action";
         uses server-match-action-choice;
       }
       container duid {
         description "Match duid processing";
         uses apply-advanced;
         container equals {
           description "Duid equals";
           uses server-match-v6-ascii-hex;
         }
         container starts-with {
           description "Duid starts with";
           uses server-match-v6-ascii-hex;
         }
       }
       list address {
         key name;
         ordered-by user;
         description "Server ipv6 address";
         leaf name {
           description "Server ipv6 address for matching";
           type jt:ipv6prefix;
         }
         uses apply-advanced;
         choice server-match-action-choice {
           case case_1 {
             leaf forward-only {
               description "Forward without subscriber services when a match is made";
               type empty;
             }
           }
           case case_2 {
             leaf create-relay-entry {
               description "Create relay entry and allow subscriber services";
               type empty;
             }
           }
         }
       }
     }
     leaf relay-agent-option-79 {
       description "Add the client MAC address to the Relay Forward header.";
       type empty;
     }
     container vendor-specific-information {
       description "DHCPv6 option 17 vendor-specific processing";
       uses jdhcp-vendor-specific-type;
     }
     container forward-only {
       description "Forward DHCPv6 packets without creating binding";
       presence "enable forward-only";
       uses forward-only-to-rc-type;
     }
     leaf forward-only-replies {
       description "Forward-only replies from server to appropriate logical-system:routing-instance based on options";
       type empty;
     }
     container forward-snooped-clients {
       junos:must "((!(\".. forward-only\") && (!(\".. forward-only-replies\") && !(any \".. group <*> forward-only\"))))";
       junos:must-message "forward-only and forward-only-replies cannot be configured when forward-snooped-clients is configured";
       description "Forward snooped (unicast) packets";
       choice interface-type {
         case case_1 {
           leaf configured-interfaces {
             description "Forward snooped (unicast) packets on configured interfaces";
             type empty;
           }
         }
         case case_2 {
           leaf non-configured-interfaces {
             description "Forward snooped (unicast) packets on non-configured interfaces";
             type empty;
           }
         }
         case case_3 {
           leaf all-interfaces {
             description "Forward snooped (unicast) packets on configured and non-configured interfaces";
             type empty;
           }
         }
       }
     }
     container route-suppression {
       description "Suppress access-internal and/or access route addition";
       uses dhcpv6-route-suppression-type;
     }
     list group {
       key name;
       ordered-by user;
       description "Define a DHCPv6 relay group";
       uses dhcpv6-relay-group;
     }
     container relay-agent-interface-id {
       description "DHCPv6 interface-id option processing";
       presence "enable relay-agent-interface-id";
       uses v6-relay-option-interface-id-type;
     }
     container relay-agent-remote-id {
       description "DHCPv6 remote-id option processing";
       presence "enable relay-agent-remote-id";
       uses v6-relay-option-remote-id-type;
     }
     container server-group {
       description "Define a DHCPv6 server group";
       uses v6-server-group-type;
     }
     container active-server-group {
       description "Name of DHCPv6 server group";
       uses dhcpv6-gbl-active-sg-type;
     }
     leaf server-response-time {
       description "Number of seconds in a period of activity between the last server response and an unaswered request";
       default "0";
       type union {
         type uint32;
         type string {
           pattern "<.*>|$.*";
         }
       }
     }
     container lease-time-validation {
       presence "enable lease-time-validation";
       description "Configure lease time violation validation";
       uses apply-advanced;
       leaf lease-time-threshold {
         description "Threshold for lease time violation in seconds";
         units "seconds";
         type union {
           type string {
             pattern "<.*>|$.*";
           }
           type uint32 {
             range "60 .. 2147483647";
           }
         }
       }
       container violation-action {
         description "Lease time validation violation action";
         leaf drop {
           description "Drop dhcpv6 advertise and reply packets";
           type empty;
         }
       }
     }
     leaf no-snoop {
       description "Do not snoop DHCPV6 packets";
       junos:must "(!(\"legacy-snooping\"))";
       junos:must-message "'no-snoop' statement cannot be included along with 'legacy-snooping' statement";
       type empty;
     }
     container leasequery {
       description "DHCPv6 leasequery configuration";
       presence "enable leasequery";
       junos:must "(\".. relay-agent-interface-id\")";
       junos:must-message "Must configure [relay-agent-interface-id] to insert interface-id";
       uses relay-leasequery-type;
     }
     container bulk-leasequery {
       description "DHCPv6 bulk leasequery configuration";
       presence "enable bulk-leasequery";
       junos:must "(\".. relay-agent-interface-id\")";
       junos:must-message "Must configure [relay-agent-interface-id] to insert interface-id";
       uses relay-bulk-leasequery-v6-type;
     }
     container remote-id-mismatch {
       description "DHCP client remote-id mismatch";
       presence "enable remote-id-mismatch";
       uses dhcp-remote-id-mismatch-type;
     }
     container duplicate-clients {
       description "Allow duplicate clients";
       uses dhcpv6-duplicate-clients-type;
     }
   }
   grouping dhcp-generic-v6-option {
     description "Generic DHCPv6 options processing";
     uses apply-advanced;
     leaf option-number {
       description "Option number";
       status deprecated;
       type enumeration {
         enum "15" {
           description "Option 15";
           status deprecated;
         }
         enum "16" {
           description "Option 16";
           status deprecated;
         }
       }
     }
     container equals {
       description "Generic option equals";
       status deprecated;
       uses relay-v6-option-ascii-hex;
     }
     container default-action {
       description "Generic option default action";
       status deprecated;
       uses dhcp-v6-option-default-action;
     }
     container starts-with {
       description "Generic option starts with";
       status deprecated;
       uses relay-v6-option-ascii-hex;
     }
     container option-15 {
       description "Add option 15 processing";
       presence "enable option-15";
       junos:must "(!(\"option-number\"))";
       junos:must-message "Cannot specify option-15  with option-number";
       uses dhcp-generic-v6-option-type;
     }
     container option-16 {
       description "Add option 16 processing";
       presence "enable option-16";
       junos:must "(!(\"option-number\"))";
       junos:must-message "Cannot specify option-16  with option-number";
       uses dhcp-generic-v6-option-type;
     }
     list option-order {
       key name;
       ordered-by user;
       description "Options precedence order";
       junos:must "(!(\"option-number\"))";
       junos:must-message "Cannot specify option-order  with option-number";
       leaf name {
         description "Option number";
         type enumeration {
           enum "15" {
             description "Option 15";
           }
           enum "16" {
             description "Option 16";
           }
         }
       }
       uses apply-advanced;
     }
   }
   grouping dhcp-generic-v6-option-type {
     uses apply-advanced;
     container equals {
       description "Generic option equals";
       uses relay-v6-option-ascii-hex;
     }
     container default-action {
       description "Generic option default action";
       uses dhcp-v6-option-default-action;
     }
     container starts-with {
       description "Generic option starts with";
       uses relay-v6-option-ascii-hex;
     }
   }
   grouping dhcp-v6-option-default-action {
     description "Default action";
     uses apply-advanced;
     choice server-group-choice {
       case case_1 {
         leaf relay-server-group {
           description "Name of DHCP relay server group when match is made";
           junos:must "((\".. .. .. .. .. .. server-group $$\" || (\".. .. .. .. .. server-group $$\" || (\".. .. .. .. server-group $$\" || \".. .. .. server-group $$\"))))";
           junos:must-message "Referenced group must be defined under [edit forwarding options dhcp-relay dhcpv6 server-group]";
           type string {
             length "1 .. 64";
           }
         }
       }
       case case_2 {
         leaf drop {
           description "Discard when a match is made";
           type empty;
         }
       }
       case case_3 {
         leaf forward-only {
           description "Forward without subscriber services when a match is made";
           type empty;
         }
       }
     }
   }
   grouping dhcpv6-authentication-type {
     description "DHCPv6 authentication";
     uses apply-advanced;
     leaf password {
       description "Username password to use";
       type string {
         length "1 .. 64";
       }
     }
     container username-include {
       description "Add username options";
       uses apply-advanced;
       leaf delimiter {
         description "Change delimiter/separator character";
         type string {
           length 1;
         }
       }
       leaf domain-name {
         description "Add domain name";
         type string {
           length "1 .. 64";
         }
       }
       leaf user-prefix {
         description "Add user defined prefix";
         type string {
           length "1 .. 64";
         }
       }
       leaf mac-address {
         description "Include MAC address";
         type empty;
       }
       leaf client-id {
         description "Include client ID";
         type empty;
       }
       container relay-agent-remote-id {
         presence "enable relay-agent-remote-id";
         description "Include the relay agent remote ID";
         uses apply-advanced;
         choice relay-agent-remote-id-choice {
           case case_1 {
             leaf enterprise-id {
               description "Only use enterprise-id portion of option-37";
               status deprecated;
               type empty;
             }
           }
           case case_2 {
             leaf remote-id {
               description "Only use remote-id portion of option-37";
               status deprecated;
               type empty;
             }
           }
         }
       }
       leaf logical-system-name {
         description "Include logical system name";
         type empty;
       }
       leaf routing-instance-name {
         description "Include routing instance name";
         type empty;
       }
       leaf relay-agent-subscriber-id {
         description "Include the relay agent subscriber ID";
         type empty;
       }
       leaf relay-agent-interface-id {
         description "Include the relay agent interface ID";
         type empty;
       }
       leaf circuit-type {
         description "Include circuit type";
         type empty;
       }
       leaf interface-name {
         description "Include interface name";
         type empty;
       }
       leaf interface-description {
         description "Include interface description";
         type enumeration {
           enum "device" {
             description "Add the device interface description";
           }
           enum "logical" {
             description "Add the logical interface description";
           }
         }
       }
       leaf vlan-tags {
         description "Include the vlan tag(s)";
         type empty;
       }
     }
   }
   grouping dhcpv6-duplicate-clients-type {
     description "Allow duplicate clients";
     choice distinguish-with {
       case case_1 {
         leaf incoming-interface {
           description "Allow duplicate clients on different underlying interfaces";
           type empty;
         }
       }
     }
   }
   grouping dhcpv6-gbl-active-sg-type {
     uses apply-advanced;
     leaf active-server-group {
       description "Name of DHCPv6 server group";
       junos:must "(\".. .. server-group $$\")";
       junos:must-message "Referenced group must be defined under [edit forwarding-options dhcp-relay dhcpv6 server-group]";
       type string {
         length "1 .. 64";
       }
     }
   }
   grouping dhcpv6-liveness-detection-type {
     description "DHCPv6 client liveness detection processing";
     uses apply-advanced;
     container failure-action {
       description "Liveness detection failure action options";
       uses dhcp-liveness-detection-failure-action-type;
     }
     container method {
       description "Liveness detection method options";
       uses apply-advanced;
       choice method-choice {
         case case_1 {
           container bfd {
             description "Bidirectional Forwarding Detection (BFD) options";
             uses dhcp-bfd-liveness-detection-type;
           }
         }
         case case_2 {
           container layer2-liveness-detection {
             description "Neighbor discovery options";
             uses dhcp-arp-nud-liveness-detection-type;
           }
         }
       }
     }
   }
   grouping dhcpv6-override-relay-type {
     description "DHCPv6 relay override processing";
     uses apply-advanced;
     choice allow-snooped-clients-choice {
       leaf allow-snooped-clients {
         description "Allow client creation from snooped PDUs";
         type empty;
       }
       leaf no-allow-snooped-clients {
         description "Don't allow client creation from snooped PDUs";
         type empty;
       }
     }
     leaf delay-authentication {
       description "Delay subscriber authentication in DHCP protocol processing until request packet";
       type empty;
     }
     leaf interface-client-limit {
       description "Limit the number of clients allowed on an interface";
       type union {
         type string {
           pattern "<.*>|$.*";
         }
         type uint32 {
           range "1 .. 500000";
         }
       }
     }
     leaf dual-stack {
       description "Dual stack group to use.";
       type string {
         length "1 .. 64";
       }
     }
     leaf no-bind-on-request {
       description "Do not bind if stray DHCPv6 RENEW, REBIND is received";
       type empty;
     }
     container client-negotiation-match {
       description "Use secondary match criteria for SOLICIT PDU";
       choice match-with {
         case case_1 {
           leaf incoming-interface {
             description "Use incoming interface";
             type empty;
           }
         }
       }
     }
     leaf send-release-on-delete {
       description "Always send RELEASE to the server when a binding is deleted";
       type empty;
     }
     leaf always-process-option-request-option {
       description "Always process option even after address allocation failure";
       type empty;
     }
     leaf relay-source {
       description "Interface for relay source";
       type union {
         type jt:interface-name;
         type string {
           pattern "<.*>|$.*";
         }
       }
     }
     leaf delete-binding-on-renegotiation {
       description "Delete binding on renegotiation";
       type empty;
     }
     leaf asymmetric-lease-time {
       description "Use a reduced lease time for the client. In seconds";
       units "seconds";
       type union {
         type string {
           pattern "<.*>|$.*";
         }
         type uint32 {
           range "600 .. 86400";
         }
       }
     }
     leaf asymmetric-prefix-lease-time {
       description "Use a reduced prefix lease time for the client. In seconds";
       units "seconds";
       type union {
         type string {
           pattern "<.*>|$.*";
         }
         type uint32 {
           range "600 .. 86400";
         }
       }
     }
   }
   grouping dhcpv6-relay-group {
     description "DHCPv6 groups";
     leaf name {
       description "Group name";
       type string {
         length "1 .. 64";
         junos:posix-pattern "^[A-Za-z0-9][_0-9A-Za-z-]*$";
         junos:pattern-message "Must be a non-reserved string of 64 characters or less";
       }
     }
     uses apply-advanced;
     container active-server-group {
       description "Name of DHCPv6 server group";
       uses dhcpv6-gp-active-sg-type;
     }
     list dual-stack-group {
       key name;
       description "Define a DHCP dual stack group";
       uses dhcp-dual-stack-group;
     }
     container authentication {
       description "DHCPv6 authentication";
       uses dhcpv6-authentication-type;
     }
     container liveness-detection {
       description "DHCPv6 client liveness detection processing";
       uses dhcpv6-liveness-detection-type;
     }
     container dynamic-profile {
       description "Dynamic profile to use";
       uses dynamic-profile-type;
     }
     leaf service-profile {
       description "Dynamic profile to use for default service activation";
       type string {
         length "1 .. 128";
       }
     }
     leaf access-profile {
       description "Access profile to use for AAA services";
       junos:must "(\"access profile $$\")";
       junos:must-message "Matching access profile must be defined";
       type string {
         length "1 .. 128";
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container overrides {
       description "DHCPv6 override processing";
       presence "enable overrides";
       uses dhcpv6-override-relay-type;
     }
     container relay-option {
       description "DHCPv6 option processing";
       presence "enable relay-option";
       uses dhcp-generic-v6-option;
     }
     container vendor-specific-information {
       description "DHCPv6 option 17 vendor-specific processing";
       uses jdhcp-vendor-specific-type;
     }
     container forward-only {
       description "Forward DHCPv6 packets without creating binding";
       presence "enable forward-only";
       uses forward-only-to-rc-type;
     }
     container relay-agent-interface-id {
       description "DHCPv6 interface-id option processing";
       presence "enable relay-agent-interface-id";
       uses v6-relay-option-interface-id-type;
     }
     container relay-agent-remote-id {
       description "DHCPv6 remote-id option processing";
       presence "enable relay-agent-remote-id";
       uses v6-relay-option-remote-id-type;
     }
     container route-suppression {
       description "Suppress access-internal and/or access route addition";
       uses dhcpv6-route-suppression-type;
     }
     leaf relay-agent-option-79 {
       description "Add the client MAC address to the Relay Forward header.";
       type empty;
     }
     list interface {
       key name;
       description "One or more interfaces";
       leaf name {
         description "Interface name";
         junos:must "((unique \"forwarding-options dhcp-relay dhcpv6 group <*> interface $$\" && !(any \"system services dhcp-local-server dhcpv6 group <*> interface $$\")))";
         junos:must-message "Interface used in other relay or server group";
         type union {
           type jt:interface-name;
           type string {
             pattern "<.*>|$.*";
           }
         }
       }
       uses apply-advanced;
       leaf upto {
         description "Interface up to";
         junos:must "(!(\".. .. interface $$\"))";
         junos:must-message "Range end point must not equal start";
         type union {
           type jt:interface-name;
           type string {
             pattern "<.*>|$.*";
           }
         }
       }
       leaf exclude {
         description "Exclude this interface range";
         type empty;
       }
       leaf trace {
         description "Enable tracing for this interface";
         junos:must "(!(\".. exclude\"))";
         junos:must-message "Cannot specify tracing with exclude";
         type empty;
       }
       container overrides {
         description "DHCPv6 override processing";
         junos:must "(!(\".. exclude\"))";
         junos:must-message "Cannot specify overrides with exclude";
         uses dhcpv6-override-relay-type;
       }
       container dynamic-profile {
         description "Dynamic profile to use";
         junos:must "(!(\".. exclude\"))";
         junos:must-message "Cannot specify dynamic-profile with exclude";
         uses dynamic-profile-type;
       }
       leaf service-profile {
         description "Dynamic profile to use for default service activation";
         type string {
           length "1 .. 128";
         }
       }
       leaf access-profile {
         description "Access profile to use for AAA services";
         junos:must "(\"access profile $$\")";
         junos:must-message "Matching access profile must be defined";
         junos:must "(!(\".. exclude\"))";
         junos:must-message "Cannot specify overrides with exclude";
         type string {
           length "1 .. 128";
         }
       }
       container short-cycle-protection {
         description "Short cycle lockout configuration";
         leaf lockout-min-time {
           description "Short cycle lockout time in seconds";
           type union {
             type string {
               pattern "<.*>|$.*";
             }
             type uint32 {
               range "1 .. 86400";
             }
           }
         }
         leaf lockout-max-time {
           description "Short cycle lockout time in seconds";
           type union {
             type string {
               pattern "<.*>|$.*";
             }
             type uint32 {
               range "1 .. 86400";
             }
           }
         }
       }
     }
     container lease-time-validation {
       presence "enable lease-time-validation";
       description "Configure lease time violation validation";
       uses apply-advanced;
       leaf lease-time-threshold {
         description "Threshold for lease time violation in seconds";
         units "seconds";
         type union {
           type string {
             pattern "<.*>|$.*";
           }
           type uint32 {
             range "60 .. 2147483647";
           }
         }
       }
       container violation-action {
         description "Lease time validation violation action";
         leaf drop {
           description "Drop dhcpv6 advertise and reply packets";
           type empty;
         }
       }
     }
     container remote-id-mismatch {
       description "DHCP client remote-id mismatch";
       presence "enable remote-id-mismatch";
       uses dhcp-remote-id-mismatch-type;
     }
     container server-match {
       description "Server match processing";
       uses apply-advanced;
       container default-action {
         description "Server match default action";
         uses server-match-action-choice;
       }
       container duid {
         description "Match duid processing";
         uses apply-advanced;
         container equals {
           description "Duid equals";
           uses server-match-v6-ascii-hex;
         }
         container starts-with {
           description "Duid starts with";
           uses server-match-v6-ascii-hex;
         }
       }
       list address {
         key name;
         ordered-by user;
         description "Server ipv6 address";
         leaf name {
           description "Server ipv6 address for matching";
           type jt:ipv6prefix;
         }
         uses apply-advanced;
         choice server-match-action-choice {
           case case_1 {
             leaf forward-only {
               description "Forward without subscriber services when a match is made";
               type empty;
             }
           }
           case case_2 {
             leaf create-relay-entry {
               description "Create relay entry and allow subscriber services";
               type empty;
             }
           }
         }
       }
     }
   }
   grouping dhcpv6-gp-active-sg-type {
     uses apply-advanced;
     leaf active-server-group {
       description "Name of DHCPv6 server group";
       junos:must "(\".. .. .. server-group $$\")";
       junos:must-message "Referenced group must be defined under [edit forwarding-options dhcp-relay dhcpv6 server-group]";
       type string {
         length "1 .. 64";
       }
     }
   }
   grouping dhcpv6-route-suppression-type {
     description "Suppress access-internal and/or access route addition";
     leaf access {
       description "Suppress access route addition";
       type empty;
     }
     leaf access-internal {
       description "Suppress access-internal route addition";
       type empty;
     }
   }
   grouping dual-stack-authentication-type {
     description "DHCP dual stack authentication";
     uses apply-advanced;
     leaf password {
       description "Username password to use";
       type string {
         length "1 .. 64";
       }
     }
     container username-include {
       description "Add username options";
       uses apply-advanced;
       leaf delimiter {
         description "Change delimiter/separator character";
         type string {
           length 1;
         }
       }
       leaf domain-name {
         description "Add domain name";
         type string {
           length "1 .. 64";
         }
       }
       leaf user-prefix {
         description "Add user defined prefix";
         type string {
           length "1 .. 64";
         }
       }
       leaf mac-address {
         description "Include MAC address";
         type empty;
       }
       leaf relay-agent-remote-id {
         description "Include the relay agent remote ID";
         type empty;
       }
       leaf logical-system-name {
         description "Include logical system name";
         type empty;
       }
       leaf routing-instance-name {
         description "Include routing instance name";
         type empty;
       }
       leaf relay-agent-interface-id {
         description "Include the relay agent interface ID";
         type empty;
       }
       leaf interface-name {
         description "Include interface name";
         type empty;
       }
       leaf interface-description {
         description "Include interface description";
         type enumeration {
           enum "device" {
             description "Add the device interface description";
           }
           enum "logical" {
             description "Add the logical interface description";
           }
         }
       }
       leaf circuit-type {
         description "Include circuit type";
         type empty;
       }
       leaf vlan-tags {
         description "Include the vlan tag(s)";
         type empty;
       }
     }
   }
   grouping dynamic-profile-type {
     description "Dynamic profile to use";
     uses apply-advanced;
     leaf dynamic-profile {
       description "Dynamic profile to use";
       junos:must "(\"dynamic-profiles $$\")";
       junos:must-message "Dynamic profile must be defined";
       type string {
         length "1 .. 80";
       }
     }
     choice dynamic-profile-type-choice {
       case case_1 {
         leaf use-primary {
           description "Dynamic profile to use on the primary interface";
           junos:must "(\"dynamic-profiles $$\")";
           junos:must-message "Dynamic profile must be defined";
           type string {
             length "1 .. 80";
           }
         }
       }
       case case_2 {
         container aggregate-clients {
           presence "enable aggregate-clients";
           description "Aggregate client profiles";
           uses apply-advanced;
           choice aggregate-type {
             case case_1 {
               leaf merge {
                 description "Merge the client dynamic profiles";
                 type empty;
               }
             }
             case case_2 {
               leaf replace {
                 description "Replace client dynamic profiles";
                 type empty;
               }
             }
           }
         }
       }
     }
   }
   grouping forward-only-to-rc-type {
     description "Forward DHCP packets without creating binding";
     uses apply-advanced;
     leaf logical-system {
       default "current";
       type string;
     }
     leaf routing-instance {
       default "current";
       type string;
     }
   }
   grouping jdhcp-dual-stack-protocol-mstr-type {
     description "Select family as protocol master";
     choice addr-fam {
       case case_1 {
         leaf inet {
           description "INET family has protocol master behavior";
           type empty;
         }
       }
       case case_2 {
         leaf inet6 {
           description "INET6 family has protocol master behavior";
           type empty;
         }
       }
     }
   }
   grouping jdhcp-duplicate-clients-in-subnet-type {
     description "Allow duplicate clients in a subnet";
     choice distinguish-with {
       case case_1 {
         leaf incoming-interface {
           description "Allow duplicate clients on different interfaces in a subnet";
           type empty;
         }
       }
       case case_2 {
         leaf option-82 {
           description "Allow duplicate clients using different option-82 options in a subnet";
           type empty;
         }
       }
     }
   }
   grouping jdhcp-interface-traceoptions-type {
     description "Interface trace options for DHCP";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Interface trace categories";
       leaf name {
         type enumeration {
           enum "state" {
             description "State-transition operations";
           }
           enum "packet" {
             description "Packet-decoding operations";
           }
           enum "flow" {
             description "Flow-decoding operations";
           }
           enum "packet-option" {
             description "DHCP option-decoding operations";
           }
           enum "dhcpv6-state" {
             description "State-transition operations for dhcpv6";
           }
           enum "dhcpv6-packet" {
             description "Packet-decoding operations for dhcpv6";
           }
           enum "dhcpv6-packet-option" {
             description "DHCP option-decoding operations for dhcpv6";
           }
           enum "all" {
             description "All operations";
           }
         }
       }
     }
   }
   grouping jdhcp-traceoptions-type {
     description "Trace options for DHCP";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "DHCP operations to include in debugging trace";
       leaf name {
         type enumeration {
           enum "state" {
             description "State-transition operations";
           }
           enum "packet" {
             description "Packet-decoding operations";
           }
           enum "flow" {
             description "Flow-decoding operations";
           }
           enum "packet-option" {
             description "DHCP option-decoding operations";
           }
           enum "dhcpv6-state" {
             description "State-transition operations for dhcpv6";
           }
           enum "dhcpv6-packet" {
             description "Packet-decoding operations for dhcpv6";
           }
           enum "dhcpv6-packet-option" {
             description "DHCP option-decoding operations for dhcpv6";
           }
           enum "all" {
             description "All operations";
           }
           enum "database" {
             description "Database operations";
           }
           enum "persistent" {
             description "Persitent file operations";
           }
           enum "lockout-db" {
             description "Lockout database operations";
           }
           enum "interface" {
             description "Interface operations";
           }
           enum "rtsock" {
             description "Routing socket operations";
           }
           enum "flow-notify" {
             description "Flow notification operations";
           }
           enum "io" {
             description "I/O operations";
           }
           enum "ha" {
             description "High Availability-related operations";
           }
           enum "ui" {
             description "User Interface operations";
           }
           enum "general" {
             description "Miscellaneous operations";
           }
           enum "fwd" {
             description "Firewall process operations";
           }
           enum "rpd" {
             description "Routing Protocol process operations";
           }
           enum "auth" {
             description "Authentication operations";
           }
           enum "profile" {
             description "Profile operations";
           }
           enum "session-db" {
             description "Session database operations";
           }
           enum "performance" {
             description "Performance measurement operations";
           }
           enum "statistics" {
             description "Baseline statistics operations";
           }
           enum "dhcpv6-io" {
             description "I/O operations for dhcpv6";
           }
           enum "dhcpv6-rpd" {
             description "Routing Protocol process operations for dhcpv6";
           }
           enum "dhcpv6-session-db" {
             description "Session database operations for dhcpv6";
           }
           enum "dhcpv6-general" {
             description "Miscellaneous operations for dhcpv6";
           }
           enum "liveness-detection" {
             description "Liveness detection operations";
           }
           enum "security-persistence" {
             description "Liveness detection operations";
           }
           enum "mclag" {
             description "Multichassis LAG";
           }
           enum "ra-guard" {
             description "DHCP RA guard option for dhcpv6";
           }
         }
       }
     }
   }
   grouping jdhcp-vendor-specific-type {
     description "Add vendor-specific option processing";
     uses apply-advanced;
     leaf host-name {
       description "Add router host name";
       type empty;
     }
     leaf location {
       description "Add location information expressed as interface name format";
       type empty;
     }
   }
   grouping juniper-forwarding-sandbox-options {
     leaf name {
       description "Sandbox name";
       junos:must "(\".. port\")";
       junos:must-message "At least one port is required for port configuration";
       type string;
     }
     uses apply-advanced;
     leaf size {
       description "Size of the sandbox";
       default "small";
       type enumeration {
         enum "small" {
           description "Sandbox size small";
         }
         enum "medium" {
           description "Sandbox size medium";
         }
         enum "large" {
           description "Sandbox size large";
         }
       }
     }
     list port {
       key name;
       description "Sandbox port";
       max-elements 64;
       uses juniper-forwarding-sandbox-port-options;
     }
   }
   grouping juniper-forwarding-sandbox-port-options {
     leaf name {
       description "Port name";
       junos:must "(\".. interface\")";
       junos:must-message "At least one interface is required for port configuration";
       type string;
     }
     uses apply-advanced;
     list interface {
       key name;
       ordered-by user;
       description "Interface to which the port is mapped";
       max-elements 1;
       leaf name {
         description "Interface name";
         junos:must "(!(\"interfaces $$ unit\"))";
         junos:must-message "Interface must not have configuration defined for adding to a forwarding sandbox";
         type union {
           type jt:interface-device;
           type string {
             pattern "<.*>|$.*";
           }
         }
       }
       uses apply-advanced;
     }
   }
   grouping juniper-monitoring-options {
     leaf name {
       description "Name for monitoring group";
       type string;
     }
     uses apply-advanced;
     container family {
       description "Address family of packets to monitor";
       container inet {
         presence "enable inet";
         description "Monitor IPv4 packets";
         uses apply-advanced;
         container input {
           description "Monitor data acquisition";
           presence "enable input";
           status deprecated;
           uses monitoring_input_type;
         }
         container output {
           description "Monitoring data disposition";
           presence "enable output";
           uses monitoring_output_type;
         }
       }
     }
   }
   grouping juniper-next-hop-group-options {
     leaf name {
       description "Next hop group name";
       type string;
     }
     uses apply-advanced;
     leaf group-type {
       description "Next hop group type";
       default "inet";
       type enumeration {
         enum "inet" {
           description "Group of family inet next-hops";
         }
         enum "layer-2" {
           description "Layer-2 next-hop group";
         }
         enum "inet6" {
           description "Group of family inet6 next-hops";
         }
       }
     }
     list interface {
       key name;
       description "Interfaces through which to send sampled traffic";
       uses next_hop_group_intf_type;
     }
     list next-hop-subgroup {
       key name;
       description "Group of interfaces through which to send sampled traffic";
       uses juniper-next-hop-subgroup-options;
     }
   }
   grouping juniper-next-hop-subgroup-options {
     leaf name {
       description "Next-hop sub-group name";
       junos:must "(\".. interface\")";
       junos:must-message "At least two interfaces are required for next-hop-subgroup configuration";
       type string;
     }
     uses apply-advanced;
     list interface {
       key name;
       description "Interface through which to send the sampled traffic";
       max-elements 16;
       uses next_hop_subgroup_intf_type;
     }
   }
   grouping juniper-packet-accounting-options {
     leaf name {
       description "Name for accounting group";
       type string;
     }
     uses apply-advanced;
     container output {
       description "Accounting data disposition";
       uses packet_accounting_output_type;
     }
   }
   grouping juniper-packet-capture-options {
     description "Packet capture options";
     uses apply-advanced;
     choice enable-disable {
       case case_1 {
         leaf disable {
           description "Disable packet-capture";
           type empty;
         }
       }
     }
     container file {
       description "Parameters for file that contains captured packets";
       leaf filename {
         description "Name of file";
         type string {
           length "1 .. 900";
           junos:posix-pattern "![/ %.]";
           junos:pattern-message "Must not contain '/', '%', '.' or a space";
         }
       }
       leaf files {
         description "Maximum number of files";
         default "10";
         type union {
           type string {
             pattern "<.*>|$.*";
           }
           type uint32 {
             range "2 .. 10000";
           }
         }
       }
       leaf size {
         description "Maximum file size";
         type string;
       }
       choice world-readable-choice {
         leaf world-readable {
           description "Allow any user to read packet-capture files";
           type empty;
         }
         leaf no-world-readable {
           description "Don't allow any user to read packet-capture files";
           type empty;
         }
       }
     }
     leaf maximum-capture-size {
       description "Maximum packet size to capture";
       default "68";
       units "bytes";
       type union {
         type string {
           pattern "<.*>|$.*";
         }
         type uint32 {
           range "68 .. 1520";
         }
       }
     }
   }
   grouping juniper-port-mirror-options {
     uses apply-advanced;
     container traceoptions {
       description "Port-mirroring trace options";
       uses sampling_traceoptions_type;
     }
     leaf disable {
       description "Disable the global port-mirroring instance";
       type empty;
     }
     leaf disable-all-instances {
       description "Disable the all port-mirroring instances";
       type empty;
     }
     leaf mirror-once {
       description "Sample the packet for port mirroring only once";
       type empty;
     }
     leaf no-preserve-ingress-tag {
       description "Mirror the packet retaining tag value before normalization";
       type empty;
     }
     container input {
       description "Settings for sampling of input packets";
       uses pm_family_input_type;
     }
     container family {
       description "Address family of packets to mirror";
       container inet {
         description "Mirror IPv4 packets";
         uses apply-advanced;
         container input {
           description "Settings for sampling of input packets";
           status deprecated;
           junos:must "(!(\".. .. .. input\"))";
           junos:must-message "input parameters under family and outside family are mutually exclusive";
           uses pm_family_input_type;
         }
         container output {
           description "One or more next hops for port-mirrored packets";
           uses inet_pm_family_output_type;
         }
       }
       container inet6 {
         description "Mirror IPv6 packets";
         uses apply-advanced;
         container input {
           description "Settings for sampling of input packets";
           status deprecated;
           junos:must "(!(\".. .. .. input\"))";
           junos:must-message "input parameters under family and outside family are mutually exclusive";
           uses pm_family_input_type;
         }
         container output {
           description "One or more next hops for port-mirrored packets";
           uses inet6_pm_family_output_type;
         }
       }
       container mpls {
         description "Mirror MPLS packets";
         uses apply-advanced;
         container input {
           description "Settings for sampling of input packets";
           status deprecated;
           junos:must "(!(\".. .. .. input\"))";
           junos:must-message "input parameters under family and outside family are mutually exclusive";
           uses pm_family_input_type;
         }
         container output {
           description "One or more next hops for port-mirrored packets";
           uses mpls_pm_family_output_type;
         }
       }
       container any {
         description "Mirror any packets";
         uses apply-advanced;
         container output {
           description "One or more next hops for port-mirrored packets";
           uses any_pm_family_output_type;
         }
       }
       container vpls {
         description "Mirror Layer-2 bridged/vpls packets";
         uses apply-advanced;
         container input {
           description "Settings for sampling of input packets";
           status deprecated;
           junos:must "(!(\".. .. ..  input\"))";
           junos:must-message "input parameters under family and outside family are mutually exclusive";
           uses pm_family_input_type;
         }
         container output {
           description "Destination for port-mirrored packets";
           uses layer2_pm_family_output_type;
         }
       }
       container ethernet-switching {
         description "Mirror Layer-2 ethernet-switched packets";
         uses apply-advanced;
         container output {
           description "Destination for port-mirrored packets";
           uses layer2_pm_family_output_type;
         }
       }
       container ccc {
         description "Mirror layer-2 ccc packets";
         uses apply-advanced;
         container input {
           description "Settings for sampling of input packets";
           status deprecated;
           junos:must "(!(\".. .. ..  input\"))";
           junos:must-message "input parameters under family and outside family are mutually exclusive";
           uses pm_family_input_type;
         }
         container output {
           description "Destination for port-mirrored packets";
           uses layer2_pm_family_output_type;
         }
       }
     }
     list instance {
       key name;
       ordered-by user;
       description "Instance of port-mirroring parameters";
       leaf name {
         description "Name for port-mirroring instance";
         type string {
           length "1 .. 63";
           junos:posix-pattern "!^((__.*)|(.{65,}))$";
           junos:pattern-message "Must be a non-reserved string of 64 characters or less";
         }
       }
       uses apply-advanced;
       leaf disable {
         description "Disable the this port-mirroring instance";
         type empty;
       }
       choice input_params_or_instance {
         case case_1 {
           container input {
             description "Settings for sampling of input packets";
             uses pm_family_input_type;
           }
         }
         case case_2 {
           leaf input-parameters-instance {
             description "Name of port-mirroring instance to use for input parameters";
             junos:must "(\"forwarding-options port-mirroring instance $$\")";
             junos:must-message "Referenced port-mirroring instance does not exist";
             type string;
           }
         }
       }
       container family {
         description "Address family of packets to mirror";
         container inet {
           description "Mirror IPv4 packets";
           uses apply-advanced;
           container input {
             description "Settings for sampling of input packets";
             status deprecated;
             junos:must "(!(\".. .. .. input\"))";
             junos:must-message "input parameters under family and outside family are mutually exclusive";
             uses pm_family_input_type;
           }
           container output {
             description "One or more next hops for port-mirrored packets";
             uses inet_pm_family_output_type;
           }
         }
         container inet6 {
           description "Mirror IPv6 packets";
           uses apply-advanced;
           container input {
             description "Settings for sampling of input packets";
             status deprecated;
             junos:must "(!(\".. .. .. input\"))";
             junos:must-message "input parameters under family and outside family are mutually exclusive";
             uses pm_family_input_type;
           }
           container output {
             description "One or more next hops for port-mirrored packets";
             uses inet6_pm_family_output_type;
           }
         }
         container mpls {
           description "Mirror MPLS packets";
           uses apply-advanced;
           container input {
             description "Settings for sampling of input packets";
             status deprecated;
             junos:must "(!(\".. .. .. input\"))";
             junos:must-message "input parameters under family and outside family are mutually exclusive";
             uses pm_family_input_type;
           }
           container output {
             description "One or more next hops for port-mirrored packets";
             uses mpls_pm_family_output_type;
           }
         }
         container any {
           description "Mirror any packets";
           uses apply-advanced;
           container output {
             description "One or more next hops for port-mirrored packets";
             uses any_pm_family_output_type;
           }
         }
         container vpls {
           description "Mirror Layer-2 bridged/vpls packets";
           uses apply-advanced;
           container input {
             description "Settings for sampling of input packets";
             status deprecated;
             junos:must "(!(\".. .. ..  input\"))";
             junos:must-message "input parameters under family and outside family are mutually exclusive";
             uses pm_family_input_type;
           }
           container output {
             description "Destination for port-mirrored packets";
             uses layer2_pm_family_output_type;
           }
         }
         container ethernet-switching {
           description "Mirror Layer-2 ethernet-switched packets";
           uses apply-advanced;
           container output {
             description "Destination for port-mirrored packets";
             uses layer2_pm_family_output_type;
           }
         }
         container ccc {
           description "Mirror layer-2 ccc packets";
           uses apply-advanced;
           container input {
             description "Settings for sampling of input packets";
             status deprecated;
             junos:must "(!(\".. .. ..  input\"))";
             junos:must-message "input parameters under family and outside family are mutually exclusive";
             uses pm_family_input_type;
           }
           container output {
             description "Destination for port-mirrored packets";
             uses layer2_pm_family_output_type;
           }
         }
       }
     }
   }
   grouping any_pm_family_output_type {
     uses apply-advanced;
     choice interface-or-next-hop-index {
       case case_1 {
         list interface {
           key name;
           description "Interfaces through which to send sampled traffic";
           uses any_pm_intf_type;
         }
       }
       case case_2 {
         leaf next-hop-group {
           description "Next-hop-group through which to send port-mirror traffic";
           junos:must "(!(\".. no-filter-check\"))";
           junos:must-message "no-filter-check is not allowed with next-hop-group";
           junos:must "(\"forwarding-options next-hop-group $$ group-type layer-2\")";
           junos:must-message "Referenced next-hop-group must be defined as layer-2 group";
           type string;
         }
       }
     }
     leaf no-filter-check {
       description "Do not check for filters on port-mirroring interface";
       type empty;
     }
     container hosted-service {
       description "Configure Hosted Service";
       uses apply-advanced;
       leaf server-profile {
         description "Server profile name";
         junos:must "(\"services hosted-services server-profile $$\")";
         junos:must-message "Only server profiles configured under [services hosted-services server-profile] can be configured here";
         type string {
           length "3 .. 32";
         }
       }
     }
   }
   grouping any_pm_intf_type {
     leaf name {
       description "Interface through which to send sampled traffic";
       junos:must "(!((\"interfaces $$-IFL family inet\" || \"interfaces $$-IFL family inet6\")))";
       junos:must-message "An interface configured as family inet/inet6 cannot be configured as output interface";
       type union {
         type jt:interface-name;
         type string {
           pattern "<.*>|$.*";
         }
       }
     }
     uses apply-advanced;
     list next-hop {
       key name;
       ordered-by user;
       description "Address of next hop through which to send sampled traffic";
       uses inet_next_hop_type;
     }
   }
   grouping inet6_pm_family_output_type {
     uses apply-advanced;
     choice interface-or-next-hop-index {
       case case_1 {
         list interface {
           key name;
           description "Interfaces through which to send sampled traffic";
           uses inet6_pm_intf_type;
         }
       }
       case case_2 {
         leaf next-hop-group {
           description "Next-hop-group through which to send port-mirror traffic";
           junos:must "(!(\".. no-filter-check\"))";
           junos:must-message "no-filter-check is not allowed with next-hop-group";
           junos:must "(\"forwarding-options next-hop-group $$ group-type inet6\")";
           junos:must-message "Referenced next-hop-group must be defined as inet6 group";
           type string;
         }
       }
     }
     leaf no-filter-check {
       description "Do not check for filters on port-mirroring interface";
       type empty;
     }
     leaf server-profile {
       description "Server profile name";
       junos:must "((\"services hosted-services server-profile $$\" && (\"services hosted-services server-profile $$ server-address\" && \"services hosted-services server-profile $$ client-address\")))";
       junos:must-message "Only complete server profiles configured under [services hosted-services server-profile] can be configured here";
       type string {
         length "3 .. 32";
       }
     }
   }
   grouping inet6_pm_intf_type {
     leaf name {
       description "Interface through which to send sampled traffic";
       type union {
         type jt:interface-name;
         type string {
           pattern "<.*>|$.*";
         }
       }
     }
     uses apply-advanced;
     list next-hop {
       key name;
       ordered-by user;
       description "Address of next hop through which to send sampled traffic";
       uses inet6_next_hop_type;
     }
   }
   grouping inet6_next_hop_type {
     description "Address of next hop through which to send sampled traffic";
     leaf name {
       type jt:ipv6addr;
     }
     uses apply-advanced;
   }
   grouping inet_next_hop_type {
     description "Address of next hop through which to send sampled traffic";
     leaf name {
       type jt:ipv4addr;
     }
     uses apply-advanced;
   }
   grouping inet_pm_family_output_type {
     uses apply-advanced;
     choice interface-or-next-hop-index {
       case case_1 {
         list interface {
           key name;
           description "Interfaces through which to send sampled traffic";
           uses inet_pm_intf_type;
         }
       }
       case case_2 {
         leaf next-hop-group {
           description "Next-hop-group through which to send port-mirror traffic";
           junos:must "(!(\".. no-filter-check\"))";
           junos:must-message "no-filter-check is not allowed with next-hop-group";
           junos:must "(\"forwarding-options next-hop-group $$ group-type inet\")";
           junos:must-message "Referenced next-hop-group must be defined as inet group";
           type string;
         }
       }
     }
     leaf no-filter-check {
       description "Do not check for filters on port-mirroring interface";
       type empty;
     }
     leaf ip-address {
       description "ERSPAN Destination IP Address";
       type jt:ipv4addr;
     }
     list routing-instance {
       key name;
       description "Routing instances";
       max-elements 1;
       uses inet_pm_output-routing-instance-type;
     }
     leaf server-profile {
       description "Server profile name";
       junos:must "((\"services hosted-services server-profile $$\" && (\"services hosted-services server-profile $$ server-address\" && \"services hosted-services server-profile $$ client-address\")))";
       junos:must-message "Only complete server profiles configured under [services hosted-services server-profile] can be configured here";
       type string {
         length "3 .. 32";
       }
     }
   }
   grouping inet_pm_intf_type {
     leaf name {
       description "Interface through which to send sampled traffic";
       type union {
         type jt:interface-name;
         type string {
           pattern "<.*>|$.*";
         }
       }
     }
     uses apply-advanced;
     list next-hop {
       key name;
       ordered-by user;
       description "Address of next hop through which to send sampled traffic";
       uses inet_next_hop_type;
     }
   }
   grouping inet_pm_output-routing-instance-type {
     leaf name {
       description "Routing instance name";
       type string {
         junos:posix-pattern "!^((__.*__)|(all)|(.*[ ].*)|(\"\")|(.{129,}))$";
         junos:pattern-message "Must be a non-reserved string of 128 characters or less with no spaces.";
       }
     }
     uses apply-advanced;
     leaf ip-address {
       description "ERSPAN Destination IP Address";
       type jt:ipv4addr;
     }
   }
   grouping juniper-sampling-options {
     uses apply-advanced;
     choice enable-disable {
       case case_1 {
         leaf disable {
           description "Disable global sampling instance";
           type empty;
         }
       }
     }
     container traceoptions {
       description "Traffic sampling trace options";
       uses sampling_traceoptions_type;
     }
     leaf sample-once {
       description "Sample the packet for active-monitoring only once";
       type empty;
     }
     leaf pre-rewrite-tos {
       description "Sample the packet retaining tos value before normalization";
       type empty;
     }
     container input {
       description "Traffic Sampling data acquisition";
       uses sampling_input_type;
     }
     container output {
       description "Traffic sampling data disposition";
       status deprecated;
       junos:must "(!(\".. family\"))";
       junos:must-message " 'sampling family <*> ' and 'sampling output' are mutually exclusive";
       junos:must "(\"forwarding-options sampling input\")";
       junos:must-message "Sampling input configuration is not specified";
       uses sampling_output_type;
     }
     container family {
       description "Address family of packets to sample";
       container inet {
         description "Sample IPv4 packets";
         uses apply-advanced;
         choice enable-disable {
           case case_1 {
             leaf disable {
               description "Disable sampling family inet";
               type empty;
             }
           }
         }
         container input {
           description "Settings for sampling of input packets";
           junos:must "(!(\".. .. .. input\"))";
           junos:must-message "instance <*> 'family <*> input' and 'instance <*> input' are mutually exclusive";
           uses sampling_family_input_type;
         }
         container output {
           description "Traffic sampling data disposition";
           junos:must "((!(\"forwarding-options sampling input family inet\") && (!(\"forwarding-options sampling input family inet6\") && !(\"forwarding-options sampling input family mpls\"))))";
           junos:must-message "output configuration mismatch with old deprecated input configuration";
           junos:must "((\".. .. .. input rate\" || \" .. input rate\"))";
           junos:must-message "sampling input rate is not specified";
           junos:must "((\".. .. .. input\" || \".. input\"))";
           junos:must-message "Sampling input configuration is not specified";
           uses sampling_instance_inet_global_output_type;
         }
       }
       container inet6 {
         description "Sample IPv6 packets";
         uses apply-advanced;
         choice enable-disable {
           case case_1 {
             leaf disable {
               description "Disable sampling family inet6";
               type empty;
             }
           }
         }
         container input {
           description "Settings for sampling of input packets";
           junos:must "(!(\".. .. .. input\"))";
           junos:must-message "instance <*> 'family <*> input' and 'instance <*> input' are mutually exclusive";
           uses sampling_family_input_type;
         }
         container output {
           description "Traffic sampling data disposition";
           junos:must "((!(\"forwarding-options sampling input family inet\") && (!(\"forwarding-options sampling input family inet6\") && !(\"forwarding-options sampling input family mpls\"))))";
           junos:must-message "output configuration mismatch with old deprecated input configuration";
           junos:must "((\".. .. .. input\" || \".. input\"))";
           junos:must-message "Sampling input configuration is not specified";
           uses sampling_family_inet6_output_type;
         }
       }
       container mpls {
         description "Sample mpls packets";
         uses apply-advanced;
         choice enable-disable {
           case case_1 {
             leaf disable {
               description "Disable sampling family mpls";
               type empty;
             }
           }
         }
         container input {
           description "Settings for sampling of input packets";
           junos:must "(!(\".. .. .. input\"))";
           junos:must-message "instance <*> 'family <*> input' and 'instance <*> input' are mutually exclusive";
           uses sampling_family_input_type;
         }
         container output {
           description "Traffic sampling data disposition";
           junos:must "((!(\"forwarding-options sampling input family inet\") && (!(\"forwarding-options sampling input family inet6\") && !(\"forwarding-options sampling input family mpls\"))))";
           junos:must-message "output configuration mismatch with old deprecated input configuration";
           junos:must "((\".. .. .. input\" || \".. input\"))";
           junos:must-message "Sampling input configuration is not specified";
           uses sampling_global_mpls_output_type;
         }
       }
     }
     list instance {
       key name;
       ordered-by user;
       description "Instance of sampling parameters";
       leaf name {
         description "Name for sampling instance";
         junos:must "(!(\"forwarding-options port-mirroring instance $$\"))";
         junos:must-message "Instance $$ is also defined under port-mirroring hierarchy";
         type string;
       }
       uses apply-advanced;
       choice enable-disable {
         case case_1 {
           leaf disable {
             description "Disable sampling instance";
             type empty;
           }
         }
       }
       container input {
         description "Traffic Sampling data acquisition";
         uses sampling_instance_input_type;
       }
       container family {
         description "Address family of packets to sample";
         container inet {
           description "Sample IPv4 packets";
           uses apply-advanced;
           choice enable-disable {
             case case_1 {
               leaf disable {
                 description "Disable instance family inet";
                 status deprecated;
                 type empty;
               }
             }
           }
           container input {
             description "Settings for sampling of input packets";
             junos:must "(!(\".. .. .. input\"))";
             junos:must-message "instance <*> 'family <*> input' and 'instance <*> input' are mutually exclusive";
             uses sampling_family_input_type;
           }
           container output {
             description "Traffic sampling data disposition";
             junos:must "((!(\"forwarding-options sampling input family inet\") && (!(\"forwarding-options sampling input family inet6\") && !(\"forwarding-options sampling input family mpls\"))))";
             junos:must-message "output configuration mismatch with old deprecated input configuration";
             junos:must "((\".. .. .. input\" || \".. input\"))";
             junos:must-message "Sampling input configuration is not specified";
             uses sampling_instance_inet_output_type;
           }
         }
         container inet6 {
           description "Sample IPv6 packets";
           uses apply-advanced;
           choice enable-disable {
             case case_1 {
               leaf disable {
                 description "Disable instance family inet6";
                 status deprecated;
                 type empty;
               }
             }
           }
           container input {
             description "Settings for sampling of input packets";
             junos:must "(!(\".. .. .. input\"))";
             junos:must-message "instance <*> 'family <*> input' and 'instance <*> input' are mutually exclusive";
             uses sampling_family_input_type;
           }
           container output {
             description "Traffic sampling data disposition";
             junos:must "((!(\"forwarding-options sampling input family inet\") && (!(\"forwarding-options sampling input family inet6\") && !(\"forwarding-options sampling input family mpls\"))))";
             junos:must-message "output configuration mismatch with old deprecated input configuration";
             junos:must "((\".. .. .. input\" || \".. input\"))";
             junos:must-message "Sampling input configuration is not specified";
             uses sampling_instance_inet6_output_type;
           }
         }
         container mpls {
           description "Sample mpls packets";
           uses apply-advanced;
           choice enable-disable {
             case case_1 {
               leaf disable {
                 description "Disable instance family mpls";
                 status deprecated;
                 type empty;
               }
             }
           }
           container input {
             description "Settings for sampling of input packets";
             junos:must "(!(\".. .. .. input\"))";
             junos:must-message "instance <*> 'family <*> input' and 'instance <*> input' are mutually exclusive";
             uses sampling_family_input_type;
           }
           container output {
             description "Traffic sampling data disposition";
             junos:must "((!(\"forwarding-options sampling input family inet\") && (!(\"forwarding-options sampling input family inet6\") && !(\"forwarding-options sampling input family mpls\"))))";
             junos:must-message "output configuration mismatch with old deprecated input configuration";
             junos:must "((\".. .. .. input\" || \".. input\"))";
             junos:must-message "Sampling input configuration is not specified";
             uses sampling_instance_mpls_output_type;
           }
         }
         container vpls {
           description "Sample vpls packets";
           status deprecated;
           uses apply-advanced;
           choice enable-disable {
             case case_1 {
               leaf disable {
                 description "Disable instance family vpls";
                 type empty;
               }
             }
           }
           container input {
             description "Settings for sampling of input packets";
             junos:must "(!(\".. .. .. input\"))";
             junos:must-message "instance <*> 'family <*> input' and 'instance <*> input' are mutually exclusive";
             uses sampling_family_input_type;
           }
           container output {
             description "Traffic sampling data disposition";
             junos:must "((\".. .. .. input\" || \".. input\"))";
             junos:must-message "Sampling input configuration is not specified";
             uses sampling_instance_vpls_output_type;
           }
         }
         container bridge {
           junos:must "(!(\".. .. family vpls\"))";
           junos:must-message "bridge and vpls families are mutually exclusive";
           description "Sample bridge packets";
           uses apply-advanced;
           choice enable-disable {
             case case_1 {
               leaf disable {
                 description "Disable instance family bridge";
                 type empty;
               }
             }
           }
           container input {
             description "Settings for sampling of input packets";
             junos:must "(!(\".. .. .. input\"))";
             junos:must-message "instance <*> 'family <*> input' and 'instance <*> input' are mutually exclusive";
             uses sampling_family_input_type;
           }
           container output {
             description "Traffic sampling data disposition";
             junos:must "((\".. .. .. input\" || \".. input\"))";
             junos:must-message "Sampling input configuration is not specified";
             uses sampling_instance_bridge_output_type;
           }
         }
       }
     }
     container jflow-service {
       description "Jflow service configuration";
       uses apply-advanced;
       container traceoptions {
         description "Jflow service trace options";
         uses jflow_service_traceoptions;
       }
     }
     container route-record {
       description "Sampling route record configuration";
       uses apply-advanced;
       container traceoptions {
         description "Sampling route record trace options";
         uses route_record_traceoptions;
       }
     }
   }
   grouping jflow_service_traceoptions {
     description "Traceoptions for jflow-service";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Area of jflow-service to enable debuging output";
       leaf name {
         type enumeration {
           enum "parse" {
             description "Trace parsing code";
           }
           enum "rtsock" {
             description "Trace rtsock code";
           }
           enum "sm" {
             description "Trace State machine code";
           }
           enum "all" {
             description "Trace all area of jflow-service code";
           }
         }
       }
     }
   }
   grouping junos_hash_key {
     description "Select data used in the hash key";
     uses apply-advanced;
     container family {
       description "Protocol family";
       container fcoe {
         description "FCoE protocol family";
         uses apply-advanced;
         container ethernet-interfaces {
           description "FCoE hash-key configuration on ethernet interfaces";
           uses apply-advanced;
           leaf oxid {
             description "Originator Exchange ID";
             type enumeration {
               enum "enable" {
                 description "Include Originator Exchange ID in the hash key";
               }
               enum "disable" {
                 description "Do not include Originator Exchange ID in the hash key";
               }
             }
           }
         }
         container fabric-interfaces {
           description "FCoE hash-key configuration on fabric interfaces";
           uses apply-advanced;
           leaf oxid {
             description "Originator Exchange ID";
             type enumeration {
               enum "enable" {
                 description "Include Originator Exchange ID in the hash key";
               }
               enum "disable" {
                 description "Do not include Originator Exchange ID in the hash key";
               }
             }
           }
         }
       }
       container inet {
         description "IPv4 protocol family";
         uses apply-advanced;
         container layer-3 {
           presence "enable layer-3";
           description "Include Layer 3 (IP) data in the hash key";
           uses apply-advanced;
           leaf destination-address {
             description "Include IP destination address in the hash key";
             type empty;
           }
         }
         container layer-4 {
           presence "enable layer-4";
           description "Include Layer 4 (TCP or UDP) data in the hash key";
           uses apply-advanced;
           leaf gtp-tunnel-endpoint-identifier {
             description "Include GTP TEID in the hash key";
             type empty;
           }
         }
         container symmetric-hash {
           presence "enable symmetric-hash";
           junos:must "((\"forwarding-options hash-key family inet layer-3\" || \"forwarding-options hash-key family inet layer-4\"))";
           junos:must-message "layer-3 and/or layer-4 to be configured for symmetric/complement Hash";
           description "Create symmetric hash-key with source & destination ports";
           uses apply-advanced;
           leaf complement {
             description "Create complement of symmetric hash-key";
             type empty;
           }
         }
       }
       container inet6 {
         description "IPv6 protocol family";
         uses apply-advanced;
         container layer-3 {
           presence "enable layer-3";
           description "Include Layer 3 (IP) data in the hash key";
           uses apply-advanced;
           leaf destination-address {
             description "Include IP destination address in the hash key";
             type empty;
           }
           leaf incoming-interface-index {
             description "Include incoming interface index in the hash key";
             type empty;
           }
           leaf next-header {
             description "Include IP Next Header field in the hash key";
             type empty;
           }
           leaf source-address {
             description "Include IP source address in the hash key";
             type empty;
           }
           leaf traffic-class {
             description "Include Traffic Class field in the hash key";
             type empty;
           }
           leaf ipv6-flow-label {
             description "Include IPV6 flow label field in the hash key";
             type empty;
           }
         }
         container layer-4 {
           presence "enable layer-4";
           description "Include Layer 4 (TCP or UDP) data in the hash key";
           uses apply-advanced;
           leaf destination-port {
             description "Include IP destination port in the hash key";
             type empty;
           }
           leaf source-port {
             description "Include IP source port in the hash key";
             type empty;
           }
           leaf gtp-tunnel-endpoint-identifier {
             description "Include GTP TEID in the hash key";
             type empty;
           }
         }
       }
       container mpls {
         description "MPLS protocol family";
         uses apply-advanced;
         choice label {
           case case_1 {
             leaf label-1 {
               description "Include the first MPLS label in the hash key";
               type empty;
             }
           }
           case case_2 {
             leaf all-labels {
               description "Include all MPLS labels in hash key";
               type empty;
             }
           }
           case case_3 {
             leaf no-labels {
               description "Exclude all MPLS labels from hash key";
               type empty;
             }
           }
           case case_4 {
             leaf bottom-label-1 {
               description "Include the first MPLS label from bottom-of-stack in the hash key";
               type empty;
             }
           }
         }
         leaf label-2 {
           description "Include the second MPLS label in the hash key";
           junos:must "(\".. label-1\")";
           junos:must-message "Must also specify label 1;";
           type empty;
         }
         leaf label-3 {
           description "Include the third MPLS label in the hash key";
           junos:must "(\".. label-2\")";
           junos:must-message "Must also specify label 2;";
           type empty;
         }
         leaf bottom-label-2 {
           description "Include the second MPLS label from bottom-of-stack in the hash key";
           junos:must "(\".. bottom-label-1\")";
           junos:must-message "Must also specify bottom-label-1. Cannot use top-of-stack labels.";
           type empty;
         }
         leaf bottom-label-3 {
           description "Include the third MPLS label from bottom-of-stack in the hash key";
           junos:must "(\".. bottom-label-2\")";
           junos:must-message "Must also specify bottom-label-2. Cannot use top-of-stack labels.";
           type empty;
         }
         leaf no-label-1-exp {
           description "Omit EXP bits of first MPLS label from the hash key";
           junos:must "((\".. label-1\" || \".. no-labels\"))";
           junos:must-message "Either label-1 or no-labels statement is mandatory";
           type empty;
         }
         container payload {
           junos:must "((\".. label-1\" || (\".. no-labels\" || (\".. all-labels\" || \".. bottom-label-1\"))))";
           junos:must-message "Either label-1, bottom-label-1, all-labels or no-labels statement is mandatory";
           description "Include payload data in the hash key";
           uses apply-advanced;
           container ether-pseudowire {
             presence "enable ether-pseudowire";
             description "Load-balance IP over ethernet PW";
             uses apply-advanced;
             leaf zero-control-word {
               description "MPLS ether-pseudowire payload with zero-control-word preceding ethernet packet";
               type empty;
             }
           }
           container ip {
             presence "enable ip";
             description "Include IPv4 or IPv6 payload data in the hash key";
             uses apply-advanced;
             choice layer-4-select {
               case case_1 {
                 choice ip-payload {
                   case case_1 {
                     leaf layer-3-only {
                       description "Include only layer-3 IP information";
                       type empty;
                     }
                   }
                   case case_2 {
                     leaf enable {
                       description "Include layer3/4 IP payload in the hash key";
                       type empty;
                     }
                   }
                   case case_3 {
                     leaf disable {
                       description "Exclude layer3/4 IP payload in the hash key";
                       type empty;
                     }
                   }
                 }
               }
               case case_2 {
                 container port-data {
                   presence "enable port-data";
                   uses apply-advanced;
                   leaf source-msb {
                     description "Include the most significant byte of the source port";
                     type empty;
                   }
                   leaf source-lsb {
                     description "Include the least significant byte of the source port";
                     type empty;
                   }
                   leaf destination-msb {
                     description "Include the most significant byte of the destination port";
                     type empty;
                   }
                   leaf destination-lsb {
                     description "Include the least significant byte of the destination port";
                     type empty;
                   }
                 }
               }
             }
           }
         }
       }
       container multiservice {
         description "Multiservice protocol family";
         uses apply-advanced;
         leaf source-mac {
           description "Include source MAC address in hash key";
           type empty;
         }
         leaf destination-mac {
           description "Include destination MAC address in hash key";
           type empty;
         }
         leaf label-1 {
           description "Include the first MPLS label in the hash key";
           type empty;
         }
         leaf label-2 {
           description "Include the second MPLS label in the hash key";
           junos:must "(\".. label-1\")";
           junos:must-message "Must also specify label 1;";
           type empty;
         }
         container payload {
           description "Include payload data in the hash key";
           uses apply-advanced;
           container ip {
             description "Include IPv4 payload data in the hash key";
             uses apply-advanced;
             container layer-3 {
               presence "enable layer-3";
               description "Include layer-3 ip info for VPLS/Bridge";
               uses apply-advanced;
               choice layer-3-options {
                 case case_1 {
                   leaf source-ip-only {
                     description "Include source IP only in hash-key";
                     type empty;
                   }
                 }
                 case case_2 {
                   leaf destination-ip-only {
                     description "Include desintation IP only in hash-key";
                     type empty;
                   }
                 }
               }
             }
             leaf layer-4 {
               description "Include layer-4 IP information for VPLS/Bridge";
               type empty;
             }
             leaf layer-3-only {
               description "Include only layer-3 IP information";
               type empty;
             }
           }
         }
         container symmetric-hash {
           presence "enable symmetric-hash";
           junos:must "((\"forwarding-options hash-key family multiservice payload\" || (\"forwarding-options hash-key family multiservice source-mac\" || \"forwarding-options hash-key family multiservice destination-mac\")))";
           junos:must-message "Payload and/or source-MAC and/or destination-MAC to be configured for symmetric/complement Hash";
           description "Create a/symmetric hash-key with any attributes";
           uses apply-advanced;
           leaf complement {
             description "Create complement of symmetric hash-key";
             type empty;
           }
         }
       }
     }
   }
   grouping layer2_pm_family_output_type {
     uses apply-advanced;
     choice interface-or-next-hop-index {
       case case_1 {
         leaf interface {
           description "Interface through which to send sampled traffic";
           type union {
             type jt:interface-name;
             type string {
               pattern "<.*>|$.*";
             }
           }
         }
       }
       case case_2 {
         leaf next-hop-group {
           description "Next-hop-group through which to send port-mirror traffic";
           junos:must "(!(\".. no-filter-check\"))";
           junos:must-message "no-filter-check is not allowed with next-hop-group";
           junos:must "(\"forwarding-options next-hop-group $$ group-type layer-2\")";
           junos:must-message "Referenced next-hop-group must be defined as layer-2 group";
           type string;
         }
       }
       case case_3 {
         list routing-instance {
           key name;
           description "Routing instances";
           max-elements 1;
           uses layer2_pm_output-routing-instance-type;
         }
       }
       case case_4 {
         list vlan {
           key name;
           description "Outgoing VLAN for mirrored packets";
           max-elements 1;
           uses pm-rspan-vlan;
         }
       }
       case case_5 {
         list bridge-domain {
           key name;
           description "Outgoing bridge-domain for mirrored packets";
           max-elements 1;
           uses pm-rspan-bridge-domain;
         }
       }
     }
     leaf no-filter-check {
       description "Do not check for filters on port-mirroring interface";
       type empty;
     }
   }
   grouping layer2_pm_output-routing-instance-type {
     leaf name {
       description "Routing instance name";
       type string {
         junos:posix-pattern "!^((__.*__)|(all)|(.*[ ].*)|(\"\")|(.{129,}))$";
         junos:pattern-message "Must be a non-reserved string of 128 characters or less with no spaces.";
       }
     }
     uses apply-advanced;
     list vlan {
       key name;
       description "Outgoing VLAN for mirrored packets";
       max-elements 1;
       uses pm-rspan-vlan;
     }
     list bridge-domain {
       key name;
       description "Outgoing bridge-domain for mirrored packets";
       max-elements 1;
       uses pm-rspan-bridge-domain;
     }
   }
   grouping macro-data-type {
     leaf name {
       description "Keyword part of the keyword-value pair";
       type string;
     }
     leaf value {
       description "Value part of the keyword-value pair";
       type string;
     }
   }
   grouping monitoring_input_type {
     uses apply-advanced;
     list interface {
       key name;
       ordered-by user;
       leaf name {
         description "Interface which will be monitored";
         type union {
           type jt:interface-name;
           type string {
             pattern "<.*>|$.*";
           }
         }
       }
       uses apply-advanced;
     }
   }
   grouping monitoring_output_type {
     uses apply-advanced;
     leaf export-format {
       description "Format for sending monitoring information";
       type enumeration {
         enum "cflowd-version-5" {
           description "Export in cflowd version 5 format";
         }
       }
     }
     leaf destination-address {
       description "Address to which monitored packets will be sent";
       status deprecated;
       type jt:ipv4addr;
     }
     leaf destination-port {
       description "Port to which monitored packets will be sent";
       status deprecated;
       type union {
         type uint16;
         type string {
           pattern "<.*>|$.*";
         }
       }
     }
     leaf source-address {
       description "Address to use for generating monitored packets";
       status deprecated;
       type jt:ipv4addr;
     }
     leaf flow-active-timeout {
       description "Interval after which an active flow is exported";
       default "1800";
       units "seconds";
       type union {
         type string {
           pattern "<.*>|$.*";
         }
         type uint32 {
           range "60 .. 1800";
         }
       }
     }
     leaf flow-inactive-timeout {
       description "Interval of inactivity that marks a flow inactive";
       default "60";
       units "seconds";
       type union {
         type string {
           pattern "<.*>|$.*";
         }
         type uint32 {
           range "15 .. 1800";
         }
       }
     }
     leaf flow-export-destination {
       description "Destination for flow export";
       type enumeration {
         enum "collector-pic" {
           description "Send flow information to collector PIC";
         }
         enum "cflowd-collector" {
           description "Send flow information to cflowd collector";
         }
       }
     }
     list cflowd {
       key name;
       description "Collector destination where flow records are sent";
       junos:must "(!(\".. flow-export-destination collector-pic\"))";
       junos:must-message "cflowd cannot be configured when flow collection mode is set";
       uses cflowd_monitoring_type;
     }
     list interface {
       key name;
       description "Interfaces used to send monitored information";
       uses monitor_export_intf_type;
     }
   }
   grouping cflowd_monitoring_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       junos:must "(\".. .. inline-jflow\")";
       junos:must-message "DSCP can be configured for inline-jflow";
       type union {
         type string {
           pattern "<.*>|$.*";
         }
         type uint8 {
           range "0 .. 63";
         }
       }
     }
     leaf forwarding-class {
       description "Forwarding-class for exported jflow packets, applicable only for inline-jflow";
       junos:must "(\".. .. inline-jflow\")";
       junos:must-message "forwarding-class can be configured for inline-jflow";
       type string {
         length "1 .. 64";
       }
     }
     leaf routing-instance {
       description "Name of routing instance on which flow collector is reachable";
       junos:must "(\".. .. inline-jflow\")";
       junos:must-message "Routing Instances can be configured for inline-jflow";
       junos:must "(\"routing-instances $$ instance-type vrf\")";
       junos:must-message "routing instance should be defined and should be of type Virtual routing forwarding instance(VRF)";
       type string;
     }
   }
   grouping monitor_export_intf_type {
     leaf name {
       description "Interface to be used for sending monitored information";
       type union {
         type jt:interface-name;
         type string {
           pattern "<.*>|$.*";
         }
       }
     }
     uses apply-advanced;
     leaf engine-id {
       description "Identity (number) of this monitoring interface";
       type union {
         type uint8;
         type string {
           pattern "<.*>|$.*";
         }
       }
     }
     leaf engine-type {
       description "Type (number) of this monitoring interface";
       type union {
         type uint8;
         type string {
           pattern "<.*>|$.*";
         }
       }
     }
     leaf input-interface-index {
       description "Input interface index for records from this interface";
       default "0";
       type union {
         type uint32;
         type string {
           pattern "<.*>|$.*";
         }
       }
     }
     leaf output-interface-index {
       description "Output interface index for records from this interface";
       default "0";
       type union {
         type uint32;
         type string {
           pattern "<.*>|$.*";
         }
       }
     }
     leaf source-address {
       description "Address to use for generating monitored packets";
       type jt:ipv4addr;
     }
   }
   grouping mpls_pm_family_output_type {
     uses apply-advanced;
     leaf server-profile {
       description "Server profile name";
       junos:must "((\"services hosted-services server-profile $$\" && (\"services hosted-services server-profile $$ server-address\" && \"services hosted-services server-profile $$ client-address\")))";
       junos:must-message "Only complete server profiles configured under [services hosted-services server-profile] can be configured here";
       type string {
         length "3 .. 32";
       }
     }
   }
   grouping next_hop_group_intf_type {
     leaf name {
       description "Interface through which to send sampled traffic";
       type union {
         type jt:interface-name;
         type string {
           pattern "<.*>|$.*";
         }
       }
     }
     uses apply-advanced;
     list next-hop {
       key name;
       ordered-by user;
       description "Address of next hop through which to send sampled traffic";
       junos:must "((\".. .. group-type inet\" || \".. .. group-type inet6\"))";
       junos:must-message "Next-hop can be specified only for group-type inet or inet6";
       uses next_hop_type;
     }
   }
   grouping next_hop_subgroup_intf_type {
     leaf name {
       description "Interface through which to send sampled traffic";
       type union {
         type jt:interface-name;
         type string {
           pattern "<.*>|$.*";
         }
       }
     }
     uses apply-advanced;
     list next-hop {
       key name;
       ordered-by user;
       description "Address of next hop through which to send sampled traffic";
       junos:must "((\".. .. .. group-type inet\" || \".. .. .. group-type inet6\"))";
       junos:must-message "Next-hop can be specified only for group-type inet or inet6";
       uses next_hop_type;
     }
   }
   grouping next_hop_type {
     description "Address of next hop through which to send sampled traffic";
     leaf name {
       type jt:ipaddr;
     }
     uses apply-advanced;
   }
   grouping override-type {
     description "DHCP override processing";
     uses apply-advanced;
     choice allow-snooped-clients-choice {
       leaf allow-snooped-clients {
         description "Allow client creation from snooped PDUs";
         type empty;
       }
       leaf no-allow-snooped-clients {
         description "Don't allow client creation from snooped PDUs";
         type empty;
       }
     }
     leaf allow-no-end-option {
       description "Allow packets without end-of-option";
       type empty;
     }
     leaf always-write-giaddr {
       description "Overwrite existing 'giaddr' field, when present";
       type empty;
     }
     container always-write-option-82 {
       description "Overwrite existing value of option 82, when present";
       presence "enable always-write-option-82";
       uses write-option-82-type;
     }
     leaf user-defined-option-82 {
       description "Set user defined description for option-82";
       type string {
         length "1 .. 252";
       }
     }
     leaf layer2-unicast-replies {
       description "Do not broadcast client responses";
       junos:must "(!(\".. no-unicast-replies\"))";
       junos:must-message "layer2-unicast-replies cannot be configured with no-unicast-replies";
       type empty;
     }
     leaf trust-option-82 {
       description "Trust options-82 option";
       type empty;
     }
     leaf delay-authentication {
       description "Delay subscriber authentication in DHCP protocol processing until request packet";
       type empty;
     }
     leaf disable-relay {
       description "Disable DHCP relay processing";
       type empty;
     }
     leaf no-bind-on-request {
       description "Do not bind if stray DHCP request is received";
       type empty;
     }
     leaf interface-client-limit {
       description "Limit the number of client allowed on an interface";
       type union {
         type string {
           pattern "<.*>|$.*";
         }
         type uint32 {
           range "1 .. 500000";
         }
       }
     }
     leaf no-arp {
       description "Disable DHCP ARP table population";
       status deprecated;
       junos:must "((!(\".. route-suppression destination\") && !(\".. route-suppression access-internal\")))";
       junos:must-message "Cannot specify route-suppression with overrides no-arp";
       type empty;
     }
     leaf bootp-support {
       description "Allows relay of bootp req and reply";
       type empty;
     }
     leaf dual-stack {
       description "Dual stack group to use.";
       type string {
         length "1 .. 64";
       }
     }
     container client-discover-match {
       presence "enable client-discover-match";
       description "Use secondary match criteria for DISCOVER PDU";
       choice match-with {
         case case_1 {
           leaf option60-and-option82 {
             description "Use option 60 and option 82";
             type empty;
           }
         }
         case case_2 {
           leaf incoming-interface {
             description "Use incoming interface";
             type empty;
           }
         }
       }
     }
     container proxy-mode {
       presence "enable proxy-mode";
       description "Put the relay in proxy mode";
     }
     leaf asymmetric-lease-time {
       description "Use a reduced lease time for the client. In seconds";
       units "seconds";
       type union {
         type string {
           pattern "<.*>|$.*";
         }
         type uint32 {
           range "600 .. 86400";
         }
       }
     }
     container replace-ip-source-with {
       description "Replace IP source address in request and release packets";
       choice replacement-type {
         case case_1 {
           leaf giaddr {
             description "Replace IP source address with giaddr";
             type empty;
           }
         }
       }
     }
     leaf send-release-on-delete {
       description "Always send RELEASE to the server when a binding is deleted";
       type empty;
     }
     leaf relay-source {
       description "Interface for relay source";
       type union {
         type jt:interface-name;
         type string {
           pattern "<.*>|$.*";
         }
       }
     }
     leaf delete-binding-on-renegotiation {
       description "Delete binding on rengotiation";
       type empty;
     }
   }
   grouping packet_accounting_output_type {
     uses apply-advanced;
     leaf aggregate-export-interval {
       description "Interval of exporting aggregate accounting information";
       default "90";
       units "seconds";
       type union {
         type string {
           pattern "<.*>|$.*";
         }
         type uint32 {
           range "90 .. 1800";
         }
       }
     }
     leaf flow-inactive-timeout {
       description "Interval of inactivity that marks a flow inactive";
       default "60";
       units "seconds";
       type union {
         type string {
           pattern "<.*>|$.*";
         }
         type uint32 {
           range "15 .. 1800";
         }
       }
     }
     leaf flow-active-timeout {
       description "Interval after which an active flow is exported";
       default "1800";
       units "seconds";
       type union {
         type string {
           pattern "<.*>|$.*";
         }
         type uint32 {
           range "60 .. 1800";
         }
       }
     }
     list cflowd {
       key name;
       description "Cflowd collector where flow records are sent";
       junos:must "(all \".. interface <*> source-address\")";
       junos:must-message "'forwarding-options accounting output interface source-address' must be specified with 'flow-server' and 'interface'";
       junos:must "(any \".. interface <*>\")";
       junos:must-message "'forwarding-options accounting output interface' must be specified";
       uses cflowd_packet_accounting_type;
     }
     list interface {
       key name;
       description "Interfaces used to send monitored information";
       uses packet_export_intf_type;
     }
   }
   grouping cflowd_packet_accounting_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       junos:must "(\".. .. inline-jflow\")";
       junos:must-message "DSCP can be configured for inline-jflow";
       type union {
         type string {
           pattern "<.*>|$.*";
         }
         type uint8 {
           range "0 .. 63";
         }
       }
     }
     leaf forwarding-class {
       description "Forwarding-class for exported jflow packets, applicable only for inline-jflow";
       junos:must "(\".. .. inline-jflow\")";
       junos:must-message "forwarding-class can be configured for inline-jflow";
       type string {
         length "1 .. 64";
       }
     }
     leaf routing-instance {
       description "Name of routing instance on which flow collector is reachable";
       junos:must "(\".. .. inline-jflow\")";
       junos:must-message "Routing Instances can be configured for inline-jflow";
       junos:must "(\"routing-instances $$ instance-type vrf\")";
       junos:must-message "routing instance should be defined and should be of type Virtual routing forwarding instance(VRF)";
       type string;
     }
     leaf version {
       description "Format of exported cflowd aggregates";
       default "5";
       type enumeration {
         enum "5" {
           description "Export cflowd aggregates in version 5 format";
         }
         enum "8" {
           description "Export cflowd aggregates in version 8 format";
         }
       }
     }
     leaf autonomous-system-type {
       description "Type of autonomous system number to export";
       default "origin";
       type enumeration {
         enum "origin" {
           description "Export origin-AS numbers";
         }
         enum "peer" {
           description "Export peer-AS numbers";
         }
       }
     }
     container aggregation {
       description "Aggregations to perform for exported flows (version 8 only)";
       uses aggregation_type;
     }
   }
   grouping aggregation_type {
     uses apply-advanced;
     leaf autonomous-system {
       description "Aggregate by autonomous system number";
       type empty;
     }
     leaf protocol-port {
       description "Aggregate by protocol and port number";
       type empty;
     }
     leaf source-prefix {
       description "Aggregate by source prefix";
       type empty;
     }
     leaf destination-prefix {
       description "Aggregate by destination prefix";
       type empty;
     }
     container source-destination-prefix {
       presence "enable source-destination-prefix";
       description "Aggregate by source and destination prefix";
       uses apply-advanced;
       leaf caida-compliant {
         description "Compatible with Caida record format for prefix aggregation (v8)";
         type empty;
       }
     }
   }
   grouping packet_export_intf_type {
     leaf name {
       description "Interfaces used to send monitored information";
       type union {
         type jt:interface-unit;
         type string {
           pattern "<.*>|$.*";
         }
       }
     }
     uses apply-advanced;
     leaf engine-id {
       description "Identity (number) of this accounting interface";
       type union {
         type uint8;
         type string {
           pattern "<.*>|$.*";
         }
       }
     }
     leaf engine-type {
       description "Type (number) of this accounting interface";
       type union {
         type uint8;
         type string {
           pattern "<.*>|$.*";
         }
       }
     }
     leaf source-address {
       description "Address to use for generating monitored packets";
       type jt:ipaddr;
     }
     container export-port {
       description "Jflow export port configuration";
       presence "enable export-port";
       uses export_port_address_type;
     }
   }
   grouping export_port_address_type {
     uses apply-advanced;
     leaf address {
       description "Address to use for jflow export port";
       type jt:ipv4prefix;
     }
     leaf gateway {
       description "Gateway address to reach jflow server";
       type jt:ipv4addr;
     }
   }
   grouping pm-rspan-bridge-domain {
     description "RSPAN bridge-domain for pm";
     leaf name {
       description "Bridge domain name or VLAN id";
       type string {
         junos:posix-pattern "^([[:alpha:]][[:alnum:]_.-]+)|^([1-9][0-9]{0,2}|[1-3][0-9]{3}|40[0-8][0-9]|409[0-4])$";
         junos:pattern-message "Must be a valid VLAN name or VLAN tag";
       }
     }
     uses apply-advanced;
   }
   grouping pm-rspan-vlan {
     description "RSPAN vlan for pm";
     leaf name {
       description "VLAN name or VLAN id";
       type string {
         junos:posix-pattern "^([[:alpha:]][[:alnum:]_.-]+)|^([1-9][0-9]{0,2}|[1-3][0-9]{3}|40[0-8][0-9]|409[0-4])$";
         junos:pattern-message "Must be a valid VLAN name or VLAN tag";
       }
     }
     uses apply-advanced;
     leaf no-tag {
       description "Removes extra RSPAN tag from mirrored packets";
       type empty;
     }
   }
   grouping pm_family_input_type {
     description "Input options for port mirroring";
     uses apply-advanced;
     leaf rate {
       description "Ratio of packets to be sampled (1 out of N)";
       type union {
         type string {
           pattern "<.*>|$.*";
         }
         type uint16 {
           range "1 .. 65535";
         }
       }
     }
     leaf run-length {
       description "Number of samples after initial trigger";
       type union {
         type string {
           pattern "<.*>|$.*";
         }
         type uint32 {
           range "0 .. 20";
         }
       }
     }
     leaf maximum-packet-length {
       description "Maximum length of the mirrored packet";
       default "0";
       units "bytes";
       type union {
         type string {
           pattern "<.*>|$.*";
         }
         type uint32 {
           range "0 .. 9216";
         }
       }
     }
   }
   grouping relay-bulk-leasequery-v4-type {
     junos:must "(\".. overrides always-write-option-82\")";
     junos:must-message "Must configure [overrides always-write-option-82] to overwrite circuit-id for bulk-leasequery";
     junos:must "((\".. relay-option-82 circuit-id\" && !((\".. relay-option-82 circuit-id use-interface-description\" || \".. relay-option-82 circuit-id require-interface-description\"))))";
     junos:must-message "Must configure [relay-option-82 circuit-id] without description to insert circuit-id for bulk-leasequery";
     description "Configure bulk leasequery";
     uses apply-advanced;
     leaf attempts {
       description "Number of retry attempts";
       default "360";
       type union {
         type string {
           pattern "<.*>|$.*";
         }
         type uint32 {
           range "1 .. 720";
         }
       }
     }
     leaf timeout {
       description "Number of seconds";
       default "10";
       units "seconds";
       type union {
         type string {
           pattern "<.*>|$.*";
         }
         type uint32 {
           range "1 .. 10";
         }
       }
     }
   }
   grouping relay-bulk-leasequery-v6-type {
     junos:must "(\".. relay-agent-interface-id\")";
     junos:must-message "Must configure [relay-agent-interface-id] to insert interface-id for bulk-leasequery";
     description "Configure bulk leasequery";
     uses apply-advanced;
     leaf attempts {
       description "Number of retry attempts";
       default "6";
       type union {
         type string {
           pattern "<.*>|$.*";
         }
         type uint32 {
           range "1 .. 10";
         }
       }
     }
     leaf timeout {
       description "Number of seconds";
       default "10";
       units "seconds";
       type union {
         type string {
           pattern "<.*>|$.*";
         }
         type uint32 {
           range "1 .. 10";
         }
       }
     }
     container trigger {
       description "Trigger for bulk leasequery";
       leaf automatic {
         description "Trigger automatically";
         type empty;
       }
     }
   }
   grouping relay-leasequery-type {
     description "Configure leasequery";
     uses apply-advanced;
     leaf attempts {
       description "Number of retry attempts";
       default "6";
       type union {
         type string {
           pattern "<.*>|$.*";
         }
         type uint32 {
           range "1 .. 10";
         }
       }
     }
     leaf timeout {
       description "Number of seconds";
       default "10";
       units "seconds";
       type union {
         type string {
           pattern "<.*>|$.*";
         }
         type uint32 {
           range "1 .. 10";
         }
       }
     }
   }
   grouping relay-option-60-type-group {
     description "DHCP option-60 processing";
     uses apply-advanced;
     container vendor-option {
       description "Add vendor option";
       uses apply-advanced;
       container equals {
         description "Option 60 equals";
         uses relay-option-60-match-group;
       }
       container not-equals {
         description "Option 60 does not equal";
         status deprecated;
         uses relay-option-60-match-group;
       }
       container starts-with {
         description "Option 60 starts with";
         uses relay-option-60-match-group;
       }
       choice server-group-choice {
         case case_1 {
           leaf default-relay-server-group {
             description "Name of DHCP relay server group when match is not made";
             junos:must "(\".. .. .. .. server-group $$\")";
             junos:must-message "Referenced group must be defined under [edit dhcp-relay server-group]";
             type string {
               length "1 .. 64";
             }
           }
         }
         case case_2 {
           leaf default-local-server-group {
             description "Name of DHCP local server group when match is not made";
             junos:must "(\".. .. .. .. .. .. system services dhcp-local-server group $$\")";
             junos:must-message "Referenced group must be defined under [edit system services dhcp-local-server group]";
             type string {
               length "1 .. 64";
             }
           }
         }
         case case_3 {
           leaf drop {
             description "Discard when a match is not made";
             type empty;
           }
         }
         case case_4 {
           leaf forward-only {
             description "Forward without subscriber services when a match is not made";
             type empty;
           }
         }
       }
     }
   }
   grouping relay-option-60-match-group {
     uses apply-advanced;
     list ascii {
       key name;
       description "ASCII string";
       leaf name {
         description "ASCII string";
         type string {
           length "1 .. 256";
         }
       }
       uses apply-advanced;
       choice server-group-choice {
         case case_1 {
           leaf relay-server-group {
             description "Name of DHCP relay server group when match is made";
             junos:must "(\".. .. .. .. .. .. server-group $$\")";
             junos:must-message "Referenced group must be defined under [edit forwarding options dhcp-relay server-group]";
             type string {
               length "1 .. 64";
             }
           }
         }
         case case_2 {
           leaf local-server-group {
             description "Name of DHCP local server group when match is made";
             junos:must "(\".. .. .. .. .. .. .. .. system services dhcp-local-server group $$\")";
             junos:must-message "Referenced group must be defined under [edit system services dhcp-local-server group]";
             type string {
               length "1 .. 64";
             }
           }
         }
         case case_3 {
           leaf drop {
             description "Discard when a match is made";
             type empty;
           }
         }
         case case_4 {
           leaf forward-only {
             description "Forward without subscriber services when a match is made";
             type empty;
           }
         }
       }
     }
     list hexadecimal {
       key name;
       description "Hexadecimal string";
       leaf name {
         description "Hexadecimal string";
         type string {
           length "1 .. 512";
           junos:posix-pattern "^[[:xdigit:]]+$";
           junos:pattern-message "Must be hexadecimal digits (0-9, a-f, A-F)";
         }
       }
       uses apply-advanced;
       choice server-group-choice {
         case case_1 {
           leaf relay-server-group {
             description "Name of DHCP relay server group when match is made";
             junos:must "(\".. .. .. .. .. .. server-group $$\")";
             junos:must-message "Referenced group must be defined under [edit forwarding-options dhcp-relay server-group]";
             type string {
               length "1 .. 64";
             }
           }
         }
         case case_2 {
           leaf local-server-group {
             description "Name of DHCP local server group when match is made";
             junos:must "(\".. .. .. .. .. .. .. .. system services dhcp-local-server group $$\")";
             junos:must-message "Referenced group must be defined under [edit system services dhcp-local-server group]";
             type string {
               length "1 .. 64";
             }
           }
         }
         case case_3 {
           leaf drop {
             description "Discard when a match is made";
             type empty;
           }
         }
         case case_4 {
           leaf forward-only {
             description "Forward without subscriber services when a match is made";
             type empty;
           }
         }
       }
     }
   }
   grouping relay-option-60-type-top {
     description "DHCP option-60 processing";
     uses apply-advanced;
     container vendor-option {
       description "Add vendor option";
       uses apply-advanced;
       container equals {
         description "Option 60 equals";
         uses relay-option-60-match-top;
       }
       container not-equals {
         description "Option 60 does not equal";
         status deprecated;
         uses relay-option-60-match-top;
       }
       container starts-with {
         description "Option 60 starts with";
         uses relay-option-60-match-top;
       }
       choice server-group-choice {
         case case_1 {
           leaf default-relay-server-group {
             description "Name of DHCP relay server group when match is not made";
             junos:must "(\".. .. .. server-group $$\")";
             junos:must-message "Referenced group must be defined under [edit dhcp-relay server-group]";
             type string {
               length "1 .. 64";
             }
           }
         }
         case case_2 {
           leaf default-local-server-group {
             description "Name of DHCP local server group when match is not made";
             junos:must "(\".. .. .. .. .. system services dhcp-local-server group $$\")";
             junos:must-message "Referenced group must be defined under [edit system services dhcp-local-server group]";
             type string {
               length "1 .. 64";
             }
           }
         }
         case case_3 {
           leaf drop {
             description "Discard when a match is not made";
             type empty;
           }
         }
         case case_4 {
           leaf forward-only {
             description "Forward without subscriber services when a match is not made";
             type empty;
           }
         }
       }
     }
   }
   grouping relay-option-60-match-top {
     uses apply-advanced;
     list ascii {
       key name;
       description "ASCII string";
       leaf name {
         description "ASCII string";
         type string {
           length "1 .. 256";
         }
       }
       uses apply-advanced;
       choice server-group-choice {
         case case_1 {
           leaf relay-server-group {
             description "Name of DHCP relay server group when match is made";
             junos:must "(\".. .. .. .. .. server-group $$\")";
             junos:must-message "Referenced group must be defined under [edit forwarding options dhcp-relay server-group]";
             type string {
               length "1 .. 64";
             }
           }
         }
         case case_2 {
           leaf local-server-group {
             description "Name of DHCP local server group when match is made";
             junos:must "(\".. .. .. .. .. .. .. system services dhcp-local-server group $$\")";
             junos:must-message "Referenced group must be defined under [edit system services dhcp-local-server group]";
             type string {
               length "1 .. 64";
             }
           }
         }
         case case_3 {
           leaf drop {
             description "Discard when a match is made";
             type empty;
           }
         }
         case case_4 {
           leaf forward-only {
             description "Forward without subscriber services when a match is made";
             type empty;
           }
         }
       }
     }
     list hexadecimal {
       key name;
       description "Hexadecimal string";
       leaf name {
         description "Hexadecimal string";
         type string {
           length "1 .. 512";
           junos:posix-pattern "^[[:xdigit:]]+$";
           junos:pattern-message "Must be hexadecimal digits (0-9, a-f, A-F)";
         }
       }
       uses apply-advanced;
       choice server-group-choice {
         case case_1 {
           leaf relay-server-group {
             description "Name of DHCP relay server group when match is made";
             junos:must "(\".. .. .. .. .. server-group $$\")";
             junos:must-message "Referenced group must be defined under [edit forwarding-options dhcp-relay server-group]";
             type string {
               length "1 .. 64";
             }
           }
         }
         case case_2 {
           leaf local-server-group {
             description "Name of DHCP local server group when match is made";
             junos:must "(\".. .. .. .. .. .. .. system services dhcp-local-server group $$\")";
             junos:must-message "Referenced group must be defined under [edit system services dhcp-local-server group]";
             type string {
               length "1 .. 64";
             }
           }
         }
         case case_3 {
           leaf drop {
             description "Discard when a match is made";
             type empty;
           }
         }
         case case_4 {
           leaf forward-only {
             description "Forward without subscriber services when a match is made";
             type empty;
           }
         }
       }
     }
   }
   grouping relay-option-82-type {
     description "DHCP option-82 processing";
     uses apply-advanced;
     container circuit-id {
       presence "enable circuit-id";
       description "Add circuit identifier";
       uses apply-advanced;
       container prefix {
         description "Add prefix to circuit/interface-id or remote-id";
         uses apply-advanced;
         leaf host-name {
           description "Add router host name to circuit / interface-id or remote-id";
           type empty;
         }
         leaf logical-system-name {
           description "Add logical system name to circuit / interface-id or remote-id";
           type empty;
         }
         leaf routing-instance-name {
           description "Add routing instance name to circuit / interface-id or remote-id";
           type empty;
         }
       }
       leaf use-interface-description {
         description "Use interface description instead of circuit identifier";
         junos:must "(!(\".. require-interface-description\"))";
         junos:must-message "use-interface-description may not be set with require-interface-desciption";
         type enumeration {
           enum "logical" {
             description "Use the logical interface description";
           }
           enum "device" {
             description "Use the device interface description";
           }
         }
       }
       leaf use-vlan-id {
         description "Use VLAN id instead of name";
         junos:must "((!(\".. no-vlan-interface-name\") && (!(\".. use-interface-description\") && !(\".. require-interface-description\"))))";
         junos:must-message "Vlan-tag cannot be added as no-vlan-interface-name or interface-description is configured";
         type empty;
       }
       leaf no-vlan-interface-name {
         description "Not include vlan or interface name";
         type empty;
       }
       leaf include-irb-and-l2 {
         description "Include IRB and L2 interface name";
         type empty;
       }
       leaf user-defined {
         description "Include user defined string";
         junos:must "(!((\".. include-irb-and-l2\" || (\".. keep-incoming-circuit-id\" || (\".. no-vlan-interface-name\" || (\".. use-interface-description\" || (\".. use-vlan-id\" || (\".. prefix\" || \".. require-interface-description\"))))))))";
         junos:must-message "The user defined description for option 82 must be defined in order to see the usage and doesnt coexist with prefix";
         type empty;
       }
       leaf keep-incoming-circuit-id {
         description "Keep incoming circuit identifier";
         type empty;
       }
     }
     container remote-id {
       presence "enable remote-id";
       description "Add remote identifier";
       uses apply-advanced;
       container prefix {
         description "Add prefix to circuit/interface-id or remote-id";
         uses apply-advanced;
         leaf host-name {
           description "Add router host name to circuit / interface-id or remote-id";
           type empty;
         }
         leaf logical-system-name {
           description "Add logical system name to circuit / interface-id or remote-id";
           type empty;
         }
         leaf routing-instance-name {
           description "Add routing instance name to circuit / interface-id or remote-id";
           type empty;
         }
       }
       leaf use-interface-description {
         description "Use interface description instead of circuit identifier";
         junos:must "(!(\".. require-interface-description\"))";
         junos:must-message "use-interface-description may not be set with require-interface-desciption";
         type enumeration {
           enum "logical" {
             description "Use the logical interface description";
           }
           enum "device" {
             description "Use the device interface description";
           }
         }
       }
       leaf use-vlan-id {
         description "Use VLAN id instead of name";
         junos:must "((!(\".. no-vlan-interface-name\") && (!(\".. use-interface-description\") && !(\".. require-interface-description\"))))";
         junos:must-message "Vlan-tag cannot be added as no-vlan-interface-name or interface-description is configured";
         type empty;
       }
       leaf no-vlan-interface-name {
         description "Not include vlan or interface name";
         type empty;
       }
       leaf include-irb-and-l2 {
         description "Include IRB and L2 interface name";
         type empty;
       }
       leaf keep-incoming-remote-id {
         description "Keep incoming remote identifier";
         type empty;
       }
       leaf use-string {
         description "Use raw string instead of the default remote id";
         junos:must "(!((\".. use-interface-description\" || (\".. require-interface-description\" || (\".. include-irb-and-l2\" || (\".. keep-incoming-circuit-id\" || (\".. no-vlan-interface-name\" || \".. use-vlan-id\")))))))";
         junos:must-message "use-string can only coexist with prefix";
         type string;
       }
     }
     leaf server-id-override {
       description "Add link-selection and server-id sub-options on packets to server";
       type empty;
     }
     container vendor-specific {
       description "Add vendor-specific information";
       uses jdhcp-vendor-specific-type;
     }
   }
   grouping relay-v4-option-ascii-hex {
     uses apply-advanced;
     list ascii {
       key name;
       description "ASCII string";
       leaf name {
         description "ASCII string";
         type string {
           length "1 .. 256";
         }
       }
       uses apply-advanced;
       choice server-group-choice {
         case case_1 {
           leaf relay-server-group {
             description "Name of DHCP relay server group when match is made";
             junos:must "((\".. .. .. .. .. .. server-group $$\" || (\".. .. .. .. .. server-group $$\" || (\".. .. .. .. server-group $$\" || \".. .. .. server-group $$\"))))";
             junos:must-message "Referenced group must be defined under [edit forwarding dhcp-relay server-group]";
             type string {
               length "1 .. 64";
             }
           }
         }
         case case_2 {
           leaf local-server-group {
             description "Name of DHCP local server group when match is made";
             junos:must "((\".. .. .. .. .. .. .. .. system services dhcp-local-server group $$\" || (\".. .. .. .. .. .. .. system services dhcp-local-server group $$\" || (\".. .. .. .. .. .. system services dhcp-local-server group $$\" || \".. .. .. .. .. system services dhcp-local-server group $$\"))))";
             junos:must-message "Referenced group must be defined under [edit system services dhcp-local-server group]";
             type string {
               length "1 .. 64";
             }
           }
         }
         case case_3 {
           leaf drop {
             description "Discard when a match is made";
             type empty;
           }
         }
         case case_4 {
           leaf forward-only {
             description "Forward without subscriber services when a match is made";
             type empty;
           }
         }
       }
     }
     list hexadecimal {
       key name;
       description "Hexadecimal string";
       leaf name {
         description "Hexadecimal string";
         type string {
           length "1 .. 512";
           junos:posix-pattern "^[[:xdigit:]]+$";
           junos:pattern-message "Must be hexadecimal digits (0-9, a-f, A-F)";
         }
       }
       uses apply-advanced;
       choice server-group-choice {
         case case_1 {
           leaf relay-server-group {
             description "Name of DHCP relay server group when match is made";
             junos:must "((\".. .. .. .. .. .. server-group $$\" || (\".. .. .. .. .. server-group $$\" || (\".. .. .. .. server-group $$\" || \".. .. .. server-group $$\"))))";
             junos:must-message "Referenced group must be defined under [edit forwarding dhcp-relay server-group]";
             type string {
               length "1 .. 64";
             }
           }
         }
         case case_2 {
           leaf local-server-group {
             description "Name of DHCP local server group when match is made";
             junos:must "((\".. .. .. .. .. .. .. .. system services dhcp-local-server group $$\" || (\".. .. .. .. .. .. .. system services dhcp-local-server group $$\" || (\".. .. .. .. .. .. system services dhcp-local-server group $$\" || \".. .. .. .. .. system services dhcp-local-server group $$\"))))";
             junos:must-message "Referenced group must be defined under [edit system services dhcp-local-server group]";
             type string {
               length "1 .. 64";
             }
           }
         }
         case case_3 {
           leaf drop {
             description "Discard when a match is made";
             type empty;
           }
         }
         case case_4 {
           leaf forward-only {
             description "Forward without subscriber services when a match is made";
             type empty;
           }
         }
       }
     }
   }
   grouping relay-v6-option-ascii-hex {
     uses apply-advanced;
     list ascii {
       key name;
       description "ASCII string";
       leaf name {
         description "ASCII string";
         type string {
           length "1 .. 256";
         }
       }
       uses apply-advanced;
       choice server-group-choice {
         case case_1 {
           leaf relay-server-group {
             description "Name of DHCP relay server group when match is made";
             junos:must "((\".. .. .. .. .. .. server-group $$\" || (\".. .. .. .. .. server-group $$\" || (\".. .. .. .. server-group $$\" || \".. .. .. server-group $$\"))))";
             junos:must-message "Referenced group must be defined under [edit forwarding options dhcp-relay dhcpv6 server-group]";
             type string {
               length "1 .. 64";
             }
           }
         }
         case case_2 {
           leaf drop {
             description "Discard when a match is made";
             type empty;
           }
         }
         case case_3 {
           leaf forward-only {
             description "Forward without subscriber services when a match is made";
             type empty;
           }
         }
       }
     }
     list hexadecimal {
       key name;
       description "Hexadecimal string";
       leaf name {
         description "Hexadecimal string";
         type string {
           length "1 .. 512";
           junos:posix-pattern "^[[:xdigit:]]+$";
           junos:pattern-message "Must be hexadecimal digits (0-9, a-f, A-F)";
         }
       }
       uses apply-advanced;
       choice server-group-choice {
         case case_1 {
           leaf relay-server-group {
             description "Name of DHCP relay server group when match is made";
             junos:must "((\".. .. .. .. .. .. server-group $$\" || (\".. .. .. .. .. server-group $$\" || (\".. .. .. .. server-group $$\" || \".. .. .. server-group $$\"))))";
             junos:must-message "Referenced group must be defined under [edit forwarding options dhcp-relay dhcpv6 server-group]";
             type string {
               length "1 .. 64";
             }
           }
         }
         case case_2 {
           leaf drop {
             description "Discard when a match is made";
             type empty;
           }
         }
         case case_3 {
           leaf forward-only {
             description "Forward without subscriber services when a match is made";
             type empty;
           }
         }
       }
     }
   }
   grouping route_record_traceoptions {
     description "Traceoptions for sampling route record";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Area of route-record to enable debuging output";
       leaf name {
         type enumeration {
           enum "parse" {
             description "Trace parsing code";
           }
           enum "all" {
             description "Trace all area of jflow-service code";
           }
         }
       }
     }
   }
   grouping sampling_family_inet6_output_type {
     description "Configure output options for packet sampling";
     uses apply-advanced;
     leaf aggregate-export-interval {
       description "Interval of exporting aggregate accounting information";
       default "90";
       units "seconds";
       type union {
         type string {
           pattern "<.*>|$.*";
         }
         type uint32 {
           range "90 .. 1800";
         }
       }
     }
     leaf flow-inactive-timeout {
       description "Interval of inactivity that marks a flow inactive";
       default "60";
       units "seconds";
       type union {
         type string {
           pattern "<.*>|$.*";
         }
         type uint32 {
           range "15 .. 1800";
         }
       }
     }
     leaf flow-active-timeout {
       description "Interval after which an active flow is exported";
       default "1800";
       units "seconds";
       type union {
         type string {
           pattern "<.*>|$.*";
         }
         type uint32 {
           range "60 .. 1800";
         }
       }
     }
     list flow-server {
       key name;
       description "Configure sending traffic aggregates in cflowd format";
       max-elements 8;
       junos:must "((!(any \".. interface <*>\") || all \".. interface <*> source-address\"))";
       junos:must-message "'output interface source-address' must be specified with 'flow-server' and 'interface'";
       uses cflowd_sampling_inet6_sampling_type;
     }
     list interface {
       key name;
       description "Interfaces used to send monitored information";
       max-elements 1;
       junos:must "((any \".. flow-server <*>\" || any \".. extension-service <*>\"))";
       junos:must-message "'flow-server' or 'extension-service' must be specified with 'interface'";
       uses packet_export_intf_type;
     }
     container inline-jflow {
       description "Inline processing of sampled packets";
       presence "enable inline-jflow";
       junos:must "(any \".. flow-server <*>\")";
       junos:must-message "'flow-server' must be specified with the inline Jflow";
       uses packet_export_inline;
     }
     list extension-service {
       key name;
       ordered-by user;
       description "Define the customer specific sampling configuration";
       junos:must "(!(\".. flow-active-timeout\"))";
       junos:must-message "'.. flow-active-timeout' is not needed with 'extension-service'";
       junos:must "(!(\".. flow-inactive-timeout\"))";
       junos:must-message "'.. flow-inactive-timeout' is not valid for 'extension-service'";
       junos:must "(!(\".. aggregate-export-interval\"))";
       junos:must-message "'.. aggregate-export-interval' is not valid for 'extension-service'";
       junos:must "(!(any \".. flow-server <*>\"))";
       junos:must-message "'.. flow-server' is not needed with 'extension-service'";
       junos:must "(!(any \".. interface <*> source-address\"))";
       junos:must-message "'.. interface source-address' is not valid for 'extension-service'";
       junos:must "(!(any \".. interface <*> engine-id\"))";
       junos:must-message "'.. interface engine-id' is not valid for 'extension-service'";
       junos:must "(!(any \".. interface <*> engine-type\"))";
       junos:must-message "'.. interface engine-type' is not valid for 'extension-service'";
       junos:must "(any \".. interface <*>\")";
       junos:must-message "'.. interface' must be specified with 'extension-service'";
       leaf name {
         description "Customer prefixed sampling service name";
         type string {
           length "1 .. 63";
         }
       }
       uses apply-advanced;
     }
   }
   grouping cflowd_sampling_inet6_sampling_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       junos:must "(\".. .. inline-jflow\")";
       junos:must-message "DSCP can be configured for inline-jflow";
       type union {
         type string {
           pattern "<.*>|$.*";
         }
         type uint8 {
           range "0 .. 63";
         }
       }
     }
     leaf forwarding-class {
       description "Forwarding-class for exported jflow packets, applicable only for inline-jflow";
       junos:must "(\".. .. inline-jflow\")";
       junos:must-message "forwarding-class can be configured for inline-jflow";
       type string {
         length "1 .. 64";
       }
     }
     leaf routing-instance {
       description "Name of routing instance on which flow collector is reachable";
       junos:must "(\".. .. inline-jflow\")";
       junos:must-message "Routing Instances can be configured for inline-jflow";
       junos:must "(\"routing-instances $$ instance-type vrf\")";
       junos:must-message "routing instance should be defined and should be of type Virtual routing forwarding instance(VRF)";
       type string;
     }
     leaf autonomous-system-type {
       description "Type of autonomous system number to export";
       default "origin";
       type enumeration {
         enum "origin" {
           description "Export origin-AS numbers";
         }
         enum "peer" {
           description "Export peer-AS numbers";
         }
       }
     }
     container aggregation {
       description "Aggregations to perform for exported flows (version 8 only)";
       junos:must "(!(any \".. .. flow-server <*> version9\"))";
       junos:must-message "Select only one version";
       uses aggregation_type;
     }
     choice local-dump-choice {
       leaf local-dump {
         description "Dump cflowd records to log file before exporting";
         type empty;
       }
       leaf no-local-dump {
         description "Don't dump cflowd records to log file before exporting";
         type empty;
       }
     }
     leaf source-address {
       description "Source IPv4 address for cflowd packets";
       type jt:ipv4addr;
     }
     container version9 {
       presence "enable version9";
       junos:must "((!(any \".. .. .. .. inet output flow-server <*> version\") || !(any \".. .. .. .. inet output interface <*>\")))";
       junos:must-message "Select only one version or configure only RE based samping under family inet";
       junos:must "((any \".. .. interface <*>\" || \".. .. inline-jflow\"))";
       junos:must-message "Service PIC or inline-jflow (j-series and SRX only) must be specified for version9";
       description "Export data in version 9 format";
       uses apply-advanced;
       container template {
         description "Template configuration";
         uses apply-advanced;
         leaf template-name {
           description "Template name";
           junos:must "(\"services flow-monitoring version9 template $$ ipv6-template\")";
           junos:must-message "Template type must match input protocol";
           type string;
         }
       }
     }
   }
   grouping packet_export_inline {
     uses apply-advanced;
     leaf source-address {
       description "Address to use for generating monitored packets";
       type jt:ipaddr;
     }
     leaf flow-export-rate {
       description "Flow export rate of monitored packets in kpps";
       type union {
         type string {
           pattern "<.*>|$.*";
         }
         type uint32 {
           range "1 .. 3200";
         }
       }
     }
   }
   grouping sampling_family_input_type {
     description "Configure input options for packet sampling";
     uses apply-advanced;
     leaf rate {
       description "Ratio of packets to be sampled (1 out of N)";
       type union {
         type string {
           pattern "<.*>|$.*";
         }
         type uint32;
       }
     }
     leaf run-length {
       description "Number of samples after initial trigger";
       default "0";
       type union {
         type string {
           pattern "<.*>|$.*";
         }
         type uint32 {
           range "0 .. 20";
         }
       }
     }
     leaf max-packets-per-second {
       description "Threshold of samples per second before dropping";
       default "1000";
       type union {
         type uint16;
         type string {
           pattern "<.*>|$.*";
         }
       }
     }
     leaf maximum-packet-length {
       description "Maximum length of the sampled packet";
       default "0";
       units "bytes";
       type union {
         type string {
           pattern "<.*>|$.*";
         }
         type uint32 {
           range "0 .. 9192";
         }
       }
     }
   }
   grouping sampling_global_mpls_output_type {
     description "Configure output options for packet sampling";
     uses apply-advanced;
     leaf aggregate-export-interval {
       description "Interval of exporting aggregate accounting information";
       default "90";
       units "seconds";
       type union {
         type string {
           pattern "<.*>|$.*";
         }
         type uint32 {
           range "90 .. 1800";
         }
       }
     }
     leaf flow-inactive-timeout {
       description "Interval of inactivity that marks a flow inactive";
       default "60";
       units "seconds";
       type union {
         type string {
           pattern "<.*>|$.*";
         }
         type uint32 {
           range "15 .. 1800";
         }
       }
     }
     leaf flow-active-timeout {
       description "Interval after which an active flow is exported";
       default "1800";
       units "seconds";
       type union {
         type string {
           pattern "<.*>|$.*";
         }
         type uint32 {
           range "60 .. 1800";
         }
       }
     }
     list flow-server {
       key name;
       description "Configure sending traffic aggregates in cflowd format";
       max-elements 8;
       junos:must "((!(any \".. interface <*>\") || all \".. interface <*> source-address\"))";
       junos:must-message "'output interface source-address' must be specified with 'flow-server' and 'interface'";
       uses cflowd_global_mpls_sampling_type;
     }
     list interface {
       key name;
       description "Interfaces used to send monitored information";
       max-elements 1;
       junos:must "(any \".. flow-server <*>\")";
       junos:must-message "'flow-server' must be specified with 'interface'";
       uses packet_export_intf_type;
     }
   }
   grouping cflowd_global_mpls_sampling_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       junos:must "(\".. .. inline-jflow\")";
       junos:must-message "DSCP can be configured for inline-jflow";
       type union {
         type string {
           pattern "<.*>|$.*";
         }
         type uint8 {
           range "0 .. 63";
         }
       }
     }
     leaf forwarding-class {
       description "Forwarding-class for exported jflow packets, applicable only for inline-jflow";
       junos:must "(\".. .. inline-jflow\")";
       junos:must-message "forwarding-class can be configured for inline-jflow";
       type string {
         length "1 .. 64";
       }
     }
     leaf routing-instance {
       description "Name of routing instance on which flow collector is reachable";
       junos:must "(\".. .. inline-jflow\")";
       junos:must-message "Routing Instances can be configured for inline-jflow";
       junos:must "(\"routing-instances $$ instance-type vrf\")";
       junos:must-message "routing instance should be defined and should be of type Virtual routing forwarding instance(VRF)";
       type string;
     }
     leaf autonomous-system-type {
       description "Type of autonomous system number to export";
       default "origin";
       type enumeration {
         enum "origin" {
           description "Export origin-AS numbers";
         }
         enum "peer" {
           description "Export peer-AS numbers";
         }
       }
     }
     container aggregation {
       description "Aggregations to perform for exported flows (version 8 only)";
       junos:must "(!(any \".. .. flow-server <*> version9\"))";
       junos:must-message "Select only one version";
       uses aggregation_type;
     }
     choice local-dump-choice {
       leaf local-dump {
         description "Dump cflowd records to log file before exporting";
         type empty;
       }
       leaf no-local-dump {
         description "Don't dump cflowd records to log file before exporting";
         type empty;
       }
     }
     leaf source-address {
       description "Source IPv4 address for cflowd packets";
       type jt:ipv4addr;
     }
     container version9 {
       presence "enable version9";
       junos:must "((!(any \".. .. .. .. inet output flow-server <*> version\") || !(any \".. .. .. .. inet output interface <*>\")))";
       junos:must-message "Select only one version or configure only RE based samping under family inet";
       junos:must "((any \".. .. interface <*>\" || \".. .. inline-jflow\"))";
       junos:must-message "Service PIC or inline-jflow (j-series and SRX only) must be specified for version9";
       description "Export data in version 9 format";
       uses apply-advanced;
       container template {
         description "Template configuration";
         uses apply-advanced;
         leaf template-name {
           description "Template name";
           junos:must "((\"services flow-monitoring version9 template $$ mpls-template\" || (\"services flow-monitoring version9 template $$ mpls-ipv4-template\" || \"services flow-monitoring version9 template $$ mpls-ipvx-template\")))";
           junos:must-message "Template type must match input protocol";
           junos:must "((!(\".. .. .. .. inline-jflow source-address\") || (\".. .. .. .. inline-jflow source-address\" && all \".. .. .. .. flow-server <*> version9 template $$\")))";
           junos:must-message "All the collector under same family should share the same template in Inline-Jflow";
           type string;
         }
       }
     }
   }
   grouping sampling_input_type {
     description "Configure input options for packet sampling";
     uses apply-advanced;
     leaf rate {
       description "Ratio of packets to be sampled (1 out of N)";
       type union {
         type string {
           pattern "<.*>|$.*";
         }
         type uint32;
       }
     }
     leaf run-length {
       description "Number of samples after initial trigger";
       default "0";
       type union {
         type string {
           pattern "<.*>|$.*";
         }
         type uint32 {
           range "0 .. 20";
         }
       }
     }
     leaf max-packets-per-second {
       description "Threshold of samples per second before dropping";
       default "1000";
       type union {
         type uint16;
         type string {
           pattern "<.*>|$.*";
         }
       }
     }
     leaf maximum-packet-length {
       description "Maximum length of the sampled packet";
       default "0";
       units "bytes";
       type union {
         type string {
           pattern "<.*>|$.*";
         }
         type uint32 {
           range "0 .. 9192";
         }
       }
     }
     container family {
       presence "enable family";
       description "Protocol family";
       status deprecated;
       container inet {
         description "Sampling parameters for IPv4";
         uses apply-advanced;
         leaf rate {
           description "Ratio of packets to be sampled (1 out of N)";
           type union {
             type string {
               pattern "<.*>|$.*";
             }
             type uint32;
           }
         }
         leaf run-length {
           description "Number of samples after initial trigger";
           default "0";
           type union {
             type string {
               pattern "<.*>|$.*";
             }
             type uint32 {
               range "0 .. 20";
             }
           }
         }
         leaf max-packets-per-second {
           description "Threshold of samples per second before dropping";
           default "1000";
           type union {
             type uint16;
             type string {
               pattern "<.*>|$.*";
             }
           }
         }
         leaf maximum-packet-length {
           description "Maximum length of the sampled packet";
           default "0";
           units "bytes";
           type union {
             type string {
               pattern "<.*>|$.*";
             }
             type uint32 {
               range "0 .. 9192";
             }
           }
         }
       }
       container mpls {
         description "Sampling parameters for MPLS";
         uses apply-advanced;
         leaf rate {
           description "Ratio of packets to be sampled (1 out of N)";
           type union {
             type string {
               pattern "<.*>|$.*";
             }
             type uint32;
           }
         }
         leaf run-length {
           description "Number of samples after initial trigger";
           default "0";
           type union {
             type string {
               pattern "<.*>|$.*";
             }
             type uint32 {
               range "0 .. 20";
             }
           }
         }
         leaf max-packets-per-second {
           description "Threshold of samples per second before dropping";
           default "1000";
           type union {
             type uint16;
             type string {
               pattern "<.*>|$.*";
             }
           }
         }
         leaf maximum-packet-length {
           description "Maximum length of the sampled packet";
           default "0";
           units "bytes";
           type union {
             type string {
               pattern "<.*>|$.*";
             }
             type uint32 {
               range "0 .. 9192";
             }
           }
         }
       }
       container inet6 {
         description "Sampling parameters for IPv6";
         uses apply-advanced;
         leaf rate {
           description "Ratio of packets to be sampled (1 out of N)";
           type union {
             type string {
               pattern "<.*>|$.*";
             }
             type uint32;
           }
         }
         leaf run-length {
           description "Number of samples after initial trigger";
           default "0";
           type union {
             type string {
               pattern "<.*>|$.*";
             }
             type uint32 {
               range "0 .. 20";
             }
           }
         }
         leaf max-packets-per-second {
           description "Threshold of samples per second before dropping";
           default "1000";
           type union {
             type uint16;
             type string {
               pattern "<.*>|$.*";
             }
           }
         }
         leaf maximum-packet-length {
           description "Maximum length of the sampled packet";
           default "0";
           units "bytes";
           type union {
             type string {
               pattern "<.*>|$.*";
             }
             type uint32 {
               range "0 .. 9192";
             }
           }
         }
       }
     }
   }
   grouping sampling_instance_bridge_output_type {
     description "Configure output options for packet sampling";
     uses apply-advanced;
     list flow-server {
       key name;
       description "Configure sending traffic aggregates in cflowd format";
       max-elements 8;
       junos:must "(\".. inline-jflow\")";
       junos:must-message "Output 'inline Jflow' should be configured with flow-server";
       uses cflowd_instance_bridge_sampling_type;
     }
     container inline-jflow {
       description "Inline processing of sampled packets";
       presence "enable inline-jflow";
       junos:must "(any \".. flow-server <*>\")";
       junos:must-message "'flow-server' must be specified with the inline Jflow";
       uses packet_export_inline_instance;
     }
   }
   grouping cflowd_instance_bridge_sampling_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       junos:must "(\".. .. inline-jflow\")";
       junos:must-message "DSCP can be configured for inline-jflow";
       type union {
         type string {
           pattern "<.*>|$.*";
         }
         type uint8 {
           range "0 .. 63";
         }
       }
     }
     leaf forwarding-class {
       description "Forwarding-class for exported jflow packets, applicable only for inline-jflow";
       junos:must "(\".. .. inline-jflow\")";
       junos:must-message "forwarding-class can be configured for inline-jflow";
       type string {
         length "1 .. 64";
       }
     }
     leaf routing-instance {
       description "Name of routing instance on which flow collector is reachable";
       junos:must "(\".. .. inline-jflow\")";
       junos:must-message "Routing Instances can be configured for inline-jflow";
       junos:must "(\"routing-instances $$ instance-type vrf\")";
       junos:must-message "routing instance should be defined and should be of type Virtual routing forwarding instance(VRF)";
       type string;
     }
     container version9 {
       presence "enable version9";
       junos:must "(\".. .. inline-jflow\")";
       junos:must-message "inline Jflow must be specified for version9";
       description "Export data in version 9 format";
       uses apply-advanced;
       container template {
         description "Template configuration";
         uses apply-advanced;
         leaf template-name {
           description "Template name";
           junos:must "(\"services flow-monitoring version9 template $$ bridge-template\")";
           junos:must-message "Template type must match input protocol";
           junos:must "((!(\".. .. .. .. inline-jflow source-address\") || (\".. .. .. .. inline-jflow source-address\" && all \".. .. .. .. flow-server <*> version9 template $$\")))";
           junos:must-message "All the collector under same family should share the same template in Inline-Jflow";
           type string;
         }
       }
     }
     container version-ipfix {
       presence "enable version-ipfix";
       junos:must "(\".. .. inline-jflow\")";
       junos:must-message "inline Jflow must be specified for version-ipfix";
       description "Export data in version ipfix format";
       uses apply-advanced;
       container template {
         description "Template configuration";
         uses apply-advanced;
         leaf template-name {
           description "Template name";
           junos:must "(\"services flow-monitoring version-ipfix template $$ bridge-template\")";
           junos:must-message "Template type must match input protocol";
           junos:must "((!(\".. .. .. .. inline-jflow source-address\") || (\".. .. .. .. inline-jflow source-address\" && all \".. .. .. .. flow-server <*> version-ipfix template $$\")))";
           junos:must-message "All the collector under same family should share the same template in Inline-Jflow";
           type string;
         }
       }
     }
   }
   grouping packet_export_inline_instance {
     uses apply-advanced;
     leaf source-address {
       description "Address to use for generating monitored packets";
       type jt:ipaddr;
     }
     leaf flow-export-rate {
       description "Flow export rate of monitored packets in kpps";
       type union {
         type string {
           pattern "<.*>|$.*";
         }
         type uint32 {
           range "1 .. 3200";
         }
       }
     }
   }
   grouping sampling_instance_inet6_output_type {
     description "Configure output options for packet sampling";
     uses apply-advanced;
     leaf aggregate-export-interval {
       description "Interval of exporting aggregate accounting information";
       default "90";
       units "seconds";
       type union {
         type string {
           pattern "<.*>|$.*";
         }
         type uint32 {
           range "90 .. 1800";
         }
       }
     }
     leaf flow-inactive-timeout {
       description "Interval of inactivity that marks a flow inactive";
       default "60";
       units "seconds";
       type union {
         type string {
           pattern "<.*>|$.*";
         }
         type uint32 {
           range "15 .. 1800";
         }
       }
     }
     leaf flow-active-timeout {
       description "Interval after which an active flow is exported";
       default "1800";
       units "seconds";
       type union {
         type string {
           pattern "<.*>|$.*";
         }
         type uint32 {
           range "60 .. 1800";
         }
       }
     }
     list flow-server {
       key name;
       description "Configure sending traffic aggregates in cflowd format";
       max-elements 8;
       junos:must "((!(any \".. interface <*>\") || all \".. interface <*> source-address\"))";
       junos:must-message "'output interface source-address' must be specified with 'flow-server' and 'interface'";
       uses cflowd_instance_inet6_sampling_type;
     }
     list interface {
       key name;
       description "Interfaces used to send monitored information";
       max-elements 1;
       junos:must "((any \".. flow-server <*>\" || any \".. extension-service <*>\"))";
       junos:must-message "'flow-server' or 'extension-service' must be specified with 'interface'";
       uses packet_export_intf_type;
     }
     container inline-jflow {
       description "Inline processing of sampled packets";
       presence "enable inline-jflow";
       junos:must "(any \".. flow-server <*>\")";
       junos:must-message "'flow-server' must be specified with the inline Jflow";
       uses packet_export_inline_instance;
     }
     list extension-service {
       key name;
       ordered-by user;
       description "Define the customer specific sampling configuration";
       junos:must "(!(\".. flow-active-timeout\"))";
       junos:must-message "'.. flow-active-timeout' is not needed with 'extension-service'";
       junos:must "(!(\".. flow-inactive-timeout\"))";
       junos:must-message "'.. flow-inactive-timeout' is not valid for 'extension-service'";
       junos:must "(!(\".. aggregate-export-interval\"))";
       junos:must-message "'.. aggregate-export-interval' is not valid for 'extension-service'";
       junos:must "(!(any \".. flow-server <*>\"))";
       junos:must-message "'.. flow-server' is not needed with 'extension-service'";
       junos:must "(!(any \".. interface <*> source-address\"))";
       junos:must-message "'.. interface source-address' is not valid for 'extension-service'";
       junos:must "(!(any \".. interface <*> engine-id\"))";
       junos:must-message "'.. interface engine-id' is not valid for 'extension-service'";
       junos:must "(!(any \".. interface <*> engine-type\"))";
       junos:must-message "'.. interface engine-type' is not valid for 'extension-service'";
       junos:must "(any \".. interface <*>\")";
       junos:must-message "'.. interface' must be specified with 'extension-service'";
       leaf name {
         description "Customer prefixed sampling service name";
         type string {
           length "1 .. 63";
         }
       }
       uses apply-advanced;
     }
   }
   grouping cflowd_instance_inet6_sampling_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       junos:must "(\".. .. inline-jflow\")";
       junos:must-message "DSCP can be configured for inline-jflow";
       type union {
         type string {
           pattern "<.*>|$.*";
         }
         type uint8 {
           range "0 .. 63";
         }
       }
     }
     leaf forwarding-class {
       description "Forwarding-class for exported jflow packets, applicable only for inline-jflow";
       junos:must "(\".. .. inline-jflow\")";
       junos:must-message "forwarding-class can be configured for inline-jflow";
       type string {
         length "1 .. 64";
       }
     }
     leaf routing-instance {
       description "Name of routing instance on which flow collector is reachable";
       junos:must "(\".. .. inline-jflow\")";
       junos:must-message "Routing Instances can be configured for inline-jflow";
       junos:must "(\"routing-instances $$ instance-type vrf\")";
       junos:must-message "routing instance should be defined and should be of type Virtual routing forwarding instance(VRF)";
       type string;
     }
     leaf autonomous-system-type {
       description "Type of autonomous system number to export";
       default "origin";
       type enumeration {
         enum "origin" {
           description "Export origin-AS numbers";
         }
         enum "peer" {
           description "Export peer-AS numbers";
         }
       }
     }
     container aggregation {
       description "Aggregations to perform for exported flows (version 8 only)";
       junos:must "(!(any \".. .. flow-server <*> version9\"))";
       junos:must-message "Select only one version";
       uses aggregation_type;
     }
     choice local-dump-choice {
       leaf local-dump {
         description "Dump cflowd records to log file before exporting";
         type empty;
       }
       leaf no-local-dump {
         description "Don't dump cflowd records to log file before exporting";
         type empty;
       }
     }
     leaf source-address {
       description "Source IPv4 address for cflowd packets";
       type jt:ipv4addr;
     }
     container version9 {
       presence "enable version9";
       junos:must "((!(any \".. .. .. .. inet output flow-server <*> version\") || !(any \".. .. .. .. inet output interface <*>\")))";
       junos:must-message "Select only one version or configure only RE based samping under family inet";
       junos:must "((any \".. .. interface <*>\" || \".. .. inline-jflow\"))";
       junos:must-message "Service PIC or inline-jflow (j-series and SRX only) must be specified for version9";
       description "Export data in version 9 format";
       uses apply-advanced;
       container template {
         description "Template configuration";
         uses apply-advanced;
         leaf template-name {
           description "Template name";
           junos:must "(\"services flow-monitoring version9 template $$ ipv6-template\")";
           junos:must-message "Template type must match input protocol";
           junos:must "((!(\".. .. .. .. inline-jflow source-address\") || (\".. .. .. .. inline-jflow source-address\" && all \".. .. .. .. flow-server <*> version9 template $$\")))";
           junos:must-message "All the collector under same family should share the same template in Inline-Jflow";
           type string;
         }
       }
     }
     container version-ipfix {
       presence "enable version-ipfix";
       junos:must "(\".. .. inline-jflow\")";
       junos:must-message "inline Jflow must be specified for version-ipfix";
       description "Export data in version ipfix format";
       uses apply-advanced;
       container template {
         description "Template configuration";
         uses apply-advanced;
         leaf template-name {
           description "Template name";
           junos:must "(\"services flow-monitoring version-ipfix template $$ ipv6-template\")";
           junos:must-message "Template type must match input protocol";
           junos:must "((!(\".. .. .. .. inline-jflow source-address\") || (\".. .. .. .. inline-jflow source-address\" && all \".. .. .. .. flow-server <*> version-ipfix template $$\")))";
           junos:must-message "All the collector under same family should share the same template in Inline-Jflow";
           type string;
         }
       }
     }
   }
   grouping sampling_instance_inet_global_output_type {
     description "Configure output options for packet sampling";
     uses apply-advanced;
     leaf aggregate-export-interval {
       description "Interval of exporting aggregate accounting information";
       default "90";
       units "seconds";
       type union {
         type string {
           pattern "<.*>|$.*";
         }
         type uint32 {
           range "90 .. 1800";
         }
       }
     }
     leaf flow-inactive-timeout {
       description "Interval of inactivity that marks a flow inactive";
       default "60";
       units "seconds";
       type union {
         type string {
           pattern "<.*>|$.*";
         }
         type uint32 {
           range "15 .. 1800";
         }
       }
     }
     leaf flow-active-timeout {
       description "Interval after which an active flow is exported";
       default "1800";
       units "seconds";
       type union {
         type string {
           pattern "<.*>|$.*";
         }
         type uint32 {
           range "60 .. 1800";
         }
       }
     }
     container file {
       junos:must "(!(any \".. extension-service <*>\"))";
       junos:must-message "This configuration is not required with 'extension-service'";
       description "Configure parameters for dumping sampled packets";
       choice enable-disable {
         case case_1 {
           leaf disable {
             description "Disable sampled packet dumps";
             type empty;
           }
         }
       }
       leaf filename {
         description "Name of file to contain sampled packet dumps";
         type string {
           length "1 .. 1024";
           junos:posix-pattern "![/ %]";
           junos:pattern-message "Must not contain '/', % or a space";
         }
       }
       leaf files {
         description "Maximum number of sampled packet dump files";
         default "10";
         type union {
           type string {
             pattern "<.*>|$.*";
           }
           type uint32 {
             range "2 .. 10000";
           }
         }
       }
       leaf size {
         description "Maximum sample dump file size";
         type string;
       }
       choice world-readable-choice {
         leaf world-readable {
           description "Allow any user to read the sampled dump";
           type empty;
         }
         leaf no-world-readable {
           description "Don't allow any user to read the sampled dump";
           type empty;
         }
       }
       choice stamp-choice {
         leaf stamp {
           description "Timestamp every packet in the dump";
           type empty;
         }
         leaf no-stamp {
           description "Don't timestamp every packet in the dump";
           type empty;
         }
       }
     }
     container port-mirroring {
       description "Configure sending sampled traffic out through an interface";
       presence "enable port-mirroring";
       junos:must "(!(any \".. extension-service <*>\"))";
       junos:must-message "This configuration is not required with 'extension-service'";
       uses inet_pm_family_output_type;
     }
     list flow-server {
       key name;
       description "Configure sending traffic aggregates in cflowd format";
       max-elements 8;
       junos:must "((!(any \".. interface <*>\") || all \".. interface <*> source-address\"))";
       junos:must-message "'output interface source-address' must be specified with 'flow-server' and 'interface'";
       uses cflowd_sampling_inet_type;
     }
     list interface {
       key name;
       description "Interfaces used to send monitored information";
       max-elements 1;
       junos:must "((any \".. flow-server <*>\" || any \".. extension-service <*>\"))";
       junos:must-message "'flow-server' or 'extension-service' must be specified with 'interface'";
       uses packet_export_intf_type;
     }
     container inline-jflow {
       description "Inline processing of sampled packets";
       presence "enable inline-jflow";
       junos:must "(any \".. flow-server <*>\")";
       junos:must-message "'flow-server' must be specified with the inline Jflow";
       uses packet_export_inline;
     }
     list extension-service {
       key name;
       ordered-by user;
       description "Define the customer specific sampling configuration";
       junos:must "(!(\".. flow-active-timeout\"))";
       junos:must-message "'.. flow-active-timeout' is not needed with 'extension-service'";
       junos:must "(!(\".. flow-inactive-timeout\"))";
       junos:must-message "'.. flow-inactive-timeout' is not valid for 'extension-service'";
       junos:must "(!(\".. aggregate-export-interval\"))";
       junos:must-message "'.. aggregate-export-interval' is not valid for 'extension-service'";
       junos:must "(!(any \".. flow-server <*>\"))";
       junos:must-message "'.. flow-server' is not needed with 'extension-service'";
       junos:must "(!(any \".. interface <*> source-address\"))";
       junos:must-message "'.. interface source-address' is not valid for 'extension-service'";
       junos:must "(!(any \".. interface <*> engine-id\"))";
       junos:must-message "'.. interface engine-id' is not valid for 'extension-service'";
       junos:must "(!(any \".. interface <*> engine-type\"))";
       junos:must-message "'.. interface engine-type' is not valid for 'extension-service'";
       junos:must "(any \".. interface <*>\")";
       junos:must-message "'.. interface' must be specified with 'extension-service'";
       leaf name {
         description "Customer prefixed sampling service name";
         type string {
           length "1 .. 63";
         }
       }
       uses apply-advanced;
     }
   }
   grouping cflowd_sampling_inet_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       junos:must "(\".. .. inline-jflow\")";
       junos:must-message "DSCP can be configured for inline-jflow";
       type union {
         type string {
           pattern "<.*>|$.*";
         }
         type uint8 {
           range "0 .. 63";
         }
       }
     }
     leaf forwarding-class {
       description "Forwarding-class for exported jflow packets, applicable only for inline-jflow";
       junos:must "(\".. .. inline-jflow\")";
       junos:must-message "forwarding-class can be configured for inline-jflow";
       type string {
         length "1 .. 64";
       }
     }
     leaf routing-instance {
       description "Name of routing instance on which flow collector is reachable";
       junos:must "(\".. .. inline-jflow\")";
       junos:must-message "Routing Instances can be configured for inline-jflow";
       junos:must "(\"routing-instances $$ instance-type vrf\")";
       junos:must-message "routing instance should be defined and should be of type Virtual routing forwarding instance(VRF)";
       type string;
     }
     leaf autonomous-system-type {
       description "Type of autonomous system number to export";
       default "origin";
       type enumeration {
         enum "origin" {
           description "Export origin-AS numbers";
         }
         enum "peer" {
           description "Export peer-AS numbers";
         }
       }
     }
     container aggregation {
       description "Aggregations to perform for exported flows (version 8 only)";
       junos:must "(!(any \".. .. flow-server <*> version9\"))";
       junos:must-message "Select only one version";
       uses aggregation_type;
     }
     choice local-dump-choice {
       leaf local-dump {
         description "Dump cflowd records to log file before exporting";
         type empty;
       }
       leaf no-local-dump {
         description "Don't dump cflowd records to log file before exporting";
         type empty;
       }
     }
     leaf source-address {
       description "Source IPv4 address for cflowd packets";
       type jt:ipv4addr;
     }
     container version9 {
       presence "enable version9";
       junos:must "((!(any \".. .. .. .. inet output flow-server <*> version\") || !(any \".. .. .. .. inet output interface <*>\")))";
       junos:must-message "Select only one version or configure only RE based samping under family inet";
       junos:must "((any \".. .. interface <*>\" || \".. .. inline-jflow\"))";
       junos:must-message "Service PIC or inline-jflow (j-series and SRX only) must be specified for version9";
       description "Export data in version 9 format";
       uses apply-advanced;
       container template {
         description "Template configuration";
         uses apply-advanced;
         leaf template-name {
           description "Template name";
           junos:must "((\"services flow-monitoring version9 template $$ ipv4-template\" || \"services flow-monitoring version9 template $$ peer-as-billing-template\"))";
           junos:must-message "Template type must match input protocol";
           type string;
         }
       }
     }
     container version-ipfix {
       presence "enable version-ipfix";
       description "Export data in version ipfix format";
       status deprecated;
       uses apply-advanced;
       container template {
         description "Template configuration";
         uses apply-advanced;
         leaf template-name {
           description "Template name";
           type string;
         }
       }
     }
     leaf version {
       description "Format of exported cflowd aggregates";
       default "5";
       junos:must "(!(any \".. .. flow-server <*> version9\"))";
       junos:must-message "Select only one version";
       type enumeration {
         enum "5" {
           description "Export cflowd aggregates in version 5 format";
           junos:must "(\"system ntp\")";
           junos:must-message " NTP must be configured for sampling v5/8/500 to work properly";
         }
         enum "8" {
           description "Export cflowd aggregates in version 8 format";
           junos:must "(\"system ntp\")";
           junos:must-message " NTP must be configured for sampling v5/8/500 to work properly";
         }
         enum "500" {
           description "Export cflowd aggregates in ASN 500 format";
           junos:must "(!(\".. .. interface\"))";
           junos:must-message "This feature is only supported for RE based sampling";
           junos:must "(\"system ntp\")";
           junos:must-message " NTP must be configured for sampling v5/8/500 to work properly";
         }
       }
     }
   }
   grouping sampling_instance_inet_output_type {
     description "Configure output options for packet sampling";
     uses apply-advanced;
     leaf aggregate-export-interval {
       description "Interval of exporting aggregate accounting information";
       default "90";
       units "seconds";
       type union {
         type string {
           pattern "<.*>|$.*";
         }
         type uint32 {
           range "90 .. 1800";
         }
       }
     }
     leaf flow-inactive-timeout {
       description "Interval of inactivity that marks a flow inactive";
       default "60";
       units "seconds";
       type union {
         type string {
           pattern "<.*>|$.*";
         }
         type uint32 {
           range "15 .. 1800";
         }
       }
     }
     leaf flow-active-timeout {
       description "Interval after which an active flow is exported";
       default "1800";
       units "seconds";
       type union {
         type string {
           pattern "<.*>|$.*";
         }
         type uint32 {
           range "60 .. 1800";
         }
       }
     }
     list flow-server {
       key name;
       description "Configure sending traffic aggregates in cflowd format";
       max-elements 8;
       junos:must "((!(any \".. interface <*>\") || all \".. interface <*> source-address\"))";
       junos:must-message "'output interface source-address' must be specified with 'flow-server' and 'interface'";
       junos:must "((\".. interface\" || \".. inline-jflow\"))";
       junos:must-message "Output 'interface' or 'inline Jflow' should be configured with flow-server";
       uses cflowd_instance_inet_sampling_type;
     }
     list interface {
       key name;
       description "Interfaces used to send monitored information";
       max-elements 1;
       junos:must "((any \".. flow-server <*>\" || any \".. extension-service <*>\"))";
       junos:must-message "'flow-server' or 'extension-service' must be specified with 'interface'";
       uses packet_export_intf_type;
     }
     container inline-jflow {
       description "Inline processing of sampled packets";
       presence "enable inline-jflow";
       junos:must "(any \".. flow-server <*>\")";
       junos:must-message "'flow-server' must be specified with the inline Jflow";
       uses packet_export_inline_instance;
     }
     list extension-service {
       key name;
       ordered-by user;
       description "Define the customer specific sampling configuration";
       junos:must "(!(\".. flow-active-timeout\"))";
       junos:must-message "'.. flow-active-timeout' is not needed with 'extension-service'";
       junos:must "(!(\".. flow-inactive-timeout\"))";
       junos:must-message "'.. flow-inactive-timeout' is not valid for 'extension-service'";
       junos:must "(!(\".. aggregate-export-interval\"))";
       junos:must-message "'.. aggregate-export-interval' is not valid for 'extension-service'";
       junos:must "(!(any \".. flow-server <*>\"))";
       junos:must-message "'.. flow-server' is not needed with 'extension-service'";
       junos:must "(!(any \".. interface <*> source-address\"))";
       junos:must-message "'.. interface source-address' is not valid for 'extension-service'";
       junos:must "(!(any \".. interface <*> engine-id\"))";
       junos:must-message "'.. interface engine-id' is not valid for 'extension-service'";
       junos:must "(!(any \".. interface <*> engine-type\"))";
       junos:must-message "'.. interface engine-type' is not valid for 'extension-service'";
       junos:must "(any \".. interface <*>\")";
       junos:must-message "'.. interface' must be specified with 'extension-service'";
       leaf name {
         description "Customer prefixed sampling service name";
         type string {
           length "1 .. 63";
         }
       }
       uses apply-advanced;
     }
   }
   grouping cflowd_instance_inet_sampling_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       junos:must "(\".. .. inline-jflow\")";
       junos:must-message "DSCP can be configured for inline-jflow";
       type union {
         type string {
           pattern "<.*>|$.*";
         }
         type uint8 {
           range "0 .. 63";
         }
       }
     }
     leaf forwarding-class {
       description "Forwarding-class for exported jflow packets, applicable only for inline-jflow";
       junos:must "(\".. .. inline-jflow\")";
       junos:must-message "forwarding-class can be configured for inline-jflow";
       type string {
         length "1 .. 64";
       }
     }
     leaf routing-instance {
       description "Name of routing instance on which flow collector is reachable";
       junos:must "(\".. .. inline-jflow\")";
       junos:must-message "Routing Instances can be configured for inline-jflow";
       junos:must "(\"routing-instances $$ instance-type vrf\")";
       junos:must-message "routing instance should be defined and should be of type Virtual routing forwarding instance(VRF)";
       type string;
     }
     leaf autonomous-system-type {
       description "Type of autonomous system number to export";
       default "origin";
       type enumeration {
         enum "origin" {
           description "Export origin-AS numbers";
         }
         enum "peer" {
           description "Export peer-AS numbers";
         }
       }
     }
     container aggregation {
       description "Aggregations to perform for exported flows (version 8 only)";
       junos:must "(!(any \".. .. flow-server <*> version9\"))";
       junos:must-message "Select only one version";
       uses aggregation_type;
     }
     choice local-dump-choice {
       leaf local-dump {
         description "Dump cflowd records to log file before exporting";
         type empty;
       }
       leaf no-local-dump {
         description "Don't dump cflowd records to log file before exporting";
         type empty;
       }
     }
     leaf source-address {
       description "Source IPv4 address for cflowd packets";
       type jt:ipv4addr;
     }
     container version9 {
       presence "enable version9";
       junos:must "((!(any \".. .. .. .. inet output flow-server <*> version\") || !(any \".. .. .. .. inet output interface <*>\")))";
       junos:must-message "Select only one version or configure only RE based samping under family inet";
       junos:must "((any \".. .. interface <*>\" || \".. .. inline-jflow\"))";
       junos:must-message "Service PIC or inline-jflow (j-series and SRX only) must be specified for version9";
       description "Export data in version 9 format";
       uses apply-advanced;
       container template {
         description "Template configuration";
         uses apply-advanced;
         leaf template-name {
           description "Template name";
           junos:must "(\"services flow-monitoring version9 template $$ ipv4-template\")";
           junos:must-message "Template type must match input protocol";
           junos:must "((!(\".. .. .. .. inline-jflow source-address\") || (\".. .. .. .. inline-jflow source-address\" && all \".. .. .. .. flow-server <*> version9 template $$\")))";
           junos:must-message "All the collector under same family should share the same template in Inline-Jflow";
           type string;
         }
       }
     }
     container version-ipfix {
       presence "enable version-ipfix";
       junos:must "(\".. .. inline-jflow\")";
       junos:must-message "inline Jflow must be specified for version-ipfix";
       description "Export data in version ipfix format";
       uses apply-advanced;
       container template {
         description "Template configuration";
         uses apply-advanced;
         leaf template-name {
           description "Template name";
           junos:must "(\"services flow-monitoring version-ipfix template $$ ipv4-template\")";
           junos:must-message "Template type must match input protocol";
           junos:must "((!(\".. .. .. .. inline-jflow source-address\") || (\".. .. .. .. inline-jflow source-address\" && all \".. .. .. .. flow-server <*> version-ipfix template $$\")))";
           junos:must-message "All the collector under same family should share the same template in Inline-Jflow";
           type string;
         }
       }
     }
     leaf version {
       description "Format of exported cflowd aggregates";
       default "5";
       junos:must "(!(any \".. .. .. .. .. family mpls output flow-server <*> version9\"))";
       junos:must-message "Select only one version";
       junos:must "(!(any \".. .. .. .. .. family inet6 output flow-server <*> version9\"))";
       junos:must-message "Select only one version";
       junos:must "(!(any \".. .. .. .. .. family inet output flow-server <*> version9\"))";
       junos:must-message "Select only one version";
       junos:must "(!(any \".. .. flow-server <*> version-ipfix\"))";
       junos:must-message "Select only one version";
       junos:must "(!(any \".. .. flow-server <*> version9\"))";
       junos:must-message "Select only one version";
       type enumeration {
         enum "5" {
           description "Export cflowd aggregates in version 5 format";
           junos:must "(\"system ntp\")";
           junos:must-message " NTP must be configured for sampling v5/8/500 to work properly";
         }
         enum "8" {
           description "Export cflowd aggregates in version 8 format";
           junos:must "(\"system ntp\")";
           junos:must-message " NTP must be configured for sampling v5/8/500 to work properly";
         }
       }
     }
   }
   grouping sampling_instance_input_type {
     description "Configure input options for packet sampling";
     uses apply-advanced;
     leaf rate {
       description "Ratio of packets to be sampled (1 out of N)";
       type union {
         type string {
           pattern "<.*>|$.*";
         }
         type uint32;
       }
     }
     leaf run-length {
       description "Number of samples after initial trigger";
       default "0";
       type union {
         type string {
           pattern "<.*>|$.*";
         }
         type uint32 {
           range "0 .. 20";
         }
       }
     }
     leaf max-packets-per-second {
       description "Threshold of samples per second before dropping";
       default "1000";
       type union {
         type uint16;
         type string {
           pattern "<.*>|$.*";
         }
       }
     }
     leaf maximum-packet-length {
       description "Maximum length of the sampled packet";
       default "0";
       units "bytes";
       type union {
         type string {
           pattern "<.*>|$.*";
         }
         type uint32 {
           range "0 .. 9192";
         }
       }
     }
   }
   grouping sampling_instance_mpls_output_type {
     description "Configure output options for packet sampling";
     uses apply-advanced;
     leaf aggregate-export-interval {
       description "Interval of exporting aggregate accounting information";
       default "90";
       units "seconds";
       type union {
         type string {
           pattern "<.*>|$.*";
         }
         type uint32 {
           range "90 .. 1800";
         }
       }
     }
     leaf flow-inactive-timeout {
       description "Interval of inactivity that marks a flow inactive";
       default "60";
       units "seconds";
       type union {
         type string {
           pattern "<.*>|$.*";
         }
         type uint32 {
           range "15 .. 1800";
         }
       }
     }
     leaf flow-active-timeout {
       description "Interval after which an active flow is exported";
       default "1800";
       units "seconds";
       type union {
         type string {
           pattern "<.*>|$.*";
         }
         type uint32 {
           range "60 .. 1800";
         }
       }
     }
     list flow-server {
       key name;
       description "Configure sending traffic aggregates in cflowd format";
       max-elements 8;
       junos:must "((!(any \".. interface <*>\") || all \".. interface <*> source-address\"))";
       junos:must-message "'output interface source-address' must be specified with 'flow-server' and 'interface'";
       junos:must "((\".. interface\" || \".. inline-jflow\"))";
       junos:must-message "Output 'interface' or 'inline Jflow' should be configured with flow-server";
       uses cflowd_instance_mpls_sampling_type;
     }
     list interface {
       key name;
       description "Interfaces used to send monitored information";
       max-elements 1;
       junos:must "(any \".. flow-server <*>\")";
       junos:must-message "'flow-server' must be specified with 'interface'";
       uses packet_export_intf_type;
     }
     container inline-jflow {
       description "Inline processing of sampled packets";
       presence "enable inline-jflow";
       junos:must "(any \".. flow-server <*>\")";
       junos:must-message "'flow-server' must be specified with the inline Jflow";
       uses packet_export_inline_instance;
     }
   }
   grouping cflowd_instance_mpls_sampling_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       junos:must "(\".. .. inline-jflow\")";
       junos:must-message "DSCP can be configured for inline-jflow";
       type union {
         type string {
           pattern "<.*>|$.*";
         }
         type uint8 {
           range "0 .. 63";
         }
       }
     }
     leaf forwarding-class {
       description "Forwarding-class for exported jflow packets, applicable only for inline-jflow";
       junos:must "(\".. .. inline-jflow\")";
       junos:must-message "forwarding-class can be configured for inline-jflow";
       type string {
         length "1 .. 64";
       }
     }
     leaf routing-instance {
       description "Name of routing instance on which flow collector is reachable";
       junos:must "(\".. .. inline-jflow\")";
       junos:must-message "Routing Instances can be configured for inline-jflow";
       junos:must "(\"routing-instances $$ instance-type vrf\")";
       junos:must-message "routing instance should be defined and should be of type Virtual routing forwarding instance(VRF)";
       type string;
     }
     leaf autonomous-system-type {
       description "Type of autonomous system number to export";
       default "origin";
       type enumeration {
         enum "origin" {
           description "Export origin-AS numbers";
         }
         enum "peer" {
           description "Export peer-AS numbers";
         }
       }
     }
     container aggregation {
       description "Aggregations to perform for exported flows (version 8 only)";
       junos:must "(!(any \".. .. flow-server <*> version9\"))";
       junos:must-message "Select only one version";
       uses aggregation_type;
     }
     choice local-dump-choice {
       leaf local-dump {
         description "Dump cflowd records to log file before exporting";
         type empty;
       }
       leaf no-local-dump {
         description "Don't dump cflowd records to log file before exporting";
         type empty;
       }
     }
     leaf source-address {
       description "Source IPv4 address for cflowd packets";
       type jt:ipv4addr;
     }
     container version9 {
       presence "enable version9";
       junos:must "((!(any \".. .. .. .. inet output flow-server <*> version\") || !(any \".. .. .. .. inet output interface <*>\")))";
       junos:must-message "Select only one version or configure only RE based samping under family inet";
       junos:must "((any \".. .. interface <*>\" || \".. .. inline-jflow\"))";
       junos:must-message "Service PIC or inline-jflow (j-series and SRX only) must be specified for version9";
       description "Export data in version 9 format";
       uses apply-advanced;
       container template {
         description "Template configuration";
         uses apply-advanced;
         leaf template-name {
           description "Template name";
           junos:must "((\"services flow-monitoring version9 template $$ mpls-template\" || (\"services flow-monitoring version9 template $$ mpls-ipv4-template\" || \"services flow-monitoring version9 template $$ mpls-ipvx-template\")))";
           junos:must-message "Template type must match input protocol";
           junos:must "((!(\".. .. .. .. inline-jflow source-address\") || (\".. .. .. .. inline-jflow source-address\" && all \".. .. .. .. flow-server <*> version9 template $$\")))";
           junos:must-message "All the collector under same family should share the same template in Inline-Jflow";
           type string;
         }
       }
     }
     container version-ipfix {
       presence "enable version-ipfix";
       junos:must "(\".. .. inline-jflow\")";
       junos:must-message "inline Jflow must be specified for version-ipfix";
       description "Export data in version ipfix format";
       uses apply-advanced;
       container template {
         description "Template configuration";
         uses apply-advanced;
         leaf template-name {
           description "Template name";
           junos:must "((\"services flow-monitoring version-ipfix template $$ mpls-template\" || (\"services flow-monitoring version-ipfix template $$ mpls-ipv4-template\" || \"services flow-monitoring version-ipfix template $$ mpls-ipvx-template\")))";
           junos:must-message "Template type must match input protocol";
           junos:must "((!(\".. .. .. .. inline-jflow source-address\") || (\".. .. .. .. inline-jflow source-address\" && all \".. .. .. .. flow-server <*> version-ipfix template $$\")))";
           junos:must-message "All the collector under same family should share the same template in Inline-Jflow";
           type string;
         }
       }
     }
   }
   grouping sampling_instance_vpls_output_type {
     description "Configure output options for packet sampling";
     uses apply-advanced;
     list flow-server {
       key name;
       description "Configure sending traffic aggregates in cflowd format";
       max-elements 8;
       junos:must "(\".. inline-jflow\")";
       junos:must-message "Output 'inline Jflow' should be configured with flow-server";
       uses cflowd_instance_vpls_sampling_type;
     }
     container inline-jflow {
       description "Inline processing of sampled packets";
       presence "enable inline-jflow";
       junos:must "(any \".. flow-server <*>\")";
       junos:must-message "'flow-server' must be specified with the inline Jflow";
       uses packet_export_inline_instance;
     }
   }
   grouping cflowd_instance_vpls_sampling_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       junos:must "(\".. .. inline-jflow\")";
       junos:must-message "DSCP can be configured for inline-jflow";
       type union {
         type string {
           pattern "<.*>|$.*";
         }
         type uint8 {
           range "0 .. 63";
         }
       }
     }
     leaf forwarding-class {
       description "Forwarding-class for exported jflow packets, applicable only for inline-jflow";
       junos:must "(\".. .. inline-jflow\")";
       junos:must-message "forwarding-class can be configured for inline-jflow";
       type string {
         length "1 .. 64";
       }
     }
     leaf routing-instance {
       description "Name of routing instance on which flow collector is reachable";
       junos:must "(\".. .. inline-jflow\")";
       junos:must-message "Routing Instances can be configured for inline-jflow";
       junos:must "(\"routing-instances $$ instance-type vrf\")";
       junos:must-message "routing instance should be defined and should be of type Virtual routing forwarding instance(VRF)";
       type string;
     }
     container version9 {
       presence "enable version9";
       junos:must "(\".. .. inline-jflow\")";
       junos:must-message "inline Jflow must be specified for version9";
       description "Export data in version 9 format";
       uses apply-advanced;
       container template {
         description "Template configuration";
         uses apply-advanced;
         leaf template-name {
           description "Template name";
           junos:must "(\"services flow-monitoring version9 template $$ vpls-template\")";
           junos:must-message "Template type must match input protocol";
           junos:must "((!(\".. .. .. .. inline-jflow source-address\") || (\".. .. .. .. inline-jflow source-address\" && all \".. .. .. .. flow-server <*> version9 template $$\")))";
           junos:must-message "All the collector under same family should share the same template in Inline-Jflow";
           type string;
         }
       }
     }
     container version-ipfix {
       presence "enable version-ipfix";
       junos:must "(\".. .. inline-jflow\")";
       junos:must-message "inline Jflow must be specified for version-ipfix";
       description "Export data in version ipfix format";
       uses apply-advanced;
       container template {
         description "Template configuration";
         uses apply-advanced;
         leaf template-name {
           description "Template name";
           junos:must "(\"services flow-monitoring version-ipfix template $$ vpls-template\")";
           junos:must-message "Template type must match input protocol";
           junos:must "((!(\".. .. .. .. inline-jflow source-address\") || (\".. .. .. .. inline-jflow source-address\" && all \".. .. .. .. flow-server <*> version-ipfix template $$\")))";
           junos:must-message "All the collector under same family should share the same template in Inline-Jflow";
           type string;
         }
       }
     }
   }
   grouping sampling_output_type {
     description "Configure output options for packet sampling";
     uses apply-advanced;
     leaf aggregate-export-interval {
       description "Interval of exporting aggregate accounting information";
       default "90";
       units "seconds";
       type union {
         type string {
           pattern "<.*>|$.*";
         }
         type uint32 {
           range "90 .. 1800";
         }
       }
     }
     leaf flow-inactive-timeout {
       description "Interval of inactivity that marks a flow inactive";
       default "60";
       units "seconds";
       type union {
         type string {
           pattern "<.*>|$.*";
         }
         type uint32 {
           range "15 .. 1800";
         }
       }
     }
     leaf flow-active-timeout {
       description "Interval after which an active flow is exported";
       default "1800";
       units "seconds";
       type union {
         type string {
           pattern "<.*>|$.*";
         }
         type uint32 {
           range "60 .. 1800";
         }
       }
     }
     container file {
       junos:must "(!(any \".. extension-service <*>\"))";
       junos:must-message "This configuration is not required with 'extension-service'";
       description "Configure parameters for dumping sampled packets";
       choice enable-disable {
         case case_1 {
           leaf disable {
             description "Disable sampled packet dumps";
             type empty;
           }
         }
       }
       leaf filename {
         description "Name of file to contain sampled packet dumps";
         type string {
           length "1 .. 1024";
           junos:posix-pattern "![/ %]";
           junos:pattern-message "Must not contain '/', % or a space";
         }
       }
       leaf files {
         description "Maximum number of sampled packet dump files";
         default "10";
         type union {
           type string {
             pattern "<.*>|$.*";
           }
           type uint32 {
             range "2 .. 10000";
           }
         }
       }
       leaf size {
         description "Maximum sample dump file size";
         type string;
       }
       choice world-readable-choice {
         leaf world-readable {
           description "Allow any user to read the sampled dump";
           type empty;
         }
         leaf no-world-readable {
           description "Don't allow any user to read the sampled dump";
           type empty;
         }
       }
       choice stamp-choice {
         leaf stamp {
           description "Timestamp every packet in the dump";
           type empty;
         }
         leaf no-stamp {
           description "Don't timestamp every packet in the dump";
           type empty;
         }
       }
     }
     container port-mirroring {
       description "Configure sending sampled traffic out through an interface";
       presence "enable port-mirroring";
       junos:must "(!(any \".. extension-service <*>\"))";
       junos:must-message "This configuration is not required with 'extension-service'";
       uses inet_pm_family_output_type;
     }
     list flow-server {
       key name;
       description "Configure sending traffic aggregates in cflowd format";
       max-elements 8;
       junos:must "((!(any \".. interface <*>\") || all \".. interface <*> source-address\"))";
       junos:must-message "'output interface source-address' must be specified with 'flow-server' and 'interface'";
       uses cflowd_sampling_type;
     }
     list interface {
       key name;
       description "Interfaces used to send monitored information";
       max-elements 1;
       junos:must "((any \".. flow-server <*>\" || any \".. extension-service <*>\"))";
       junos:must-message "'flow-server' or 'extension-service' must be specified with 'interface'";
       uses packet_export_intf_type;
     }
     container inline-jflow {
       description "Inline processing of sampled packets";
       presence "enable inline-jflow";
       junos:must "(any \".. flow-server <*>\")";
       junos:must-message "'flow-server' must be specified with the inline Jflow";
       uses packet_export_inline;
     }
     list extension-service {
       key name;
       ordered-by user;
       description "Define the customer specific sampling configuration";
       junos:must "(!(\".. flow-active-timeout\"))";
       junos:must-message "'.. flow-active-timeout' is not needed with 'extension-service'";
       junos:must "(!(\".. flow-inactive-timeout\"))";
       junos:must-message "'.. flow-inactive-timeout' is not valid for 'extension-service'";
       junos:must "(!(\".. aggregate-export-interval\"))";
       junos:must-message "'.. aggregate-export-interval' is not valid for 'extension-service'";
       junos:must "(!(any \".. flow-server <*>\"))";
       junos:must-message "'.. flow-server' is not needed with 'extension-service'";
       junos:must "(!(any \".. interface <*> source-address\"))";
       junos:must-message "'.. interface source-address' is not valid for 'extension-service'";
       junos:must "(!(any \".. interface <*> engine-id\"))";
       junos:must-message "'.. interface engine-id' is not valid for 'extension-service'";
       junos:must "(!(any \".. interface <*> engine-type\"))";
       junos:must-message "'.. interface engine-type' is not valid for 'extension-service'";
       junos:must "(any \".. interface <*>\")";
       junos:must-message "'.. interface' must be specified with 'extension-service'";
       leaf name {
         description "Customer prefixed sampling service name";
         type string {
           length "1 .. 63";
         }
       }
       uses apply-advanced;
     }
   }
   grouping cflowd_sampling_type {
     leaf name {
       description "Name of host collecting cflowd packets";
       type jt:ipaddr;
     }
     uses apply-advanced;
     leaf port {
       description "UDP port number on host collecting cflowd packets";
       type union {
         type uint16;
         type string {
           pattern "<.*>|$.*";
         }
       }
     }
     leaf dscp {
       description "Numeric DSCP value in the range 0 to 63";
       default "0";
       junos:must "(\".. .. inline-jflow\")";
       junos:must-message "DSCP can be configured for inline-jflow";
       type union {
         type string {
           pattern "<.*>|$.*";
         }
         type uint8 {
           range "0 .. 63";
         }
       }
     }
     leaf forwarding-class {
       description "Forwarding-class for exported jflow packets, applicable only for inline-jflow";
       junos:must "(\".. .. inline-jflow\")";
       junos:must-message "forwarding-class can be configured for inline-jflow";
       type string {
         length "1 .. 64";
       }
     }
     leaf routing-instance {
       description "Name of routing instance on which flow collector is reachable";
       junos:must "(\".. .. inline-jflow\")";
       junos:must-message "Routing Instances can be configured for inline-jflow";
       junos:must "(\"routing-instances $$ instance-type vrf\")";
       junos:must-message "routing instance should be defined and should be of type Virtual routing forwarding instance(VRF)";
       type string;
     }
     leaf autonomous-system-type {
       description "Type of autonomous system number to export";
       default "origin";
       type enumeration {
         enum "origin" {
           description "Export origin-AS numbers";
         }
         enum "peer" {
           description "Export peer-AS numbers";
         }
       }
     }
     container aggregation {
       description "Aggregations to perform for exported flows (version 8 only)";
       junos:must "(!(any \".. .. flow-server <*> version9\"))";
       junos:must-message "Select only one version";
       uses aggregation_type;
     }
     choice local-dump-choice {
       leaf local-dump {
         description "Dump cflowd records to log file before exporting";
         type empty;
       }
       leaf no-local-dump {
         description "Don't dump cflowd records to log file before exporting";
         type empty;
       }
     }
     leaf source-address {
       description "Source IPv4 address for cflowd packets";
       type jt:ipv4addr;
     }
     container version9 {
       presence "enable version9";
       junos:must "(!(any \".. .. flow-server <*> version\"))";
       junos:must-message "Select only one version";
       junos:must "((any \".. .. interface <*>\" || \".. .. inline-jflow\"))";
       junos:must-message "Service PIC or inline-jflow (j-series and SRX only) must be specified for version9";
       description "Export data in version 9 format";
       uses apply-advanced;
       container template {
         description "Template configuration";
         uses apply-advanced;
         leaf template-name {
           description "Template name";
           junos:must "(((\"services flow-monitoring version9 template $$ ipv4-template\" && \"forwarding-options sampling input family inet\") || ((\"services flow-monitoring version9 template $$ ipv6-template\" && \"forwarding-options sampling input family inet6\") || ((\"services flow-monitoring version9 template $$ mpls-template\" && \"forwarding-options sampling input family mpls\") || ((\"services flow-monitoring version9 template $$ mpls-ipv4-template\" && \"forwarding-options sampling input family mpls\") || (\"services flow-monitoring version9 template $$ mpls-ipvx-template\" && \"forwarding-options sampling input family mpls\"))))))";
           junos:must-message "Template type must match input protocol";
           type string;
         }
       }
     }
     container version-ipfix {
       presence "enable version-ipfix";
       description "Export data in version ipfix format";
       status deprecated;
       uses apply-advanced;
       container template {
         description "Template configuration";
         uses apply-advanced;
         leaf template-name {
           description "Template name";
           type string;
         }
       }
     }
     leaf version {
       description "Format of exported cflowd aggregates";
       default "5";
       junos:must "(\"forwarding-options sampling input family inet\")";
       junos:must-message "input 'family inet' must be configured";
       junos:must "(!(any \".. .. flow-server <*> version9\"))";
       junos:must-message "Select only one version";
       type enumeration {
         enum "5" {
           description "Export cflowd aggregates in version 5 format";
           junos:must "(\"system ntp\")";
           junos:must-message " NTP must be configured for sampling v5/8/500 to work properly";
         }
         enum "8" {
           description "Export cflowd aggregates in version 8 format";
           junos:must "(\"system ntp\")";
           junos:must-message " NTP must be configured for sampling v5/8/500 to work properly";
         }
         enum "500" {
           description "Export cflowd aggregates in ASN 500 format";
           junos:must "(!(\".. .. interface\"))";
           junos:must-message "This feature is only supported for RE based sampling";
           junos:must "(\"system ntp\")";
           junos:must-message " NTP must be configured for sampling v5/8/500 to work properly";
         }
       }
     }
   }
   grouping sampling_traceoptions_type {
     description "Configure packet sampling traceoptions";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
   }
   grouping server-group-type {
     uses apply-advanced;
     list server-group {
       key name;
       ordered-by user;
       description "One or more server groups";
       leaf name {
         description "Server group name";
         type string {
           length "1 .. 64";
           junos:posix-pattern "^[A-Za-z0-9][_0-9A-Za-z-]*$";
           junos:pattern-message "Must be a non-reserved string of 64 characters or less";
         }
       }
       uses apply-advanced;
       list address {
         key name;
         ordered-by user;
         description "IP Address of one or more DHCP servers";
         leaf name {
           description "IP Address of DHCP server";
           type jt:ipaddr;
         }
         uses apply-advanced;
       }
     }
   }
   grouping server-match-action-choice {
     uses apply-advanced;
     choice v4-action-choice {
       case case_1 {
         leaf forward-only {
           description "Forward without subscriber services";
           type empty;
         }
       }
       case case_2 {
         leaf create-relay-entry {
           description "Create relay entry and allow subscriber services";
           type empty;
         }
       }
     }
   }
   grouping server-match-v6-ascii-hex {
     uses apply-advanced;
     list ascii {
       key name;
       description "ASCII string";
       leaf name {
         description "ASCII string";
         type string {
           length "1 .. 256";
         }
       }
       uses apply-advanced;
       choice server-match-action-choice {
         case case_1 {
           leaf forward-only {
             description "Forward without subscriber services when a match is made";
             type empty;
           }
         }
         case case_2 {
           leaf create-relay-entry {
             description "Create relay entry and allow subscriber services";
             type empty;
           }
         }
       }
     }
     list hexadecimal {
       key name;
       description "Hexadecimal string";
       leaf name {
         description "Hexadecimal string";
         type string {
           length "1 .. 512";
           junos:posix-pattern "^[[:xdigit:]]+$";
           junos:pattern-message "Must be hexadecimal digits (0-9, a-f, A-F)";
         }
       }
       uses apply-advanced;
       choice server-match-action-choice {
         case case_1 {
           leaf forward-only {
             description "Forward without subscriber services when a match is made";
             type empty;
           }
         }
         case case_2 {
           leaf create-relay-entry {
             description "Create relay entry and allow subscriber services";
             type empty;
           }
         }
       }
     }
   }
   grouping slaacd-config-type {
     description "Slaacd configuration options";
     uses apply-advanced;
     container vlans {
       description "Slaac config on vlan";
       uses apply-advanced;
       list vlan-config {
         key name;
         description "Virtual LAN configuration";
         uses vlan-slaacd;
       }
     }
     container interface {
       description "Slaac config on interface";
       uses apply-advanced;
       list intf-config {
         key name;
         description "Interface configuration";
         uses slaacd-interface;
       }
     }
     container link-local-expiry-interval {
       description "Link local address expiry interval";
       uses apply-advanced;
       leaf interval {
         description "Expiry interval";
         default "86400";
         units "seconds";
         type union {
           type string {
             pattern "<.*>|$.*";
           }
           type uint32 {
             range "60 .. 86400";
           }
         }
       }
     }
     container traceoptions {
       description "Slaac Snooping trace options";
       uses apply-advanced;
       leaf no-remote-trace {
         description "Disable remote tracing";
         junos:must "(\"system tracing\")";
         junos:must-message "'no-remote-trace' is valid only when [system tracing] is configured";
         type empty;
       }
       container file {
         description "Trace file information";
         leaf filename {
           description "Name of file in which to write trace information";
           type string {
             length "1 .. 1024";
             junos:posix-pattern "![/ %]";
             junos:pattern-message "Must not contain '/', % or a space";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         description "Tracing parameters";
         leaf name {
           type enumeration {
             enum "configuration" {
               description "Log configuration events";
             }
             enum "init" {
               description "Trace init message events";
             }
             enum "state" {
               description "Trace state message events";
             }
             enum "rtsock" {
               description "Trace rtsock message events";
             }
             enum "packet" {
               description "Trace packet events";
             }
             enum "fsm" {
               description "Trace fsm update events";
             }
             enum "io" {
               description "Trace io events";
             }
             enum "verbose" {
               description "Trace verbose events";
             }
             enum "task" {
               description "Trace TASK related events";
             }
             enum "all" {
               description "Trace all events";
             }
           }
         }
       }
     }
   }
   grouping slaacd-interface {
     description "Interface name";
     leaf name {
       description "Interface name";
       type string;
     }
     uses apply-advanced;
     container mark-interface {
       junos:must "(!(\".. max-allowed-contention\"))";
       junos:must-message "Trusted interface cannot have contention configuration.";
       description "Mark interface";
       uses apply-advanced;
       leaf trusted {
         description "Mark interface trusted";
         type empty;
       }
     }
     container auto-dad {
       description "Auto duplicate address detection";
       uses apply-advanced;
       leaf retries {
         description "DAD retry value";
         default "1";
         type union {
           type string {
             pattern "<.*>|$.*";
           }
           type uint16 {
             range "1 .. 3";
           }
         }
       }
       leaf retrans-interval {
         description "DAD re-transmission interval";
         default "1";
         units "seconds";
         type union {
           type string {
             pattern "<.*>|$.*";
           }
           type uint16 {
             range "1 .. 6";
           }
         }
       }
     }
     container max-allowed-contention {
       junos:must "(!(\".. mark-interface trusted\"))";
       junos:must-message "Trusted interface cannot have contention configuration.";
       description "Maximum allowed contention count";
       uses apply-advanced;
       leaf count {
         description "Contention count";
         junos:must "(\".. duration\")";
         junos:must-message "Duration cannot be zero for non-zero count.";
         type union {
           type string {
             pattern "<.*>|$.*";
           }
           type uint16 {
             range "1 .. 10";
           }
         }
       }
       leaf duration {
         description "Contention duration";
         units "seconds";
         junos:must "(\".. count\")";
         junos:must-message "Count cannot be zero for non-zero duration.";
         type union {
           type string {
             pattern "<.*>|$.*";
           }
           type uint16 {
             range "60 .. 3600";
           }
         }
       }
     }
   }
   grouping smpl-analyzer-type {
     leaf name {
       description "Analyzer name";
       junos:must "(!(\"forwarding-options sampling instance $$\"))";
       junos:must-message "analyzer must not have the same name as of any other sampling instance";
       junos:must "(!(\"forwarding-options port-mirroring instance $$\"))";
       junos:must-message "analyzer must not have the same name as of any other port mirror instance";
       type string {
         length "1 .. 63";
         junos:posix-pattern "^[[:alpha:]][[:alnum:]_-]+$";
         junos:pattern-message "Must be a string beginning with a letter and             consisting of letters, numbers, dashes, and underscores";
       }
     }
     uses apply-advanced;
     container input {
       description "Ports and VLANs to monitor";
       uses smpl-analyzer-input-type;
     }
     container output {
       description "Outgoing port or VLAN for mirrored packets";
       uses smpl-analyzer-output-type;
     }
   }
   grouping smpl-analyzer-input-type {
     uses apply-advanced;
     leaf rate {
       description "Ratio of packets to be sampled (1 out of N)";
       type union {
         type string {
           pattern "<.*>|$.*";
         }
         type uint32 {
           range "1 .. 65535";
         }
       }
     }
     leaf maximum-packet-length {
       description "Maximum length of the mirrored packet";
       units "bytes";
       type union {
         type string {
           pattern "<.*>|$.*";
         }
         type uint32 {
           range "0 .. 9216";
         }
       }
     }
     container ingress {
       description "Ports and VLANs to monitor incoming traffic";
       uses smpl-analyzer-ingress-type;
     }
     container egress {
       description "Ports and VLANs to monitor outgoing traffic";
       uses smpl-analyzer-egress-type;
     }
   }
   grouping smpl-analyzer-egress-type {
     uses apply-advanced;
     list interface {
       key name;
       ordered-by user;
       description "Port to monitor outgoing traffic";
       uses analyzer-egress-interface-type;
     }
     list routing-instance {
       key name;
       description "Routing instances";
       uses analyzer-egress-routing-instance-type;
     }
     list vlan {
       key name;
       ordered-by user;
       description "VLAN to monitor outgoing traffic";
       uses analyzer-egress-vlan-type;
     }
     list bridge-domain {
       key name;
       ordered-by user;
       description "Bridge-domain to monitor outgoing traffic";
       uses analyzer-egress-bridge-domain-type;
     }
   }
   grouping analyzer-egress-bridge-domain-type {
     leaf name {
       description "Bridge domain name, VLAN id or VLAN range string";
       junos:must "(!(any \"forwarding-options analyzer <*> output bridge-domain $$\"))";
       junos:must-message "bridge-domain must not be output of any analyzer session";
       junos:must "(unique \"forwarding-options analyzer <*> input egress bridge-domain $$\")";
       junos:must-message "bridge-domain must not be input egress to any other analyzer";
       type string;
     }
     uses apply-advanced;
   }
   grouping analyzer-egress-interface-type {
     leaf name {
       description "Logical interface name";
       type string;
     }
     uses apply-advanced;
   }
   grouping analyzer-egress-routing-instance-type {
     leaf name {
       description "Routing instance name";
       type string {
         junos:posix-pattern "!^((__.*__)|(all)|(.*[ ].*)|(\"\")|(.{129,}))$";
         junos:pattern-message "Must be a non-reserved string of 128 characters or less with no spaces.";
       }
     }
     uses apply-advanced;
     list vlan {
       key name;
       ordered-by user;
       description "VLAN to monitor outgoing traffic";
       uses analyzer-egress-vlan-type;
     }
     list bridge-domain {
       key name;
       ordered-by user;
       description "Bridge-domain to monitor outgoing traffic";
       uses analyzer-egress-bridge-domain-type;
     }
   }
   grouping analyzer-egress-vlan-type {
     leaf name {
       description "VLAN name, VLAN id or VLAN range string";
       junos:must "(!(any \"forwarding-options analyzer <*> output vlan $$\"))";
       junos:must-message "vlan must not be output of any analyzer session";
       junos:must "(unique \"forwarding-options analyzer <*> input egress vlan $$\")";
       junos:must-message "vlan must not be input egress to any other analyzer";
       type string;
     }
     uses apply-advanced;
   }
   grouping smpl-analyzer-ingress-type {
     uses apply-advanced;
     list interface {
       key name;
       ordered-by user;
       description "Port to monitor incoming traffic";
       uses analyzer-ingress-interface-type;
     }
     list routing-instance {
       key name;
       description "Routing instances";
       uses analyzer-ingress-routing-instance-type;
     }
     list vlan {
       key name;
       ordered-by user;
       description "VLAN to monitor incoming traffic";
       uses analyzer-ingress-vlan-type;
     }
     list bridge-domain {
       key name;
       ordered-by user;
       description "Bridge-domain to monitor incoming traffic";
       uses analyzer-ingress-bridge-domain-type;
     }
   }
   grouping analyzer-ingress-bridge-domain-type {
     leaf name {
       description "Bridge domain name, VLAN id or VLAN range string";
       junos:must "(!(any \"forwarding-options analyzer <*> output bridge-domain $$\"))";
       junos:must-message "vlan must not be output of any analyzer session";
       junos:must "(unique \"forwarding-options analyzer <*> input ingress bridge-domain $$\")";
       junos:must-message "vlan must not be input ingress to any other analyzer";
       junos:must "(!(\"vlans $$ vlan-id-list\"))";
       junos:must-message "vlan-id-list cannot be configured on forwarding-options analyzer";
       type string;
     }
     uses apply-advanced;
   }
   grouping analyzer-ingress-interface-type {
     leaf name {
       description "Logical interface name";
       type string;
     }
     uses apply-advanced;
   }
   grouping analyzer-ingress-routing-instance-type {
     leaf name {
       description "Routing instance name";
       type string {
         junos:posix-pattern "!^((__.*__)|(all)|(.*[ ].*)|(\"\")|(.{129,}))$";
         junos:pattern-message "Must be a non-reserved string of 128 characters or less with no spaces.";
       }
     }
     uses apply-advanced;
     list vlan {
       key name;
       ordered-by user;
       description "VLAN to monitor incoming traffic";
       uses analyzer-ingress-vlan-type;
     }
     list bridge-domain {
       key name;
       ordered-by user;
       description "Bridge-domain to monitor incoming traffic";
       uses analyzer-ingress-bridge-domain-type;
     }
   }
   grouping analyzer-ingress-vlan-type {
     leaf name {
       description "VLAN name, VLAN id or VLAN range string";
       junos:must "(!(any \"forwarding-options analyzer <*> output vlan $$\"))";
       junos:must-message "vlan must not be output of any analyzer session";
       junos:must "(unique \"forwarding-options analyzer <*> input ingress vlan $$\")";
       junos:must-message "vlan must not be input ingress to any other analyzer";
       junos:must "(!(\"vlans $$ vlan-id-list\"))";
       junos:must-message "vlan-id-list cannot be configured on forwarding-options analyzer";
       type string;
     }
     uses apply-advanced;
   }
   grouping smpl-analyzer-output-type {
     uses apply-advanced;
     choice interface_or_vlan {
       case case_1 {
         leaf interface {
           description "Outgoing port for mirrored packets";
           junos:must "(!(\"interfaces $$-IFL family inet\"))";
           junos:must-message "An interface configured as family inet cannot be configured as analyzer output interface";
           type union {
             type jt:interface-name;
             type string {
               pattern "<.*>|$.*";
             }
           }
         }
       }
       case case_2 {
         leaf ip-address {
           description "ERSPAN Destination IP Address";
           type jt:ipv4addr;
         }
       }
       case case_3 {
         leaf next-hop-group {
           description "Next-hop-group through which to send port-mirror traffic";
           junos:must "(\"forwarding-options next-hop-group $$ group-type layer-2\")";
           junos:must-message "Referenced next-hop-group must be defined as layer-2 group";
           type string;
         }
       }
       case case_4 {
         list routing-instance {
           key name;
           description "Routing instances";
           max-elements 1;
           uses output-routing-instance-type;
         }
       }
       case case_5 {
         list vlan {
           key name;
           description "Outgoing VLAN for mirrored packets";
           max-elements 1;
           uses pm-rspan-vlan;
         }
       }
       case case_6 {
         list bridge-domain {
           key name;
           description "Outgoing bridge-domain for mirrored packets";
           max-elements 1;
           uses pm-rspan-bridge-domain;
         }
       }
     }
   }
   grouping output-routing-instance-type {
     leaf name {
       description "Routing instance name";
       type string {
         junos:posix-pattern "!^((__.*__)|(all)|(.*[ ].*)|(\"\")|(.{129,}))$";
         junos:pattern-message "Must be a non-reserved string of 128 characters or less with no spaces.";
       }
     }
     uses apply-advanced;
     leaf ip-address {
       description "ERSPAN Destination IP Address";
       type jt:ipv4addr;
     }
     list vlan {
       key name;
       description "Outgoing VLAN for mirrored packets";
       max-elements 1;
       uses pm-rspan-vlan;
     }
     list bridge-domain {
       key name;
       description "Outgoing bridge-domain for mirrored packets";
       max-elements 1;
       uses pm-rspan-bridge-domain;
     }
   }
   grouping v6-relay-option-interface-id-type {
     description "Interface ID processing";
     uses apply-advanced;
     container prefix {
       description "Add prefix to circuit/interface-id or remote-id";
       uses apply-advanced;
       leaf host-name {
         description "Add router host name to circuit / interface-id or remote-id";
         type empty;
       }
       leaf logical-system-name {
         description "Add logical system name to circuit / interface-id or remote-id";
         type empty;
       }
       leaf routing-instance-name {
         description "Add routing instance name to circuit / interface-id or remote-id";
         type empty;
       }
     }
     leaf use-interface-description {
       description "Use interface description instead of circuit identifier";
       junos:must "(!(\".. require-interface-description\"))";
       junos:must-message "use-interface-description may not be set with require-interface-desciption";
       type enumeration {
         enum "logical" {
           description "Use the logical interface description";
         }
         enum "device" {
           description "Use the device interface description";
         }
       }
     }
     leaf use-vlan-id {
       description "Use VLAN id instead of name";
       junos:must "((!(\".. no-vlan-interface-name\") && (!(\".. use-interface-description\") && !(\".. require-interface-description\"))))";
       junos:must-message "Vlan-tag cannot be added as no-vlan-interface-name or interface-description is configured";
       type empty;
     }
     leaf no-vlan-interface-name {
       description "Not include vlan or interface name";
       type empty;
     }
     leaf include-irb-and-l2 {
       description "Include IRB and L2 interface name";
       type empty;
     }
     container use-option-82 {
       description "Use option-82 circuit-id for interface-id";
       presence "enable use-option-82";
       uses v6-relay-option-cid-rid-action;
     }
     container keep-incoming-interface-id {
       description "Keep incoming interface identifier";
       presence "enable keep-incoming-interface-id";
       uses v6-relay-option-cid-rid-action;
     }
   }
   grouping v6-relay-option-cid-rid-action {
     uses apply-advanced;
     leaf strict {
       description "Drop packet if id not present";
       type empty;
     }
   }
   grouping v6-relay-option-remote-id-type {
     description "Remote ID processing";
     uses apply-advanced;
     container prefix {
       description "Add prefix to circuit/interface-id or remote-id";
       uses apply-advanced;
       leaf host-name {
         description "Add router host name to circuit / interface-id or remote-id";
         type empty;
       }
       leaf logical-system-name {
         description "Add logical system name to circuit / interface-id or remote-id";
         type empty;
       }
       leaf routing-instance-name {
         description "Add routing instance name to circuit / interface-id or remote-id";
         type empty;
       }
     }
     leaf use-interface-description {
       description "Use interface description instead of circuit identifier";
       junos:must "(!(\".. require-interface-description\"))";
       junos:must-message "use-interface-description may not be set with require-interface-desciption";
       type enumeration {
         enum "logical" {
           description "Use the logical interface description";
         }
         enum "device" {
           description "Use the device interface description";
         }
       }
     }
     leaf use-vlan-id {
       description "Use VLAN id instead of name";
       junos:must "((!(\".. no-vlan-interface-name\") && (!(\".. use-interface-description\") && !(\".. require-interface-description\"))))";
       junos:must-message "Vlan-tag cannot be added as no-vlan-interface-name or interface-description is configured";
       type empty;
     }
     leaf no-vlan-interface-name {
       description "Not include vlan or interface name";
       type empty;
     }
     leaf include-irb-and-l2 {
       description "Include IRB and L2 interface name";
       type empty;
     }
     container use-option-82 {
       description "Use option-82 remote-id for v6 remote-id";
       presence "enable use-option-82";
       uses v6-relay-option-cid-rid-action;
     }
     leaf keep-incoming-remote-id {
       description "Keep incoming remote identifier";
       type empty;
     }
   }
   grouping v6-server-group-type {
     uses apply-advanced;
     list server-group {
       key name;
       ordered-by user;
       description "One or more server groups";
       leaf name {
         description "DHCPv6 Server group name";
         type string {
           length "1 .. 64";
           junos:posix-pattern "^[A-Za-z0-9][_0-9A-Za-z-]*$";
           junos:pattern-message "Must be a non-reserved string of 64 characters or less";
         }
       }
       uses apply-advanced;
       list address {
         key name;
         ordered-by user;
         description "IP Address of one or more DHCP servers";
         max-elements 32;
         leaf name {
           description "IP Address of DHCP server";
           type jt:ipaddr;
         }
         uses apply-advanced;
       }
     }
   }
   grouping vlan-policy {
     description "Virtual LAN";
     leaf name {
       description "VLAN id";
       type string;
     }
     uses apply-advanced;
     container policy {
       description "Attach policy";
       uses apply-advanced;
       leaf policy-name {
         description "Router Advertisement Guard policy name";
         type string;
       }
       choice policy-type {
         case case_1 {
           leaf stateful {
             description "Stateful router advertisement guard";
             type empty;
           }
         }
         case case_2 {
           leaf stateless {
             description "Stateless router advertisement guard";
             type empty;
           }
         }
       }
     }
   }
   grouping vlan-slaacd {
     description "Virtual LAN";
     leaf name {
       description "VLAN id";
       type string;
     }
     uses apply-advanced;
   }
   grouping write-option-82-type {
     uses apply-advanced;
   }
 }
