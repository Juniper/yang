/*
 * Copyright (c) 2019 Juniper Networks, Inc.
 * All rights reserved.
 */
 module junos-rpc-ospf {
   namespace "http://yang.juniper.net/junos/rpc/ospf";

   prefix ospf;

   import junos-common-types {
     prefix jt;
   }

   organization "Juniper Networks, Inc.";

   contact "yang-support@juniper.net";

   description "Junos RPC YANG module for ospf command(s)";

   revision 2019-01-01 {
     description "Junos: 18.4R3.3";
   }

   rpc get-ospf-overview-information {
     description "Show overview of OSPF information";
     input {
       leaf logical-system {
         description "Name of logical system, or 'all'";
         type string {
         }
       }
       leaf verbosity_level {
         default "brief";
         type enumeration {
           enum "brief" {
             description "Display brief output (default)";
           }
           enum "extensive" {
             description "Display extensive output";
           }
         }
       }
       leaf instance {
         description "Name of OSPF instance";
         type string;
       }
     }
     output {
       choice output_c {
         case output-tag {
           leaf output {
             type string;
           }
         }
         case actual-tag {
           anyxml ospf-overview-information;
         }
         case multichassis-tag {
           anyxml multi-routing-engine-results;
         }
       }
     }
   }
   rpc get-ospf-database-information {
     description "Show OSPF link-state database";
     input {
       leaf logical-system {
         description "Name of logical system, or 'all'";
         type string {
         }
       }
       leaf level {
         default "brief";
         type enumeration {
           enum "brief" {
             description "Display brief output (default)";
           }
           enum "detail" {
             description "Display detailed output";
           }
           enum "extensive" {
             description "Display extensive output";
           }
           enum "summary" {
             description "Display summary output";
           }
         }
       }
       leaf lsa-type {
         type enumeration {
           enum "router" {
             description "Router link-state advertisements";
           }
           enum "network" {
             description "Network link-state advertisements";
           }
           enum "netsummary" {
             description "Summary network link-state advertisements";
           }
           enum "asbrsummary" {
             description "Summary AS boundary router link-state advertisements";
           }
           enum "external" {
             description "External link-state advertisements";
           }
           enum "nssa" {
             description "Not-so-stubby area link-state advertisements";
           }
           enum "link-local" {
             description "Link local link-state advertisements";
           }
           enum "opaque-area" {
             description "Opaque area-scope link-state advertisements";
           }
           enum "opaque-as" {
             description "Opaque as-scope link-state advertisements";
           }
         }
       }
       leaf area {
         description "OSPF area ID";
         default "all";
         type string;
       }
       leaf lsa-id {
         description "Link-state advertisement ID";
         default "all";
         type string;
       }
       leaf advertising-router {
         description "Router ID of advertising router";
         type string;
       }
       leaf instance {
         description "Name of OSPF instance";
         type string;
       }
     }
     output {
       choice output_c {
         case output-tag {
           leaf output {
             type string;
           }
         }
         case actual-tag {
           anyxml ospf-database-information;
         }
         case multichassis-tag {
           anyxml multi-routing-engine-results;
         }
       }
     }
   }
   rpc get-ospf-interface-information {
     description "Show OSPF interface status information";
     input {
       leaf logical-system {
         description "Name of logical system, or 'all'";
         type string {
         }
       }
       leaf verbosity_level {
         default "brief";
         type enumeration {
           enum "brief" {
             description "Display brief output (default)";
           }
           enum "detail" {
             description "Display detailed output";
           }
           enum "extensive" {
             description "Display extensive output";
           }
         }
       }
       leaf interface-name {
         description "Name of logical interface";
         type string;
       }
       leaf area {
         description "OSPF area ID";
         type jt:areaid;
       }
       leaf instance {
         description "Name of OSPF instance";
         type string;
       }
     }
     output {
       choice output_c {
         case output-tag {
           leaf output {
             type string;
           }
         }
         case actual-tag {
           anyxml ospf-interface-information;
         }
         case multichassis-tag {
           anyxml multi-routing-engine-results;
         }
       }
     }
   }
   rpc get-ospf-context-id-information {
     description "Show OSPF context identifier information";
     input {
       leaf logical-system {
         description "Name of logical system, or 'all'";
         type string {
         }
       }
       leaf verbosity_level {
         default "brief";
         type enumeration {
           enum "brief" {
             description "Display brief output (default)";
           }
           enum "detail" {
             description "Display detailed output";
           }
         }
       }
       leaf context-id {
         description "IP address representing a context identifier";
         type string;
       }
       leaf area {
         description "OSPF area ID";
         type jt:areaid;
       }
       leaf instance {
         description "Name of OSPF instance";
         type string;
       }
     }
     output {
       choice output_c {
         case output-tag {
           leaf output {
             type string;
           }
         }
         case actual-tag {
           anyxml ospf-context-id-information;
         }
         case multichassis-tag {
           anyxml multi-routing-engine-results;
         }
       }
     }
   }
   rpc get-ospf-neighbor-information {
     description "Show OSPF neighbor status information";
     input {
       leaf logical-system {
         description "Name of logical system, or 'all'";
         type string {
         }
       }
       leaf verbosity_level {
         default "brief";
         type enumeration {
           enum "brief" {
             description "Display brief output (default)";
           }
           enum "detail" {
             description "Display detailed output";
           }
           enum "extensive" {
             description "Display extensive output";
           }
         }
       }
       leaf interface {
         description "Name of logical interface";
         type string;
       }
       leaf area {
         description "OSPF area ID";
         type jt:areaid;
       }
       leaf neighbor {
         description "IP address or ID of neighbor";
         type string;
       }
       leaf instance {
         description "Name of OSPF instance";
         type string;
       }
     }
     output {
       choice output_c {
         case output-tag {
           leaf output {
             type string;
           }
         }
         case actual-tag {
           anyxml ospf-neighbor-information;
         }
         case multichassis-tag {
           anyxml multi-routing-engine-results;
         }
       }
     }
   }
   rpc get-ospf-route-information {
     description "Show OSPF routing table";
     input {
       leaf logical-system {
         description "Name of logical system, or 'all'";
         type string {
         }
       }
       leaf topology {
         description "Name of topology";
         type string;
       }
       leaf path-type {
         description "OSPF path type";
         type enumeration {
           enum "intra" {
             description "Display intra-area routes";
           }
           enum "inter" {
             description "Display inter-area routes";
           }
           enum "extern" {
             description "Display external routes";
           }
         }
       }
       leaf route-type {
         description "OSPF route type";
         type enumeration {
           enum "router" {
             description "Display routes to all routers";
           }
           enum "abr" {
             description "Display routes to area border routers";
           }
           enum "asbr" {
             description "Display routes to AS border routers";
           }
           enum "network" {
             description "Display routes to networks";
           }
         }
       }
       leaf no-backup-coverage {
         description "Display routes with no backup coverage";
         type empty;
       }
       leaf destination {
         description "IP address and optional prefix length of destination";
         type jt:ipv4prefix;
       }
       leaf verbosity_level {
         default "brief";
         type enumeration {
           enum "brief" {
             description "Display brief output (default)";
           }
           enum "detail" {
             description "Display detailed output";
           }
           enum "extensive" {
             description "Display extensive output";
           }
         }
       }
       leaf instance {
         description "Name of OSPF instance";
         type string;
       }
     }
     output {
       choice output_c {
         case output-tag {
           leaf output {
             type string;
           }
         }
         case actual-tag {
           anyxml ospf-route-information;
         }
         case multichassis-tag {
           anyxml multi-routing-engine-results;
         }
       }
     }
   }
   rpc get-ospf-statistics-information {
     description "Show OSPF statistics";
     input {
       leaf logical-system {
         description "Name of logical system, or 'all'";
         type string {
         }
       }
       leaf instance {
         description "Name of OSPF instance";
         type string;
       }
     }
     output {
       choice output_c {
         case output-tag {
           leaf output {
             type string;
           }
         }
         case actual-tag {
           anyxml ospf-statistics-information;
         }
         case multichassis-tag {
           anyxml multi-routing-engine-results;
         }
       }
     }
   }
   rpc get-ospf-io-statistics-information {
     description "Show OSPF I/O statistics";
     input {
       leaf logical-system {
         description "Name of logical system, or 'all'";
         type string {
         }
       }
     }
     output {
       choice output_c {
         case output-tag {
           leaf output {
             type string;
           }
         }
         case actual-tag {
           anyxml ospf-io-statistics-information;
         }
         case multichassis-tag {
           anyxml multi-routing-engine-results;
         }
       }
     }
   }
   rpc get-ospf-log-information {
     description "Show shortest-path-first calculations from OSPF log";
     input {
       leaf logical-system {
         description "Name of logical system, or 'all'";
         type string {
         }
       }
       leaf instance {
         description "Name of OSPF instance";
         type string;
       }
       leaf topology {
         description "Name of topology";
         type string;
       }
     }
     output {
       choice output_c {
         case output-tag {
           leaf output {
             type string;
           }
         }
         case actual-tag {
           anyxml ospf-log-information;
         }
         case multichassis-tag {
           anyxml multi-routing-engine-results;
         }
       }
     }
   }
   rpc get-ospf-backup-spf-information {
     description "Show OSPF backup SPF calculations information";
     input {
       leaf logical-system {
         description "Name of logical system, or 'all'";
         type string {
         }
       }
       leaf instance {
         description "Name of OSPF instance";
         type string;
       }
       leaf topology {
         description "Name of topology";
         type string;
       }
       leaf area {
         description "OSPF area ID";
         type jt:areaid;
       }
       leaf no-coverage {
         description "Entries with no backup coverage";
         type empty;
       }
       leaf node-id {
         description "Display nodes matching the node-id";
         type string;
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml ospf-backup-spf-information;
         }
         case multichassis-tag {
           anyxml multi-routing-engine-results;
         }
       }
     }
   }
   rpc get-ospf-backup-lsp-information {
     description "Show OSPF MPLS backup LSP information";
     input {
       leaf logical-system {
         description "Name of logical system, or 'all'";
         type string {
         }
       }
     }
     output {
       choice output_c {
         case output-tag {
           leaf output {
             type string;
           }
         }
         case actual-tag {
           anyxml ospf-backup-mplsp-information;
         }
         case multichassis-tag {
           anyxml multi-routing-engine-results;
         }
       }
     }
   }
   rpc get-ospf-backup-coverage-information {
     description "Show OSPF backup coverage";
     input {
       leaf logical-system {
         description "Name of logical system, or 'all'";
         type string {
         }
       }
       leaf instance {
         description "Name of OSPF instance";
         type string;
       }
       leaf topology {
         description "Name of topology";
         type string;
       }
     }
     output {
       choice output_c {
         case output-tag {
           leaf output {
             type string;
           }
         }
         case actual-tag {
           anyxml ospf-backup-coverage-information;
         }
         case multichassis-tag {
           anyxml multi-routing-engine-results;
         }
       }
     }
   }
   rpc get-ospf-backup-neighbor-information {
     description "Show OSPF backup neighbors";
     input {
       leaf logical-system {
         description "Name of logical system, or 'all'";
         type string {
         }
       }
       leaf instance {
         description "Name of OSPF instance";
         type string;
       }
       leaf topology {
         description "Name of topology";
         type string;
       }
       leaf area {
         description "OSPF area ID";
         type jt:areaid;
       }
     }
     output {
       choice output_c {
         case output-tag {
           leaf output {
             type string;
           }
         }
         case actual-tag {
           anyxml ospf-backup-neighbor-information;
         }
         case multichassis-tag {
           anyxml multi-routing-engine-results;
         }
       }
     }
   }
   rpc get-ospf-bgporr-information {
     description "Show BGP optimal route-reflection groups";
     input {
       leaf logical-system {
         description "Name of logical system, or 'all'";
         type string {
         }
       }
       leaf topology {
         description "Name of topology";
         type string;
       }
       leaf path-type {
         description "OSPF path type";
         type enumeration {
           enum "intra" {
             description "Display intra-area routes";
           }
           enum "inter" {
             description "Display inter-area routes";
           }
           enum "extern" {
             description "Display external routes";
           }
         }
       }
       leaf route-type {
         description "OSPF route type";
         type enumeration {
           enum "router" {
             description "Display routes to all routers";
           }
           enum "abr" {
             description "Display routes to area border routers";
           }
           enum "asbr" {
             description "Display routes to AS border routers";
           }
           enum "network" {
             description "Display routes to networks";
           }
         }
       }
       leaf destination {
         description "IP address and optional prefix length of destination";
         type jt:ipv4prefix;
       }
       leaf instance {
         description "Name of OSPF instance";
         type string;
       }
       leaf group {
         description "BGP optimal route-reflection peer group name";
         type string;
       }
       leaf verbosity_level {
         default "brief";
         type enumeration {
           enum "brief" {
             description "Display brief output (default)";
           }
           enum "detail" {
             description "Display detailed output";
           }
           enum "extensive" {
             description "Display extensive output";
           }
         }
       }
     }
     output {
       choice output_c {
         case output-tag {
           leaf output {
             type string;
           }
         }
         case actual-tag {
           anyxml ospf-bgporr-route-information;
         }
         case multichassis-tag {
           anyxml multi-routing-engine-results;
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member";
           type union {
             type string {
               pattern "<.*>|$.*";
             }
             type uint32;
           }
         }
       }
     }
   }
 }
