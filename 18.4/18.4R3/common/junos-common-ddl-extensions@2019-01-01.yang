/*
 * Copyright (c) 2019 Juniper Networks, Inc.
 * All rights reserved.
 */
 module junos-common-ddl-extensions {
   namespace "http://yang.juniper.net/junos/common/ddl-extensions";

   prefix junos;

   organization "Juniper Networks, Inc.";

   contact "yang-support@juniper.net";

   description "This module contains definitions for Junos YANG extensions.";

   revision 2019-01-01 {
     description "Junos: 18.4R3.3";
   }

   extension must {
     argument "stmt-algebra";
     description "
      expression of configuration-statement paths having special
      keywords like any, all, unique";
   }
   extension must-message {
     argument "message-string";
     description "
      When specifying the junos:must constraint, a must-message should
      also be specified so that when the contraint is not met,the 
      warning message informs users what the constraints are.

      If the must-message is missing, the input file will compile,
      but the warning message will say (null) which won't be 
      helpful for users to fix the problem";
   }
   extension posix-pattern {
     argument "value";
     description "
      expression of pattern in posix format";
   }
   extension pattern-message {
     argument "value";
     description "
      Error message in case of mismatch";
   }
   extension command {
     argument "command";
     description "
      The junos cli command for this rpc";
   }
   extension action-execute {
     description "
      The junos action execute for rpc";
   }
   extension script {
     argument "script";
     description "
      The junos action execute script for rpc";
   }
   extension trans-script {
     argument "value";
     description "
      List of space seperated tranlsation scripts invoked by 
      associated hierarchy";
   }
 }
