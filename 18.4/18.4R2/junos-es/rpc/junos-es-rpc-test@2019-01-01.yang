/*
 * Copyright (c) 2019 Juniper Networks, Inc.
 * All rights reserved.
 */
 module junos-es-rpc-test {
   namespace "http://yang.juniper.net/junos-es/rpc/test";

   prefix test;

   import junos-common-types {
     prefix jt;
   }

   organization "Juniper Networks, Inc.";

   contact "yang-support@juniper.net";

   description "Junos RPC YANG module for test command(s)";

   revision 2019-01-01 {
     description "Junos: 18.4R2.7";
   }

   rpc test-services-traffic-load-balance-code-coverage {
     description "Execute Traffic load balance code-coverage";
     input {
       leaf database-id {
         description "Database identifier";
         type enumeration {
           enum "all" {
             description "All databases";
           }
           enum "probe" {
             description "Probe database";
           }
           enum "firewall" {
             description "Firewall";
           }
           enum "ip-db" {
             description "Ip database";
           }
           enum "clear-db" {
             description "Clear all databases";
           }
           enum "stats" {
             description "Stats";
           }
           enum "group-db" {
             description "Group database";
           }
           enum "heap" {
             description "Heap";
           }
           enum "virtual-svc-db" {
             description "Virtual srv database";
           }
           enum "instance-db" {
             description "Instance database";
           }
           enum "real-svc-db" {
             description "Real srv database";
           }
           enum "group-real-svc-db" {
             description "Group real srv database";
           }
           enum "validation-db" {
             description "Validation database";
           }
           enum "pconn-db" {
             description "Pconn database";
           }
           enum "gencfg-db" {
             description "Gencfg database";
           }
           enum "main" {
             description "Main functions";
           }
           enum "snmp" {
             description "SNMP functions";
           }
           enum "ui" {
             description "UI functions";
           }
           enum "config-parse" {
             description "Config parse functions";
           }
           enum "filter-config" {
             description "Filter database";
           }
           enum "ssd" {
             description "SSD functions";
           }
           enum "commit-checks" {
             description "Commit checks";
           }
         }
       }
     }
     output {
       choice output_c {
         case output-tag {
           leaf output {
             type string;
           }
         }
         case multichassis-tag {
           anyxml multi-routing-engine-results;
         }
       }
     }
   }
   rpc test-services-traffic-load-balance-inject-error {
     description "Execute Traffic load balance error-injection";
     input {
       leaf error-id {
         description "Error identifier";
         type union {
           type uint32;
           type string {
             pattern "<.*>|$.*";
           }
         }
         mandatory true;
       }
       leaf always-fail {
         description "Fail always";
         type enumeration {
           enum "enable" {
             description "Enable failure";
           }
           enum "disable" {
             description "Disable failure";
           }
         }
         mandatory true;
       }
     }
     output {
       choice output_c {
         case output-tag {
           leaf output {
             type string;
           }
         }
         case multichassis-tag {
           anyxml multi-routing-engine-results;
         }
       }
     }
   }
   rpc test-interface {
     description "Perform test on interface";
     input {
       choice test-command {
         case send-modem-commands {
           leaf send-modem-commands {
             description "Send AT command string to modem";
             type string;
           }
         }
         case feac-loop-initiate {
           leaf feac-loop-initiate {
             description "Initiate FEAC loopback";
             type empty;
           }
         }
         case feac-loop-terminate {
           leaf feac-loop-terminate {
             description "Terminate FEAC loopback";
             type empty;
           }
         }
         case t3-bert-start {
           leaf t3-bert-start {
             description "Start bit error rate test on T3 interface";
             type empty;
           }
         }
         case e3-bert-start {
           leaf e3-bert-start {
             description "Start bit error rate test on E3 interface";
             type empty;
           }
         }
         case t1-bert-start {
           leaf t1-bert-start {
             description "Start bit error rate test on T1 interface";
             type empty;
           }
         }
         case ds0-bert-start {
           leaf ds0-bert-start {
             description "Start bit error rate test on DS-0 interface";
             type empty;
           }
         }
         case e1-bert-start {
           leaf e1-bert-start {
             description "Start bit error rate test on E1 interface";
             type empty;
           }
         }
         case t3-bert-stop {
           leaf t3-bert-stop {
             description "Stop bit error rate test on T3 interface";
             type empty;
           }
         }
         case e3-bert-stop {
           leaf e3-bert-stop {
             description "Stop bit error rate test on E3 interface";
             type empty;
           }
         }
         case t1-bert-stop {
           leaf t1-bert-stop {
             description "Stop bit error rate test on T1 interface";
             type empty;
           }
         }
         case ds0-bert-stop {
           leaf ds0-bert-stop {
             description "Stop bit error rate test on DS-0 interface";
             type empty;
           }
         }
         case e1-bert-stop {
           leaf e1-bert-stop {
             description "Stop bit error rate test on E1 interface";
             type empty;
           }
         }
         case restart-auto-negotiation {
           leaf restart-auto-negotiation {
             description "Restart autonegotiation";
             type empty;
           }
         }
         case ima-test-start {
           leaf ima-test-start {
             description "Start IMA group test";
             type empty;
           }
         }
         case ima-test-stop {
           leaf ima-test-stop {
             description "Stop IMA group test";
             type empty;
           }
         }
       }
       leaf interface-name {
         description "Name of physical interface";
         type string;
         mandatory true;
       }
     }
     output {
       choice output_c {
         case output-tag {
           leaf output {
             type string;
           }
         }
         case multichassis-tag {
           anyxml multi-routing-engine-results;
         }
       }
     }
   }
   rpc test-intf-inband-line-loop-terminate {
     description "Terminate loopback";
     input {
       leaf interface-name {
         description "Name of physical interface";
         type string;
         mandatory true;
       }
     }
     output {
       choice output_c {
         case output-tag {
           leaf output {
             type string;
           }
         }
         case multichassis-tag {
           anyxml multi-routing-engine-results;
         }
       }
     }
   }
   rpc test-intf-inband-line-loop-initiate {
     description "Initiate loopback";
     input {
       leaf interface-name {
         description "Name of physical interface";
         type string;
         mandatory true;
       }
     }
     output {
       choice output_c {
         case output-tag {
           leaf output {
             type string;
           }
         }
         case multichassis-tag {
           anyxml multi-routing-engine-results;
         }
       }
     }
   }
   rpc test-intf-inband-line-ansi-terminate {
     description "Terminate loopback";
     input {
       leaf interface-name {
         description "Name of physical interface";
         type string;
         mandatory true;
       }
     }
     output {
       choice output_c {
         case output-tag {
           leaf output {
             type string;
           }
         }
         case multichassis-tag {
           anyxml multi-routing-engine-results;
         }
       }
     }
   }
   rpc test-intf-inband-line-ansi-initiate {
     description "Initiate loopback";
     input {
       leaf interface-name {
         description "Name of physical interface";
         type string;
         mandatory true;
       }
     }
     output {
       choice output_c {
         case output-tag {
           leaf output {
             type string;
           }
         }
         case multichassis-tag {
           anyxml multi-routing-engine-results;
         }
       }
     }
   }
   rpc test-intf-inband-line-bellcore-terminate {
     description "Terminate loopback";
     input {
       leaf interface-name {
         description "Name of physical interface";
         type string;
         mandatory true;
       }
     }
     output {
       choice output_c {
         case output-tag {
           leaf output {
             type string;
           }
         }
         case multichassis-tag {
           anyxml multi-routing-engine-results;
         }
       }
     }
   }
   rpc test-intf-inband-line-bellcore-initiate {
     description "Initiate loopback";
     input {
       leaf interface-name {
         description "Name of physical interface";
         type string;
         mandatory true;
       }
     }
     output {
       choice output_c {
         case output-tag {
           leaf output {
             type string;
           }
         }
         case multichassis-tag {
           anyxml multi-routing-engine-results;
         }
       }
     }
   }
   rpc test-intf-fdl-payload-ansi-terminate {
     description "Terminate loopback";
     input {
       leaf interface-name {
         description "Name of physical interface";
         type string;
         mandatory true;
       }
     }
     output {
       choice output_c {
         case output-tag {
           leaf output {
             type string;
           }
         }
         case multichassis-tag {
           anyxml multi-routing-engine-results;
         }
       }
     }
   }
   rpc test-intf-fdl-payload-ansi-initiate {
     description "Initiate loopback";
     input {
       leaf interface-name {
         description "Name of physical interface";
         type string;
         mandatory true;
       }
     }
     output {
       choice output_c {
         case output-tag {
           leaf output {
             type string;
           }
         }
         case multichassis-tag {
           anyxml multi-routing-engine-results;
         }
       }
     }
   }
   rpc test-intf-fdl-payload-bellcore-terminate {
     description "Terminate loopback";
     input {
       leaf interface-name {
         description "Name of physical interface";
         type string;
         mandatory true;
       }
     }
     output {
       choice output_c {
         case output-tag {
           leaf output {
             type string;
           }
         }
         case multichassis-tag {
           anyxml multi-routing-engine-results;
         }
       }
     }
   }
   rpc test-intf-fdl-payload-bellcore-initiate {
     description "Initiate loopback";
     input {
       leaf interface-name {
         description "Name of physical interface";
         type string;
         mandatory true;
       }
     }
     output {
       choice output_c {
         case output-tag {
           leaf output {
             type string;
           }
         }
         case multichassis-tag {
           anyxml multi-routing-engine-results;
         }
       }
     }
   }
   rpc test-intf-fdl-line-ansi-terminate {
     description "Terminate loopback";
     input {
       leaf interface-name {
         description "Name of physical interface";
         type string;
         mandatory true;
       }
     }
     output {
       choice output_c {
         case output-tag {
           leaf output {
             type string;
           }
         }
         case multichassis-tag {
           anyxml multi-routing-engine-results;
         }
       }
     }
   }
   rpc test-intf-fdl-line-ansi-initiate {
     description "Initiate loopback";
     input {
       leaf interface-name {
         description "Name of physical interface";
         type string;
         mandatory true;
       }
     }
     output {
       choice output_c {
         case output-tag {
           leaf output {
             type string;
           }
         }
         case multichassis-tag {
           anyxml multi-routing-engine-results;
         }
       }
     }
   }
   rpc test-intf-fdl-line-bellcore-terminate {
     description "Terminate loopback";
     input {
       leaf interface-name {
         description "Name of physical interface";
         type string;
         mandatory true;
       }
     }
     output {
       choice output_c {
         case output-tag {
           leaf output {
             type string;
           }
         }
         case multichassis-tag {
           anyxml multi-routing-engine-results;
         }
       }
     }
   }
   rpc test-intf-fdl-line-bellcore-initiate {
     description "Initiate loopback";
     input {
       leaf interface-name {
         description "Name of physical interface";
         type string;
         mandatory true;
       }
     }
     output {
       choice output_c {
         case output-tag {
           leaf output {
             type string;
           }
         }
         case multichassis-tag {
           anyxml multi-routing-engine-results;
         }
       }
     }
   }
   rpc test-intf-inband-payload-ansi-terminate {
     description "Terminate loopback";
     input {
       leaf interface-name {
         description "Name of physical interface";
         type string;
         mandatory true;
       }
     }
     output {
       choice output_c {
         case output-tag {
           leaf output {
             type string;
           }
         }
         case multichassis-tag {
           anyxml multi-routing-engine-results;
         }
       }
     }
   }
   rpc test-intf-inband-payload-ansi-initiate {
     description "Initiate loopback";
     input {
       leaf interface-name {
         description "Name of physical interface";
         type string;
         mandatory true;
       }
     }
     output {
       choice output_c {
         case output-tag {
           leaf output {
             type string;
           }
         }
         case multichassis-tag {
           anyxml multi-routing-engine-results;
         }
       }
     }
   }
   rpc test-intf-inband-payload-bellcore-terminate {
     description "Terminate loopback";
     input {
       leaf interface-name {
         description "Name of physical interface";
         type string;
         mandatory true;
       }
     }
     output {
       choice output_c {
         case output-tag {
           leaf output {
             type string;
           }
         }
         case multichassis-tag {
           anyxml multi-routing-engine-results;
         }
       }
     }
   }
   rpc test-intf-inband-payload-bellcore-initiate {
     description "Initiate loopback";
     input {
       leaf interface-name {
         description "Name of physical interface";
         type string;
         mandatory true;
       }
     }
     output {
       choice output_c {
         case output-tag {
           leaf output {
             type string;
           }
         }
         case multichassis-tag {
           anyxml multi-routing-engine-results;
         }
       }
     }
   }
   rpc get-dhcp-user-aaa-test-result {
     description "Test the aaa servers for a dhcp user";
     input {
       leaf user {
         description "The username to test";
         type string;
         mandatory true;
       }
       leaf password {
         description "The password associated with username";
         type string;
       }
       leaf profile {
         description "Specify the access profile name which to use for user";
         type string;
       }
       leaf logical-system {
         description "Specify the logical-system in which to authenticate user";
         type string;
       }
       leaf routing-instance {
         description "Specify the routing-instance in which to authenticate user";
         type string;
       }
       leaf service-type {
         description "Service type ";
         type string;
       }
       leaf mac-address {
         description "Specify the Mac address of the DHCP client";
         type jt:mac-addr;
       }
       leaf option-82 {
         description "Specify the DHCP option 82";
         type string;
       }
       leaf agent-remote-id {
         description "DSL forum agent remote id ";
         type string {
           length "1 .. 63";
         }
       }
       leaf source-address {
         description "Use specified address as source address";
         type jt:ipv4addr;
       }
       leaf no-address-request {
         description "Request is for authentication without address-allocation";
         type empty;
       }
       leaf terminate-code {
         description "Specify DHCP terminate-code";
         type enumeration {
           enum "client-request" {
             description "Terminated-id with default mapping to 1";
           }
           enum "lost-carrier" {
             description "Terminated-id with default mapping to 2";
           }
           enum "nak" {
             description "Terminated-id with default mapping to 15";
           }
           enum "nas-logout" {
             description "Terminated-id with default mapping to 10";
           }
           enum "no-offers" {
             description "Terminated-id with default mapping to 4";
           }
         }
       }
     }
     output {
       choice output_c {
         case output-tag {
           leaf output {
             type string;
           }
         }
         case actual-tag {
           anyxml aaa-test-result;
         }
         case multichassis-tag {
           anyxml multi-routing-engine-results;
         }
       }
     }
   }
   rpc get-authdlite-user-aaa-test-result {
     description "Test the aaa servers for a authdlite user";
     input {
       leaf user {
         description "The username to test";
         type string;
         mandatory true;
       }
       leaf password {
         description "The password associated with username";
         type string;
       }
       leaf profile {
         description "Specify the access profile name which to use for user";
         type string;
       }
       leaf port {
         description "Specify NAS-port to be used for test";
         type string;
       }
       leaf zero-stats {
         description "Specify that acct stats should be set to zero";
         type empty;
       }
       leaf xauth {
         description "Emulate xauth client";
         type empty;
       }
     }
     output {
       choice output_c {
         case output-tag {
           leaf output {
             type string;
           }
         }
         case actual-tag {
           anyxml aaa-test-result;
         }
         case multichassis-tag {
           anyxml multi-routing-engine-results;
         }
       }
     }
   }
   rpc test-dot1x-sync-req {
     description "Send sync request to peer AD";
     input {
       leaf rg-id {
         description "Specify redundancy-group";
         type union {
           type uint32;
           type string {
             pattern "<.*>|$.*";
           }
         }
       }
     }
     output {
       choice output_c {
         case output-tag {
           leaf output {
             type string;
           }
         }
         case actual-tag {
           anyxml dot1x-sync-req;
         }
         case multichassis-tag {
           anyxml multi-routing-engine-results;
         }
       }
     }
   }
   rpc test-dot1x-sync-all {
     description "Send sync message containing all the authenticated entries";
     input {
       leaf rg-id {
         description "Specify redundancy-group";
         type union {
           type uint32;
           type string {
             pattern "<.*>|$.*";
           }
         }
       }
     }
     output {
       choice output_c {
         case output-tag {
           leaf output {
             type string;
           }
         }
         case actual-tag {
           anyxml dot1x-sync-all;
         }
         case multichassis-tag {
           anyxml multi-routing-engine-results;
         }
       }
     }
   }
   rpc test-dot1x-sync-mac {
     description "Simulate receiving sync message for particular session";
     input {
       leaf session {
         description "Session param ae-id, ifl-nm, mac, ch-id, user, filter-id, vlan, voip";
         type string;
       }
     }
     output {
       choice output_c {
         case output-tag {
           leaf output {
             type string;
           }
         }
         case actual-tag {
           anyxml dot1x-sync-mac;
         }
         case multichassis-tag {
           anyxml multi-routing-engine-results;
         }
       }
     }
   }
   rpc test-dot1x-del-sync-mac {
     input {
       leaf session {
         description "Session param ae-id, ifl-nm, mac";
         type string;
       }
     }
     output {
       choice output_c {
         case output-tag {
           leaf output {
             type string;
           }
         }
         case actual-tag {
           anyxml dot1x-del-sync-mac;
         }
         case multichassis-tag {
           anyxml multi-routing-engine-results;
         }
       }
     }
   }
   rpc test-routing-policy {
     description "Import and export policy evaluation";
     input {
       leaf policy {
         description "Policy name";
         type string;
       }
       leaf prefix {
         description "Destination prefix";
         type string;
       }
     }
     output {
       choice output_c {
         case output-tag {
           leaf output {
             type string;
           }
         }
         case actual-tag {
           anyxml route-information;
         }
         case multichassis-tag {
           anyxml multi-routing-engine-results;
         }
       }
     }
   }
   rpc test-msdp-dependent-peers {
     description "Find downstream dependent peers for a prefix";
     input {
       leaf logical-system {
         description "Name of logical system, or 'all'";
         type string {
         }
       }
       leaf instance {
         description "Name of instance";
         type string;
       }
       leaf prefix {
         description "IPv4 address and optional prefix length";
         type jt:ipv4prefix;
         mandatory true;
       }
     }
     output {
       choice output_c {
         case output-tag {
           leaf output {
             type string;
           }
         }
         case multichassis-tag {
           anyxml multi-routing-engine-results;
         }
       }
     }
   }
   rpc test-msdp-rpf-peers {
     description "Find MSDP reverse-path forwarding peer for an originator";
     input {
       leaf logical-system {
         description "Name of logical system, or 'all'";
         type string {
         }
       }
       leaf instance {
         description "Name of instance";
         type string;
       }
       leaf originator {
         description "IPv4 address and optional prefix length of originator";
         type jt:ipv4prefix;
         mandatory true;
       }
     }
     output {
       choice output_c {
         case output-tag {
           leaf output {
             type string;
           }
         }
         case multichassis-tag {
           anyxml multi-routing-engine-results;
         }
       }
     }
   }
   rpc none {
     description "Layer 2 forwarding commands";
     input {
       leaf in-memory-debug {
         description "Enable or disable in-memory tracing";
         type enumeration {
           enum "disable" {
             description "Disable in-memory tracing";
           }
           enum "enable" {
             description "Enable in-memory tracing";
           }
         }
       }
     }
     output {
       choice output_c {
         case output-tag {
           leaf output {
             type string;
           }
         }
         case multichassis-tag {
           anyxml multi-routing-engine-results;
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member";
           type union {
             type string {
               pattern "<.*>|$.*";
             }
             type uint32;
           }
         }
       }
     }
   }
 }
