/*
 * Copyright (c) 2019 Juniper Networks, Inc.
 * All rights reserved.
 */
 module junos-es-conf-services {
   namespace "http://yang.juniper.net/junos-es/conf/services";

   prefix jc-services;

   import junos-common-ddl-extensions {
     prefix junos;
   }

   import junos-common-types {
     prefix jt;
   }

   import junos-es-conf-root {
     prefix jc;
   }

   organization "Juniper Networks, Inc.";

   contact "yang-support@juniper.net";

   description "Junos services configuration module";

   revision 2019-01-01 {
     description "Junos: 18.4R2.7";
   }

   augment /jc:configuration {
     uses services-group;
   }
   augment /jc:configuration/jc:groups {
     uses services-group;
   }
   grouping services-group {
     container services {
       description "Set services parameters";
       uses apply-advanced;
       container flow-tap {
         description "Configure flow-tap parameters";
         uses apply-advanced;
         container family {
           description "Address family of packets to tap";
           uses apply-advanced;
           leaf inet {
             description "IPv4 family";
             type empty;
           }
           leaf inet6 {
             description "IPv4 family";
             type empty;
           }
           leaf ccc {
             description "CCC family";
             type empty;
           }
         }
         leaf interface {
           description "Service interface on which to configure flow-tap service";
           junos:must "(!(\"services flow-tap tunnel-interface\"))";
           junos:must-message "tunnel-interface and service interface cannot be confgured together for flowtap application";
           junos:must "(!(\"services dynamic-flow-capture\"))";
           junos:must-message "Dynamic flow capture cannot be configured when flow tap is configured";
           junos:must "(\"interfaces $$-IFL family inet\")";
           junos:must-message "Interface with family inet must be defined in the [edit interfaces] hierarchy";
           type union {
             type jt:interface-name;
             type string {
               pattern "<.*>|$.*";
             }
           }
         }
         leaf tunnel-interface {
           description "Tunnel interface through which flow-tap would communicate with MD";
           junos:must "(!(\"services flow-tap interface\"))";
           junos:must-message "tunnel-interface and service interface cannot be confgured together for flowtap application";
           junos:must "(!(\"services dynamic-flow-capture\"))";
           junos:must-message "Dynamic flow capture cannot be configured when flow tap is configured";
           junos:must "(\"interfaces $$-IFL family inet6\")";
           junos:must-message "Interface with family inet6 must be defined in the [edit interfaces] hierarchy";
           junos:must "(\"interfaces $$-IFL family inet\")";
           junos:must-message "Interface with family inet must be defined in the [edit interfaces] hierarchy";
           type union {
             type jt:interface-name;
             type string {
               pattern "<.*>|$.*";
             }
           }
         }
       }
       container radius-flow-tap {
         description "Configure radius triggered flow-tap parameters";
         uses apply-advanced;
         leaf forwarding-class {
           description "Forwarding class assigned to intercepted packets";
           type string {
             junos:posix-pattern "^.{1,64}$";
             junos:pattern-message "Must be string of 64 characters or less";
           }
         }
         leaf source-ipv4-address {
           description "IP Address to use as source address in IPv4 header appended to intercepted packets";
           type jt:ipv4addr;
         }
         leaf multicast-interception {
           description "Enable Multicast Tapping";
           type empty;
         }
         container interfaces {
           description "Tunnel Interfaces";
           uses apply-advanced;
           list tunnel-interface {
             key name;
             uses tunnel_interface_type;
           }
         }
         choice ri_or_ls {
           case case_1 {
             leaf routing-instance {
               description "Routing instance to be used for radius flow tap";
               junos:must "(\"routing-instances $$\")";
               junos:must-message "Referenced routing instance must be defined";
               type string;
             }
           }
           case case_2 {
             list logical-system {
               key name;
               ordered-by user;
               description "Logical system to be used for radius flow tap";
               max-elements 1;
               leaf name {
                 description "Logical system name";
                 junos:must "(\"logical-systems $$\")";
                 junos:must-message "Referenced logical system must be defined";
                 type string;
               }
               uses apply-advanced;
               leaf routing-instance {
                 description "Routing instance to be used for radius flow tap";
                 junos:must "(\"logical-systems ${logical-system} routing-instances $$\")";
                 junos:must-message "Referenced routing instance must be defined";
                 type string;
               }
             }
           }
         }
         list policy {
           key name;
           ordered-by user;
           description "Policy";
           leaf name {
             description "Policy Name";
             type string {
               junos:posix-pattern "^.{1,64}$";
               junos:pattern-message "Must be string of 64 characters or less";
             }
           }
           uses apply-advanced;
           container inet {
             description "Protocol family IPv4 drop policy terms";
             uses apply-advanced;
             list drop-policy {
               key name;
               ordered-by user;
               description "Define an IPv4 drop policy";
               uses drop-policy-term;
             }
           }
           container inet6 {
             description "Protocol family IPv6 drop policy terms";
             uses apply-advanced;
             list drop-policy {
               key name;
               ordered-by user;
               description "Define an IPv6 drop policy";
               uses drop-policy6-term;
             }
           }
         }
         container snmp {
           description "SNMP options for radius flow tap";
           uses apply-advanced;
           list notify-targets {
             key name;
             ordered-by user;
             description "Target list for packet mirror SNMP notifications";
             leaf name {
               description "Target IP address";
               type jt:ipaddr;
             }
             uses apply-advanced;
           }
         }
       }
       container flow-monitoring {
         presence "enable flow-monitoring";
         description "Configure flow monitoring";
         uses apply-advanced;
         container version9 {
           description "Version 9 configuration";
           uses apply-advanced;
           list template {
             key name;
             ordered-by user;
             description "One or more version 9 templates";
             max-elements 10;
             uses version9-template;
           }
         }
         container version-ipfix {
           description "Version IP-Fix configuration";
           uses apply-advanced;
           list template {
             key name;
             ordered-by user;
             description "One or more version ip-fix templates";
             max-elements 10;
             uses version-ipfix-template;
           }
         }
       }
       container jdaf {
         description "Juniper distributed application framework (JDAF)";
         uses apply-advanced;
         leaf-list routing-instances {
           ordered-by user;
           description "List of routing-instance name for JDAF clients";
           type string {
             length "1 .. 128";
           }
         }
       }
       container rpm {
         presence "enable rpm";
         description "Real-time performance monitoring";
         uses apply-advanced;
         container traceoptions {
           description "RMOPD trace options";
           uses rmopd-traceoptions;
         }
         container bgp {
           description "BGP options for real-time performance monitoring";
           uses apply-advanced;
           leaf probe-type {
             description "RPM-BGP probe request type";
             default "icmp-ping";
             type enumeration {
               enum "icmp-ping" {
                 description "Send ICMP echo request to target address";
               }
               enum "icmp-ping-timestamp" {
                 description "Send ICMP timestamp request to target address";
               }
               enum "icmp6-ping" {
                 description "Send ICMP6 echo request to target address";
               }
               enum "tcp-ping" {
                 description "Send TCP packets to target";
               }
               enum "udp-ping" {
                 description "Send UDP packets to target";
               }
               enum "udp-ping-timestamp" {
                 description "Send UDP packets with timestamp to target";
               }
             }
           }
           leaf probe-count {
             description "Total number of probes per test";
             default "1";
             type union {
               type string {
                 pattern "<.*>|$.*";
               }
               type uint32 {
                 range "1 .. 15";
               }
             }
           }
           leaf probe-interval {
             description "Delay between probes";
             default "3";
             units "seconds";
             type union {
               type string {
                 pattern "<.*>|$.*";
               }
               type uint32 {
                 range "1 .. 255";
               }
             }
           }
           leaf test-interval {
             description "Delay between tests";
             default "1";
             units "seconds";
             type union {
               type string {
                 pattern "<.*>|$.*";
               }
               type uint32 {
                 range "0 .. 86400";
               }
             }
           }
           leaf destination-port {
             description "TCP/UDP port number";
             type union {
               type string {
                 pattern "<.*>|$.*";
               }
               type uint16 {
                 range "7 .. 65535";
               }
             }
           }
           leaf history-size {
             description "Number of stored history entries";
             default "50";
             type union {
               type string {
                 pattern "<.*>|$.*";
               }
               type uint32 {
                 range "0 .. 512";
               }
             }
           }
           leaf moving-average-size {
             description "Number of samples used for moving average";
             default "0";
             type union {
               type string {
                 pattern "<.*>|$.*";
               }
               type uint32 {
                 range "0 .. 1024";
               }
             }
           }
           leaf data-size {
             description "Size of the data portion of the probes";
             default "0";
             type union {
               type string {
                 pattern "<.*>|$.*";
               }
               type uint32 {
                 range "0 .. 65400";
               }
             }
           }
           leaf data-fill {
             description "Define contents of the data portion of the probes";
             type string {
               length "1 .. 2048";
               junos:posix-pattern "^[[:xdigit:]]+$";
               junos:pattern-message "Must be hexadecimal digits (0-9, a-f, A-F)";
             }
           }
           leaf ttl {
             description "Time to Live (hop-limit) value for an RPM IPv4(IPv6) packet";
             default "64";
             type union {
               type string {
                 pattern "<.*>|$.*";
               }
               type uint32 {
                 range "1 .. 254";
               }
             }
           }
           list logical-system {
             key name;
             description "Logical systems";
             uses bgp-logical-system;
           }
           list routing-instances {
             key name;
             description "Routing instances";
             uses bgp-routing-instances;
           }
         }
         list probe {
           key name;
           ordered-by user;
           description "TCP/UDP/ICMP ping";
           leaf name {
             description "Name of owner";
             type string {
               length "1 .. 32";
             }
           }
           uses apply-advanced;
           leaf delegate-probes {
             description "Offload real-time performance monitoring probes to MS-MIC/MS-MPC card";
             type empty;
           }
           list test {
             key name;
             ordered-by user;
             description "TCP/UDP/ICMP/ICMP6 ping test";
             leaf name {
               description "Name of test";
               type string {
                 length "1 .. 32";
               }
             }
             uses apply-advanced;
             container rpm-scale {
               presence "enable rpm-scale";
               description "Configuring real-time performance monitoring scale tests";
               uses apply-advanced;
               leaf tests-count {
                 description "Number of probe-tests generated using scale config";
                 type union {
                   type string {
                     pattern "<.*>|$.*";
                   }
                   type uint32 {
                     range "1 .. 500000";
                   }
                 }
               }
               choice target-type {
                 case case_1 {
                   container target {
                     presence "enable target";
                     junos:must "(!(\".. source-inet6\"))";
                     junos:must-message "source-inet6 knob not valid for IPV4 probes";
                     description "Target address generation for scale test config";
                     uses apply-advanced;
                     leaf address-base {
                       description "Base address of target host in a.b.c.d format";
                       type jt:ipv4addr;
                     }
                     leaf step {
                       description "Steps to increment target address in a.b.c.d format";
                       type jt:ipv4addr;
                     }
                     leaf count {
                       description "Target address count";
                       type union {
                         type string {
                           pattern "<.*>|$.*";
                         }
                         type uint32 {
                           range "1 .. 500000";
                         }
                       }
                     }
                   }
                 }
                 case case_2 {
                   container target-inet6 {
                     presence "enable target-inet6";
                     junos:must "(!(\".. source\"))";
                     junos:must-message "source knob not valid for IPV6 probes";
                     description "IPv6 target address generation for scale test config";
                     uses apply-advanced;
                     leaf address-base {
                       description "Base address of target host in a:b:c:d:e:f:g:h format";
                       type jt:ipv6addr;
                     }
                     leaf step {
                       description "Steps to increment target address in a:b:c:d:e:f:g:h format";
                       type jt:ipv6addr;
                     }
                     leaf count {
                       description "Target address count";
                       type union {
                         type string {
                           pattern "<.*>|$.*";
                         }
                         type uint32 {
                           range "1 .. 500000";
                         }
                       }
                     }
                   }
                 }
               }
               choice source-type {
                 case case_1 {
                   container source {
                     presence "enable source";
                     junos:must "(!(\".. target-inet6\"))";
                     junos:must-message "target-inet6 knob not valid for IPV4 probes";
                     description "Source address generation in scale tests";
                     uses apply-advanced;
                     leaf address-base {
                       description "Base address of host in a.b.c.d format";
                       type jt:ipv4addr;
                     }
                     leaf step {
                       description "Steps to increment src address in a.b.c.d format";
                       type jt:ipv4addr;
                     }
                     leaf count {
                       description "Source-address count";
                       type union {
                         type string {
                           pattern "<.*>|$.*";
                         }
                         type uint32 {
                           range "1 .. 500000";
                         }
                       }
                     }
                   }
                 }
                 case case_2 {
                   container source-inet6 {
                     presence "enable source-inet6";
                     junos:must "(!(\".. target\"))";
                     junos:must-message "target knob not valid for IPV6 probes";
                     description "IPv6 source address generation in scale tests";
                     uses apply-advanced;
                     leaf address-base {
                       description "Base address of host in a:b:c:d:e:f:g:h format";
                       type jt:ipv6addr;
                     }
                     leaf step {
                       description "Steps to increment src address in a:b:c:d:e:f:g:h format";
                       type jt:ipv6addr;
                     }
                     leaf count {
                       description "Source-address count";
                       type union {
                         type string {
                           pattern "<.*>|$.*";
                         }
                         type uint32 {
                           range "1 .. 500000";
                         }
                       }
                     }
                   }
                 }
               }
               container destination {
                 presence "enable destination";
                 description "Name of output interface for probes";
                 uses apply-advanced;
                 leaf interface {
                   description "Base destination interface for scale test";
                   type union {
                     type jt:interface-name;
                     type string {
                       pattern "<.*>|$.*";
                     }
                   }
                 }
                 leaf subunit-cnt {
                   description "Subunit count for destination interface for scale test";
                   type union {
                     type string {
                       pattern "<.*>|$.*";
                     }
                     type uint32 {
                       range "1 .. 500000";
                     }
                   }
                 }
               }
             }
             leaf probe-type {
               description "Probe request type";
               default "icmp-ping";
               type enumeration {
                 enum "http-get" {
                   description "Perform HTTP Get request at target URL";
                 }
                 enum "http-metadata-get" {
                   description "Perform HTTP Get request of metadata at target URL";
                 }
                 enum "icmp-ping" {
                   description "Send ICMP echo request to target address";
                 }
                 enum "icmp-ping-timestamp" {
                   description "Send ICMP timestamp request to target address";
                 }
                 enum "icmp6-ping" {
                   description "Send ICMP6 echo request to target address";
                 }
                 enum "tcp-ping" {
                   description "Send TCP packets to target";
                 }
                 enum "udp-ping" {
                   description "Send UDP packets to target";
                 }
                 enum "udp-ping-timestamp" {
                   description "Send UDP packets with timestamp to target";
                 }
               }
             }
             container target {
               presence "enable target";
               description "Target destination for probe";
               choice target-type {
                 case case_1 {
                   leaf address {
                     description "Address of target host";
                     junos:must "(!(\".. .. inet6-options\"))";
                     junos:must-message "inet6-options knob not valid for IPV4 probes";
                     type jt:ipv4addr;
                   }
                 }
                 case case_2 {
                   leaf inet6-address {
                     description "Inet6 Address of target host";
                     junos:must "(!(\".. .. source-address\"))";
                     junos:must-message "source-address knob not valid for IPV6 probes";
                     type jt:ipv6addr;
                   }
                 }
                 case case_3 {
                   leaf url {
                     description "Fully formed target URL";
                     junos:must "(!(\".. .. inet6-options\"))";
                     junos:must-message "inet6-options knob not valid for IPV4 probes";
                     type string;
                   }
                 }
                 case case_4 {
                   leaf inet6-url {
                     description "Fully formed target IPV6 URL";
                     junos:must "(!(\".. .. source-address\"))";
                     junos:must-message "source-address knob not valid for IPV6 probes";
                     type string;
                   }
                 }
               }
             }
             container inet6-options {
               presence "enable inet6-options";
               description "IPV6 related options";
               uses apply-advanced;
               leaf source-address {
                 description "Inet6 Source Address of the probe";
                 type jt:ipv6addr;
               }
             }
             leaf probe-count {
               description "Total number of probes per test";
               default "1";
               type union {
                 type string {
                   pattern "<.*>|$.*";
                 }
                 type uint32 {
                   range "1 .. 15";
                 }
               }
             }
             leaf probe-interval {
               description "Delay between probes";
               default "3";
               units "seconds";
               type union {
                 type string {
                   pattern "<.*>|$.*";
                 }
                 type uint32 {
                   range "1 .. 255";
                 }
               }
             }
             leaf test-interval {
               description "Delay between tests";
               default "1";
               units "seconds";
               type union {
                 type string {
                   pattern "<.*>|$.*";
                 }
                 type uint32 {
                   range "0 .. 86400";
                 }
               }
             }
             leaf destination-port {
               description "TCP/UDP port number";
               type union {
                 type string {
                   pattern "<.*>|$.*";
                 }
                 type uint16 {
                   range "7 .. 65535";
                 }
               }
             }
             leaf source-address {
               description "Source address for probe";
               junos:must "(!(\".. target inet6-address\"))";
               junos:must-message "source-address knob for IPV6 based probes is under inet6-options";
               type jt:ipv4addr;
             }
             leaf routing-instance {
               description "Routing instance used by probes";
               junos:must "(\"routing-instances $$\")";
               junos:must-message "referenced routing-instance must be defined";
               type string {
                 junos:posix-pattern "!^((__.*__)|(all)|(.*[ ].*)|(\"\")|(.{129,}))$";
                 junos:pattern-message "Must be a non-reserved string of 128 characters or less with no spaces.";
               }
             }
             leaf history-size {
               description "Number of stored history entries";
               default "50";
               type union {
                 type string {
                   pattern "<.*>|$.*";
                 }
                 type uint32 {
                   range "0 .. 512";
                 }
               }
             }
             leaf moving-average-size {
               description "Number of samples used for moving average";
               default "0";
               type union {
                 type string {
                   pattern "<.*>|$.*";
                 }
                 type uint32 {
                   range "0 .. 1024";
                 }
               }
             }
             leaf dscp-code-points {
               description "Differentiated Services code point bits or alias";
               default "000000";
               type string {
                 junos:posix-pattern "^(([01]{6})|([a-zA-Z].{0,63}))$";
                 junos:pattern-message "Not 6-bit pattern or code point alias";
               }
             }
             leaf data-size {
               description "Size of the data portion of the probes";
               default "0";
               type union {
                 type string {
                   pattern "<.*>|$.*";
                 }
                 type uint32 {
                   range "0 .. 65400";
                 }
               }
             }
             leaf data-fill {
               description "Define contents of the data portion of the probes";
               type string {
                 length "1 .. 2048";
                 junos:posix-pattern "^[[:xdigit:]]+$";
                 junos:pattern-message "Must be hexadecimal digits (0-9, a-f, A-F)";
               }
             }
             leaf ttl {
               description "Time to Live (hop-limit) value for an RPM IPv4(IPv6) packet";
               default "64";
               type union {
                 type string {
                   pattern "<.*>|$.*";
                 }
                 type uint32 {
                   range "1 .. 254";
                 }
               }
             }
             container thresholds {
               presence "enable thresholds";
               description "Probe and test threshold values. Set 0 to disable respective threshold";
               uses apply-advanced;
               leaf successive-loss {
                 description "Successive probe loss count indicating probe failure";
                 default "1";
                 type union {
                   type string {
                     pattern "<.*>|$.*";
                   }
                   type uint32 {
                     range "0 .. 15";
                   }
                 }
               }
               leaf total-loss {
                 description "Total probe loss count indicating test failure";
                 default "1";
                 type union {
                   type string {
                     pattern "<.*>|$.*";
                   }
                   type uint32 {
                     range "0 .. 15";
                   }
                 }
               }
               leaf rtt {
                 description "Maximum round trip time per probe";
                 default "0";
                 units "microseconds";
                 type union {
                   type string {
                     pattern "<.*>|$.*";
                   }
                   type uint32 {
                     range "0 .. 60000000";
                   }
                 }
               }
               leaf jitter-rtt {
                 description "Maximum jitter per test";
                 default "0";
                 units "microseconds";
                 type union {
                   type string {
                     pattern "<.*>|$.*";
                   }
                   type uint32 {
                     range "0 .. 60000000";
                   }
                 }
               }
               leaf std-dev-rtt {
                 description "Maximum standard deviation per test";
                 default "0";
                 units "microseconds";
                 type union {
                   type string {
                     pattern "<.*>|$.*";
                   }
                   type uint32 {
                     range "0 .. 60000000";
                   }
                 }
               }
               leaf egress-time {
                 description "Maximum source to destination time per probe";
                 default "0";
                 units "microseconds";
                 type union {
                   type string {
                     pattern "<.*>|$.*";
                   }
                   type uint32 {
                     range "0 .. 60000000";
                   }
                 }
               }
               leaf ingress-time {
                 description "Maximum destination to source time per probe";
                 default "0";
                 units "microseconds";
                 type union {
                   type string {
                     pattern "<.*>|$.*";
                   }
                   type uint32 {
                     range "0 .. 60000000";
                   }
                 }
               }
               leaf jitter-ingress {
                 description "Maximum destination to source jitter per test";
                 default "0";
                 units "microseconds";
                 type union {
                   type string {
                     pattern "<.*>|$.*";
                   }
                   type uint32 {
                     range "0 .. 60000000";
                   }
                 }
               }
               leaf jitter-egress {
                 description "Maximum source to destination jitter per test";
                 default "0";
                 units "microseconds";
                 type union {
                   type string {
                     pattern "<.*>|$.*";
                   }
                   type uint32 {
                     range "0 .. 60000000";
                   }
                 }
               }
               leaf std-dev-ingress {
                 description "Maximum destination to source standard deviation per test";
                 default "0";
                 units "microseconds";
                 type union {
                   type string {
                     pattern "<.*>|$.*";
                   }
                   type uint32 {
                     range "0 .. 60000000";
                   }
                 }
               }
               leaf std-dev-egress {
                 description "Maximum source to destination standard deviation per test";
                 default "0";
                 units "microseconds";
                 type union {
                   type string {
                     pattern "<.*>|$.*";
                   }
                   type uint32 {
                     range "0 .. 60000000";
                   }
                 }
               }
             }
             leaf-list traps {
               ordered-by user;
               description "Trap to send if threshold is met or exceeded";
               type enumeration {
                 enum "probe-failure" {
                   description "Successive probe loss threshold reached";
                 }
                 enum "test-failure" {
                   description "Total probe loss threshold reached";
                 }
                 enum "test-completion" {
                   description "Test completed";
                 }
                 enum "rtt-exceeded" {
                   description "Exceeded maximum round trip time threshold";
                 }
                 enum "std-dev-exceeded" {
                   description "Exceeded round trip time standard deviation threshold";
                 }
                 enum "jitter-exceeded" {
                   description "Exceeded jitter in round trip time threshold";
                 }
                 enum "ingress-time-exceeded" {
                   description "Exceeded maximum ingress time threshold";
                 }
                 enum "ingress-std-dev-exceeded" {
                   description "Exceeded ingress time standard deviation threshold";
                 }
                 enum "ingress-jitter-exceeded" {
                   description "Exceeded jitter in ingress time threshold";
                 }
                 enum "egress-time-exceeded" {
                   description "Exceeded maximum egress time threshold";
                 }
                 enum "egress-std-dev-exceeded" {
                   description "Exceeded egress time standard deviation threshold";
                 }
                 enum "egress-jitter-exceeded" {
                   description "Exceeded jitter in egress time threshold";
                 }
               }
             }
             leaf destination-interface {
               description "Name of output interface for probes";
               type union {
                 type jt:interface-name;
                 type string {
                   pattern "<.*>|$.*";
                 }
               }
             }
             leaf hardware-timestamp {
               description "Packet Forwarding Engine updates timestamps";
               junos:must "(!(\".. target inet6-address\"))";
               junos:must-message "Hardware timestamping not supported for IPV6 based probes.";
               junos:must "((!(\".. destination-port\") || \".. destination-port $$={7}\"))";
               junos:must-message "For UDP pings, only port 7 can be configured for hardware timestamping.";
               type empty;
             }
             leaf one-way-hardware-timestamp {
               description "Enable hardware timestamps for one-way measurements";
               junos:must "(!(\".. target inet6-address\"))";
               junos:must-message "One-way hardware timestamping not supported for IPV6 based probes.";
               type empty;
             }
             leaf next-hop {
               description "Next-hop to which probe should be sent";
               type jt:ipv4addr;
             }
           }
         }
         container probe-server {
           description "ICMP/TCP/UDP probe server";
           uses apply-advanced;
           container icmp {
             description "ICMP probe server";
             uses apply-advanced;
             leaf destination-interface {
               description "Name of output interface for probes";
               type union {
                 type jt:interface-name;
                 type string {
                   pattern "<.*>|$.*";
                 }
               }
             }
           }
           container tcp {
             description "TCP probe server";
             uses apply-advanced;
             leaf port {
               description "Port number 7 through 65535";
               type union {
                 type uint16;
                 type string {
                   pattern "<.*>|$.*";
                 }
               }
             }
             leaf destination-interface {
               description "Name of output interface for probes";
               type union {
                 type jt:interface-name;
                 type string {
                   pattern "<.*>|$.*";
                 }
               }
             }
           }
           container udp {
             description "UDP probe server";
             uses apply-advanced;
             leaf port {
               description "Port number 7 through 65535";
               type union {
                 type uint16;
                 type string {
                   pattern "<.*>|$.*";
                 }
               }
             }
             leaf destination-interface {
               description "Name of output interface for probes";
               type union {
                 type jt:interface-name;
                 type string {
                   pattern "<.*>|$.*";
                 }
               }
             }
           }
         }
         leaf probe-limit {
           description "Maximum number of concurrent probes allowed";
           default "100";
           type union {
             type string {
               pattern "<.*>|$.*";
             }
             type uint32 {
               range "1 .. 500";
             }
           }
         }
         container twamp {
           description "Two-way Active Measurement Protocol configuration";
           uses apply-advanced;
           leaf post-cli-implicit-firewall {
             description "Enable post cli implicit firewall";
             type empty;
           }
           container client {
             description "TWAMP client configuration";
             uses apply-advanced;
             list control-connection {
               key name;
               ordered-by user;
               description "TWAMP control session configuration";
               leaf name {
                 description "Client name";
                 type string {
                   length "1 .. 32";
                 }
               }
               uses apply-advanced;
               container authentication-mode {
                 description "Authentication modes";
                 uses apply-advanced;
                 leaf none {
                   description "No authentication or encryption";
                   type empty;
                 }
               }
               leaf destination-interface {
                 description "Name of output interface for all test sessions";
                 type union {
                   type jt:interface-name;
                   type string {
                     pattern "<.*>|$.*";
                   }
                 }
               }
               leaf persistent-results {
                 description "Displays the old results along with present. Default disable";
                 type empty;
               }
               leaf tcp-keepidle {
                 description "Time to start TCP KEEPALIVEs on control connection (default 120)";
                 default "120";
                 units "seconds";
                 type union {
                   type string {
                     pattern "<.*>|$.*";
                   }
                   type uint32 {
                     range "1 .. 600";
                   }
                 }
               }
               leaf tcp-keepintvl {
                 description "Delay between succesive TCP KEEPALIVEs (default 5)";
                 default "5";
                 units "seconds";
                 type union {
                   type string {
                     pattern "<.*>|$.*";
                   }
                   type uint32 {
                     range "1 .. 600";
                   }
                 }
               }
               leaf tcp-keepcnt {
                 description "Number of TCP KEEPALIVEs sent (default 6)";
                 default "6";
                 type union {
                   type string {
                     pattern "<.*>|$.*";
                   }
                   type uint32 {
                     range "1 .. 50";
                   }
                 }
               }
               leaf destination-port {
                 description "TCP TWAMP client listening port for the test sessions. Default 862";
                 default "862";
                 type union {
                   type string {
                     pattern "<.*>|$.*";
                   }
                   type uint16 {
                     range "1 .. 65535";
                   }
                 }
               }
               leaf history-size {
                 description "Number of stored history entries";
                 default "50";
                 type union {
                   type string {
                     pattern "<.*>|$.*";
                   }
                   type uint16 {
                     range "0 .. 500";
                   }
                 }
               }
               leaf moving-average-size {
                 description "Number of samples used for moving average";
                 default "0";
                 type union {
                   type string {
                     pattern "<.*>|$.*";
                   }
                   type uint32 {
                     range "0 .. 1024";
                   }
                 }
               }
               leaf routing-instance {
                 description "Routing instance used by the test sessions";
                 junos:must "(\"routing-instances $$\")";
                 junos:must-message "referenced routing-instance must be defined";
                 type string {
                   junos:posix-pattern "!^((__.*__)|(all)|(.*[ ].*)|(\"\")|(.{129,}))$";
                   junos:pattern-message "Must be a non-reserved string of 128 characters or less with no spaces.";
                 }
               }
               leaf target-address {
                 description "Destination address of TWAMP responder";
                 type jt:ipv4addr;
               }
               leaf test-count {
                 description "Total number of test session iterations";
                 default "0";
                 type union {
                   type string {
                     pattern "<.*>|$.*";
                   }
                   type uint32 {
                     range "0 .. 4294967290";
                   }
                 }
               }
               leaf test-interval {
                 description "Delay between test session iterations";
                 default "1";
                 units "seconds";
                 type union {
                   type string {
                     pattern "<.*>|$.*";
                   }
                   type uint16 {
                     range "1 .. 255";
                   }
                 }
               }
               container traps {
                 description "Trap to send if threshold is met or exceeded";
                 uses apply-advanced;
                 leaf test-iteration-done {
                   description "All test sessions configured under the control connection have completed an iteration";
                   type empty;
                 }
                 leaf control-connection-closed {
                   description "Control connection closed";
                   type empty;
                 }
               }
               list test-session {
                 key name;
                 ordered-by user;
                 description "Test session details";
                 leaf name {
                   description "Test session name";
                   type string {
                     length "1 .. 32";
                   }
                 }
                 uses apply-advanced;
                 leaf target-address {
                   description "Destination address of TWAMP responder";
                   type jt:ipv4addr;
                 }
                 leaf data-fill-with-zeros {
                   description "Fill contents of test packet with zeros";
                   type empty;
                 }
                 leaf data-size {
                   description "Size of the data portion of the probes";
                   default "60";
                   type union {
                     type string {
                       pattern "<.*>|$.*";
                     }
                     type uint16 {
                       range "60 .. 1400";
                     }
                   }
                 }
                 leaf dscp-code-points {
                   description "Differentiated Services code point bits or alias used for TCP control and UDP TWAMP test packets";
                   default "000000";
                   type string {
                     junos:posix-pattern "^(([01]{6})|([a-zA-Z].{0,63}))$";
                     junos:pattern-message "Not 6-bit pattern or code point alias";
                   }
                 }
                 leaf ttl {
                   description "Time to Live (hop-limit) value for an RPM IPv4(IPv6) packet";
                   default "64";
                   type union {
                     type string {
                       pattern "<.*>|$.*";
                     }
                     type uint32 {
                       range "1 .. 254";
                     }
                   }
                 }
                 leaf probe-count {
                   description "Total number of probes per test";
                   default "1";
                   type union {
                     type string {
                       pattern "<.*>|$.*";
                     }
                     type uint32 {
                       range "1 .. 4294967290";
                     }
                   }
                 }
                 leaf probe-interval {
                   description "Delay between two consecutive probes";
                   default "1";
                   units "seconds";
                   type union {
                     type string {
                       pattern "<.*>|$.*";
                     }
                     type uint32 {
                       range "1 .. 255";
                     }
                   }
                 }
                 container thresholds {
                   presence "enable thresholds";
                   description "TWAMP test threshold values. Set 0 to disable respective threshold";
                   uses apply-advanced;
                   leaf successive-loss {
                     description "Successive probe loss count indicating probe failure";
                     default "1";
                     type union {
                       type string {
                         pattern "<.*>|$.*";
                       }
                       type uint32 {
                         range "0 .. 15";
                       }
                     }
                   }
                   leaf total-loss {
                     description "Total probe loss count indicating test failure";
                     default "1";
                     type union {
                       type string {
                         pattern "<.*>|$.*";
                       }
                       type uint32 {
                         range "0 .. 4294967290";
                       }
                     }
                   }
                   leaf rtt {
                     description "Maximum round trip time per probe";
                     default "0";
                     units "microseconds";
                     type union {
                       type string {
                         pattern "<.*>|$.*";
                       }
                       type uint32 {
                         range "0 .. 60000000";
                       }
                     }
                   }
                   leaf max-rtt {
                     description "Maximum round trip time per test";
                     default "0";
                     units "microseconds";
                     type union {
                       type string {
                         pattern "<.*>|$.*";
                       }
                       type uint32 {
                         range "0 .. 60000000";
                       }
                     }
                   }
                   leaf jitter-rtt {
                     description "Maximum jitter per test";
                     default "0";
                     units "microseconds";
                     type union {
                       type string {
                         pattern "<.*>|$.*";
                       }
                       type uint32 {
                         range "0 .. 60000000";
                       }
                     }
                   }
                   leaf std-dev-rtt {
                     description "Maximum standard deviation per test";
                     default "0";
                     units "microseconds";
                     type union {
                       type string {
                         pattern "<.*>|$.*";
                       }
                       type uint32 {
                         range "0 .. 60000000";
                       }
                     }
                   }
                   leaf egress-time {
                     description "Maximum source to destination time per probe";
                     default "0";
                     units "microseconds";
                     type union {
                       type string {
                         pattern "<.*>|$.*";
                       }
                       type uint32 {
                         range "0 .. 60000000";
                       }
                     }
                   }
                   leaf ingress-time {
                     description "Maximum destination to source time per probe";
                     default "0";
                     units "microseconds";
                     type union {
                       type string {
                         pattern "<.*>|$.*";
                       }
                       type uint32 {
                         range "0 .. 60000000";
                       }
                     }
                   }
                   leaf jitter-ingress {
                     description "Maximum destination to source jitter per test";
                     default "0";
                     units "microseconds";
                     type union {
                       type string {
                         pattern "<.*>|$.*";
                       }
                       type uint32 {
                         range "0 .. 60000000";
                       }
                     }
                   }
                   leaf jitter-egress {
                     description "Maximum source to destination jitter per test";
                     default "0";
                     units "microseconds";
                     type union {
                       type string {
                         pattern "<.*>|$.*";
                       }
                       type uint32 {
                         range "0 .. 60000000";
                       }
                     }
                   }
                   leaf std-dev-ingress {
                     description "Maximum destination to source standard deviation per test";
                     default "0";
                     units "microseconds";
                     type union {
                       type string {
                         pattern "<.*>|$.*";
                       }
                       type uint32 {
                         range "0 .. 60000000";
                       }
                     }
                   }
                   leaf std-dev-egress {
                     description "Maximum source to destination standard deviation per test";
                     default "0";
                     units "microseconds";
                     type union {
                       type string {
                         pattern "<.*>|$.*";
                       }
                       type uint32 {
                         range "0 .. 60000000";
                       }
                     }
                   }
                 }
                 container traps {
                   description "Trap to send if threshold is met or exceeded";
                   uses apply-advanced;
                   leaf probe-failure {
                     description "Successive probe loss threshold reached";
                     type empty;
                   }
                   leaf test-failure {
                     description "Total probe loss threshold reached";
                     type empty;
                   }
                   leaf test-completion {
                     description "Test completed";
                     type empty;
                   }
                   leaf rtt-exceeded {
                     description "Exceeded maximum round trip time threshold";
                     type empty;
                   }
                   leaf max-rtt-exceeded {
                     description "Exceeded maximum round trip time threshold at the end of per test";
                     type empty;
                   }
                   leaf std-dev-exceeded {
                     description "Exceeded round trip time standard deviation threshold";
                     type empty;
                   }
                   leaf jitter-exceeded {
                     description "Exceeded jitter in round trip time threshold";
                     type empty;
                   }
                   leaf ingress-time-exceeded {
                     description "Exceeded maximum ingress time threshold";
                     type empty;
                   }
                   leaf ingress-std-dev-exceeded {
                     description "Exceeded ingress time standard deviation threshold";
                     type empty;
                   }
                   leaf ingress-jitter-exceeded {
                     description "Exceeded jitter in ingress time threshold";
                     type empty;
                   }
                   leaf egress-time-exceeded {
                     description "Exceeded maximum egress time threshold";
                     type empty;
                   }
                   leaf egress-std-dev-exceeded {
                     description "Exceeded egress time standard deviation threshold";
                     type empty;
                   }
                   leaf egress-jitter-exceeded {
                     description "Exceeded jitter in egress time threshold";
                     type empty;
                   }
                 }
               }
             }
           }
           container server {
             description "TWAMP server configuration";
             uses apply-advanced;
             leaf tcp-keepidle {
               description "Time to start TCP KEEPALIVEs on control connection (default 120)";
               default "120";
               units "seconds";
               type union {
                 type string {
                   pattern "<.*>|$.*";
                 }
                 type uint32 {
                   range "1 .. 600";
                 }
               }
             }
             leaf tcp-keepintvl {
               description "Delay between succesive TCP KEEPALIVEs (default 5)";
               default "5";
               units "seconds";
               type union {
                 type string {
                   pattern "<.*>|$.*";
                 }
                 type uint32 {
                   range "1 .. 600";
                 }
               }
             }
             leaf tcp-keepcnt {
               description "Number of TCP KEEPALIVEs sent (default 6)";
               default "6";
               type union {
                 type string {
                   pattern "<.*>|$.*";
                 }
                 type uint32 {
                   range "1 .. 50";
                 }
               }
             }
             list routing-instance-list {
               key name;
               ordered-by user;
               description "List of allowed routing instances,not more than 100, along with ports";
               leaf name {
                 description "Name of the routing instance";
                 junos:must "(\"routing-instances $$\")";
                 junos:must-message "referenced routing-instance must be defined";
                 type string {
                   junos:posix-pattern "!^((__.*__)|(all)|(.*[ ].*)|(\"\")|(.{129,}))$";
                   junos:pattern-message "Must be a non-reserved string of 128 characters or less with no spaces.";
                 }
               }
               uses apply-advanced;
               leaf port {
                 description "Port to be used by the routing instance";
                 type union {
                   type string {
                     pattern "<.*>|$.*";
                   }
                   type uint32 {
                     range "1 .. 65535";
                   }
                 }
               }
             }
             container authentication-mode {
               description "Authentication modes";
               uses apply-advanced;
               leaf none {
                 description "No authentication or encryption";
                 type empty;
               }
               container authenticated {
                 presence "enable authenticated";
                 description "Authenticated mode";
                 leaf control-only {
                   description "Authentication mode only for TWAMP control protocol";
                   status deprecated;
                   type empty;
                 }
               }
               container encrypted {
                 presence "enable encrypted";
                 description "Encrypted mode";
                 leaf control-only {
                   description "Encryption mode only for TWAMP control protocol";
                   status deprecated;
                   junos:must "(!(\".. .. encrypted-control-only\"))";
                   junos:must-message "'encrypted control-only' and 'control-only-encrypted' cannot be configured simultaneously";
                   type empty;
                 }
               }
               leaf control-only-encrypted {
                 description "Encrypted control and unauthenticated data mode";
                 type empty;
               }
             }
             list authentication-key-chain {
               key name;
               ordered-by user;
               description "Authentication key chain configuration";
               uses twamp-authentication-key-chain;
             }
             leaf server-inactivity-timeout {
               description "Control packet idle timeout value in minutes, 0 to disable";
               default "15";
               units "minutes";
               type union {
                 type string {
                   pattern "<.*>|$.*";
                 }
                 type uint32 {
                   range "0 .. 30";
                 }
               }
             }
             leaf max-connection-duration {
               description "Maximum Connection duration in hours, 0 to disable";
               default "0";
               units "hours";
               type union {
                 type string {
                   pattern "<.*>|$.*";
                 }
                 type uint32 {
                   range "0 .. 120";
                 }
               }
             }
             leaf maximum-sessions {
               description "Maximum number of test sessions for the server";
               default "64";
               type union {
                 type string {
                   pattern "<.*>|$.*";
                 }
                 type uint32 {
                   range "1 .. 2048";
                 }
               }
             }
             leaf maximum-sessions-per-connection {
               description "Maximum number of test sessions per client connection";
               type union {
                 type string {
                   pattern "<.*>|$.*";
                 }
                 type uint32 {
                   range "1 .. 1024";
                 }
               }
             }
             leaf maximum-connections {
               description "Maximum number of connections for the server";
               default "64";
               type union {
                 type string {
                   pattern "<.*>|$.*";
                 }
                 type uint32 {
                   range "1 .. 1000";
                 }
               }
             }
             leaf maximum-connections-per-client {
               description "Maximum number of server connections per client";
               type union {
                 type string {
                   pattern "<.*>|$.*";
                 }
                 type uint32 {
                   range "1 .. 500";
                 }
               }
             }
             leaf port {
               description "TWAMP server listening port";
               default "862";
               type union {
                 type string {
                   pattern "<.*>|$.*";
                 }
                 type uint32 {
                   range "1 .. 65535";
                 }
               }
             }
             list client-list {
               key name;
               ordered-by user;
               description "List of allowed clients";
               leaf name {
                 description "Name of client list";
                 type string {
                   length "1 .. 127";
                 }
               }
               uses apply-advanced;
               list address {
                 key name;
                 ordered-by user;
                 description "IP prefix of client";
                 leaf name {
                   description "IP prefix of client";
                   junos:must "(unique \"services rpm twamp server client-list <*> address $$\")";
                   junos:must-message "Same ip address can not be configured under multiple client lists";
                   type jt:ipv4prefix;
                 }
                 uses apply-advanced;
               }
             }
           }
         }
       }
       container app-engine {
         description "App-engine";
         uses apply-advanced;
         container security {
           presence "enable security";
           description "Enable app-engine security";
         }
         container monitor-cpu {
           description "Monitor node CPU usage";
           uses monitor-threshold;
         }
         container monitor-memory {
           description "Monitor node memory usage";
           uses monitor-threshold;
         }
         container monitor-storage {
           description "Monitor storage usage";
           uses monitor-threshold;
         }
         leaf default-compute-node-package {
           description "Default JunosV App Engine package for appliance";
           type string;
         }
         list compute-cluster {
           key name;
           ordered-by user;
           description "Configure compute cluster";
           leaf name {
             description "Compute cluster name";
             type string {
               length "1 .. 15";
             }
           }
           uses apply-advanced;
           container local-management {
             junos:must "(all \".. compute-node <*> interfaces\")";
             junos:must-message "Must specify compute-node management interface";
             description "Management address connected to compute cluster";
             uses apply-advanced;
             list routing-instance {
               key routing-instance-name;
               ordered-by user;
               description "Packets are restriction to specified routing instance";
               junos:must "(!(any \".. logical-system <*>\"))";
               junos:must-message "Must specify 'family' only under one hierarchy";
               max-elements 1;
               leaf routing-instance-name {
                 description "Name of routing instance";
                 type string {
                   junos:posix-pattern "!^((__.*__)|(all)|(.*[ ].*)|(\"\")|(.{129,}))$";
                   junos:pattern-message "Must be a non-reserved string of 128 characters or less with no spaces.";
                 }
               }
               uses apply-advanced;
               container family {
                 description "Protocol family";
                 container inet {
                   description "IPv4 parameters";
                   uses apply-advanced;
                   leaf address {
                     description "Interface address";
                     type jt:ipv4addr;
                   }
                 }
               }
             }
             container family {
               junos:must "(!(any \".. routing-instance <*>\"))";
               junos:must-message "Must specify 'family' only under one hierarchy";
               description "Protocol family";
               container inet {
                 description "IPv4 parameters";
                 uses apply-advanced;
                 leaf address {
                   description "Interface address";
                   type jt:ipv4addr;
                 }
               }
             }
           }
           container monitor-cpu {
             description "Monitor node CPU usage";
             uses monitor-threshold;
           }
           container monitor-memory {
             description "Monitor node memory usage";
             uses monitor-threshold;
           }
           container monitor-storage {
             description "Monitor storage usage";
             uses monitor-threshold;
           }
           list compute-node {
             key name;
             ordered-by user;
             description "Compute node name";
             max-elements 1;
             leaf name {
               description "Compute node name";
               type string {
                 length "1 .. 15";
               }
             }
             uses apply-advanced;
             container monitor-cpu {
               description "Monitor node CPU usage";
               uses monitor-threshold;
             }
             container monitor-memory {
               description "Monitor node memory usage";
               uses monitor-threshold;
             }
             container monitor-storage {
               description "Monitor storage usage";
               uses monitor-threshold;
             }
             choice compute-node-identifier {
               case case_1 {
                 leaf mac-address {
                   description "MAC address of the network boot interface";
                   junos:must "(\".. interfaces\")";
                   junos:must-message "Must specify management interface";
                   junos:must "(\".. .. local-management\")";
                   junos:must-message "Must specify compute cluster local-management";
                   junos:must "(unique \"services app-engine compute-cluster <*> compute-node <*> mac-address $$\")";
                   junos:must-message "MAC address must be unique across compute clusters";
                   type jt:mac-addr;
                 }
               }
               case case_2 {
               }
               case case_3 {
               }
             }
             leaf package {
               description "JunosV App Engine package";
               type string;
             }
             container routing-options {
               description "Route configuration for compute node";
               uses apply-advanced;
               container static {
                 description "Static routes";
                 uses apply-advanced;
                 list route {
                   key name;
                   ordered-by user;
                   description "Static route";
                   leaf name {
                     description "Destination IP address or prefix";
                     junos:must "(!(any \".. .. .. rib <*> static route $$\"))";
                     junos:must-message "Duplicate route entry";
                     type jt:ipv4prefix;
                   }
                   uses apply-advanced;
                   leaf next-hop {
                     description "Next hop to destination";
                     type jt:ipv4addr;
                   }
                 }
               }
               list rib {
                 key name;
                 ordered-by user;
                 description "Routing table options";
                 leaf name {
                   description "Routing table name";
                   type string {
                     length "1 .. 10";
                     junos:posix-pattern "inet.0";
                     junos:pattern-message "Only inet.0 is supported";
                   }
                 }
                 uses apply-advanced;
                 container static {
                   description "Static routes";
                   uses apply-advanced;
                   list route {
                     key name;
                     ordered-by user;
                     description "Static route";
                     leaf name {
                       description "Destination IP address or prefix";
                       junos:must "(!(\".. .. .. .. static route $$\"))";
                       junos:must-message "Duplicate route entry";
                       type jt:ipv4prefix;
                     }
                     uses apply-advanced;
                     leaf next-hop {
                       description "Next hop to destination";
                       type jt:ipv4addr;
                     }
                   }
                 }
               }
             }
             container interfaces {
               description "Network interfaces configuration";
               uses apply-advanced;
               list ethernet {
                 key name;
                 ordered-by user;
                 description "Interface configuration";
                 leaf name {
                   description "Interface name";
                   junos:must "(!(any \".. .. bridge <*> interface $$\"))";
                   junos:must-message "This interface is already associated with a bridge";
                   junos:must "(!(\".. .. bridge $$\"))";
                   junos:must-message "A bridge is configured with this name";
                   type string {
                     length "1 .. 15";
                     junos:posix-pattern "^eth[0-9]{1,2}$";
                     junos:pattern-message "Must be of the form eth<0-99>";
                   }
                 }
                 uses apply-advanced;
                 leaf management {
                   description "Use this as management interface";
                   junos:must "(!(\".. ether-options\"))";
                   junos:must-message "This interface belongs to an aggregated interface";
                   junos:must "(!(\".. .. .. fpc\"))";
                   junos:must-message "Must not specify any interface as management with fpc";
                   junos:must "((\".. family inet address\" || \".. family inet dhcp\"))";
                   junos:must-message "Management interface must have an address or dhcp configured";
                   junos:must "(!(\".. enable-passthrough\"))";
                   junos:must-message "Management interface cannot be passthrough interface";
                   type empty;
                 }
                 container family {
                   description "Protocol family";
                   junos:must "(!(\".. ether-options\"))";
                   junos:must-message "This interface belongs to an aggregated interface";
                   uses family;
                   junos:must "(!(\".. ether-options\"))";
                   junos:must-message "This interface belongs to an aggregated interface";
                 }
                 leaf enable-passthrough {
                   description "Enable passthrough on this interface";
                   junos:must "(!(\".. ether-options\"))";
                   junos:must-message "This interface belongs to an aggregated interface";
                   junos:must "(!(\".. mtu\"))";
                   junos:must-message "Passthrough interface cannot have MTU";
                   junos:must "(!(\".. family inet address\"))";
                   junos:must-message "Passthrough interface cannot have an address";
                   type empty;
                 }
                 leaf mtu {
                   description "Maximum transmit packet size";
                   type union {
                     type string {
                       pattern "<.*>|$.*";
                     }
                     type uint16 {
                       range "256 .. 9192";
                     }
                   }
                 }
                 container ether-options {
                   junos:must "((!(\".. management\") && (!(\".. family\") && !(\".. enable-passthrough\"))))";
                   junos:must-message "Ethernet interface can not exist separately if it is under a aggregated interface and vice versa";
                   uses apply-advanced;
                   choice agg-intf {
                     case case_1 {
                       leaf ieee-802-3ad {
                         description "Aggregated interface name";
                         junos:must "(!(\".. .. mtu\"))";
                         junos:must-message "Aggregate slave interface cannot have MTU";
                         junos:must "(!(\".. .. .. bridge $$\"))";
                         junos:must-message "A bridge is configured with this name";
                         type string {
                           length "1 .. 15";
                           junos:posix-pattern "^ae[0-9]{1,2}$";
                           junos:pattern-message "Must be of the form ae<0-99>";
                         }
                       }
                     }
                   }
                 }
               }
               list bridge {
                 key name;
                 ordered-by user;
                 description "Bridge configuration";
                 leaf name {
                   description "Bridge name";
                   junos:must "(!(any \".. .. bridge <*> interface $$\"))";
                   junos:must-message "Bridge name is already used in one of the bridge interface list";
                   junos:must "(!(\".. .. aggregate $$\"))";
                   junos:must-message "An aggregate interface is configured with this name";
                   junos:must "(!(\".. .. ethernet $$\"))";
                   junos:must-message "An interface is configured with this name";
                   type string {
                     length "1 .. 15";
                     junos:posix-pattern "^[A-za-z][.0-9A-Za-z_]{1,15}$";
                     junos:pattern-message "Must be a string of 15 or fewer characters. The string should start with a letter and can contain letters, digits, underscores and periods";
                   }
                 }
                 uses apply-advanced;
                 leaf management {
                   description "Use this as management bridge";
                   junos:must "(!(\".. .. .. fpc\"))";
                   junos:must-message "Must not specify any interface as management with FPC compute node";
                   junos:must "((\".. family inet address\" || \".. family inet dhcp\"))";
                   junos:must-message "Management bridge must have an address or dhcp configured";
                   type empty;
                 }
                 container family {
                   description "Protocol family";
                   uses family;
                 }
                 leaf-list interface {
                   ordered-by user;
                   description "Bridge interface list";
                   junos:must "((!(\".. .. aggregate family inet address\") && !(\".. .. aggregate family inet dhcp\")))";
                   junos:must-message "Interface associated to bridge can not have address";
                   type string {
                     length "1 .. 15";
                   }
                   max-elements 4;
                 }
                 leaf mtu {
                   description "Maximum transmit packet size";
                   type union {
                     type string {
                       pattern "<.*>|$.*";
                     }
                     type uint16 {
                       range "256 .. 9192";
                     }
                   }
                 }
               }
               list aggregate {
                 key name;
                 ordered-by user;
                 description "Aggregate interface configuration";
                 leaf name {
                   description "Aggregated interface name";
                   junos:must "(!(\".. .. bridge $$\"))";
                   junos:must-message "A bridge is configured with this name";
                   junos:must "(!(\".. .. ethernet $$\"))";
                   junos:must-message "An interface is configured with this name";
                   junos:must "(any \".. .. ethernet <*> ether-options ieee-802-3ad $$\")";
                   junos:must-message "Aggregated interface must have some slave interface";
                   type string {
                     length "1 .. 15";
                     junos:posix-pattern "^ae[0-9]{1,2}$";
                     junos:pattern-message "Must be of the form ae<0-99>";
                   }
                 }
                 uses apply-advanced;
                 leaf management {
                   description "Use this as management aggregate";
                   junos:must "((\".. family inet address\" || \".. family inet dhcp\"))";
                   junos:must-message "Management aggregate must have an address or dhcp configured";
                   type empty;
                 }
                 container family {
                   description "Protocol family";
                   uses family;
                 }
                 leaf mtu {
                   description "Maximum transmit packet size";
                   type union {
                     type string {
                       pattern "<.*>|$.*";
                     }
                     type uint16 {
                       range "256 .. 9192";
                     }
                   }
                 }
                 container aggregated-ether-options {
                   presence "enable aggregated-ether-options";
                   description "Link aggregation parameters";
                   uses apply-advanced;
                   leaf hash-policy {
                     default "layer-3-and-4";
                     type enumeration {
                       enum "layer-2" {
                         description "Uses mac address of both source and destination for hashing";
                       }
                       enum "layer-3-and-4" {
                         description "Uses port number and IP address of both source and destination for hashing";
                       }
                       enum "layer-2-and-3" {
                         description "Uses mac and IP address of both source and destination for hashing";
                       }
                     }
                   }
                   leaf miimon {
                     description "Link monitoring interval in milli-second";
                     type union {
                       type uint32;
                       type string {
                         pattern "<.*>|$.*";
                       }
                     }
                   }
                 }
               }
             }
             list syslog {
               key name;
               ordered-by user;
               description "System logging facility";
               leaf name {
                 description "Facility type";
                 type enumeration {
                   enum "any" {
                     description "All facilities";
                   }
                   enum "authorization" {
                     description "Authorization system";
                   }
                   enum "privileged" {
                     description "Privileged authorization events";
                   }
                   enum "cron" {
                     description "Cron daemon";
                   }
                   enum "daemon" {
                     description "Various system processes";
                   }
                   enum "kernel" {
                     description "Kernel";
                   }
                   enum "syslog" {
                     description "Syslog messages";
                   }
                   enum "user" {
                     description "User processes";
                   }
                   enum "uucp" {
                     description "UUCP system";
                   }
                   enum "local0" {
                     description "Local 0 messages";
                   }
                   enum "local1" {
                     description "Local 1 messages";
                   }
                   enum "local2" {
                     description "Local 2 messages";
                   }
                   enum "local3" {
                     description "Local 3 messages";
                   }
                   enum "local4" {
                     description "Local 4 messages";
                   }
                   enum "local5" {
                     description "Local 5 messages";
                   }
                   enum "local6" {
                     description "Local 6 messages";
                   }
                   enum "local7" {
                     description "Local 7 messages";
                   }
                 }
               }
               choice level {
                 case case_1 {
                   leaf any {
                     description "All levels";
                     type empty;
                   }
                 }
                 case case_2 {
                   leaf emergency {
                     description "Panic conditions";
                     type empty;
                   }
                 }
                 case case_3 {
                   leaf alert {
                     description "Conditions that should be corrected immediately";
                     type empty;
                   }
                 }
                 case case_4 {
                   leaf critical {
                     description "Critical conditions";
                     type empty;
                   }
                 }
                 case case_5 {
                   leaf error {
                     description "Error conditions";
                     type empty;
                   }
                 }
                 case case_6 {
                   leaf warning {
                     description "Warning messages";
                     type empty;
                   }
                 }
                 case case_7 {
                   leaf notice {
                     description "Conditions that should be handled specially";
                     type empty;
                   }
                 }
                 case case_8 {
                   leaf info {
                     description "Informational messages";
                     type empty;
                   }
                 }
                 case case_9 {
                   leaf debug {
                     description "Debug messages";
                     type empty;
                   }
                 }
               }
             }
           }
         }
         container virtual-machines {
           description "Virtual-machine management";
           uses apply-advanced;
           list instance {
             key name;
             ordered-by user;
             description "Virtual-machine instance";
             leaf name {
               description "Virtual-machine instance identifier";
               type string {
                 length "1 .. 39";
               }
             }
             uses apply-advanced;
             leaf cpu {
               description "Units of CPUs (default 1 cpu)";
               default "1";
               type union {
                 type string {
                   pattern "<.*>|$.*";
                 }
                 type uint32 {
                   range "1 .. 16";
                 }
               }
             }
             leaf memory {
               description "Memory for the virtual-machine (default 1 gigabytes)";
               default "1";
               units "gigabytes";
               type union {
                 type string {
                   pattern "<.*>|$.*";
                 }
                 type uint32 {
                   range "1 .. 32";
                 }
               }
             }
             leaf package {
               description "Virtual-machine package";
               type string {
                 length "1 .. 120";
               }
             }
             container local-management {
               description "Management address connected to virtual machine";
               uses apply-advanced;
               list routing-instance {
                 key routing-instance-name;
                 ordered-by user;
                 description "Packets are restriction to specified routing instance";
                 junos:must "(!(any \".. logical-system <*>\"))";
                 junos:must-message "Must specify 'family' only under one hierarchy";
                 max-elements 1;
                 leaf routing-instance-name {
                   description "Name of routing instance";
                   type string {
                     junos:posix-pattern "!^((__.*__)|(all)|(.*[ ].*)|(\"\")|(.{129,}))$";
                     junos:pattern-message "Must be a non-reserved string of 128 characters or less with no spaces.";
                   }
                 }
                 uses apply-advanced;
                 container family {
                   description "Protocol family";
                   container inet {
                     description "IPv4 parameters";
                     uses apply-advanced;
                     leaf address {
                       description "Interface address";
                       type jt:ipv4addr;
                     }
                   }
                 }
               }
               container family {
                 junos:must "(!(any \".. routing-instance <*>\"))";
                 junos:must-message "Must specify 'family' only under one hierarchy";
                 description "Protocol family";
                 container inet {
                   description "IPv4 parameters";
                   uses apply-advanced;
                   leaf address {
                     description "Interface address";
                     type jt:ipv4addr;
                   }
                 }
               }
             }
             list compute-cluster {
               key name;
               ordered-by user;
               description "Compute cluster on which the virtual-machine runs";
               max-elements 1;
               leaf name {
                 description "Compute cluster name";
                 junos:must "(\"services app-engine compute-cluster $$\")";
                 junos:must-message "Referenced compute cluster must be defined";
                 type string {
                   length "1 .. 15";
                 }
               }
               uses apply-advanced;
               leaf compute-node {
                 description "Compute node on which the virtual-machine runs";
                 junos:must "(((\"services app-engine compute-cluster ${compute-cluster} compute-node $$ fpc\" && \".. .. local-management\") || !(\"services app-engine compute-cluster ${compute-cluster} compute-node $$ fpc\")))";
                 junos:must-message "Must specify local-management for virtual machine on FPC compute node";
                 junos:must "(\"services app-engine compute-cluster ${compute-cluster} compute-node $$\")";
                 junos:must-message "Referenced compute node must be defined";
                 type string {
                   length "1 .. 15";
                 }
               }
             }
             list interface {
               key name;
               ordered-by user;
               description "Virtual-machine interface configuration";
               leaf name {
                 description "Virtual-machine interface name";
                 type string {
                   length "1 .. 31";
                 }
               }
               uses apply-advanced;
               leaf hw-model {
                 description "Interface hardware model";
                 default "e1000g";
                 type enumeration {
                   enum "e1000g" {
                     description "Gigabit Ethernet e1000g driver";
                   }
                   enum "virtio" {
                     description "Para-virtualizing the interface";
                   }
                 }
               }
               leaf host-interface {
                 description "Passthrough host interface for virtual-machine";
                 type string {
                   length "1 .. 15";
                 }
               }
               leaf bridge {
                 description "Bridge that the interface connected to";
                 junos:must "(!(\".. mtu\"))";
                 junos:must-message "Bridged VM interface inherits MTU from the bridge";
                 junos:must "(!(\".. host-interface\"))";
                 junos:must-message "bridge can not defined with passthrough/host-interface";
                 type string {
                   length "1 .. 15";
                 }
               }
               leaf mtu {
                 description "Maximum transmit packet size";
                 type union {
                   type string {
                     pattern "<.*>|$.*";
                   }
                   type uint16 {
                     range "256 .. 9192";
                   }
                 }
               }
               container family {
                 description "Interface address family";
                 container inet {
                   presence "enable inet";
                   description "IPv4 parameters";
                   uses apply-advanced;
                   list address {
                     key name;
                     ordered-by user;
                     description "Interface address/destination prefix";
                     leaf name {
                       description "Interface address/destination prefix";
                       type jt:ipv4prefix;
                     }
                     uses apply-advanced;
                     leaf primary {
                       description "Primary address on the interface";
                       type empty;
                     }
                   }
                 }
               }
             }
             container routing-options {
               description "Route configuration for virutal machine";
               uses apply-advanced;
               container static {
                 description "Static routes";
                 uses apply-advanced;
                 list route {
                   key name;
                   ordered-by user;
                   description "Static route";
                   leaf name {
                     description "Destination IP address or prefix";
                     junos:must "(!(any \".. .. .. rib <*> static route $$\"))";
                     junos:must-message "Duplicate route entry";
                     type jt:ipv4prefix;
                   }
                   uses apply-advanced;
                   leaf next-hop {
                     description "Next hop to destination";
                     type jt:ipv4addr;
                   }
                 }
               }
               list rib {
                 key name;
                 ordered-by user;
                 description "Routing table options";
                 leaf name {
                   description "Routing table name";
                   type string {
                     length "1 .. 10";
                     junos:posix-pattern "inet.0";
                     junos:pattern-message "Only inet.0 is supported";
                   }
                 }
                 uses apply-advanced;
                 container static {
                   description "Static routes";
                   uses apply-advanced;
                   list route {
                     key name;
                     ordered-by user;
                     description "Static route";
                     leaf name {
                       description "Destination IP address or prefix";
                       junos:must "(!(\".. .. .. .. static route $$\"))";
                       junos:must-message "Duplicate route entry";
                       type jt:ipv4prefix;
                     }
                     uses apply-advanced;
                     leaf next-hop {
                       description "Next hop to destination";
                       type jt:ipv4addr;
                     }
                   }
                 }
               }
             }
             list secondary-disk {
               key name;
               ordered-by user;
               description "Virtual-machine disk";
               leaf name {
                 description "Virtual-machine disk name";
                 type enumeration {
                   enum "hdb" {
                     description "Disk name is hdb";
                   }
                   enum "hdc" {
                     description "Disk name is hdc";
                   }
                   enum "hdd" {
                     description "Disk name is hdd";
                   }
                 }
               }
               leaf size {
                 description "Virtual-machine secondary disk size";
                 units "gigabytes";
                 type union {
                   type string {
                     pattern "<.*>|$.*";
                   }
                   type uint32 {
                     range "1 .. 160";
                   }
                 }
               }
             }
           }
         }
       }
       container unified-access-control {
         description "Configure Unified Access Control";
         uses apply-advanced;
         list infranet-controller {
           key name;
           ordered-by user;
           description "Configure infranet controller";
           leaf name {
             description "Infranet controller name";
             type string {
               length "1 .. 31";
             }
           }
           uses apply-advanced;
           leaf address {
             description "Infranet controller IP address";
             type jt:ipv4addr;
           }
           leaf port {
             description "Infranet controller port";
             default "11123";
             type union {
               type string {
                 pattern "<.*>|$.*";
               }
               type uint32 {
                 range "1 .. 65535";
               }
             }
           }
           leaf interface {
             description "Outgoing interface";
             type union {
               type jt:interface-name;
               type string {
                 pattern "<.*>|$.*";
               }
             }
           }
           leaf password {
             description "Infranet controller server password";
             type string {
               length "1 .. 255";
             }
           }
           leaf-list ca-profile {
             ordered-by user;
             description "Define a list of certificate authority";
             type string;
           }
           leaf server-certificate-subject {
             description "Subject name of infranet controller certificate to match";
             type string {
               length "1 .. 255";
             }
           }
         }
         leaf certificate-verification {
           description "Specify certificate verification requirement";
           default "warning";
           type enumeration {
             enum "warning" {
               description "Warn if certificate is not being verified";
             }
             enum "required" {
               description "Require certificate verification. Most secure";
             }
             enum "optional" {
               description "Make verification optional, no warnings. Least secure";
             }
           }
         }
         leaf timeout {
           description "Timeout for idle infranet controller link in seconds";
           default "300";
           type union {
             type string {
               pattern "<.*>|$.*";
             }
             type uint32 {
               range "2 .. 10000";
             }
           }
         }
         leaf interval {
           description "Heartbeat interval from infranet controller in seconds";
           default "30";
           type union {
             type string {
               pattern "<.*>|$.*";
             }
             type uint32 {
               range "1 .. 9999";
             }
           }
         }
         leaf timeout-action {
           description "Specify action when infranet controller timeout occurs";
           default "close";
           type enumeration {
             enum "close" {
               description "Remove existing sessions and block further traffic";
             }
             enum "no-change" {
               description "Preserve existing connections; block new sessions";
             }
             enum "open" {
               description "Allow traffic for new and existing sessions to go through";
             }
           }
         }
         leaf test-only-mode {
           description "Allow all traffic and only log enforcement result";
           type empty;
         }
         container traceoptions {
           description "UAC trace options";
           uses apply-advanced;
           leaf no-remote-trace {
             description "Disable remote tracing";
             junos:must "(\"system tracing\")";
             junos:must-message "'no-remote-trace' is valid only when [system tracing] is configured";
             type empty;
           }
           container file {
             description "Trace file information";
             leaf filename {
               description "Name of file in which to write trace information";
               type string {
                 length "1 .. 1024";
                 junos:posix-pattern "![/ %]";
                 junos:pattern-message "Must not contain '/', % or a space";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "all" {
                   description "Trace with all flags enabled";
                 }
                 enum "ipc" {
                   description "IPC tracing";
                 }
                 enum "config" {
                   description "Configuration tracing";
                 }
                 enum "connect" {
                   description "Communication with infranet controller tracing";
                 }
               }
             }
           }
         }
         list captive-portal {
           key name;
           ordered-by user;
           description "Unauthenticated HTTP redirect";
           leaf name {
             description "Redirect policy name";
             type string {
               length "1 .. 128";
             }
           }
           uses apply-advanced;
           leaf redirect-traffic {
             description "Traffic to redirect";
             type enumeration {
               enum "unauthenticated" {
                 description "Redirect unauthenticated traffic";
               }
               enum "all" {
                 description "Redirect all traffic";
               }
             }
           }
           leaf redirect-url {
             description "Redirect URL for unauthenticated users";
             type string {
               length "1 .. 512";
               junos:posix-pattern "^https?://([[:alnum:]%]?[[:alnum:]%._-]*[[:alnum:]%]?)(/[[:alnum:]_-]*)*/?([?][[:alnum:]_%+-]*=[[:alnum:]_%+-:/.]*(&[[:alnum:]_%+-]*=[[:alnum:]_%+-:/.]*)*)?$";
               junos:pattern-message "Redirect URL be a valid HTTP URL";
             }
           }
         }
       }
       container captive-portal {
         description "Captive Portal options";
         uses juniper-services-captive-portal;
       }
       container application-identification {
         presence "enable application-identification";
         description "Application identification configuration";
         uses apply-advanced;
         leaf enable-heuristics {
           description "Enable heuristic application identification";
           status deprecated;
           type empty;
         }
         container enable-performance-mode {
           presence "enable enable-performance-mode";
           description "Enable performance mode knobs for best DPI performance";
           uses apply-advanced;
           leaf max-packet-threshold {
             description "Max packet inspection threshold including both c2s ans s2c direction packets. Default value is 2 if not configured";
             default "2";
             type union {
               type string {
                 pattern "<.*>|$.*";
               }
               type uint32 {
                 range "1 .. 100";
               }
             }
           }
         }
         leaf imap-cache-timeout {
           description "IMAP cache entry timeout in seconds";
           type union {
             type string {
               pattern "<.*>|$.*";
             }
             type uint32 {
               range "1 .. 86400";
             }
           }
         }
         leaf imap-cache-size {
           description "IMAP cache size, it will be effective only after next appid sigpack install";
           type union {
             type string {
               pattern "<.*>|$.*";
             }
             type uint32 {
               range "60 .. 512000";
             }
           }
         }
         container download {
           uses apply-advanced;
           leaf url {
             description "URL for application package download";
             type string {
               junos:posix-pattern "^((file)|(http)|(https)):";
               junos:pattern-message "URL starts with http, https or file";
             }
           }
           leaf ignore-server-validation {
             description "Disable server authentication for Applicaton Signature download";
             type empty;
           }
           container automatic {
             description "Scheduled download and update";
             uses apply-advanced;
             leaf start-time {
               description "Start time(MM-DD.hh:mm)";
               type string {
                 junos:posix-pattern "^((0[1-9]|1[012])[-](0[1-9]|[12][0-9]|3[01])[.]([0-1][0-9]|[2][0-3])[:]([0-5][0-9]))$";
                 junos:pattern-message "Invalid date; format is MM-DD.hh:mm";
               }
             }
             leaf interval {
               description "Attempt to download new application package";
               default "24";
               units "hours";
               type union {
                 type string {
                   pattern "<.*>|$.*";
                 }
                 type uint32 {
                   range "6 .. 720";
                 }
               }
             }
           }
           leaf proxy-profile {
             description "Configure web proxy for Application signature download";
             junos:must "(\"services proxy profile $$\")";
             junos:must-message "proxy profile must be defined";
             type string {
               length "1 .. 128";
             }
           }
         }
         container statistics {
           description "Configure application statistics information";
           leaf interval {
             description "Application statistics collection interval";
             default "1";
             units "minutes";
             type union {
               type string {
                 pattern "<.*>|$.*";
               }
               type uint32 {
                 range "1 .. 1440";
               }
             }
           }
         }
         container nested-application-settings {
           presence "enable nested-application-settings";
           description "Nested application settings";
           status deprecated;
           uses apply-advanced;
           leaf no-nested-application {
             description "Disable nested application identification";
             type empty;
           }
           leaf no-application-system-cache {
             description "Not to save nested AI match in application system cache";
             type empty;
           }
         }
         leaf no-application-identification {
           description "Disable all application identification methods";
           status deprecated;
           type empty;
         }
         leaf no-application-system-cache {
           description "Disable storing AI result in application system cache";
           type empty;
         }
         leaf max-sessions {
           description "Max sessions that can run AI at the same time";
           status deprecated;
           type union {
             type string {
               pattern "<.*>|$.*";
             }
             type uint32 {
               range "0 .. 500000";
             }
           }
         }
         leaf application-system-cache-timeout {
           description "Application system cache entry lifetime";
           type union {
             type string {
               pattern "<.*>|$.*";
             }
             type uint32 {
               range "0 .. 1000000";
             }
           }
         }
         container application-system-cache {
           presence "enable application-system-cache";
           description "Enable or Disable application system cache";
           uses apply-advanced;
           leaf security-services {
             description "Enable ASC for security services (appfw, appqos, idp, skyatp..)";
             type empty;
           }
           leaf no-miscellaneous-services {
             description "Disable ASC for miscellaneous services APBR,...";
             type empty;
           }
         }
         leaf max-transactions {
           description "Number of transaction finals to terminate application classification";
           type union {
             type string {
               pattern "<.*>|$.*";
             }
             type uint16 {
               range "0 .. 25";
             }
           }
         }
         leaf max-checked-bytes {
           description "Inspect the maximal number of bytes";
           status deprecated;
           type union {
             type string {
               pattern "<.*>|$.*";
             }
             type uint32 {
               range "0 .. 100000";
             }
           }
         }
         list application {
           key name;
           description "Configure application definition";
           junos:must "((any \". <*> icmp-mapping\" || (any \". <*> ip-protocol-mapping\" || (any \". <*> address-mapping\" || (any \". <*> over\" || any \". <*> signature\")))))";
           junos:must-message "All applications must have either icmp-mapping or ip-protocol-mapping or address-mapping or over or signature object ";
           leaf name {
             description "A unique application identifier";
             type string {
               length "1 .. 63";
             }
           }
           uses apply-advanced;
           leaf index {
             description "Custom index (32768..65534). Application index";
             status deprecated;
             junos:must "(unique \"services application-identification application <*> index $$\")";
             junos:must-message "Application index has to be unique among all applications";
             type union {
               type string {
                 pattern "<.*>|$.*";
               }
               type uint16 {
                 range "1 .. 65534";
               }
             }
           }
           leaf disable {
             description "Disable this application definition in AI";
             status deprecated;
             type empty;
           }
           leaf cacheable {
             description "Cacheable";
             type empty;
           }
           leaf description {
             description "Text description of application";
             type string {
               junos:posix-pattern "^.{1,255}$";
               junos:pattern-message "Must be a string of 255 characters or less";
             }
           }
           leaf priority {
             description "Application matching priority";
             default "high";
             type enumeration {
               enum "high" {
                 description "Highest priority over all other signatures";
               }
               enum "low" {
                 description "Lowest priority over all other signatures";
               }
             }
           }
           leaf order {
             description "The order value, lower the value higher the priority";
             junos:must "(unique \"services application-identification application <*> order $$\")";
             junos:must-message "Application order has to be unique among all applications";
             type union {
               type string {
                 pattern "<.*>|$.*";
               }
               type uint16 {
                 range "1 .. 50000";
               }
             }
           }
           leaf maximum-transactions {
             description "Maximum number of transactions matched by AI";
             status deprecated;
             type union {
               type uint16;
               type string {
                 pattern "<.*>|$.*";
               }
             }
           }
           container icmp-mapping {
             description "Match ICMP message";
             uses apply-advanced;
             leaf type {
               description "Numeric type value";
               type union {
                 type string {
                   pattern "<.*>|$.*";
                 }
                 type uint16 {
                   range "0 .. 254";
                 }
               }
             }
             leaf code {
               description "Numeric code value";
               junos:must "(\".. type\")";
               junos:must-message "ICMP type must be configured";
               type union {
                 type string {
                   pattern "<.*>|$.*";
                 }
                 type uint16 {
                   range "0 .. 254";
                 }
               }
             }
           }
           container ip-protocol-mapping {
             description "Match IP protocol";
             uses apply-advanced;
             leaf protocol {
               description "Numeric protocol value";
               junos:must "(unique \"services application-identification application <*> ip-protocol-mapping protocol $$\")";
               junos:must-message "Protocol has to be unique among all applications";
               type union {
                 type string {
                   pattern "<.*>|$.*";
                 }
                 type uint16 {
                   range "0 .. 254";
                 }
               }
             }
           }
           list address-mapping {
             key name;
             ordered-by user;
             description "Match IP address";
             leaf name {
               description "Address name";
               type string {
                 length "1 .. 63";
               }
             }
             uses apply-advanced;
             container filter {
               description "Match IP/port";
               uses apply-advanced;
               leaf ip {
                 description "IP address and prefix-length";
                 type jt:ipprefix;
               }
               container port-range {
                 description "Port ranges";
                 uses apply-advanced;
                 leaf-list tcp {
                   ordered-by user;
                   description "TCP port range";
                   type string;
                   max-elements 20;
                 }
                 leaf-list udp {
                   ordered-by user;
                   description "UDP port range";
                   type string;
                   max-elements 20;
                 }
               }
             }
           }
           list over {
             key name;
             description "Set of L4/L7 application that carries given application";
             max-elements 8;
             leaf name {
               description "A unique application and protocol identifier";
               type string {
                 length "1 .. 63";
               }
             }
             uses apply-advanced;
             list signature {
               key name;
               description "Application signature for pattern matching";
               leaf name {
                 description "A unique application signature identifier";
                 type string {
                   length "1 .. 63";
                 }
               }
               uses apply-advanced;
               leaf-list port-range {
                 ordered-by user;
                 description "Port range";
                 type string;
                 max-elements 64;
               }
               list member {
                 key name;
                 description "Application signature member";
                 leaf name {
                   description "Application signature member identifier in range m01 - m15";
                   type string {
                     length "1 .. 63";
                     junos:posix-pattern "^m(0[1-9]|1[0-5])";
                     junos:pattern-message "Must be m01 - m15";
                   }
                 }
                 uses apply-advanced;
                 leaf context {
                   description "Context to be matched on";
                   type string;
                 }
                 leaf pattern {
                   description "DFA pattern matched on context";
                   type string {
                     junos:posix-pattern "^.{1,127}$";
                     junos:pattern-message "Must be a string of 127 characters or less";
                   }
                 }
                 leaf direction {
                   description "Connection direction of the packets to apply pattern matching";
                   type enumeration {
                     enum "client-to-server" {
                       description "Client to server";
                     }
                     enum "server-to-client" {
                       description "Server to client";
                     }
                     enum "any" {
                       description "Any direction";
                     }
                   }
                 }
               }
             }
           }
         }
         list nested-application {
           key name;
           description "Configure nested application definition";
           status deprecated;
           leaf name {
             description "A unique application identifier";
             type string {
               length "1 .. 63";
             }
           }
           uses apply-advanced;
           leaf type {
             description "Well-known application such as FACEBOOK and KAZZA";
             junos:must "(unique \"services application-identification nested-application <*> type $$\")";
             junos:must-message "Nested application type has to be unique among all nested applications";
             type string {
               length "1 .. 63";
             }
           }
           leaf index {
             description "Custom index (32768..65534). Application index";
             status deprecated;
             junos:must "(!(any \"services application-identification application <*> index $$\"))";
             junos:must-message "Nested application index has to be unique among all applications and nested applications";
             junos:must "(unique \"services application-identification nested-application <*> index $$\")";
             junos:must-message "Nested application index has to be unique among all nested applications";
             type union {
               type string {
                 pattern "<.*>|$.*";
               }
               type uint16 {
                 range "1 .. 65534";
               }
             }
           }
           leaf protocol {
             description "Name of layer 7 application that carries nested application";
             type string {
               length "1 .. 63";
             }
           }
           list signature {
             key name;
             description "Nested application signature for pattern matching";
             leaf name {
               description "A unique nested application signature identifier";
               junos:must "(unique \"services application-identification nested-application <*> signature $$\")";
               junos:must-message "Nested application signature name has to be unique among all nested applications";
               type string {
                 length "1 .. 63";
               }
             }
             uses apply-advanced;
             list member {
               key name;
               description "Pattern matched on client-to-server packets";
               leaf name {
                 description "A unique nested application signature member identifier";
                 type string {
                   length "1 .. 63";
                   junos:posix-pattern "^m(0[1-9]|1[0-6])";
                   junos:pattern-message "Must be m01 - m16";
                 }
               }
               uses apply-advanced;
               leaf context {
                 description "Context to be matched on";
                 type string;
               }
               leaf pattern {
                 description "Pattern matched on context";
                 type string;
               }
               leaf direction {
                 description "Connection direction of the packets to apply pattern matching";
                 type enumeration {
                   enum "client-to-server" {
                     description "Client to server";
                   }
                   enum "server-to-client" {
                     description "Server to client";
                   }
                   enum "any" {
                     description "Any direction";
                   }
                 }
               }
               leaf check-bytes {
                 description "Maximum number of bytes to check for stream context ";
                 default "1000";
                 type union {
                   type string {
                     pattern "<.*>|$.*";
                   }
                   type uint32 {
                     range "1 .. 5000";
                   }
                 }
               }
             }
             leaf chain-order {
               description "The order of members is used to match the pattern";
               type empty;
             }
             leaf maximum-transactions {
               description "Maximum number of transactions matched by AI";
               type union {
                 type uint16;
                 type string {
                   pattern "<.*>|$.*";
                 }
               }
             }
             leaf order {
               description "Application matching priority";
               status deprecated;
               junos:must "(!(any \"services application-identification application <*> signature order $$\"))";
               junos:must-message "Nested application order has to be unique among all applications and nested applications";
               junos:must "(unique \"services application-identification nested-application <*> signature <*> order $$\")";
               junos:must-message "Nested application order has to be unique among all nested applications";
               type union {
                 type string {
                   pattern "<.*>|$.*";
                 }
                 type uint16 {
                   range "1 .. 65535";
                 }
               }
             }
             container insert-before {
               description "Insert before another signature";
               uses apply-advanced;
               leaf insert-before-name {
                 description "An application name";
                 type string;
               }
             }
           }
         }
         list application-group {
           key name;
           description "Define application group";
           leaf name {
             description "A unique application group identifier";
             type string {
               length "1 .. 63";
             }
           }
           uses apply-advanced;
           list application-groups {
             key name;
             description "Configure child application group(s)";
             leaf name {
               description "Name of the child application group";
               type string {
                 length "1 .. 63";
               }
             }
             uses apply-advanced;
           }
           list applications {
             key name;
             description "Configure applications that belong to this application group";
             leaf name {
               description "Configure application name";
               type string {
                 length "1 .. 63";
               }
             }
             uses apply-advanced;
           }
           leaf disable {
             description "Disable this application group definition in AI";
             status deprecated;
             type empty;
           }
         }
         container traceoptions {
           description "Trace options for application identification";
           uses apply-advanced;
           leaf no-remote-trace {
             description "Disable remote tracing";
             junos:must "(\"system tracing\")";
             junos:must-message "'no-remote-trace' is valid only when [system tracing] is configured";
             type empty;
           }
           container file {
             description "Trace file information";
             leaf filename {
               description "Name of file in which to write trace information";
               type string {
                 length "1 .. 1024";
                 junos:posix-pattern "![/ %]";
                 junos:pattern-message "Must not contain '/', % or a space";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Events and other information to include in trace output";
             leaf name {
               description "Flag name to include in trace output";
               type enumeration {
                 enum "all" {
                   description "All events";
                 }
               }
             }
           }
           leaf level {
             description "Level of debugging output";
             default "error";
             type enumeration {
               enum "error" {
                 description "Match error conditions";
               }
               enum "warning" {
                 description "Match warning messages";
               }
               enum "notice" {
                 description "Match conditions that should be handled specially";
               }
               enum "info" {
                 description "Match informational messages";
               }
               enum "verbose" {
                 description "Match verbose messages";
               }
               enum "all" {
                 description "Match all levels";
               }
             }
           }
         }
       }
       container ssl {
         description "Configuration for Secure Socket Layer support service";
         uses apply-advanced;
         container traceoptions {
           description "Trace options for Secure Socket Layer support service";
           uses ssl-traceoptions;
         }
         container termination {
           description "Configuration for Secure Socket Layer termination support service";
           uses ssl-termination-config;
         }
         container initiation {
           description "Configuration for Secure Socket Layer initiation support service";
           uses ssl-initiation-config;
         }
         container proxy {
           description "Configuration for Secure Socket Layer proxy support service";
           uses ssl-proxy-config;
         }
       }
       container softwires {
         description "Configure softwire feature";
         uses softwires-object;
       }
       container screen {
         description "Configure screen feature";
         uses apply-advanced;
         container trap {
           presence "enable trap";
           description "Configure trap interval";
           leaf interval {
             description "Trap interval";
             default "2";
             units "seconds";
             type union {
               type string {
                 pattern "<.*>|$.*";
               }
               type uint32 {
                 range "1 .. 3600";
               }
             }
           }
         }
         container cpu-throttle {
           presence "enable cpu-throttle";
           description "Configure cpu-throttle percentage";
           uses apply-advanced;
           leaf percentage {
             description "Percentage of cpu throttle";
             units "percentage";
             type union {
               type string {
                 pattern "<.*>|$.*";
               }
               type uint32 {
                 range "1 .. 100";
               }
             }
           }
         }
         list ids-option {
           key name;
           description "Configure ids-option";
           uses ids-option-type;
         }
         container traceoptions {
           description "Trace options for Network Security Screen";
           uses apply-advanced;
           leaf no-remote-trace {
             description "Disable remote tracing";
             junos:must "(\"system tracing\")";
             junos:must-message "'no-remote-trace' is valid only when [system tracing] is configured";
             type empty;
           }
           container file {
             description "Trace file information";
             leaf filename {
               description "Name of file in which to write trace information";
               type string {
                 length "1 .. 1024";
                 junos:posix-pattern "![/ %]";
                 junos:pattern-message "Must not contain '/', % or a space";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "configuration" {
                   description "Trace configuration events";
                 }
                 enum "flow" {
                   description "Trace flow events";
                 }
                 enum "all" {
                   description "Trace everything";
                 }
               }
             }
           }
         }
       }
       container security-intelligence {
         uses apply-advanced;
         container category {
           description "Category to be disabled";
           uses apply-advanced;
           container all {
             presence "enable all";
             description "All categories";
             uses apply-advanced;
             container disable {
               presence "enable disable";
               description "To disable all categories";
             }
           }
           list category-name {
             key name;
             ordered-by user;
             uses secintel-category-disable;
           }
         }
         leaf url {
           description "Configure the url of feed server [https://<ip or hostname>:<port>/<uri>]";
           type string;
         }
         leaf url-parameter {
           description "Configure the parameter of url";
           type jt:unreadable;
         }
         leaf proxy-profile {
           description "The proxy profile name";
           junos:must "(\"services proxy profile\")";
           junos:must-message "Proxy profile must be defined";
           type string {
             length "1 .. 64";
           }
         }
         container authentication {
           description "Authenticate to use feed update services";
           uses apply-advanced;
           leaf auth-token {
             description "Token string for authentication";
             type string {
               junos:posix-pattern "^[A-Za-z0-9]{32}$";
               junos:pattern-message "Auth token must be consisted of 32 alphanumeric characters";
             }
           }
           leaf tls-profile {
             description "TLS profile";
             junos:must "(\"services ssl initiation profile $$\")";
             junos:must-message "Referenced SSL initiation profile is not defined";
             type string;
           }
         }
         container traceoptions {
           description "Security intelligence trace options";
           uses secintel-traceoptions;
         }
         list profile {
           key name;
           ordered-by user;
           description "Configure security intelligence profile";
           uses secintel-profile-setting;
         }
         container default-policy {
           description "Configure security intelligence default policy";
           uses apply-advanced;
           list category-profiles {
             key name;
             ordered-by user;
             description "Security intelligence category profiles";
             leaf name {
               description "Name of security intelligence category";
               type string;
             }
             uses apply-advanced;
             leaf profile-name {
               description "Name of profile";
               junos:must "(\"services security-intelligence profile $$\")";
               junos:must-message "security intelligence profile must be defined";
               type string;
             }
           }
         }
         list policy {
           key name;
           ordered-by user;
           description "Configure security intelligence policy";
           uses secintel-policy-setting;
         }
       }
       container icap-redirect {
         description "Configure ICAP redirection service";
         uses apply-advanced;
         list profile {
           key name;
           ordered-by user;
           description "Congifure ICAP service profile";
           uses icap-profile-object;
         }
         container traceoptions {
           description "ICAP redirect trace options";
           uses icap-redirect-traceoptions;
         }
       }
       container advanced-anti-malware {
         uses apply-advanced;
         container connection {
           presence "enable connection";
           description "Cloud service RE connection, only for master logical domain";
           uses apply-advanced;
           leaf url {
             description "The url of the cloud server [https://<ip or hostname>:<port>]";
             junos:must "(\"services advanced-anti-malware connection authentication tls-profile\")";
             junos:must-message "Authentication profile must be defined";
             type string;
           }
           container authentication {
             description "The authentication profile for using cloud services";
             uses apply-advanced;
             leaf tls-profile {
               description "TLS profile";
               junos:must "((\"services ssl initiation profile $$\" && \"services advanced-anti-malware connection url\"))";
               junos:must-message "Referenced SSL initiation profile and URL must be defined";
               type string;
             }
           }
           leaf proxy-profile {
             description "Proxy profile";
             junos:must "(\"services proxy profile $$\")";
             junos:must-message "Referenced Proxy profile must be defined";
             type string {
               length "1 .. 63";
             }
           }
           leaf source-address {
             description "The source ip for connecting to the cloud server.";
             type jt:ipaddr;
           }
           leaf source-interface {
             description "The source interface for connecting to the cloud server";
             type union {
               type jt:interface-name;
               type string {
                 pattern "<.*>|$.*";
               }
             }
           }
         }
         container default-policy {
           presence "enable default-policy";
           description "Advanced Anti-malware default policy";
           uses apply-advanced;
           container http {
             description "Configure HTTP options";
             uses apply-advanced;
             leaf inspection-profile {
               description "Advanced Anti-malware inspection-profile name (default:default_profile)";
               type string {
                 length "1 .. 63";
               }
             }
             leaf action {
               description "Action taken for contents with verdict meet threshold";
               type enumeration {
                 enum "permit" {
                   description "Allow contents";
                 }
                 enum "block" {
                   description "Disallow contents";
                 }
               }
             }
             container notification {
               description "Notification action taken for contents with verdict meet threshold";
               uses apply-advanced;
               leaf log {
                 description "Logging option for Advanced Anti-malware actions";
                 type empty;
               }
             }
           }
           container smtp {
             description "Configure SMTP options";
             uses apply-advanced;
             leaf inspection-profile {
               description "Advanced Anti-malware inspection-profile name (default:default_profile)";
               type string {
                 length "1 .. 63";
               }
             }
             container notification {
               description "Notification action taken for contents with verdict meet threshold";
               uses apply-advanced;
               leaf log {
                 description "Logging option for Advanced Anti-malware actions";
                 type empty;
               }
             }
           }
           container imap {
             description "Configure IMAP options";
             uses apply-advanced;
             leaf inspection-profile {
               description "Advanced Anti-malware inspection-profile name (default:default_profile)";
               type string {
                 length "1 .. 63";
               }
             }
             container notification {
               description "Notification action taken for contents with verdict meet threshold";
               uses apply-advanced;
               leaf log {
                 description "Logging option for Advanced Anti-malware actions";
                 type empty;
               }
             }
           }
           leaf verdict-threshold {
             description "Verdict threshold";
             type enumeration {
               enum "1" {
                 description "Verdict-threshold level 1";
               }
               enum "2" {
                 description "Verdict-threshold level 2";
               }
               enum "3" {
                 description "Verdict-threshold level 3";
               }
               enum "4" {
                 description "Verdict-threshold level 4";
               }
               enum "5" {
                 description "Verdict-threshold level 5";
               }
               enum "6" {
                 description "Verdict-threshold level 6";
               }
               enum "7" {
                 description "Verdict-threshold level 7";
               }
               enum "8" {
                 description "Verdict-threshold level 8";
               }
               enum "9" {
                 description "Verdict-threshold level 9";
               }
               enum "10" {
                 description "Verdict-threshold level 10";
               }
               enum "recommended" {
                 description "Recommended verdict-threshold";
               }
             }
           }
           leaf inspection-profile {
             description "Advanced Anti-malware inspection-profile name";
             status deprecated;
             type string {
               length "1 .. 63";
             }
           }
           container fallback-options {
             description "Fallback options for abnormal conditions";
             uses apply-advanced;
             leaf action {
               description "Action taken for fallback conditions";
               type enumeration {
                 enum "permit" {
                   description "Allow contents";
                 }
                 enum "block" {
                   description "Disallow contents";
                 }
               }
             }
             container notification {
               description "Notification action taken for fallback action";
               uses apply-advanced;
               leaf log {
                 description "Logging option for Advanced Anti-malware fallback action";
                 type empty;
               }
             }
           }
           container default-notification {
             description "Notification action taken for action";
             uses apply-advanced;
             leaf log {
               description "Logging option for Advanced Anti-malware action";
               type empty;
             }
           }
           container whitelist-notification {
             description "Whitelist notification logging option";
             uses apply-advanced;
             leaf log {
               description "Logging option for Advanced Anti-malware whitelist hit";
               type empty;
             }
           }
           container blacklist-notification {
             description "Blacklist notification logging option";
             uses apply-advanced;
             leaf log {
               description "Logging option for Advanced Anti-malware blacklist hit";
               type empty;
             }
           }
         }
         list policy {
           key name;
           description "Advanced Anti-malware policy";
           leaf name {
             description "Policy name, default policy must name (default-policy)";
             type string {
               length "1 .. 63";
             }
           }
           uses apply-advanced;
           container match {
             description "Policy match conditions";
             status deprecated;
             uses apply-advanced;
             leaf application {
               description "Application";
               type enumeration {
                 enum "HTTP" {
                   description "HTTP Traffic";
                 }
               }
             }
             leaf verdict-threshold {
               description "Verdict threshold";
               type enumeration {
                 enum "1" {
                   description "Verdict-threshold level 1";
                 }
                 enum "2" {
                   description "Verdict-threshold level 2";
                 }
                 enum "3" {
                   description "Verdict-threshold level 3";
                 }
                 enum "4" {
                   description "Verdict-threshold level 4";
                 }
                 enum "5" {
                   description "Verdict-threshold level 5";
                 }
                 enum "6" {
                   description "Verdict-threshold level 6";
                 }
                 enum "7" {
                   description "Verdict-threshold level 7";
                 }
                 enum "8" {
                   description "Verdict-threshold level 8";
                 }
                 enum "9" {
                   description "Verdict-threshold level 9";
                 }
                 enum "10" {
                   description "Verdict-threshold level 10";
                 }
                 enum "recommended" {
                   description "Recommended verdict-threshold";
                 }
               }
             }
           }
           container then {
             junos:must "(\".. match\")";
             junos:must-message "match must be defined";
             status deprecated;
             uses apply-advanced;
             leaf action {
               description "Action taken for contents with verdict meet threshold";
               type enumeration {
                 enum "permit" {
                   description "Allow contents";
                 }
                 enum "block" {
                   description "Disallow contents";
                 }
               }
             }
             container notification {
               description "Notification action taken for contents with verdict meet threshold";
               uses apply-advanced;
               leaf log {
                 description "Logging option for Advanced Anti-malware actions";
                 type empty;
               }
             }
           }
           container http {
             description "Configure HTTP options";
             uses apply-advanced;
             leaf inspection-profile {
               description "Advanced Anti-malware inspection-profile name (default:default_profile)";
               type string {
                 length "1 .. 63";
               }
             }
             leaf action {
               description "Action taken for contents with verdict meet threshold";
               type enumeration {
                 enum "permit" {
                   description "Allow contents";
                 }
                 enum "block" {
                   description "Disallow contents";
                 }
               }
             }
             container notification {
               description "Notification action taken for contents with verdict meet threshold";
               uses apply-advanced;
               leaf log {
                 description "Logging option for Advanced Anti-malware actions";
                 type empty;
               }
             }
           }
           container smtp {
             description "Configure SMTP options";
             uses apply-advanced;
             leaf inspection-profile {
               description "Advanced Anti-malware inspection-profile name (default:default_profile)";
               type string {
                 length "1 .. 63";
               }
             }
             container notification {
               description "Notification action taken for contents with verdict meet threshold";
               uses apply-advanced;
               leaf log {
                 description "Logging option for Advanced Anti-malware actions";
                 type empty;
               }
             }
           }
           container imap {
             description "Configure IMAP options";
             uses apply-advanced;
             leaf inspection-profile {
               description "Advanced Anti-malware inspection-profile name (default:default_profile)";
               type string {
                 length "1 .. 63";
               }
             }
             container notification {
               description "Notification action taken for contents with verdict meet threshold";
               uses apply-advanced;
               leaf log {
                 description "Logging option for Advanced Anti-malware actions";
                 type empty;
               }
             }
           }
           leaf verdict-threshold {
             description "Verdict threshold";
             type enumeration {
               enum "1" {
                 description "Verdict-threshold level 1";
               }
               enum "2" {
                 description "Verdict-threshold level 2";
               }
               enum "3" {
                 description "Verdict-threshold level 3";
               }
               enum "4" {
                 description "Verdict-threshold level 4";
               }
               enum "5" {
                 description "Verdict-threshold level 5";
               }
               enum "6" {
                 description "Verdict-threshold level 6";
               }
               enum "7" {
                 description "Verdict-threshold level 7";
               }
               enum "8" {
                 description "Verdict-threshold level 8";
               }
               enum "9" {
                 description "Verdict-threshold level 9";
               }
               enum "10" {
                 description "Verdict-threshold level 10";
               }
               enum "recommended" {
                 description "Recommended verdict-threshold";
               }
             }
           }
           leaf inspection-profile {
             description "Advanced Anti-malware inspection-profile name";
             status deprecated;
             type string {
               length "1 .. 63";
             }
           }
           container fallback-options {
             description "Fallback options for abnormal conditions";
             uses apply-advanced;
             leaf action {
               description "Action taken for fallback conditions";
               type enumeration {
                 enum "permit" {
                   description "Allow contents";
                 }
                 enum "block" {
                   description "Disallow contents";
                 }
               }
             }
             container notification {
               description "Notification action taken for fallback action";
               uses apply-advanced;
               leaf log {
                 description "Logging option for Advanced Anti-malware fallback action";
                 type empty;
               }
             }
           }
           container default-notification {
             description "Notification action taken for action";
             uses apply-advanced;
             leaf log {
               description "Logging option for Advanced Anti-malware action";
               type empty;
             }
           }
           container whitelist-notification {
             description "Whitelist notification logging option";
             uses apply-advanced;
             leaf log {
               description "Logging option for Advanced Anti-malware whitelist hit";
               type empty;
             }
           }
           container blacklist-notification {
             description "Blacklist notification logging option";
             uses apply-advanced;
             leaf log {
               description "Logging option for Advanced Anti-malware blacklist hit";
               type empty;
             }
           }
         }
         container traceoptions {
           description "Advanced Anti-malware trace options";
           uses aamwd-traceoptions;
         }
       }
       container user-identification {
         description "Configure user-identification";
         uses apply-advanced;
         container active-directory-access {
           presence "enable active-directory-access";
           description "Configure active directory access";
           uses apply-advanced;
           container traceoptions {
             description "Active-directory-access Tracing Options";
             uses apply-advanced;
             leaf no-remote-trace {
               description "Disable remote tracing";
               junos:must "(\"system tracing\")";
               junos:must-message "'no-remote-trace' is valid only when [system tracing] is configured";
               type empty;
             }
             container file {
               description "Trace file information";
               leaf filename {
                 description "Name of file in which to write trace information";
                 type string {
                   length "1 .. 1024";
                   junos:posix-pattern "![/ %]";
                   junos:pattern-message "Must not contain '/', % or a space";
                 }
               }
               leaf size {
                 description "Maximum trace file size";
                 type string;
               }
               leaf files {
                 description "Maximum number of trace files";
                 default "3";
                 type union {
                   type string {
                     pattern "<.*>|$.*";
                   }
                   type uint32 {
                     range "2 .. 1000";
                   }
                 }
               }
               choice world-readable-choice {
                 leaf world-readable {
                   description "Allow any user to read the log file";
                   type empty;
                 }
                 leaf no-world-readable {
                   description "Don't allow any user to read the log file";
                   type empty;
                 }
               }
               leaf match {
                 description "Regular expression for lines to be logged";
                 type jt:regular-expression;
               }
             }
             leaf level {
               description "Level of debugging output";
               type enumeration {
                 enum "error" {
                   description "Match error conditions";
                 }
                 enum "warning" {
                   description "Match warning messages";
                 }
                 enum "notice" {
                   description "Match conditions that should be handled specially";
                 }
                 enum "info" {
                   description "Match informational messages";
                 }
                 enum "verbose" {
                   description "Match verbose messages";
                 }
                 enum "all" {
                   description "Match all levels";
                 }
               }
             }
             list flag {
               key name;
               ordered-by user;
               description "Tracing parameters";
               leaf name {
                 type enumeration {
                   enum "active-directory-authentication" {
                     description "Trace active directory auth";
                   }
                   enum "configuration" {
                     description "Trace configuration";
                   }
                   enum "db" {
                     description "Trace db";
                   }
                   enum "ip-user-mapping" {
                     description "Trace ip-user-mapping module";
                   }
                   enum "ip-user-probe" {
                     description "Trace ip-user-probe";
                   }
                   enum "ipc" {
                     description "Trace ipc";
                   }
                   enum "user-group-mapping" {
                     description "Trace user-group-mapping module";
                   }
                   enum "wmic" {
                     description "Trace wmic";
                   }
                   enum "all" {
                     description "Trace everything";
                   }
                 }
               }
             }
           }
           list domain {
             key name;
             ordered-by user;
             description "Configure active-directory-access domain";
             max-elements 2;
             leaf name {
               description "Domain name";
               type string {
                 length "1 .. 64";
                 junos:posix-pattern "^[[:alnum:]._-]+$|^\\\\*$";
                 junos:pattern-message "Must be a string consisting of letters, numbers, dashes, underscores and dots";
               }
             }
             uses apply-advanced;
             container user {
               description "User name";
               uses apply-advanced;
               leaf user-name {
                 description "User name";
                 type string {
                   length "1 .. 64";
                   junos:posix-pattern "^[[:alnum:]._-]+$|^\\\\*$";
                   junos:pattern-message "Must be a string consisting of letters, numbers, dashes, underscores and dots";
                 }
               }
               leaf password {
                 description "Password string";
                 type string {
                   length "1 .. 128";
                 }
               }
             }
             list domain-controller {
               key name;
               ordered-by user;
               description "Domain controller";
               max-elements 10;
               leaf name {
                 description "Domain controller name";
                 type string {
                   length "1 .. 64";
                   junos:posix-pattern "^[[:alnum:]._-]+$|^\\\\*$";
                   junos:pattern-message "Must be a string consisting of letters, numbers, dashes, underscores and dots";
                 }
               }
               uses apply-advanced;
               leaf address {
                 description "Address of domain controller";
                 type jt:ipaddr;
               }
             }
             container ip-user-mapping {
               description "Ip-user-mapping";
               uses apply-advanced;
               container discovery-method {
                 description "Discovery method";
                 uses apply-advanced;
                 container wmi {
                   presence "enable wmi";
                   description "WMI";
                   uses apply-advanced;
                   leaf event-log-scanning-interval {
                     description "Interval of event log scanning";
                     units "seconds";
                     type union {
                       type string {
                         pattern "<.*>|$.*";
                       }
                       type uint16 {
                         range "5 .. 60";
                       }
                     }
                   }
                   leaf initial-event-log-timespan {
                     description "Event log scanning timespan";
                     units "hours";
                     type union {
                       type string {
                         pattern "<.*>|$.*";
                       }
                       type uint16 {
                         range "1 .. 168";
                       }
                     }
                   }
                 }
               }
             }
             container user-group-mapping {
               description "User-group-mapping";
               uses user-group-mapping-type;
             }
           }
           leaf no-on-demand-probe {
             description "Disable on-demand probe";
             type empty;
           }
           leaf authentication-entry-timeout {
             description "Authentication entry timeout number (0, 10-1440)";
             units "minutes";
             type union {
               type uint16;
               type string {
                 pattern "<.*>|$.*";
               }
             }
           }
           leaf invalid-authentication-entry-timeout {
             description "Invalid authentication entry timeout number (0, 10-1440)";
             units "minutes";
             type union {
               type uint16;
               type string {
                 pattern "<.*>|$.*";
               }
             }
           }
           leaf firewall-authentication-forced-timeout {
             description "Firewallauth fallback authentication entry forced timeout number (10-1440)";
             units "minutes";
             type union {
               type uint16;
               type string {
                 pattern "<.*>|$.*";
               }
             }
           }
           leaf wmi-timeout {
             description "Wmi timeout number";
             units "seconds";
             type union {
               type string {
                 pattern "<.*>|$.*";
               }
               type uint32 {
                 range "3 .. 120";
               }
             }
           }
           leaf thread {
             description "Thread to do PC probe";
             type union {
               type string {
                 pattern "<.*>|$.*";
               }
               type uint16 {
                 range "1 .. 100";
               }
             }
           }
           leaf probe-rate {
             description "PC probe rate per minute";
             type union {
               type string {
                 pattern "<.*>|$.*";
               }
               type uint32 {
                 range "100 .. 1500";
               }
             }
           }
           leaf-list event-log-identifier {
             ordered-by user;
             description "Event log identifier";
             type union {
               type uint16;
               type string {
                 pattern "<.*>|$.*";
               }
             }
           }
           leaf-list logon-type {
             ordered-by user;
             description "Logon type";
             type union {
               type uint16;
               type string {
                 pattern "<.*>|$.*";
               }
             }
           }
           container filter {
             description "Configure filter address or prefix";
             uses apply-advanced;
             list include {
               key name;
               ordered-by user;
               description "Include address";
               max-elements 20;
               leaf name {
                 description "Address or prefix";
                 type jt:ipprefix;
               }
             }
             list exclude {
               key name;
               ordered-by user;
               description "Exclude address";
               max-elements 20;
               leaf name {
                 description "Address or prefix";
                 type jt:ipprefix;
               }
             }
           }
         }
         list authentication-source {
           key name;
           ordered-by user;
           description "Configure authentication-source";
           max-elements 2;
           leaf name {
             description "Authenticaton source name";
             type enumeration {
               enum "aruba-clearpass" {
                 description "Authentication source from Aruba ClearPass";
               }
             }
           }
           uses apply-advanced;
           leaf authentication-entry-timeout {
             description "Aruba ClearPass authentication entry timeout number (0, 10-1440)";
             units "minutes";
             type union {
               type uint16;
               type string {
                 pattern "<.*>|$.*";
               }
             }
           }
           leaf invalid-authentication-entry-timeout {
             description "Invalid authentication entry timeout number (0, 10-1440)";
             units "minutes";
             type union {
               type uint16;
               type string {
                 pattern "<.*>|$.*";
               }
             }
           }
           container traceoptions {
             description "Aruba ClearPass authentication table Tracing Options";
             uses apply-advanced;
             leaf no-remote-trace {
               description "Disable remote tracing";
               junos:must "(\"system tracing\")";
               junos:must-message "'no-remote-trace' is valid only when [system tracing] is configured";
               type empty;
             }
             container file {
               description "Trace file information";
               leaf filename {
                 description "Name of file in which to write trace information";
                 type string {
                   length "1 .. 1024";
                   junos:posix-pattern "![/ %]";
                   junos:pattern-message "Must not contain '/', % or a space";
                 }
               }
               leaf size {
                 description "Maximum trace file size";
                 type string;
               }
               leaf files {
                 description "Maximum number of trace files";
                 default "3";
                 type union {
                   type string {
                     pattern "<.*>|$.*";
                   }
                   type uint32 {
                     range "2 .. 1000";
                   }
                 }
               }
               choice world-readable-choice {
                 leaf world-readable {
                   description "Allow any user to read the log file";
                   type empty;
                 }
                 leaf no-world-readable {
                   description "Don't allow any user to read the log file";
                   type empty;
                 }
               }
               leaf match {
                 description "Regular expression for lines to be logged";
                 type jt:regular-expression;
               }
             }
             leaf level {
               description "Level of debugging output";
               type enumeration {
                 enum "error" {
                   description "Match error conditions";
                 }
                 enum "warning" {
                   description "Match warning messages";
                 }
                 enum "notice" {
                   description "Match conditions that should be handled specially";
                 }
                 enum "info" {
                   description "Match informational messages";
                 }
                 enum "verbose" {
                   description "Match verbose messages";
                 }
                 enum "all" {
                   description "Match all levels";
                 }
               }
             }
             list flag {
               key name;
               ordered-by user;
               description "Tracing parameters";
               leaf name {
                 type enumeration {
                   enum "all" {
                     description "Trace Aruba ClearPass all modules";
                   }
                   enum "clearpass-authentication" {
                     description "Trace Aruba ClearPass auth table management module";
                   }
                   enum "configuration" {
                     description "Trace Aruba ClearPass configuration";
                   }
                   enum "dispatcher" {
                     description "Trace dispatcher module";
                   }
                   enum "ipc" {
                     description "Trace ipc";
                   }
                   enum "user-query" {
                     description "Trace user-query module";
                   }
                 }
               }
             }
           }
           container user-query {
             description "ClearPass individual user query";
             uses apply-advanced;
             container web-server {
               description "Web server for user query";
               uses apply-advanced;
               leaf server-name {
                 description "Web server name";
                 type string {
                   length "1 .. 64";
                 }
               }
               leaf connect-method {
                 description "Method of connecting to web server";
                 type enumeration {
                   enum "https" {
                     description "HTTPS connection to web server";
                   }
                   enum "http" {
                     description "HTTP connection to web server";
                   }
                 }
               }
               leaf address {
                 description "IP address or hostname of web server";
                 type string {
                   length "1 .. 128";
                 }
               }
               leaf port {
                 description "Web server port";
                 default "443";
                 type union {
                   type string {
                     pattern "<.*>|$.*";
                   }
                   type uint32 {
                     range "1 .. 65535";
                   }
                 }
               }
             }
             leaf ca-certificate {
               description "Ca-certificate file name";
               type string {
                 length "1 .. 256";
               }
             }
             leaf client-id {
               description "Client ID for OAuth2 grant";
               type string {
                 length "1 .. 64";
               }
             }
             leaf client-secret {
               description "Client secret for OAuth2 grant";
               type string {
                 length "1 .. 128";
               }
             }
             leaf token-api {
               description "API of acquiring token for OAuth2 authentication";
               type string {
                 length "1 .. 128";
               }
             }
             leaf query-api {
               description "User query API";
               type string {
                 length "4 .. 128";
               }
             }
             leaf delay-query-time {
               description "Delay time to send user query (0~60sec)";
               default "15";
               units "seconds";
               type union {
                 type string {
                   pattern "<.*>|$.*";
                 }
                 type uint8 {
                   range "0 .. 60";
                 }
               }
             }
           }
           container no-user-query {
             presence "enable no-user-query";
             description "Disable user query from ClearPass";
           }
         }
         container device-information {
           description "Device information configuration";
           uses apply-advanced;
           container authentication-source {
             description "Configure authentication-source";
             uses apply-advanced;
             leaf authentication-source-name {
               default "no-configured";
               type enumeration {
                 enum "active-directory" {
                   description "From windows active directory";
                 }
                 enum "network-access-controller" {
                   description "From network access controller such as Aruba ClearPass or JIMS";
                 }
                 enum "no-configured" {
                   description "No configuring authentication source for device entry";
                 }
               }
             }
           }
           container end-user-profile {
             description "End-user-profile configuration";
             uses apply-advanced;
             list profile-name {
               key name;
               ordered-by user;
               description "End-user-profile profile-name configuration";
               leaf name {
                 description "End-user-profile profile-name";
                 type string {
                   length "1 .. 64";
                   junos:posix-pattern "^[[:alnum:]._-]+$|^\\\\*$";
                   junos:pattern-message "Must be a string consisting of letters, numbers, dashes, underscores and dots";
                 }
               }
               uses apply-advanced;
               leaf domain-name {
                 description "Domain name";
                 type string {
                   length "1 .. 64";
                   junos:posix-pattern "^[[:alnum:]._-]+$|^\\\\*$";
                   junos:pattern-message "Must be a string consisting of letters, numbers, dashes, underscores and dots";
                 }
               }
               list attribute {
                 key name;
                 ordered-by user;
                 description "Attribute";
                 leaf name {
                   description "Attribute name";
                   type string;
                 }
                 uses apply-advanced;
                 choice attribute-value {
                   case case_1 {
                     leaf-list string {
                       ordered-by user;
                       description "Value type is strings";
                       type string;
                       max-elements 20;
                     }
                   }
                   case case_2 {
                     container digital {
                       presence "enable digital";
                       description "Value type is digital";
                       uses apply-advanced;
                       leaf-list value {
                         ordered-by user;
                         description "Digital value";
                         type union {
                           type uint32;
                           type string {
                             pattern "<.*>|$.*";
                           }
                         }
                       }
                       list from {
                         key name;
                         ordered-by user;
                         description "Range of digital value";
                         leaf name {
                           description "Digit range's start value";
                           type union {
                             type uint32;
                             type string {
                               pattern "<.*>|$.*";
                             }
                           }
                         }
                         uses apply-advanced;
                         leaf to {
                           description "Digit range's end value";
                           type union {
                             type uint32;
                             type string {
                               pattern "<.*>|$.*";
                             }
                           }
                         }
                       }
                     }
                   }
                 }
               }
             }
           }
           container traceoptions {
             description "Device info related Tracing Options";
             uses apply-advanced;
             leaf no-remote-trace {
               description "Disable remote tracing";
               junos:must "(\"system tracing\")";
               junos:must-message "'no-remote-trace' is valid only when [system tracing] is configured";
               type empty;
             }
             container file {
               description "Trace file information";
               leaf filename {
                 description "Name of file in which to write trace information";
                 type string {
                   length "1 .. 1024";
                   junos:posix-pattern "![/ %]";
                   junos:pattern-message "Must not contain '/', % or a space";
                 }
               }
               leaf size {
                 description "Maximum trace file size";
                 type string;
               }
               leaf files {
                 description "Maximum number of trace files";
                 default "3";
                 type union {
                   type string {
                     pattern "<.*>|$.*";
                   }
                   type uint32 {
                     range "2 .. 1000";
                   }
                 }
               }
               choice world-readable-choice {
                 leaf world-readable {
                   description "Allow any user to read the log file";
                   type empty;
                 }
                 leaf no-world-readable {
                   description "Don't allow any user to read the log file";
                   type empty;
                 }
               }
               leaf match {
                 description "Regular expression for lines to be logged";
                 type jt:regular-expression;
               }
             }
             leaf level {
               description "Level of debugging output";
               type enumeration {
                 enum "error" {
                   description "Match error conditions";
                 }
                 enum "warning" {
                   description "Match warning messages";
                 }
                 enum "notice" {
                   description "Match conditions that should be handled specially";
                 }
                 enum "info" {
                   description "Match informational messages";
                 }
                 enum "verbose" {
                   description "Match verbose messages";
                 }
                 enum "all" {
                   description "Match all levels";
                 }
               }
             }
             list flag {
               key name;
               ordered-by user;
               description "Tracing parameters";
               leaf name {
                 type enumeration {
                   enum "all" {
                     description "Trace device info all modules";
                   }
                   enum "auth-source" {
                     description "Trace Auth source module";
                   }
                   enum "configuration" {
                     description "Trace Device info configuration";
                   }
                   enum "device-table" {
                     description "Trace device table management module";
                   }
                   enum "ipid-all" {
                     description "Trace IPID all functions";
                   }
                   enum "ipid-db" {
                     description "Trace IPID Database function";
                   }
                   enum "ipid-entry" {
                     description "Trace IPID entry management function";
                   }
                   enum "ipid-ipc" {
                     description "Trace IPID communication processing function";
                   }
                   enum "ipid-message" {
                     description "Trace IPID message processing function";
                   }
                   enum "ipid-others" {
                     description "Trace IPID other function";
                   }
                   enum "ipid-server" {
                     description "Trace IPID server handling function";
                   }
                   enum "ipid-statistics" {
                     description "Trace IPID statistics handling function";
                   }
                   enum "ipid-task" {
                     description "Trace IPID task handling function";
                   }
                   enum "profile-lookup" {
                     description "Trace End-user-profile lookup function";
                   }
                 }
               }
             }
           }
         }
         container identity-management {
           description "Identity management configuration";
           uses apply-advanced;
           leaf authentication-entry-timeout {
             description "Authentication entry timeout number (0, 10-1440)";
             default "60";
             units "minutes";
             type union {
               type uint16;
               type string {
                 pattern "<.*>|$.*";
               }
             }
           }
           leaf invalid-authentication-entry-timeout {
             description "Invalid authentication entry timeout number (0, 10-1440)";
             default "30";
             units "minutes";
             type union {
               type uint16;
               type string {
                 pattern "<.*>|$.*";
               }
             }
           }
           leaf preserve-valid-user {
             description "Null user will not overwrite valid user for the same ip";
             type empty;
           }
           container connection {
             description "Connection to identity management";
             uses apply-advanced;
             leaf connect-method {
               description "Method of connection";
               type enumeration {
                 enum "https" {
                   description "HTTPS connection";
                 }
                 enum "http" {
                   description "HTTP connection";
                 }
               }
             }
             leaf port {
               description "Server port";
               default "443";
               type union {
                 type string {
                   pattern "<.*>|$.*";
                 }
                 type uint32 {
                   range "1 .. 65535";
                 }
               }
             }
             container primary {
               description "Primary server";
               uses server-connection-type;
             }
             container secondary {
               description "Secondary server";
               uses server-connection-type;
             }
             leaf token-api {
               description "API of acquiring token for OAuth2 authentication";
               type string {
                 length "1 .. 128";
               }
             }
             leaf query-api {
               description "Query API";
               type string {
                 length "4 .. 128";
               }
             }
           }
           container batch-query {
             description "Batch query parameters";
             uses apply-advanced;
             leaf items-per-batch {
               description "Items number per batch query";
               default "200";
               type union {
                 type string {
                   pattern "<.*>|$.*";
                 }
                 type uint32 {
                   range "100 .. 1000";
                 }
               }
             }
             leaf query-interval {
               description "Query interval";
               default "5";
               units "seconds";
               type union {
                 type string {
                   pattern "<.*>|$.*";
                 }
                 type uint32 {
                   range "1 .. 60";
                 }
               }
             }
           }
           container ip-query {
             description "IP query parameters";
             uses apply-advanced;
             leaf query-delay-time {
               description "Delay time to send IP query (0~60sec)";
               default "15";
               units "seconds";
               type union {
                 type string {
                   pattern "<.*>|$.*";
                 }
                 type uint8 {
                   range "0 .. 60";
                 }
               }
             }
             container no-ip-query {
               presence "enable no-ip-query";
               description "Disable IP query";
             }
             leaf max-connections {
               description "Max connection number";
               type union {
                 type string {
                   pattern "<.*>|$.*";
                 }
                 type uint32 {
                   range "1 .. 20";
                 }
               }
             }
           }
           container filter {
             description "Filter for query";
             uses apply-advanced;
             list domain {
               key name;
               ordered-by user;
               description "Domain filter";
               max-elements 20;
               leaf name {
                 description "Domain name";
                 type string {
                   length "1 .. 64";
                   junos:posix-pattern "^[[:alnum:]._-]+$|^\\\\*$";
                   junos:pattern-message "Must be a string consisting of letters, numbers, dashes, underscores and dots";
                 }
               }
             }
             container include-ip {
               description "Include IP filter";
               uses address-filter-type;
             }
             container exclude-ip {
               description "Exclude IP filter";
               uses address-filter-type;
             }
           }
           container traceoptions {
             description "Tracing Options";
             uses apply-advanced;
             leaf no-remote-trace {
               description "Disable remote tracing";
               junos:must "(\"system tracing\")";
               junos:must-message "'no-remote-trace' is valid only when [system tracing] is configured";
               type empty;
             }
             container file {
               description "Trace file information";
               leaf filename {
                 description "Name of file in which to write trace information";
                 type string {
                   length "1 .. 1024";
                   junos:posix-pattern "![/ %]";
                   junos:pattern-message "Must not contain '/', % or a space";
                 }
               }
               leaf size {
                 description "Maximum trace file size";
                 type string;
               }
               leaf files {
                 description "Maximum number of trace files";
                 default "3";
                 type union {
                   type string {
                     pattern "<.*>|$.*";
                   }
                   type uint32 {
                     range "2 .. 1000";
                   }
                 }
               }
               choice world-readable-choice {
                 leaf world-readable {
                   description "Allow any user to read the log file";
                   type empty;
                 }
                 leaf no-world-readable {
                   description "Don't allow any user to read the log file";
                   type empty;
                 }
               }
               leaf match {
                 description "Regular expression for lines to be logged";
                 type jt:regular-expression;
               }
             }
             leaf level {
               description "Level of debugging output";
               type enumeration {
                 enum "error" {
                   description "Match error conditions";
                 }
                 enum "warning" {
                   description "Match warning messages";
                 }
                 enum "notice" {
                   description "Match conditions that should be handled specially";
                 }
                 enum "info" {
                   description "Match informational messages";
                 }
                 enum "verbose" {
                   description "Match verbose messages";
                 }
                 enum "all" {
                   description "Match all levels";
                 }
               }
             }
             list flag {
               key name;
               ordered-by user;
               description "Tracing parameters";
               leaf name {
                 type enumeration {
                   enum "all" {
                     description "Trace identity management all modules";
                   }
                   enum "authentication-management" {
                     description "Trace advanced-query auth table management module";
                   }
                   enum "configuration" {
                     description "Trace identity management configuration";
                   }
                   enum "dispatcher" {
                     description "Trace dispatcher module";
                   }
                   enum "query" {
                     description "Trace query process";
                   }
                 }
               }
             }
           }
         }
       }
       container ip-monitoring {
         description "IP monitoring for route action";
         uses apply-advanced;
         list policy {
           key name;
           ordered-by user;
           description "Policy for route action";
           leaf name {
             description "Policy name";
             type string {
               length "1 .. 64";
             }
           }
           uses apply-advanced;
           leaf no-preempt {
             description "No automatic failback preemption once policy failover";
             type empty;
           }
           container match {
             description "Matching probing condition";
             uses apply-advanced;
             leaf-list rpm-probe {
               ordered-by user;
               description "RPM probe name";
               type string;
             }
           }
           container then {
             description "Action to be taken";
             uses action-object-type;
           }
         }
         container traceoptions {
           description "IP-Monitoring trace options";
           uses apply-advanced;
           leaf no-remote-trace {
             description "Disable remote tracing";
             junos:must "(\"system tracing\")";
             junos:must-message "'no-remote-trace' is valid only when [system tracing] is configured";
             type empty;
           }
           container file {
             description "Trace file information";
             leaf filename {
               description "Name of file in which to write trace information";
               type string {
                 length "1 .. 1024";
                 junos:posix-pattern "![/ %]";
                 junos:pattern-message "Must not contain '/', % or a space";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "debug" {
                   description "Trace debug";
                 }
                 enum "configuration" {
                   description "Trace configuration events";
                 }
                 enum "errors" {
                   description "Trace errors";
                 }
                 enum "memory" {
                   description "Trace memory allocation or deallocation messages";
                 }
                 enum "event" {
                   description "Trace events";
                 }
                 enum "all" {
                   description "Trace events";
                 }
               }
             }
           }
         }
       }
       container wireless-wan {
         description "Wireless WAN configuration";
         uses apply-advanced;
         list adapter {
           key name;
           ordered-by user;
           description "Wireless adapter name configuration";
           leaf name {
             description "Wireless adapter name";
             type string {
               length "1 .. 16";
               junos:posix-pattern "^[A-Za-z]+[_0-9A-Za-z-]*$";
               junos:pattern-message "Must be a string beginning with a letter and consisting of no more than 16 total letters, numbers, dashes and underscores.";
             }
           }
           uses apply-advanced;
           leaf ip-address {
             description "Adapter management IP address";
             type jt:ipaddr;
           }
           leaf adapter-type {
             description "Select adapter type";
             type enumeration {
               enum "cx-bridge" {
                 description "Adapter type - CX-bridge";
               }
             }
           }
           container modem {
             description "Adapter modem settings";
             uses apply-advanced;
             container usb1 {
               presence "enable usb1";
               description "Adapter USB1 modem name";
               uses apply-advanced;
               leaf description {
                 description "Text description for modem";
                 type string;
               }
             }
             container usb2 {
               presence "enable usb2";
               description "Adapter USB2 modem name";
               uses apply-advanced;
               leaf description {
                 description "Text description for modem";
                 type string;
               }
             }
             container usb3 {
               presence "enable usb3";
               description "Adapter USB3 modem name";
               uses apply-advanced;
               leaf description {
                 description "Text description for modem";
                 type string;
               }
             }
             container expresscard {
               presence "enable expresscard";
               description "Adapter Expresscard modem name";
               uses apply-advanced;
               leaf description {
                 description "Text description for modem";
                 type string;
               }
             }
           }
         }
       }
       container proxy {
         description "Proxy setting for services";
         uses apply-advanced;
         list profile {
           key name;
           ordered-by user;
           description "Proxy profile";
           uses proxy-profile-setting;
         }
       }
       container rtlog {
         presence "enable rtlog";
         uses apply-advanced;
         container traceoptions {
           description "Security log daemon trace options";
           uses apply-advanced;
           leaf no-remote-trace {
             description "Disable remote tracing";
             junos:must "(\"system tracing\")";
             junos:must-message "'no-remote-trace' is valid only when [system tracing] is configured";
             type empty;
           }
           container file {
             description "Trace file information";
             leaf filename {
               description "Name of file in which to write trace information";
               type string {
                 length "1 .. 1024";
                 junos:posix-pattern "![/ %]";
                 junos:pattern-message "Must not contain '/', % or a space";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "List of things to include in trace";
             leaf name {
               type enumeration {
                 enum "source" {
                   description "Communication with security log forwarder";
                 }
                 enum "configuration" {
                   description "Reading of configuration";
                 }
                 enum "all" {
                   description "Everything";
                 }
                 enum "report" {
                   description "Trace report";
                 }
                 enum "hpl" {
                   description "Trace HPL logging";
                 }
               }
             }
           }
         }
       }
       container service-interface-pools {
         description "Configure service interface pools";
         uses apply-advanced;
         list pool {
           key name;
           ordered-by user;
           description "Define service interface pool";
           uses service_interface_pool_object;
         }
       }
       container hosted-services {
         description "Configuration for services performed in the remote server";
         uses apply-advanced;
         list client-profile {
           key name;
           ordered-by user;
           description "Configure client profile";
           leaf name {
             description "Client profile name";
             type string {
               length "3 .. 32";
             }
           }
           uses apply-advanced;
           leaf transport-type {
             description "Transport type";
             type enumeration {
               enum "GRE" {
                 description "GRE";
               }
               enum "UDP" {
                 description "UDP";
               }
               enum "TCP" {
                 description "TCP";
               }
             }
           }
           leaf client-address {
             description "Client address";
             type jt:ipv4addr;
           }
           leaf hosted-service-identifier {
             description "Identifier for the service performed on the remote server";
             type union {
               type string {
                 pattern "<.*>|$.*";
               }
               type int32 {
                 range "1 .. 63";
               }
             }
           }
         }
         list server-profile {
           key name;
           ordered-by user;
           description "Configure server profile";
           leaf name {
             description "Server profile name";
             type string {
               length "3 .. 32";
             }
           }
           uses apply-advanced;
           leaf transport-type {
             description "Transport type";
             type enumeration {
               enum "GRE" {
                 description "GRE";
               }
               enum "UDP" {
                 description "UDP";
               }
               enum "TCP" {
                 description "TCP";
               }
             }
           }
           leaf server-address {
             description "Server address";
             type jt:ipv4addr;
           }
           leaf client-address {
             description "Client address";
             type jt:ipv4addr;
           }
           leaf hosted-service-identifier {
             description "Identifier for the service performed in the remote server";
             type union {
               type string {
                 pattern "<.*>|$.*";
               }
               type int32 {
                 range "1 .. 63";
               }
             }
           }
         }
       }
       container jflow-log {
         presence "enable jflow-log";
         description "Configure jflow-logging parameters for services";
         uses apply-advanced;
         list collector {
           key name;
           ordered-by user;
           description "Collector attributes";
           leaf name {
             description "Profile name";
             type string {
               length "1 .. 63";
             }
           }
           uses apply-advanced;
           leaf destination-address {
             description "IPv4 Address or hostname of the collector";
             type string {
               junos:posix-pattern "^[[:alnum:]._-]+$";
               junos:pattern-message "Must be a string of letters, numbers, dashes or underscores";
             }
           }
           leaf destination-port {
             description "Destination port of the collector";
             type union {
               type string {
                 pattern "<.*>|$.*";
               }
               type uint16 {
                 range "1 .. 65535";
               }
             }
           }
           leaf source-ip {
             description "Source IPv4 Address from which logging is to be done";
             type jt:ipv4addr;
           }
         }
         list collector-group {
           key name;
           ordered-by user;
           leaf name {
             description "Name of collector-group";
             type string {
               length "1 .. 63";
             }
           }
           uses apply-advanced;
           leaf-list collector {
             ordered-by user;
             description "List of Collector profiles";
             type string {
               length "1 .. 63";
             }
             max-elements 8;
           }
         }
         list template-profile {
           key name;
           ordered-by user;
           leaf name {
             description "Specify name of the template";
             junos:must "((any \".. collector <*>\" || any \".. collector-group <*>\"))";
             junos:must-message "template-profile must have a collector or collector-group configured";
             type string {
               length "1 .. 63";
             }
           }
           uses apply-advanced;
           leaf collector {
             description "Specify a collector name";
             junos:must "(!(any \".. collector-group <*>\"))";
             junos:must-message "Collector-group is already configured for this template";
             junos:must "(\"services jflow-log collector $$\")";
             junos:must-message "The referenced collector is not defined";
             type string {
               length "1 .. 63";
             }
           }
           leaf-list collector-group {
             ordered-by user;
             description "Specify a collector-group name";
             junos:must "(!(any \".. collector <*>\"))";
             junos:must-message "Collector is already configured for this template profile";
             type string {
               length "1 .. 63";
             }
             max-elements 1;
           }
           leaf template-type {
             description "Allow jflow-log for applications";
             type enumeration {
               enum "nat" {
                 description "Enable jflow-logs for NAT events";
               }
             }
           }
           leaf version {
             description "Version of jflow-logging";
             type enumeration {
               enum "v9" {
                 description "Version 9";
               }
               enum "ipfix" {
                 description "Ipfix";
               }
             }
           }
           container refresh-rate {
             presence "enable refresh-rate";
             uses apply-advanced;
             leaf packets {
               description "Specify number of packets after which templates are sent to collector";
               default "4800";
               type union {
                 type string {
                   pattern "<.*>|$.*";
                 }
                 type uint32 {
                   range "1 .. 48000";
                 }
               }
             }
             leaf seconds {
               description "Specify number of seconds after which templates are sent to collector";
               default "1800";
               type union {
                 type string {
                   pattern "<.*>|$.*";
                 }
                 type uint32 {
                   range "10 .. 1800";
                 }
               }
             }
           }
         }
       }
       container service-device-pools {
         description "Configure service device pools";
         uses apply-advanced;
         list pool {
           key name;
           ordered-by user;
           description "Define service device pool";
           uses service_device_pool_object;
         }
       }
       container redundancy-set {
         description "Redundancy-set settings";
         uses apply-advanced;
         container traceoptions {
           description "Services redundancy trace options";
           uses srd-traceoptions-object;
         }
         list rs-id-object {
           key name;
           ordered-by user;
           description "Definition of redundancy-set";
           uses srd-rs-id-object;
         }
       }
       container web-filter {
         description "Web Filtering service configuration";
         uses apply-advanced;
         list profile {
           key name;
           ordered-by user;
           description "Web Filter profile";
           max-elements 8;
           uses urlf-profile-object;
         }
         container traceoptions {
           description "Trace options for Web Filter ";
           uses urlf-traceoptions-object;
         }
       }
     }
   }
   grouping aamwd-traceoptions {
     description "Advanced anti-malware trace options";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Trace flags";
       leaf name {
         type enumeration {
           enum "all" {
             description "Trace everything";
           }
           enum "connection" {
             description "Trace the connection to server";
           }
           enum "content" {
             description "Trace the content buffer management";
           }
           enum "daemon" {
             description "Trace advanced-anti-malware daemon";
           }
           enum "http" {
             description "Trace http protocol operations";
           }
           enum "identification" {
             description "Trace file identification";
           }
           enum "imap" {
             description "Trace imap protocol operations";
           }
           enum "parser" {
             description "Trace protocol context parser";
           }
           enum "plugin" {
             description "Trace advanced-anti-malware plugin";
           }
           enum "policy" {
             description "Trace advanced-anti-malware policy";
           }
           enum "smtp" {
             description "Trace smtp protocol operations";
           }
         }
       }
     }
   }
   grouping action-object-type {
     uses apply-advanced;
     container preferred-route {
       description "Preferred route action";
       uses apply-advanced;
       list routing-instances {
         key name;
         ordered-by user;
         description "Routing-instance";
         leaf name {
           type string;
         }
         uses apply-advanced;
         list route {
           key name;
           ordered-by user;
           description "Route";
           leaf name {
             type jt:ipprefix;
           }
           uses apply-advanced;
           choice next_hop {
             case case_1 {
               leaf-list next-hop {
                 ordered-by user;
                 description "Next hop to destination of route-action";
                 type union {
                   type jt:ipaddr-or-interface;
                   type string {
                     pattern "<.*>|$.*";
                   }
                 }
               }
             }
             case case_2 {
               leaf discard {
                 description "Drop packets to destination; send no ICMP unreachables";
                 type empty;
               }
             }
           }
           leaf preferred-metric {
             description "Preferred metric value assigned to route action";
             type union {
               type string {
                 pattern "<.*>|$.*";
               }
               type uint32 {
                 range "1 .. 255";
               }
             }
           }
         }
       }
       list route {
         key name;
         ordered-by user;
         description "Route";
         leaf name {
           type jt:ipprefix;
         }
         uses apply-advanced;
         choice next_hop {
           case case_1 {
             leaf-list next-hop {
               ordered-by user;
               description "Next hop to destination of route-action";
               type union {
                 type jt:ipaddr-or-interface;
                 type string {
                   pattern "<.*>|$.*";
                 }
               }
             }
           }
           case case_2 {
             leaf discard {
               description "Drop packets to destination; send no ICMP unreachables";
               type empty;
             }
           }
         }
         leaf preferred-metric {
           description "Preferred metric value assigned to route action";
           type union {
             type string {
               pattern "<.*>|$.*";
             }
             type uint32 {
               range "1 .. 255";
             }
           }
         }
       }
     }
     list interface {
       key name;
       ordered-by user;
       description "Interface enabling/disabling action";
       leaf name {
         type union {
           type jt:interface-wildcard;
           type string {
             pattern "<.*>|$.*";
           }
         }
       }
       uses apply-advanced;
       choice action {
         case case_1 {
           leaf enable {
             description "Enable interface";
             type empty;
           }
         }
         case case_2 {
           leaf disable {
             description "Disable interface";
             type empty;
           }
         }
       }
     }
   }
   grouping address-filter-type {
     description "IP address filter";
     uses apply-advanced;
     leaf address-book {
       description "Referenced address book";
       type string;
     }
     leaf address-set {
       description "Referenced address set";
       type string {
         length "1 .. 63";
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping bgp-logical-system {
     description "Logical systems configuration for rpm";
     leaf name {
       description "Logical system name";
       type string {
         junos:posix-pattern "![^a-zA-Z0-9_-]|(^(all|.{64,})$)";
         junos:pattern-message "Logical-system name is a string consisting of up to 63 letters, numbers, dashes and underscores";
       }
     }
     uses apply-advanced;
     list routing-instances {
       key name;
       description "Routing instances";
       uses bgp-routing-instances;
     }
   }
   grouping bgp-routing-instances {
     description "Routing-instance configuration for rpm";
     leaf name {
       description "Routing instance name";
       type string;
     }
     uses apply-advanced;
   }
   grouping drop-policy-term {
     description "One or more drop terms";
     leaf name {
       description "Term name";
       type string {
         junos:posix-pattern "^.{1,64}$";
         junos:pattern-message "Must be string of 64 characters or less";
       }
     }
     uses apply-advanced;
     container from {
       description "Define match criteria";
       uses apply-advanced;
       container source-address {
         description "Source IP Address";
         uses li_policy_addr_simple_object;
       }
       container destination-address {
         description "Destination IP Address";
         uses li_policy_addr_simple_object;
       }
       choice source-port_choice {
         case case_1 {
           container source-port {
             description "Match source port";
             uses match_li_simple_port_value;
           }
         }
       }
       choice destination-port_choice {
         case case_1 {
           container destination-port {
             description "Match destination port";
             uses match_li_simple_port_value;
           }
         }
       }
       choice protocol_choice {
         case case_1 {
           container protocol {
             description "Match IP protocol type";
             uses match_li_simple_protocol_value;
           }
         }
       }
       choice dscp_choice {
         case case_1 {
           container dscp {
             description "Match Differentiated Services (DiffServ) code point";
             uses match_li_simple_dscp_value;
           }
         }
       }
     }
   }
   grouping drop-policy6-term {
     description "One or more drop terms";
     leaf name {
       description "Term name";
       type string {
         junos:posix-pattern "^.{1,64}$";
         junos:pattern-message "Must be string of 64 characters or less";
       }
     }
     uses apply-advanced;
     container from {
       description "Define match criteria";
       uses apply-advanced;
       container source-address {
         description "Source IPv6 Address or Prefix";
         uses li_policy_addr6_simple_object;
       }
       container destination-address {
         description "Destination IPv6 Address or Prefix";
         uses li_policy_addr6_simple_object;
       }
       choice source-port_choice {
         case case_1 {
           container source-port {
             description "Match source port";
             uses match_li_simple_port_value;
           }
         }
       }
       choice destination-port_choice {
         case case_1 {
           container destination-port {
             description "Match destination port";
             uses match_li_simple_port_value;
           }
         }
       }
       choice protocol_choice {
         case case_1 {
           container protocol {
             description "Match IP protocol type";
             uses match_li_simple_protocol_value;
           }
         }
       }
       choice dscp_choice {
         case case_1 {
           container dscp {
             description "Match Differentiated Services (DiffServ) code point";
             uses match_li_simple_dscp_value;
           }
         }
       }
     }
   }
   grouping family {
     container inet {
       description "IPv4 parameters";
       uses apply-advanced;
       choice if-addr {
         case case_1 {
           leaf dhcp {
             description "Enable DHCP on ethernet interface";
             type empty;
           }
         }
         case case_2 {
           leaf address {
             description "Interface address/destination prefix";
             type jt:ipv4prefix;
           }
         }
       }
     }
   }
   grouping icap-profile-object {
     leaf name {
       description "ICAP service profile name";
       type string {
         length "1 .. 63";
         junos:posix-pattern "^[[:alnum:]][[:alnum:]_-]*$";
         junos:pattern-message "Must be a string beginning with a number or letter and consisting of letters, numbers, dashes and underscores.";
       }
     }
     uses apply-advanced;
     list server {
       key name;
       ordered-by user;
       description "Configure service redirection server";
       max-elements 16;
       uses icap-redir-server;
     }
     container http {
       description "ICAP methods switch";
       uses http-redirect-object;
     }
     container fallback-option {
       description "Failure event actions";
       uses icap-redirect-fallback;
     }
     leaf timeout {
       description "Server response timeout in milliseconds";
       default "500";
       type union {
         type string {
           pattern "<.*>|$.*";
         }
         type uint16 {
           range "100 .. 50000";
         }
       }
     }
   }
   grouping http-redirect-object {
     uses apply-advanced;
     leaf redirect-request {
       description "Enable redirect service on HTTP request";
       type empty;
     }
     leaf redirect-response {
       description "Enable redirect service on HTTP response";
       type empty;
     }
   }
   grouping icap-redir-server {
     leaf name {
       description "Server name";
       type string {
         length "1 .. 63";
         junos:posix-pattern "^[[:alnum:]][[:alnum:]_-]*$";
         junos:pattern-message "Must be a string beginning with a number or letter and consisting of letters, numbers, dashes and underscores.";
       }
     }
     uses apply-advanced;
     container authorization {
       description "User authentication";
       uses apply-advanced;
       leaf authorization-type {
         description "Authentication type. 'Basic' by default";
         type string {
           length "1 .. 127";
         }
       }
       container credentials {
         description "Credentials text";
         choice credentials-choice {
           case case_1 {
             leaf ascii {
               description "ASCII string";
               type string {
                 length "1 .. 511";
               }
             }
           }
           case case_2 {
             leaf base64 {
               description "Base64 string";
               type string {
                 length "1 .. 511";
               }
             }
           }
         }
       }
     }
     leaf host {
       description "Host name/IP address";
       type string {
         length "1 .. 255";
       }
     }
     leaf port {
       description "Server listening port";
       default "1344";
       type union {
         type string {
           pattern "<.*>|$.*";
         }
         type uint16 {
           range "1025 .. 65535";
         }
       }
     }
     leaf reqmod-uri {
       description "REQMOD option resource identifier";
       type string {
         length "0 .. 1023";
       }
     }
     leaf respmod-uri {
       description "RESPMOD option resource identifier";
       type string {
         length "0 .. 1023";
       }
     }
     container routing-instance {
       description "Routing instance";
       leaf ri-name {
         description "Routing instance name";
         junos:must "(\"routing-instances $$ instance-type virtual-router\")";
         junos:must-message "Virtual router must be defined under [routing-instances]";
         junos:must "(\"routing-instances $$\")";
         junos:must-message "Routing-instance must be defined";
         type string {
           length "1 .. 127";
           junos:posix-pattern "!^((__.*__)|(all)|(.*[ ].*)|(\"\")|(.{129,}))$";
           junos:pattern-message "Must be a non-reserved string of 128 characters or less with no spaces.";
         }
       }
     }
     leaf sockets {
       description "Number of connections to create";
       default "8";
       type union {
         type string {
           pattern "<.*>|$.*";
         }
         type uint8 {
           range "1 .. 64";
         }
       }
     }
     leaf tls-profile {
       description "TLS profile";
       junos:must "(\"services ssl initiation profile $$\")";
       junos:must-message "Referenced SSL initiation profile is not defined";
       type string {
         length "1 .. 63";
       }
     }
   }
   grouping icap-redirect-fallback {
     uses apply-advanced;
     leaf timeout {
       description "Request timeout action";
       default "permit";
       type enumeration {
         enum "permit" {
           description "Direct permit action";
         }
         enum "log-permit" {
           description "Log then permit action";
         }
         enum "block" {
           description "Block action";
         }
       }
     }
     leaf connectivity {
       description "Connection-related failure action";
       default "permit";
       type enumeration {
         enum "permit" {
           description "Direct permit action";
         }
         enum "log-permit" {
           description "Log then permit action";
         }
         enum "block" {
           description "Block action";
         }
       }
     }
     leaf default-action {
       description "Default failure action";
       default "permit";
       type enumeration {
         enum "permit" {
           description "Direct permit action";
         }
         enum "log-permit" {
           description "Log then permit action";
         }
         enum "block" {
           description "Block action";
         }
       }
     }
   }
   grouping icap-redirect-traceoptions {
     description "ICAP redirect traceoptions";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Trace flags";
       leaf name {
         type enumeration {
           enum "all" {
             description "Trace everything";
           }
           enum "icap-redirect-re" {
             description "Trace events on RE side";
           }
           enum "icap-redirect-control" {
             description "Trace events on PFE-ukernel side";
           }
           enum "icap-redirect-connection" {
             description "Trace ICAP server connection events";
           }
           enum "icap-redirect-protocol" {
             description "Trace redirect packet events";
           }
         }
       }
     }
   }
   grouping ids-option-type {
     description "Configure screen object";
     leaf name {
       description "Screen object name";
       type string {
         length "1 .. 64";
       }
     }
     uses apply-advanced;
     leaf description {
       description "Text description of screen";
       type string {
         length "1 .. 900";
         junos:posix-pattern "^[^&<>\n]+$";
         junos:pattern-message "Must be a string excluding '&', '<', '>' and '\n'";
       }
     }
     leaf alarm-without-drop {
       description "Do not drop packet, only generate alarm";
       type empty;
     }
     leaf match-direction {
       description "Match direction";
       type enumeration {
         enum "input" {
           description "Match on input to interface";
         }
         enum "output" {
           description "Match on output from interface";
         }
         enum "input-output" {
           description "Match on input to or output from interface";
         }
       }
     }
     container aggregation {
       presence "enable aggregation";
       description "Configure the source and Destination prefix for a ids-option";
       uses apply-advanced;
       leaf source-prefix-mask {
         description "Source IPV4 prefix";
         type union {
           type string {
             pattern "<.*>|$.*";
           }
           type uint32 {
             range "1 .. 32";
           }
         }
       }
       leaf destination-prefix-mask {
         description "Destination IPV4 prefix";
         type union {
           type string {
             pattern "<.*>|$.*";
           }
           type uint32 {
             range "1 .. 32";
           }
         }
       }
       leaf source-prefix-v6-mask {
         description "Source IPV6 prefix";
         type union {
           type string {
             pattern "<.*>|$.*";
           }
           type uint32 {
             range "1 .. 128";
           }
         }
       }
       leaf destination-prefix-v6-mask {
         description "Destination IPV6 prefix";
         type union {
           type string {
             pattern "<.*>|$.*";
           }
           type uint32 {
             range "1 .. 128";
           }
         }
       }
     }
     container icmp {
       description "Configure ICMP ids options";
       uses apply-advanced;
       container ip-sweep {
         presence "enable ip-sweep";
         description "Configure ip sweep ids option";
         leaf threshold {
           description "Threshold";
           default "5000";
           units "microseconds in which 10 ICMP packets are detected";
           type union {
             type string {
               pattern "<.*>|$.*";
             }
             type uint32 {
               range "1000 .. 1000000";
             }
           }
         }
       }
       leaf fragment {
         description "Enable ICMP fragment ids option";
         type empty;
       }
       leaf large {
         description "Enable large ICMP packet (size > 1024) ids option";
         type empty;
       }
       container flood {
         presence "enable flood";
         description "Configure icmp flood ids option";
         leaf threshold {
           description "Threshold";
           default "1000";
           units "ICMP packets per second";
           type union {
             type string {
               pattern "<.*>|$.*";
             }
             type uint32;
           }
         }
       }
       leaf ping-death {
         description "Enable ping of death ids option";
         type empty;
       }
       leaf icmpv6-malformed {
         description "Enable icmpv6 malformed ids option";
         type empty;
       }
     }
     container ip {
       description "Configure IP layer ids options";
       uses apply-advanced;
       leaf bad-option {
         description "Enable ip with bad option ids option";
         type empty;
       }
       leaf record-route-option {
         description "Enable ip with record route option ids option";
         type empty;
       }
       leaf timestamp-option {
         description "Enable ip with timestamp option ids option";
         type empty;
       }
       leaf security-option {
         description "Enable ip with security option ids option";
         type empty;
       }
       leaf stream-option {
         description "Enable ip with stream option ids option";
         type empty;
       }
       leaf spoofing {
         description "Enable IP address spoofing ids option";
         type empty;
       }
       leaf source-route-option {
         description "Enable ip source route ids option";
         type empty;
       }
       leaf loose-source-route-option {
         description "Enable ip with loose source route ids option";
         type empty;
       }
       leaf strict-source-route-option {
         description "Enable ip with strict source route ids option";
         type empty;
       }
       leaf unknown-protocol {
         description "Enable ip unknown protocol ids option";
         type empty;
       }
       leaf block-frag {
         description "Enable ip fragment blocking ids option";
         type empty;
       }
       leaf tear-drop {
         description "Enable tear drop ids option";
         type empty;
       }
       container ipv6-extension-header {
         description "Configure ipv6 extension header ids option";
         uses apply-advanced;
         container hop-by-hop-header {
           presence "enable hop-by-hop-header";
           description "Enable ipv6 hop by hop option header ids option";
           uses apply-advanced;
           leaf jumbo-payload-option {
             description "Enable jumbo payload option ids option";
             type empty;
           }
           leaf router-alert-option {
             description "Enable router alert option ids option";
             type empty;
           }
           leaf quick-start-option {
             description "Enable quick start option ids option";
             type empty;
           }
           leaf CALIPSO-option {
             description "Enable Common Architecture Label ipv6 Security Option ids option";
             type empty;
           }
           leaf SMF-DPD-option {
             description "Enable Simplified Multicast Forwarding ipv6 Duplicate Packet Detection option ids option";
             type empty;
           }
           leaf RPL-option {
             description "Enable Routing Protocol for Low-power and Lossy networks option ids option";
             type empty;
           }
           list user-defined-option-type {
             key name;
             ordered-by user;
             description "User-defined option type range";
             max-elements 256;
             leaf name {
               description "User-defined option type low value";
               type union {
                 type string {
                   pattern "<.*>|$.*";
                 }
                 type uint32 {
                   range "1 .. 255";
                 }
               }
             }
             container to {
               description "Upper limit of option type range";
               uses apply-advanced;
               leaf type-high {
                 description "User-defined option type high value";
                 type union {
                   type string {
                     pattern "<.*>|$.*";
                   }
                   type uint32 {
                     range "1 .. 255";
                   }
                 }
               }
             }
           }
         }
         leaf routing-header {
           description "Enable ipv6 routing header ids option";
           type empty;
         }
         leaf fragment-header {
           description "Enable ipv6 fragment header ids option";
           type empty;
         }
         leaf ESP-header {
           description "Enable ipv6 Encapsulating Security Payload header ids option";
           type empty;
         }
         leaf AH-header {
           description "Enable ipv6 Authentication Header ids option";
           type empty;
         }
         leaf no-next-header {
           description "Enable ipv6 no next header ids option";
           type empty;
         }
         container destination-header {
           presence "enable destination-header";
           description "Enable ipv6 destination option header ids option";
           uses apply-advanced;
           leaf tunnel-encapsulation-limit-option {
             description "Enable tunnel encapsulation limit option ids option";
             type empty;
           }
           leaf home-address-option {
             description "Enable home address option ids option";
             type empty;
           }
           leaf ILNP-nonce-option {
             description "Enable Identifier-Locator Network Protocol Nonce option ids option";
             type empty;
           }
           leaf line-identification-option {
             description "Enable line identification option ids option";
             type empty;
           }
           list user-defined-option-type {
             key name;
             ordered-by user;
             description "User-defined option type range";
             max-elements 256;
             leaf name {
               description "User-defined option type low value";
               type union {
                 type string {
                   pattern "<.*>|$.*";
                 }
                 type uint32 {
                   range "1 .. 255";
                 }
               }
             }
             container to {
               description "Upper limit of option type range";
               uses apply-advanced;
               leaf type-high {
                 description "User-defined option type high value";
                 type union {
                   type string {
                     pattern "<.*>|$.*";
                   }
                   type uint32 {
                     range "1 .. 255";
                   }
                 }
               }
             }
           }
         }
         leaf shim6-header {
           description "Enable ipv6 shim header ids option";
           type empty;
         }
         leaf mobility-header {
           description "Enable ipv6 mobility header ids option";
           type empty;
         }
         leaf HIP-header {
           description "Enable ipv6 Host Identify Protocol header ids option";
           type empty;
         }
         list user-defined-header-type {
           key name;
           ordered-by user;
           description "User-defined header type range";
           max-elements 256;
           leaf name {
             description "User-defined header type low value";
             type union {
               type string {
                 pattern "<.*>|$.*";
               }
               type uint32 {
                 range "0 .. 255";
               }
             }
           }
           container to {
             description "Upper limit of header type range";
             uses apply-advanced;
             leaf type-high {
               description "User-defined header type high value";
               type union {
                 type string {
                   pattern "<.*>|$.*";
                 }
                 type uint32 {
                   range "0 .. 255";
                 }
               }
             }
           }
         }
       }
       leaf ipv6-extension-header-limit {
         description "Enable ipv6 extension header limit ids option";
         type union {
           type string {
             pattern "<.*>|$.*";
           }
           type uint32 {
             range "0 .. 32";
           }
         }
       }
       leaf ipv6-malformed-header {
         description "Enable ipv6 malformed header ids option";
         type empty;
       }
       container tunnel {
         description "Configure IP tunnel ids options";
         uses apply-advanced;
         leaf bad-inner-header {
           description "Enable IP tunnel bad inner header ids option";
           type empty;
         }
         container gre {
           description "Configure IP tunnel GRE ids option";
           uses apply-advanced;
           leaf gre-6in4 {
             description "Enable IP tunnel GRE 6in4 ids option";
             type empty;
           }
           leaf gre-4in6 {
             description "Enable IP tunnel GRE 4in6 ids option";
             type empty;
           }
           leaf gre-6in6 {
             description "Enable IP tunnel GRE 6in6 ids option";
             type empty;
           }
           leaf gre-4in4 {
             description "Enable IP tunnel GRE 4in4 ids option";
             type empty;
           }
         }
         container ip-in-udp {
           description "Configure IP tunnel IPinUDP ids option";
           uses apply-advanced;
           leaf teredo {
             description "Enable IP tunnel IPinUDP Teredo ids option";
             type empty;
           }
         }
         container ipip {
           description "Configure IP tunnel IPIP ids option";
           uses apply-advanced;
           leaf ipip-6to4relay {
             description "Enable IP tunnel IPIP 6to4 Relay ids option";
             type empty;
           }
           leaf ipip-6in4 {
             description "Enable IP tunnel IPIP 6in4 ids option";
             type empty;
           }
           leaf ipip-4in6 {
             description "Enable IP tunnel IPIP 4in6 ids option";
             type empty;
           }
           leaf ipip-4in4 {
             description "Enable IP tunnel IPIP 4in4 ids option";
             type empty;
           }
           leaf ipip-6in6 {
             description "Enable IP tunnel IPIP 6in6 ids option";
             type empty;
           }
           leaf ipip-6over4 {
             description "Enable IP tunnel IPIP 6over4 ids option";
             type empty;
           }
           leaf isatap {
             description "Enable IP tunnel IPIP ISATAP ids option";
             type empty;
           }
           leaf dslite {
             description "Enable IP tunnel IPIP DS-Lite ids option";
             type empty;
           }
         }
       }
     }
     container tcp {
       description "Configure TCP Layer ids options";
       uses apply-advanced;
       leaf syn-fin {
         description "Enable SYN and FIN bits set attack ids option";
         type empty;
       }
       leaf fin-no-ack {
         description "Enable Fin bit with no ACK bit ids option";
         type empty;
       }
       leaf tcp-no-flag {
         description "Enable TCP packet without flag ids option";
         type empty;
       }
       leaf syn-frag {
         description "Enable SYN fragment ids option";
         type empty;
       }
       container port-scan {
         presence "enable port-scan";
         description "Configure TCP port scan ids option";
         leaf threshold {
           description "Threshold";
           default "5000";
           units "microseconds in which 10 attack packets are detected";
           type union {
             type string {
               pattern "<.*>|$.*";
             }
             type uint32 {
               range "1000 .. 1000000";
             }
           }
         }
       }
       container syn-ack-ack-proxy {
         presence "enable syn-ack-ack-proxy";
         description "Configure syn-ack-ack proxy ids option";
         leaf threshold {
           description "Threshold";
           default "512";
           units "un-authenticated connections";
           type union {
             type string {
               pattern "<.*>|$.*";
             }
             type uint32 {
               range "1 .. 250000";
             }
           }
         }
       }
       container syn-flood {
         presence "enable syn-flood";
         description "Configure SYN flood ids option";
         uses apply-advanced;
         leaf alarm-threshold {
           description "Alarm threshold";
           default "512";
           units "requests per second";
           type union {
             type string {
               pattern "<.*>|$.*";
             }
             type uint32;
           }
         }
         leaf attack-threshold {
           description "Attack threshold";
           default "200";
           units "proxied requests per second";
           type union {
             type string {
               pattern "<.*>|$.*";
             }
             type uint32;
           }
         }
         leaf source-threshold {
           description "Source threshold";
           default "4000";
           units "SYN pps";
           type union {
             type string {
               pattern "<.*>|$.*";
             }
             type uint32;
           }
         }
         leaf destination-threshold {
           description "Destination threshold";
           default "4000";
           units "SYN pps";
           type union {
             type string {
               pattern "<.*>|$.*";
             }
             type uint32;
           }
         }
         leaf queue-size {
           description "Queue size";
           status deprecated;
           default "1024";
           units "proxied requests in queue";
           type union {
             type string {
               pattern "<.*>|$.*";
             }
             type uint32 {
               range "200 .. 20000";
             }
           }
         }
         leaf timeout {
           description "SYN flood ager timeout";
           default "20";
           units "seconds";
           type union {
             type string {
               pattern "<.*>|$.*";
             }
             type uint32 {
               range "1 .. 50";
             }
           }
         }
         list white-list {
           key name;
           description "Set of IP addresses that will not trigger a screen";
           max-elements 2;
           leaf name {
             description "White-list name";
             type string {
               length "1 .. 32";
               junos:posix-pattern "^[[:alnum:]][[:alnum:]_-]*$";
               junos:pattern-message "Must be a string beginning with a number or letter and consisting of letters, numbers, dashes and underscores.";
             }
           }
           uses apply-advanced;
           leaf-list source-address {
             ordered-by user;
             description "Source address";
             type jt:ipprefix;
             max-elements 32;
           }
           leaf-list destination-address {
             ordered-by user;
             description "Destination address";
             type jt:ipprefix;
             max-elements 32;
           }
         }
       }
       leaf land {
         description "Enable land attack ids option";
         type empty;
       }
       leaf winnuke {
         description "Enable winnuke attack ids option";
         type empty;
       }
       container tcp-sweep {
         presence "enable tcp-sweep";
         description "Configure TCP sweep ids option";
         leaf threshold {
           description "Threshold";
           default "5000";
           units "microseconds in which 10 TCP packets are detected";
           type union {
             type string {
               pattern "<.*>|$.*";
             }
             type uint32 {
               range "1000 .. 1000000";
             }
           }
         }
       }
     }
     container udp {
       description "Configure UDP layer ids options";
       uses apply-advanced;
       container flood {
         presence "enable flood";
         description "Configure UDP flood ids option";
         uses apply-advanced;
         leaf threshold {
           description "Threshold";
           default "1000";
           units "UDP packets per second";
           type union {
             type string {
               pattern "<.*>|$.*";
             }
             type uint32;
           }
         }
         leaf-list white-list {
           ordered-by user;
           description "Configure UDP flood white list group name";
           type string;
           max-elements 2;
         }
       }
       container udp-sweep {
         presence "enable udp-sweep";
         description "Configure UDP sweep ids option";
         leaf threshold {
           description "Threshold";
           default "5000";
           units "microseconds in which 10 UDP packets are detected";
           type union {
             type string {
               pattern "<.*>|$.*";
             }
             type uint32 {
               range "1000 .. 1000000";
             }
           }
         }
       }
       container port-scan {
         presence "enable port-scan";
         description "Configure UDP port scan ids option";
         leaf threshold {
           description "Threshold";
           default "5000";
           units "microseconds in which 10 attack packets are detected";
           type union {
             type string {
               pattern "<.*>|$.*";
             }
             type uint32 {
               range "1000 .. 1000000";
             }
           }
         }
       }
     }
     container limit-session {
       description "Limit sessions";
       uses apply-advanced;
       leaf source-ip-based {
         description "Limit sessions from the same source IP";
         type union {
           type string {
             pattern "<.*>|$.*";
           }
           type uint32;
         }
       }
       leaf destination-ip-based {
         description "Limit sessions to the same destination IP";
         type union {
           type string {
             pattern "<.*>|$.*";
           }
           type uint32;
         }
       }
       container by-source {
         presence "enable by-source";
         description "Limit sessions from the same source IP or subnet";
         uses apply-advanced;
         leaf maximum-sessions {
           description "Limit sessions on the basis of maximum concurrent sessions";
           type union {
             type string {
               pattern "<.*>|$.*";
             }
             type uint32;
           }
         }
         leaf packet-rate {
           description "Limit sessions on the basis of packet rate";
           type union {
             type string {
               pattern "<.*>|$.*";
             }
             type uint32 {
               range "1 .. 4294967295";
             }
           }
         }
         leaf session-rate {
           description "Limit sessions on the basis of session rate";
           type union {
             type string {
               pattern "<.*>|$.*";
             }
             type uint32 {
               range "1 .. 4294967295";
             }
           }
         }
         container by-protocol {
           description "Limit sessions on the basis of protocol";
           uses by-protocol-object-type;
         }
       }
       container by-destination {
         presence "enable by-destination";
         description "Limit sessions to the same destination IP or subnet";
         uses apply-advanced;
         leaf maximum-sessions {
           description "Limit sessions on the basis of maximum concurrent sessions";
           type union {
             type string {
               pattern "<.*>|$.*";
             }
             type uint32;
           }
         }
         leaf packet-rate {
           description "Limit sessions on the basis of packet rate";
           type union {
             type string {
               pattern "<.*>|$.*";
             }
             type uint32 {
               range "1 .. 4294967295";
             }
           }
         }
         leaf session-rate {
           description "Limit sessions on the basis of session rate";
           type union {
             type string {
               pattern "<.*>|$.*";
             }
             type uint32 {
               range "1 .. 4294967295";
             }
           }
         }
         container by-protocol {
           description "Limit sessions on the basis of protocol";
           uses by-protocol-object-type;
         }
       }
     }
   }
   grouping by-protocol-object-type {
     description "Configure limit-session on the basis of protocol";
     uses apply-advanced;
     container tcp {
       description "Configure limit-session on the basis of TCP";
       uses by-protocol-object-limit-type;
     }
     container udp {
       description "Configure limit-session on the basis of UDP";
       uses by-protocol-object-limit-type;
     }
     container icmp {
       description "Configure limit-session on the basis of ICMP";
       uses by-protocol-object-limit-type;
     }
   }
   grouping by-protocol-object-limit-type {
     description "Configure the limit-session for each protocol";
     uses apply-advanced;
     leaf maximum-sessions {
       description "Limit sessions on the basis of maximum concurrent sessions";
       type union {
         type string {
           pattern "<.*>|$.*";
         }
         type uint32;
       }
     }
     leaf packet-rate {
       description "Limit sessions on the basis of packet rate";
       type union {
         type string {
           pattern "<.*>|$.*";
         }
         type uint32 {
           range "1 .. 4294967295";
         }
       }
     }
     leaf session-rate {
       description "Limit sessions on the basis of session rate";
       type union {
         type string {
           pattern "<.*>|$.*";
         }
         type uint32 {
           range "1 .. 4294967295";
         }
       }
     }
   }
   grouping juniper-services-captive-portal {
     junos:must "((\"services captive-portal secure-authentication\" || \"system services web-management http\"))";
     junos:must-message "HTTP web service should be enabled";
     uses apply-advanced;
     leaf authentication-profile-name {
       description "Access profile name to use for authentication";
       junos:must "(\"access profile $$\")";
       junos:must-message "Access profile name must be defined in the [edit access profile] hierarchy";
       type string {
         length "1 .. 63";
       }
     }
     container traceoptions {
       description "Trace options for CAPTIVE PORTAL";
       status deprecated;
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "dot1x-debug" {
               description "Trace dot1x events";
               junos:must "(!(\"services captive-portal traceoptions flag dot1x-event\"))";
               junos:must-message "Can not configure dot1x-event with dot1x-debug flag";
             }
             enum "parse" {
               description "Trace configuration parsing";
             }
             enum "esw-if" {
               description "Trace ESW Interactions";
               junos:must "(!(\"services captive-portal traceoptions flag dot1x-ipc\"))";
               junos:must-message "Can not configure dot1x-ipc with esw-if flag";
             }
             enum "config-internal" {
               description "Trace configuration internals";
             }
             enum "normal" {
               description "Trace normal events";
             }
             enum "general" {
               description "Trace general events";
             }
             enum "state" {
               description "Trace state transitions";
             }
             enum "task" {
               description "Trace task processing";
             }
             enum "timer" {
               description "Trace task timer processing";
             }
             enum "all" {
               description "Trace everything";
             }
             enum "dot1x-ipc" {
               description "Trace dot1x IPC interactions";
             }
             enum "dot1x-event" {
               description "Trace dot1x events";
             }
           }
         }
         leaf disable {
           description "Disable this trace flag";
           type empty;
         }
       }
     }
     list interface {
       key name;
       description "Captive Portal interface specific options";
       leaf name {
         junos:must "(!(\"system phone-home\"))";
         junos:must-message "Can't configure captive-portal along with Phone-home. Delete phone-home config to enable captive-portal";
         junos:must "(\"system services web-management http\")";
         junos:must-message "HTTP web service should be enabled";
         junos:must "((!(\"switch-options no-mac-learning\") || (!(\".. .. .. .. .. switch-options no-mac-learning\") || !(any \".. .. .. .. .. bridge-domains <*> bridge-options no-mac-learning interface $$-IFL\"))))";
         junos:must-message "Cannot configure captive-portal on this interface since no-mac-learning is enabled on the same interface";
         junos:must "(!(\"interfaces $$-IFL family bridge interface-mode trunk\"))";
         junos:must-message "Cannot configure captive-portal on this interface since the interface-mode is defined as trunk";
         junos:must "(!(\"interfaces $$-IFL family ethernet-switching interface-mode trunk\"))";
         junos:must-message "Cannot configure captive-portal on this interface since the interface-mode is defined as trunk";
         junos:must "(!(\"interfaces $$-IFL family ethernet-switching port-mode trunk\"))";
         junos:must-message "Cannot configure captive-portal on this interface since the port-mode is defined as trunk";
         type string;
       }
       uses apply-advanced;
       leaf supplicant {
         description "Set supplicant mode for this interface";
         type enumeration {
           enum "single" {
             description "Allow multiple clients; authenticate first client only";
           }
           enum "single-secure" {
             description "Allow and authenticate only a single client";
           }
           enum "multiple" {
             description "Allow multiple clients; authenticate each individually";
           }
         }
       }
       leaf retries {
         description "Number of retries after which port is placed into wait state";
         type union {
           type string {
             pattern "<.*>|$.*";
           }
           type uint32 {
             range "1 .. 10";
           }
         }
       }
       leaf quiet-period {
         description "Time to wait after an authentication failure";
         units "seconds";
         type union {
           type string {
             pattern "<.*>|$.*";
           }
           type uint32 {
             range "0 .. 65535";
           }
         }
       }
       leaf server-timeout {
         description "Authentication server timeout interval";
         units "seconds";
         type union {
           type string {
             pattern "<.*>|$.*";
           }
           type uint32 {
             range "1 .. 60";
           }
         }
       }
       leaf session-expiry {
         description "Session Expiry Timeout";
         units "seconds";
         type union {
           type string {
             pattern "<.*>|$.*";
           }
           type uint32 {
             range "1 .. 65535";
           }
         }
       }
       leaf user-keepalive {
         description "Session keepalive after mac-flush";
         units "minutes";
         type union {
           type string {
             pattern "<.*>|$.*";
           }
           type uint32 {
             range "7 .. 65535";
           }
         }
       }
     }
     leaf secure-authentication {
       description "Set secure authentication using encrypted HTTPS or insecure authentication using plain-text HTTP";
       default "http";
       type enumeration {
         enum "http" {
           description "Insecure plain-text HTTP will be used for Captive Portal authentication, username and password can be sniffed";
           junos:must "(\"system services web-management http\")";
           junos:must-message "HTTP web service should be enabled";
         }
         enum "https" {
           description "Encrypted HTTPS will be used for Captive Portal authentication";
           junos:must "((\"system services web-management http\" && \"system services web-management https\"))";
           junos:must-message "HTTP and HTTPS web services should be enabled";
         }
       }
     }
     container custom-options {
       presence "enable custom-options";
       description "Captive Portal html user interface customization options";
       uses apply-advanced;
       leaf header-logo {
         description "Path to logo image file";
         type string {
           length "1 .. 255";
           junos:posix-pattern "^.+.((jpg)|(gif)|(jpeg)|(png))$";
           junos:pattern-message "Only jpg, jpeg, gif, png image types allowed";
         }
       }
       leaf header-bgcolor {
         description "Background color of the html header in hex html format";
         type string {
           length 7;
           junos:posix-pattern "^#[A-Fa-f0-9]{1,6}$";
           junos:pattern-message "Must be Hex color code beginning with # and consisting of six digit hexadecimal numbers";
         }
       }
       leaf header-text-color {
         description "Text color of the html header in hex html format";
         type string {
           length 7;
           junos:posix-pattern "^#[A-Fa-f0-9]{1,6}$";
           junos:pattern-message "Must be Hex color code beginning with # and consisting of six digit hexadecimal numbers";
         }
       }
       leaf header-message {
         description "Message to be displayed in the html header";
         type string {
           length "1 .. 2047";
         }
       }
       leaf banner-message {
         description "Terms and Conditions of usage message";
         type string {
           length "1 .. 2047";
         }
       }
       leaf form-header-message {
         description "Message to be displayed in the login form header";
         type string {
           length "1 .. 255";
         }
       }
       leaf form-header-bgcolor {
         description "Background color of the login form header in hex html format";
         type string {
           length 7;
           junos:posix-pattern "^#[A-Fa-f0-9]{1,6}$";
           junos:pattern-message "Must be Hex color code beginning with # and consisting of six digit hexadecimal numbers";
         }
       }
       leaf form-header-text-color {
         description "Text color of the login form header in hex html format";
         type string {
           length 7;
           junos:posix-pattern "^#[A-Fa-f0-9]{1,6}$";
           junos:pattern-message "Must be Hex color code beginning with # and consisting of six digit hexadecimal numbers";
         }
       }
       leaf form-submit-label {
         description "Label to be displayed for the login form submit button";
         type string {
           length "1 .. 255";
         }
       }
       leaf form-reset-label {
         description "Label to be displayed for the login form reset button";
         type string {
           length "1 .. 255";
         }
       }
       leaf footer-message {
         description "Message to be displayed in the html footer";
         type string {
           length "1 .. 2047";
         }
       }
       leaf footer-bgcolor {
         description "Background color of the html footer in hex html format";
         type string {
           length 7;
           junos:posix-pattern "^#[A-Fa-f0-9]{1,6}$";
           junos:pattern-message "Must be Hex color code beginning with # and consisting of six digit hexadecimal numbers";
         }
       }
       leaf footer-text-color {
         description "Text color of the footer in hex html format";
         type string {
           length 7;
           junos:posix-pattern "^#[A-Fa-f0-9]{1,6}$";
           junos:pattern-message "Must be Hex color code beginning with # and consisting of six digit hexadecimal numbers";
         }
       }
       leaf post-authentication-url {
         description "Post authentication redirection URL";
         type string {
           length "1 .. 255";
         }
       }
     }
   }
   grouping li_policy_addr6_simple_object {
     uses apply-advanced;
     leaf address {
       description "Prefix to match";
       type jt:ipv6prefix;
     }
   }
   grouping li_policy_addr_simple_object {
     uses apply-advanced;
     leaf address {
       description "Prefix to match";
       type jt:ipv4prefix;
     }
   }
   grouping macro-data-type {
     leaf name {
       description "Keyword part of the keyword-value pair";
       type string;
     }
     leaf value {
       description "Value part of the keyword-value pair";
       type string;
     }
   }
   grouping match_li_simple_dscp_value {
     uses apply-advanced;
     leaf value_keyword {
       type string;
     }
   }
   grouping match_li_simple_port_value {
     uses apply-advanced;
     leaf value_keyword {
       type string;
     }
   }
   grouping match_li_simple_protocol_value {
     uses apply-advanced;
     leaf value_keyword {
       type string;
     }
   }
   grouping monitor-threshold {
     leaf normal {
       description "Usage under normal conditions";
       type union {
         type string {
           pattern "<.*>|$.*";
         }
         type uint8 {
           range "1 .. 100";
         }
       }
     }
     leaf threshold {
       description "Threshold upon which alarm is raised";
       type union {
         type string {
           pattern "<.*>|$.*";
         }
         type uint8 {
           range "1 .. 100";
         }
       }
     }
   }
   grouping proxy-profile-setting {
     description "Proxy profile settings";
     leaf name {
       description "Proxy profile name";
       type string {
         length "1 .. 64";
       }
     }
     uses apply-advanced;
     container protocol {
       description "Protocol level proxy setting";
       uses apply-advanced;
       container http {
         description "HTTP proxy setting";
         uses apply-advanced;
         leaf host {
           description "Proxy server name or IP address";
           type string {
             length "1 .. 256";
           }
         }
         leaf port {
           description "Proxy server port";
           default "3128";
           type union {
             type string {
               pattern "<.*>|$.*";
             }
             type uint16 {
               range "0 .. 65535";
             }
           }
         }
       }
     }
   }
   grouping rmopd-traceoptions {
     description "Trace options for remote-monitoring";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing parameters";
       leaf name {
         type enumeration {
           enum "configuration" {
             description "Trace configuration events";
           }
           enum "ipc" {
             description "Trace ipc messages";
           }
           enum "ppm" {
             description "Trace ppm";
           }
           enum "rpd" {
             description "Trace rpd events";
           }
           enum "info" {
             description "Trace info events";
           }
           enum "statistics" {
             description "Trace statistics";
           }
           enum "error" {
             description "Trace events related to catastrophic errors in daemon";
           }
           enum "all" {
             description "Trace everything";
           }
         }
       }
     }
   }
   grouping secintel-category-disable {
     description "Security intelligence category";
     leaf name {
       description "Name of security intelligence category";
       type enumeration {
         enum "IPFilter" {
           description "IPFilter";
         }
         enum "GeoIP" {
           description "GeoIP";
         }
         enum "CC" {
           description "Command and control";
         }
         enum "JWAS" {
           description "JWAS";
         }
         enum "Blacklist" {
           description "Blacklist";
         }
         enum "Whitelist" {
           description "Whitelist";
         }
         enum "Infected-Hosts" {
           description "Infected-Hosts";
         }
       }
     }
     uses apply-advanced;
     container disable {
       presence "enable disable";
       description "To disable category for feed update";
     }
   }
   grouping secintel-policy-setting {
     description "Security intelligence policy setting";
     leaf name {
       description "Security intelligence policy name";
       type string {
         length "1 .. 63";
       }
     }
     uses apply-advanced;
     leaf description {
       description "Text description of policy";
       type string {
         length "1 .. 900";
         junos:posix-pattern "^[^&<>\n]+$";
         junos:pattern-message "Must be a string excluding '&', '<', '>' and '\n'";
       }
     }
     list category-profiles {
       key name;
       ordered-by user;
       description "Security intelligence category profiles";
       leaf name {
         description "Name of security intelligence category";
         type string;
       }
       uses apply-advanced;
       leaf profile-name {
         description "Name of profile";
         junos:must "(\"services security-intelligence profile $$\")";
         junos:must-message "security intelligence profile must be defined";
         type string;
       }
     }
   }
   grouping secintel-profile-setting {
     description "Security intelligence profile settings";
     leaf name {
       description "Security intelligence profile name";
       type string {
         length "1 .. 63";
       }
     }
     uses apply-advanced;
     leaf description {
       description "Text description of profile";
       type string {
         length "1 .. 900";
         junos:posix-pattern "^[^&<>\n]+$";
         junos:pattern-message "Must be a string excluding '&', '<', '>' and '\n'";
       }
     }
     leaf category {
       description "Profile category name";
       type string;
     }
     list rule {
       key name;
       ordered-by user;
       description "Profile rule name";
       uses secintel-profile-rule;
     }
     container default-rule {
       presence "enable default-rule";
       description "Profile default rule";
       uses apply-advanced;
       container then {
         presence "enable then";
         description "Profile default rule action";
         uses apply-advanced;
         container action {
           description "Security intelligence profile action";
           uses apply-advanced;
           choice action {
             case case_1 {
               leaf permit {
                 description "Permit action";
                 type empty;
               }
             }
             case case_2 {
               container block {
                 description "Block action";
                 uses apply-advanced;
                 choice action {
                   case case_1 {
                     container drop {
                       presence "enable drop";
                       description "Drop packet";
                     }
                   }
                   case case_2 {
                     container close {
                       presence "enable close";
                       description "Close session";
                       uses apply-advanced;
                       container http {
                         description "Http content for block action";
                         uses apply-advanced;
                         choice http-choice {
                           case case_1 {
                             leaf file {
                               description "File name for http response to client";
                               type string;
                             }
                           }
                           case case_2 {
                             leaf message {
                               description "Block message to client";
                               type string;
                             }
                           }
                           case case_3 {
                             leaf redirect-url {
                               description "Redirect url to client";
                               type string {
                                 length "1 .. 1023";
                                 junos:posix-pattern "^https?://.*";
                                 junos:pattern-message "URL must begin with http:// or https://";
                               }
                             }
                           }
                         }
                       }
                     }
                   }
                 }
               }
             }
             case case_3 {
               container recommended {
                 presence "enable recommended";
                 description "Recommended action from feed server";
               }
             }
           }
         }
         choice log-choice {
           leaf log {
             description "Log security intelligence block action";
             type empty;
           }
           leaf no-log {
             description "Don't log security intelligence block action";
             type empty;
           }
         }
       }
     }
   }
   grouping secintel-profile-rule {
     description "Security intelligence profile rule";
     leaf name {
       description "Profile rule name";
       type string {
         length "1 .. 63";
       }
     }
     uses apply-advanced;
     container match {
       description "Profile matching feed name and threat levels";
       uses apply-advanced;
       leaf-list feed-name {
         ordered-by user;
         description "Profile matching feed name";
         type string;
         max-elements 32;
       }
       leaf-list threat-level {
         ordered-by user;
         description "Profile matching threat levels, higher number is more severe";
         type union {
           type uint32;
           type string {
             pattern "<.*>|$.*";
           }
         }
       }
     }
     container then {
       description "Profile action and log";
       uses apply-advanced;
       container action {
         description "Security intelligence profile action";
         uses apply-advanced;
         choice action {
           case case_1 {
             leaf permit {
               description "Permit action";
               type empty;
             }
           }
           case case_2 {
             container block {
               description "Block action";
               uses apply-advanced;
               choice action {
                 case case_1 {
                   container drop {
                     presence "enable drop";
                     description "Drop packet";
                   }
                 }
                 case case_2 {
                   container close {
                     presence "enable close";
                     description "Close session";
                     uses apply-advanced;
                     container http {
                       description "Http content for block action";
                       uses apply-advanced;
                       choice http-choice {
                         case case_1 {
                           leaf file {
                             description "File name for http response to client";
                             type string;
                           }
                         }
                         case case_2 {
                           leaf message {
                             description "Block message to client";
                             type string;
                           }
                         }
                         case case_3 {
                           leaf redirect-url {
                             description "Redirect url to client";
                             type string {
                               length "1 .. 1023";
                               junos:posix-pattern "^https?://.*";
                               junos:pattern-message "URL must begin with http:// or https://";
                             }
                           }
                         }
                       }
                     }
                   }
                 }
               }
             }
           }
           case case_3 {
             container recommended {
               presence "enable recommended";
               description "Recommended action from feed server";
             }
           }
         }
       }
       container log {
         presence "enable log";
         description "Log security intelligence block action";
       }
     }
   }
   grouping secintel-traceoptions {
     description "Security intelligence trace options";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Trace flags";
       leaf name {
         type enumeration {
           enum "all" {
             description "Trace everything";
           }
           enum "blacklist" {
             description "Trace security intelligence Blacklist category";
           }
           enum "cc" {
             description "Trace security intelligence CC category";
           }
           enum "infected-hosts" {
             description "Trace security intelligence Infected-Hosts category";
           }
           enum "control" {
             description "Trace control plane";
           }
           enum "feed" {
             description "Trace feed operation";
           }
           enum "ipc" {
             description "Trace ipc module";
           }
           enum "infrastucture" {
             description "Trace infrastucture functions";
           }
           enum "jwas" {
             description "Trace security intelligence JWAS category";
           }
           enum "plugin" {
             description "Trace security intelligence plugin services";
           }
           enum "whitelist" {
             description "Trace security intelligence Whitelist category";
           }
         }
       }
     }
   }
   grouping server-connection-type {
     description "Connection parameters per server";
     uses apply-advanced;
     leaf address {
       description "IP address";
       type jt:ipaddr;
     }
     leaf ca-certificate {
       description "Ca-certificate file name";
       type string {
         length "1 .. 256";
       }
     }
     leaf client-id {
       description "Client ID for OAuth2 grant";
       type string {
         length "1 .. 64";
       }
     }
     leaf client-secret {
       description "Client secret for OAuth2 grant";
       type string {
         length "1 .. 128";
       }
     }
   }
   grouping service_device_pool_object {
     leaf name {
       description "Service device pool name";
       type string {
         length "1 .. 63";
         junos:posix-pattern "^[[:alnum:]][[:alnum:]_-]*$";
         junos:pattern-message "Must be a string beginning with a number or letter and consisting of letters, numbers, dashes and underscores.";
       }
     }
     uses apply-advanced;
     list interface {
       key name;
       ordered-by user;
       description "Service device name";
       leaf name {
         junos:must "(!(any \"interfaces <*> aggregated-inline-services-options secondary-interface $$\"))";
         junos:must-message "must not be defined under asiX aggregated-inline-services-options";
         junos:must "(!(any \"interfaces <*> aggregated-inline-services-options primary-interface $$\"))";
         junos:must-message "must not be defined under asiX aggregated-inline-services-options";
         junos:must "(\"interfaces $$\")";
         junos:must-message "referenced interface must be defined";
         type union {
           type jt:interface-unit;
           type string {
             pattern "<.*>|$.*";
           }
         }
       }
       uses apply-advanced;
     }
   }
   grouping service_interface_pool_object {
     leaf name {
       description "Service interface pool name";
       type string {
         length "1 .. 63";
         junos:posix-pattern "^[[:alnum:]][[:alnum:]_-]*$";
         junos:pattern-message "Must be a string beginning with a number or letter and consisting of letters, numbers, dashes and underscores.";
       }
     }
     uses apply-advanced;
     list interface {
       key name;
       ordered-by user;
       description "Service interface name";
       leaf name {
         junos:must "(\"interfaces $$\")";
         junos:must-message "referenced interface must be defined";
         type union {
           type jt:interface-unit;
           type string {
             pattern "<.*>|$.*";
           }
         }
       }
       uses apply-advanced;
     }
   }
   grouping softwires-object {
     description "Configure softwire feature";
     uses apply-advanced;
     list softwire-name {
       key name;
       description "Configure softwire object";
       uses softwire-option-type;
     }
     container traceoptions {
       description "Trace options for Network Security DS-Lite";
       uses apply-advanced;
       leaf no-remote-trace {
         description "Disable remote tracing";
         junos:must "(\"system tracing\")";
         junos:must-message "'no-remote-trace' is valid only when [system tracing] is configured";
         type empty;
       }
       container file {
         description "Trace file information";
         leaf filename {
           description "Name of file in which to write trace information";
           type string {
             length "1 .. 1024";
             junos:posix-pattern "![/ %]";
             junos:pattern-message "Must not contain '/', % or a space";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing parameters";
         leaf name {
           type enumeration {
             enum "configuration" {
               description "Trace configuration events";
             }
             enum "flow" {
               description "Trace flow events";
             }
             enum "all" {
               description "Trace everything";
             }
           }
         }
       }
     }
     list rule-set {
       key name;
       ordered-by user;
       description "Define a softwire rule set";
       uses sw-rule-set-object;
     }
   }
   grouping softwire-option-type {
     description "Configure softwire object";
     leaf name {
       description "DS-Lite/Softwire object name";
       type string {
         length "1 .. 23";
       }
     }
     uses apply-advanced;
     leaf softwire-concentrator {
       description "Concentrator address";
       type jt:ipaddr;
     }
     leaf softwire-type {
       description "Softwire-type";
       default "IPv4-in-IPv6";
       type enumeration {
         enum "IPv4-in-IPv6" {
           description "Ipv4-in-IPv6";
         }
         enum "v6rd" {
           description "V6rd";
         }
       }
     }
     leaf ipv4-prefix {
       description "6rd customer edge IPV4 prefix";
       type jt:ipv4prefix;
     }
     leaf v6rd-prefix {
       description "6rd domain's IPV6 prefix";
       type jt:ipv6prefix;
     }
     leaf mtu-v4 {
       description "MTU for the softwire tunnel";
       type union {
         type string {
           pattern "<.*>|$.*";
         }
         type uint32 {
           range "576 .. 9192";
         }
       }
     }
   }
   grouping srd-rs-id-object {
     description "Definition of redundancy-set";
     leaf name {
       description "Redundancy set identifier";
       type union {
         type string {
           pattern "<.*>|$.*";
         }
         type uint32 {
           range "1 .. 100";
         }
       }
     }
     uses apply-advanced;
     leaf redundancy-group {
       description "Name of redundancy-group";
       type union {
         type string {
           pattern "<.*>|$.*";
         }
         type uint32 {
           range "1 .. 16";
         }
       }
     }
     leaf-list redundancy-policy {
       description "Redundancy-policy list";
       type string;
     }
     leaf keepalive {
       description "Frequency of SRD hello messages";
       default "10";
       units "seconds";
       type union {
         type string {
           pattern "<.*>|$.*";
         }
         type uint32 {
           range "1 .. 60";
         }
       }
     }
     leaf hold-time {
       description "Time before SRD peer is declared down";
       default "30";
       units "seconds";
       type union {
         type string {
           pattern "<.*>|$.*";
         }
         type uint32 {
           range "0 .. 3600";
         }
       }
     }
     leaf healthcheck-timer-interval {
       description "Healthcheck timer interval";
       default "5";
       units "seconds";
       type union {
         type string {
           pattern "<.*>|$.*";
         }
         type uint32 {
           range "1 .. 3600";
         }
       }
     }
   }
   grouping srd-traceoptions-object {
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing flag parameters";
       leaf name {
         type enumeration {
           enum "config" {
             description "Trace parse events";
           }
           enum "connect" {
             description "Trace ipc events";
           }
           enum "route" {
             description "Trace route events";
           }
           enum "ssd" {
             description "Trace SDK Service events";
           }
           enum "snmp" {
             description "Trace snmp events";
           }
           enum "system" {
             description "Trace services redundancy system events";
           }
           enum "opcmd" {
             description "Trace operational command events";
           }
           enum "state-machine" {
             description "Trace finite-state-machine events";
           }
           enum "kcom" {
             description "Trace KCOM events";
           }
           enum "database" {
             description "Trace database events";
           }
           enum "swithover" {
             description "Trace switchover events";
           }
           enum "stateful-sync" {
             description "Trace stateful-sync related events";
           }
           enum "redundancy-group" {
             description "Trace redundancy-group related events";
           }
           enum "all" {
             description "Trace everything";
           }
         }
       }
     }
   }
   grouping ssl-initiation-config {
     uses apply-advanced;
     list profile {
       key name;
       ordered-by user;
       description "SSL client profile";
       leaf name {
         description "Profile identifier";
         type string {
           length "1 .. 63";
         }
       }
       uses apply-advanced;
       leaf enable-flow-tracing {
         description "Enable flow tracing for the profile";
         type empty;
       }
       leaf protocol-version {
         description "Protocol SSL version accepted";
         default "all";
         type enumeration {
           enum "all" {
             description "TLS version 1 or TLS version 1.1 or TLS version 1.2";
           }
           enum "ssl3" {
             description "SSL version 3";
           }
           enum "tls1" {
             description "TLS version 1";
           }
           enum "tls11" {
             description "TLS version 1.1";
           }
           enum "tls12" {
             description "TLS version 1.2";
           }
         }
       }
       leaf preferred-ciphers {
         description "Select preferred ciphers";
         default "medium";
         type enumeration {
           enum "strong" {
             description "Use ciphers with key strength of 168-bits or greater";
           }
           enum "medium" {
             description "Use ciphers with key strength of 128-bits or greater";
           }
           enum "weak" {
             description "Use ciphers with key strength of 40-bits or greater";
           }
           enum "custom" {
             description "Configure custom cipher suite and order of preference";
             junos:must "(\".. custom-ciphers\")";
             junos:must-message "custom-ciphers must be configured for this choice";
           }
         }
       }
       leaf-list custom-ciphers {
         ordered-by user;
         description "Custom cipher list";
         type enumeration {
           enum "rsa-with-rc4-128-md5" {
             description "RSA, 128bit rc4, md5 hash";
           }
           enum "rsa-with-rc4-128-sha" {
             description "RSA, 128bit rc4, sha hash";
           }
           enum "rsa-with-des-cbc-sha" {
             description "RSA, des cbc, sha hash";
           }
           enum "rsa-with-3des-ede-cbc-sha" {
             description "RSA, 3des ede/cbc, sha hash";
           }
           enum "rsa-with-aes-128-cbc-sha" {
             description "RSA, 128 bit aes/cbc, sha hash";
             junos:must "((!(\".. .. preferred-ciphers custom\") || !(\".. .. protocol-version ssl3\")))";
             junos:must-message "protocol-version must be tls1 or all to use the aes cipher";
           }
           enum "rsa-with-aes-256-cbc-sha" {
             description "RSA, 256 bit aes/cbc, sha hash";
             junos:must "((!(\".. .. preferred-ciphers custom\") || !(\".. .. protocol-version ssl3\")))";
             junos:must-message "protocol-version must be tls1 or all to use the aes cipher";
           }
           enum "rsa-export-with-rc4-40-md5" {
             description "RSA-export, 40 bit rc4, md5 hash";
           }
           enum "rsa-export-with-des40-cbc-sha" {
             description "RSA-export, 40 bit des/cbc, sha hash";
           }
           enum "rsa-export1024-with-des-cbc-sha" {
             description "RSA 1024 bit export, des/cbc, sha hash";
           }
           enum "rsa-export1024-with-rc4-56-md5" {
             description "RSA 1024 bit export, 56 bit rc4, md5 hash";
           }
           enum "rsa-export1024-with-rc4-56-sha" {
             description "RSA 1024 bit export, 56 bit rc4, sha hash";
           }
           enum "rsa-with-aes-256-gcm-sha384" {
             description "RSA, 256 bit aes/gcm, sha384 hash ";
           }
           enum "rsa-with-aes-256-cbc-sha256" {
             description "RSA, 256 bit aes/cbc, sha256 hash";
           }
           enum "rsa-with-aes-128-gcm-sha256" {
             description "RSA, 128 bit aes/gcm, sha256 hash";
           }
           enum "rsa-with-aes-128-cbc-sha256" {
             description "RSA, 128 bit aes/cbc, sha256 hash";
           }
           enum "ecdhe-rsa-with-aes-256-gcm-sha384" {
             description "ECDHE/rsa, 256 bit aes/gcm, sha384 hash";
           }
           enum "ecdhe-rsa-with-aes-256-cbc-sha" {
             description "ECDHE/rsa, 256 bit aes/cbc, sha hash";
           }
           enum "ecdhe-rsa-with-aes-256-cbc-sha384" {
             description "ECDHE/rsa, 256 bit aes/cbc, sha384 hash";
           }
           enum "ecdhe-rsa-with-3des-ede-cbc-sha" {
             description "ECDHE/rsa, 3des ede/cbc, sha hash";
           }
           enum "ecdhe-rsa-with-aes-128-gcm-sha256" {
             description "ECDHE/rsa, 128 bit aes/gcm, sha256 hash";
           }
           enum "ecdhe-rsa-with-aes-128-cbc-sha" {
             description "ECDHE/rsa, 128 bit aes/cbc, sha hash";
           }
           enum "ecdhe-rsa-with-aes-128-cbc-sha256" {
             description "ECDHE/rsa, 128 bit aes/cbc, sha256 hash";
           }
           enum "ecdhe-ecdsa-with-aes-256-gcm-sha384" {
             description "ECDHE,ECDSA, 256 bit aes/gcm, sha384 hash";
           }
           enum "ecdhe-ecdsa-with-aes-256-cbc-sha" {
             description "ECDHE,ECDSA, 256 bit aes/cbc, sha hash";
           }
           enum "ecdhe-ecdsa-with-aes-256-cbc-sha384" {
             description "ECDHE,ECDSA, 256 bit aes/cbc, sha384 hash";
           }
           enum "ecdhe-ecdsa-with-aes-128-gcm-sha256" {
             description "ECDHE,ECDSA, 128 bit aes/gcm, sha256 hash";
           }
           enum "ecdhe-ecdsa-with-aes-128-cbc-sha" {
             description "ECDHE,ECDSA, 128 bit aes/cbc, sha hash";
           }
           enum "ecdhe-ecdsa-with-aes-128-cbc-sha256" {
             description "ECDHE,ECDSA, 128 bit aes/cbc, sha256 hash";
           }
           enum "ecdhe-ecdsa-with-3des-ede-cbc-sha" {
             description "ECDHE,ECDSA, 3des ede/cbc, sha hash";
           }
         }
         max-elements 64;
       }
       leaf enable-session-cache {
         description "Enable SSL session cache";
         type empty;
       }
       leaf-list trusted-ca {
         ordered-by user;
         description "List of trusted certificate authority profiles";
         type string;
         max-elements 1024;
       }
       leaf client-certificate {
         description "Local certificate identifier";
         type string {
           junos:posix-pattern "^.{1,32}$";
           junos:pattern-message "Must be string of 32 characters or less";
         }
       }
       container actions {
         description "Traffic related actions";
         uses apply-advanced;
         leaf ignore-server-auth-failure {
           description "Ignore server authentication failure";
           type empty;
         }
         container crl {
           description "Certificate Revocation actions.";
           leaf disable {
             description "Disable CRL validation.";
             type empty;
           }
           leaf if-not-present {
             description "Action if CRL information is not present.";
             default "allow";
             type enumeration {
               enum "allow" {
                 description "Allow session if CRL information is not present.";
               }
               enum "drop" {
                 description "Drop session if CRL information is not present.";
               }
             }
           }
           leaf ignore-hold-instruction-code {
             description "Ignore 'Hold Instruction Code' present in the CRL entry.";
             type empty;
           }
         }
         leaf unsupported-cipher-on-hw {
           description "Unsupported cipher processing on hardware mode";
           default "drop";
           type enumeration {
             enum "drop" {
               description "Drop session if cipher isn't supported on hardware mode";
             }
             enum "software-inspection" {
               description "Allow session in software mode";
             }
           }
         }
       }
     }
   }
   grouping ssl-proxy-config {
     uses apply-advanced;
     container global-config {
       description "Global proxy configuration";
       uses apply-advanced;
       leaf session-cache-timeout {
         description "Session cache timeout";
         units "seconds";
         type union {
           type string {
             pattern "<.*>|$.*";
           }
           type uint32 {
             range "300 .. 3600";
           }
         }
       }
       leaf disable-cert-cache {
         description "Disable proxy mode certificate cache";
         type empty;
       }
       leaf certificate-cache-timeout {
         description "Certificate cache timeout";
         units "seconds";
         type union {
           type string {
             pattern "<.*>|$.*";
           }
           type uint32 {
             range "300 .. 3600";
           }
         }
       }
       leaf invalidate-cache-on-crl-update {
         description "Invalidate certificate cache on crl update";
         type empty;
       }
     }
     list profile {
       key name;
       ordered-by user;
       description "SSL Proxy profile";
       leaf name {
         description "Profile identifier";
         type string {
           length "1 .. 63";
         }
       }
       uses apply-advanced;
       leaf enable-flow-tracing {
         description "Enable flow tracing for the profile";
         type empty;
       }
       leaf preferred-ciphers {
         description "Select preferred ciphers";
         default "medium";
         type enumeration {
           enum "strong" {
             description "Use ciphers with key strength of 168-bits or greater";
           }
           enum "medium" {
             description "Use ciphers with key strength of 128-bits or greater";
           }
           enum "weak" {
             description "Use ciphers with key strength of 40-bits or greater";
           }
           enum "custom" {
             description "Configure custom cipher suite and order of preference";
             junos:must "(\".. custom-ciphers\")";
             junos:must-message "custom-ciphers must be configured for this choice";
           }
         }
       }
       leaf-list custom-ciphers {
         ordered-by user;
         description "Custom cipher list";
         type enumeration {
           enum "rsa-with-rc4-128-md5" {
             description "RSA, 128bit rc4, md5 hash";
           }
           enum "rsa-with-rc4-128-sha" {
             description "RSA, 128bit rc4, sha hash";
           }
           enum "rsa-with-des-cbc-sha" {
             description "RSA, des cbc, sha hash";
           }
           enum "rsa-with-3des-ede-cbc-sha" {
             description "RSA, 3des ede/cbc, sha hash";
           }
           enum "rsa-with-aes-128-cbc-sha" {
             description "RSA, 128 bit aes/cbc, sha hash";
             junos:must "((!(\".. .. preferred-ciphers custom\") || !(\".. .. protocol-version ssl3\")))";
             junos:must-message "protocol-version must be tls1 or all to use the aes cipher";
           }
           enum "rsa-with-aes-256-cbc-sha" {
             description "RSA, 256 bit aes/cbc, sha hash";
             junos:must "((!(\".. .. preferred-ciphers custom\") || !(\".. .. protocol-version ssl3\")))";
             junos:must-message "protocol-version must be tls1 or all to use the aes cipher";
           }
           enum "rsa-export-with-rc4-40-md5" {
             description "RSA-export, 40 bit rc4, md5 hash";
           }
           enum "rsa-export-with-des40-cbc-sha" {
             description "RSA-export, 40 bit des/cbc, sha hash";
           }
           enum "rsa-export1024-with-des-cbc-sha" {
             description "RSA 1024 bit export, des/cbc, sha hash";
           }
           enum "rsa-export1024-with-rc4-56-md5" {
             description "RSA 1024 bit export, 56 bit rc4, md5 hash";
           }
           enum "rsa-export1024-with-rc4-56-sha" {
             description "RSA 1024 bit export, 56 bit rc4, sha hash";
           }
           enum "rsa-with-aes-256-gcm-sha384" {
             description "RSA, 256 bit aes/gcm, sha384 hash ";
           }
           enum "rsa-with-aes-256-cbc-sha256" {
             description "RSA, 256 bit aes/cbc, sha256 hash";
           }
           enum "rsa-with-aes-128-gcm-sha256" {
             description "RSA, 128 bit aes/gcm, sha256 hash";
           }
           enum "rsa-with-aes-128-cbc-sha256" {
             description "RSA, 128 bit aes/cbc, sha256 hash";
           }
           enum "ecdhe-rsa-with-aes-256-gcm-sha384" {
             description "ECDHE/rsa, 256 bit aes/gcm, sha384 hash";
           }
           enum "ecdhe-rsa-with-aes-256-cbc-sha" {
             description "ECDHE/rsa, 256 bit aes/cbc, sha hash";
           }
           enum "ecdhe-rsa-with-aes-256-cbc-sha384" {
             description "ECDHE/rsa, 256 bit aes/cbc, sha384 hash";
           }
           enum "ecdhe-rsa-with-3des-ede-cbc-sha" {
             description "ECDHE/rsa, 3des ede/cbc, sha hash";
           }
           enum "ecdhe-rsa-with-aes-128-gcm-sha256" {
             description "ECDHE/rsa, 128 bit aes/gcm, sha256 hash";
           }
           enum "ecdhe-rsa-with-aes-128-cbc-sha" {
             description "ECDHE/rsa, 128 bit aes/cbc, sha hash";
           }
           enum "ecdhe-rsa-with-aes-128-cbc-sha256" {
             description "ECDHE/rsa, 128 bit aes/cbc, sha256 hash";
           }
           enum "ecdhe-ecdsa-with-aes-256-gcm-sha384" {
             description "ECDHE,ECDSA, 256 bit aes/gcm, sha384 hash";
           }
           enum "ecdhe-ecdsa-with-aes-256-cbc-sha" {
             description "ECDHE,ECDSA, 256 bit aes/cbc, sha hash";
           }
           enum "ecdhe-ecdsa-with-aes-256-cbc-sha384" {
             description "ECDHE,ECDSA, 256 bit aes/cbc, sha384 hash";
           }
           enum "ecdhe-ecdsa-with-aes-128-gcm-sha256" {
             description "ECDHE,ECDSA, 128 bit aes/gcm, sha256 hash";
           }
           enum "ecdhe-ecdsa-with-aes-128-cbc-sha" {
             description "ECDHE,ECDSA, 128 bit aes/cbc, sha hash";
           }
           enum "ecdhe-ecdsa-with-aes-128-cbc-sha256" {
             description "ECDHE,ECDSA, 128 bit aes/cbc, sha256 hash";
           }
           enum "ecdhe-ecdsa-with-3des-ede-cbc-sha" {
             description "ECDHE,ECDSA, 3des ede/cbc, sha hash";
           }
         }
         max-elements 64;
       }
       leaf-list trusted-ca {
         ordered-by user;
         description "List of trusted certificate authority profiles";
         type string;
         max-elements 1024;
       }
       choice certificate {
         case case_1 {
           leaf-list root-ca {
             ordered-by user;
             description "Root certificate for interdicting server certificates in proxy mode";
             type string;
             max-elements 2;
           }
         }
         case case_2 {
           leaf-list server-certificate {
             ordered-by user;
             description "Local certificate identifier";
             junos:must "(!(\"security idp sensor-configuration ssl-inspection sessions\"))";
             junos:must-message "IDP SSL Inspection should not be configured with ssl proxy profile <> server-certificate";
             junos:must "(!(\".. actions crl\"))";
             junos:must-message "actions crl <>  should not be configured with server- certificate";
             junos:must "(!(\".. actions ignore-server-auth-failure\"))";
             junos:must-message "ignore-server-auth-failure  should not be configured with server-certificate";
             junos:must "(!(\".. trusted-ca\"))";
             junos:must-message "trusted-ca <>  should not be configured with server-certificate";
             type string;
             max-elements 1024;
           }
         }
       }
       container mirror-decrypt-traffic {
         description "Configure mirror interface and Destination MAC address";
         uses apply-advanced;
         leaf interface {
           description "Interface on which SSL decrypted traffic is mirrored";
           junos:must "(\"interfaces $$\")";
           junos:must-message "Interface must be defined";
           type union {
             type jt:interface-name;
             type string {
               pattern "<.*>|$.*";
             }
           }
         }
         leaf destination-mac-address {
           description "Mac address of host/server to which decrypted traffic is mirrored";
           type jt:mac-addr;
         }
         leaf only-after-security-policies-enforcement {
           description "Enables decrypted Traffic mirroring after policy enforcement";
           type empty;
         }
       }
       leaf-list whitelist {
         ordered-by user;
         description "Addresses exempted from SSL Proxy ";
         type string;
       }
       leaf-list whitelist-url-categories {
         ordered-by user;
         type string;
       }
       container actions {
         description "Logging and traffic related actions";
         uses apply-advanced;
         leaf ignore-server-auth-failure {
           description "Ignore server authentication failure";
           type empty;
         }
         container log {
           presence "enable log";
           description "Logging actions";
           leaf all {
             description "Log all events";
             type empty;
           }
           leaf sessions-dropped {
             description "Log only ssl session drop events";
             type empty;
           }
           leaf sessions-allowed {
             description "Log ssl session allow events after an error";
             type empty;
           }
           leaf sessions-ignored {
             description "Log  session ignore events ";
             type empty;
           }
           leaf sessions-whitelisted {
             description "Log ssl session whitelist events ";
             type empty;
           }
           leaf errors {
             description "Log all error events ";
             type empty;
           }
           leaf warning {
             description "Log all warning events ";
             type empty;
           }
           leaf info {
             description "Log all information events ";
             type empty;
           }
         }
         container crl {
           description "Certificate Revocation actions.";
           leaf disable {
             description "Disable CRL validation.";
             type empty;
           }
           leaf if-not-present {
             description "Action if CRL information is not present.";
             default "allow";
             type enumeration {
               enum "allow" {
                 description "Allow session if CRL information is not present.";
               }
               enum "drop" {
                 description "Drop session if CRL information is not present.";
               }
             }
           }
           leaf ignore-hold-instruction-code {
             description "Ignore 'Hold Instruction Code' present in the CRL entry.";
             type empty;
           }
         }
         leaf renegotiation {
           description "Renegotiation options";
           default "allow-secure";
           type enumeration {
             enum "allow" {
               description "Allow secure as well as non secure renegotiation";
             }
             enum "allow-secure" {
               description "Allow secure negotiation only (RFC 5746)";
             }
             enum "drop" {
               description "Drop session on renegotiation request";
             }
           }
         }
         leaf disable-session-resumption {
           description "Disable session resumption";
           type empty;
         }
         leaf unsupported-cipher-on-hw {
           description "Unsupported cipher processing on hardware mode";
           default "drop";
           type enumeration {
             enum "drop" {
               description "Drop session if cipher isn't supported on hardware mode";
             }
             enum "software-inspection" {
               description "Allow session in software mode";
             }
           }
         }
       }
     }
   }
   grouping ssl-termination-config {
     uses apply-advanced;
     list profile {
       key name;
       ordered-by user;
       description "SSL server profile";
       leaf name {
         description "Profile identifier";
         type string {
           length "1 .. 63";
         }
       }
       uses apply-advanced;
       leaf enable-flow-tracing {
         description "Enable flow tracing for the profile";
         type empty;
       }
       leaf protocol-version {
         description "Protocol SSL version accepted";
         default "all";
         type enumeration {
           enum "all" {
             description "TLS version 1 or TLS version 1.1 or TLS version 1.2";
           }
           enum "ssl3" {
             description "SSL version 3";
           }
           enum "tls1" {
             description "TLS version 1";
           }
           enum "tls11" {
             description "TLS version 1.1";
           }
           enum "tls12" {
             description "TLS version 1.2";
           }
         }
       }
       leaf preferred-ciphers {
         description "Select preferred ciphers";
         default "medium";
         type enumeration {
           enum "strong" {
             description "Use ciphers with key strength of 168-bits or greater";
           }
           enum "medium" {
             description "Use ciphers with key strength of 128-bits or greater";
           }
           enum "weak" {
             description "Use ciphers with key strength of 40-bits or greater";
           }
           enum "custom" {
             description "Configure custom cipher suite and order of preference";
             junos:must "(\".. custom-ciphers\")";
             junos:must-message "custom-ciphers must be configured for this choice";
           }
         }
       }
       leaf-list custom-ciphers {
         ordered-by user;
         description "Custom cipher list";
         type enumeration {
           enum "rsa-with-rc4-128-md5" {
             description "RSA, 128bit rc4, md5 hash";
           }
           enum "rsa-with-rc4-128-sha" {
             description "RSA, 128bit rc4, sha hash";
           }
           enum "rsa-with-des-cbc-sha" {
             description "RSA, des cbc, sha hash";
           }
           enum "rsa-with-3des-ede-cbc-sha" {
             description "RSA, 3des ede/cbc, sha hash";
           }
           enum "rsa-with-aes-128-cbc-sha" {
             description "RSA, 128 bit aes/cbc, sha hash";
             junos:must "((!(\".. .. preferred-ciphers custom\") || !(\".. .. protocol-version ssl3\")))";
             junos:must-message "protocol-version must be tls1 or all to use the aes cipher";
           }
           enum "rsa-with-aes-256-cbc-sha" {
             description "RSA, 256 bit aes/cbc, sha hash";
             junos:must "((!(\".. .. preferred-ciphers custom\") || !(\".. .. protocol-version ssl3\")))";
             junos:must-message "protocol-version must be tls1 or all to use the aes cipher";
           }
           enum "rsa-export-with-rc4-40-md5" {
             description "RSA-export, 40 bit rc4, md5 hash";
           }
           enum "rsa-export-with-des40-cbc-sha" {
             description "RSA-export, 40 bit des/cbc, sha hash";
           }
           enum "rsa-export1024-with-des-cbc-sha" {
             description "RSA 1024 bit export, des/cbc, sha hash";
           }
           enum "rsa-export1024-with-rc4-56-md5" {
             description "RSA 1024 bit export, 56 bit rc4, md5 hash";
           }
           enum "rsa-export1024-with-rc4-56-sha" {
             description "RSA 1024 bit export, 56 bit rc4, sha hash";
           }
           enum "rsa-with-aes-256-gcm-sha384" {
             description "RSA, 256 bit aes/gcm, sha384 hash ";
           }
           enum "rsa-with-aes-256-cbc-sha256" {
             description "RSA, 256 bit aes/cbc, sha256 hash";
           }
           enum "rsa-with-aes-128-gcm-sha256" {
             description "RSA, 128 bit aes/gcm, sha256 hash";
           }
           enum "rsa-with-aes-128-cbc-sha256" {
             description "RSA, 128 bit aes/cbc, sha256 hash";
           }
           enum "ecdhe-rsa-with-aes-256-gcm-sha384" {
             description "ECDHE/rsa, 256 bit aes/gcm, sha384 hash";
           }
           enum "ecdhe-rsa-with-aes-256-cbc-sha" {
             description "ECDHE/rsa, 256 bit aes/cbc, sha hash";
           }
           enum "ecdhe-rsa-with-aes-256-cbc-sha384" {
             description "ECDHE/rsa, 256 bit aes/cbc, sha384 hash";
           }
           enum "ecdhe-rsa-with-3des-ede-cbc-sha" {
             description "ECDHE/rsa, 3des ede/cbc, sha hash";
           }
           enum "ecdhe-rsa-with-aes-128-gcm-sha256" {
             description "ECDHE/rsa, 128 bit aes/gcm, sha256 hash";
           }
           enum "ecdhe-rsa-with-aes-128-cbc-sha" {
             description "ECDHE/rsa, 128 bit aes/cbc, sha hash";
           }
           enum "ecdhe-rsa-with-aes-128-cbc-sha256" {
             description "ECDHE/rsa, 128 bit aes/cbc, sha256 hash";
           }
           enum "ecdhe-ecdsa-with-aes-256-gcm-sha384" {
             description "ECDHE,ECDSA, 256 bit aes/gcm, sha384 hash";
           }
           enum "ecdhe-ecdsa-with-aes-256-cbc-sha" {
             description "ECDHE,ECDSA, 256 bit aes/cbc, sha hash";
           }
           enum "ecdhe-ecdsa-with-aes-256-cbc-sha384" {
             description "ECDHE,ECDSA, 256 bit aes/cbc, sha384 hash";
           }
           enum "ecdhe-ecdsa-with-aes-128-gcm-sha256" {
             description "ECDHE,ECDSA, 128 bit aes/gcm, sha256 hash";
           }
           enum "ecdhe-ecdsa-with-aes-128-cbc-sha" {
             description "ECDHE,ECDSA, 128 bit aes/cbc, sha hash";
           }
           enum "ecdhe-ecdsa-with-aes-128-cbc-sha256" {
             description "ECDHE,ECDSA, 128 bit aes/cbc, sha256 hash";
           }
           enum "ecdhe-ecdsa-with-3des-ede-cbc-sha" {
             description "ECDHE,ECDSA, 3des ede/cbc, sha hash";
           }
         }
         max-elements 64;
       }
       leaf enable-session-cache {
         description "Enable SSL session cache";
         type empty;
       }
       leaf server-certificate {
         description "Local certificate identifier";
         type string {
           junos:posix-pattern "^.{1,32}$";
           junos:pattern-message "Must be string of 32 characters or less";
         }
       }
     }
   }
   grouping ssl-traceoptions {
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "brief";
       type enumeration {
         enum "brief" {
           description "Brief debugging output";
         }
         enum "detail" {
           description "Detailed debugging output";
         }
         enum "extensive" {
           description "Extensive debugging output";
         }
         enum "verbose" {
           description "Verbose debugging output";
         }
       }
     }
     list flag {
       key name;
       ordered-by user;
       description "Tracing parameters";
       leaf name {
         type enumeration {
           enum "cli-configuration" {
             description "Trace CLI configuration events";
           }
           enum "termination" {
             description "Trace termination service events";
           }
           enum "initiation" {
             description "Trace initiation service events";
           }
           enum "proxy" {
             description "Trace proxy service events";
           }
           enum "selected-profile" {
             description "Trace events for profiles with enable-flow-tracing set";
           }
           enum "all" {
             description "Trace everything";
           }
         }
       }
     }
   }
   grouping sw-rule-set-object {
     leaf name {
       description "Define Rule Set name";
       type string {
         length "1 .. 63";
         junos:posix-pattern "^[[:alnum:]][[:alnum:]_-]*$";
         junos:pattern-message "Must be a string beginning with a number or letter and consisting of letters, numbers, dashes and underscores.";
       }
     }
     uses apply-advanced;
     list rule {
       key name;
       ordered-by user;
       description "Define a rule term";
       leaf name {
         description "Rule name";
         type string {
           length "1 .. 63";
           junos:posix-pattern "^[[:alnum:]][[:alnum:]_-]*$";
           junos:pattern-message "Must be a string beginning with a number or letter and consisting of letters, numbers, dashes and underscores.";
         }
       }
       uses apply-advanced;
       container then {
         description "Action to take if the condition is matched";
         uses apply-advanced;
         choice designation {
           case case_1 {
             leaf v6rd {
               description "Apply 6rd softwire";
               type string {
                 length "1 .. 63";
                 junos:posix-pattern "^[[:alnum:]][[:alnum:]_-]*$";
                 junos:pattern-message "Must be a string beginning with a number or letter and consisting of letters, numbers, dashes and underscores.";
               }
             }
           }
         }
       }
     }
     leaf match-direction {
       description "Match direction";
       type enumeration {
         enum "input" {
           description "Match on input to interface";
         }
         enum "output" {
           description "Match on output from interface";
         }
       }
     }
   }
   grouping tunnel_interface_type {
     description "One or more tunnel interfaces on which to configure flow-tap service";
     leaf name {
       description "Tunnel Interface name";
       junos:must "(!(\"services dynamic-flow-capture\"))";
       junos:must-message "Dynamic flow capture cannot be configured when flow-tap is configured";
       junos:must "(!(\"interfaces $$-IFL family inet filter\"))";
       junos:must-message "Tunnel Interface assigned for Radius-Flow-Tap cannot be configured with firewall filter";
       junos:must "(\"interfaces $$-IFL family inet\")";
       junos:must-message "Interface with family inet must be defined in the [edit interfaces] hierarchy";
       type union {
         type jt:interface-unit;
         type string {
           pattern "<.*>|$.*";
         }
       }
     }
     uses apply-advanced;
   }
   grouping twamp-authentication-key-chain {
     leaf name {
       description "Name of authentication key chain";
       type string {
         junos:posix-pattern "^.{1,32}$";
         junos:pattern-message "Must be string of 32 characters or less";
       }
     }
     uses apply-advanced;
     list key-id {
       key name;
       description "Authentication element configuration";
       leaf name {
         description "Authentication element identifier";
         type string {
           length "1 .. 80";
         }
       }
       uses apply-advanced;
       leaf secret {
         description "Authentication key";
         type string {
           length "1 .. 256";
         }
       }
     }
   }
   grouping urlf-profile-object {
     leaf name {
       description "Name of profile";
       type string {
         length "1 .. 64";
         junos:posix-pattern "^[[:alnum:]][[:alnum:]_-]*$";
         junos:pattern-message "Must be a string beginning with a number or letter and consisting of letters, numbers, dashes and underscores.";
       }
     }
     uses apply-advanced;
     leaf url-filter-database {
       description "Full path of the file";
       junos:must "(!(\".. security-intelligence-policy\"))";
       junos:must-message "Not applicable for security intelligence based profiles";
       type string {
         length "1 .. 1024";
       }
     }
     leaf global-dns-filter-stats-log-timer {
       description "Global DNS filtering statistics log timer in minutes";
       default "5";
       units "minutes";
       junos:must "(!(\".. security-intelligence-policy\"))";
       junos:must-message "Not applicable for security intelligence based profiles";
       type union {
         type string {
           pattern "<.*>|$.*";
         }
         type uint32 {
           range "0 .. 60";
         }
       }
     }
     container security-intelligence-policy {
       presence "enable security-intelligence-policy";
       description "Use the database supplied by security intelligence for blacklisted traffic.";
       uses apply-advanced;
       leaf file-type {
         type enumeration {
           enum "txt" {
             description "Policy DB is a text file";
           }
           enum "json" {
             description "Policy DB is in json format";
           }
         }
       }
       list threat-level {
         key name;
         ordered-by user;
         description "Define a URL filtering threat level";
         max-elements 10;
         uses threat-level-object;
       }
     }
     container dns-filter {
       description "DNS filter information";
       junos:must "(!(\".. security-intelligence-policy\"))";
       junos:must-message "Not applicable for security intelligence based profiles";
       uses dns-filter-object;
       junos:must "(!(\".. security-intelligence-policy\"))";
       junos:must-message "Not applicable for security intelligence based profiles";
     }
     list url-filter-template {
       key name;
       ordered-by user;
       description "URL filter template";
       max-elements 32;
       uses urlf-template-object;
     }
     list dns-filter-template {
       key name;
       ordered-by user;
       description "DNS filter template";
       max-elements 32;
       junos:must "(!(\".. security-intelligence-policy\"))";
       junos:must-message "Not applicable for security intelligence based profiles";
       uses dnsf-template-object;
     }
   }
   grouping dns-filter-object {
     uses apply-advanced;
     leaf database-file {
       description "Full path of the DNS filter database file";
       type string {
         length "1 .. 1024";
       }
     }
     leaf-list dns-server {
       ordered-by user;
       description "One or more DNS servers addresses";
       type jt:ipaddr;
       max-elements 20;
     }
     container hash-key {
       description "Define hash key for domains key";
       choice key-choice {
         case case_1 {
           leaf ascii-text {
             description "Format as text";
             type string {
               length "1 .. 255";
             }
           }
         }
         case case_2 {
           leaf hexadecimal {
             description "Format as hexadecimal";
             type string {
               length "1 .. 255";
               junos:posix-pattern "^[[:xdigit:]]+$";
               junos:pattern-message "Must be hexadecimal digits (0-9, a-f, A-F)";
             }
           }
         }
       }
     }
     leaf hash-method {
       description "Define authentication algorithm";
       junos:must "(\".. hash-key\")";
       junos:must-message "hash-key is mandatory";
       type enumeration {
         enum "hmac-sha2-256" {
           description "HMAC-SHA2-256 authentication algorithm";
         }
       }
     }
     leaf statistics-log-timer {
       description "DNS log timer in minutes";
       default "5";
       units "minutes";
       type union {
         type string {
           pattern "<.*>|$.*";
         }
         type uint32 {
           range "0 .. 60";
         }
       }
     }
     leaf dns-resp-ttl {
       description "TTL to be used in DNS response";
       default "1800";
       units "seconds";
       type union {
         type string {
           pattern "<.*>|$.*";
         }
         type uint32 {
           range "0 .. 3600";
         }
       }
     }
     leaf wildcarding-level {
       description "Wildcarding level for exact match";
       default "2";
       type union {
         type string {
           pattern "<.*>|$.*";
         }
         type uint32 {
           range "0 .. 10";
         }
       }
     }
   }
   grouping dnsf-template-object {
     leaf name {
       description "Name of template";
       type string {
         length "1 .. 64";
         junos:posix-pattern "^[[:alnum:]][[:alnum:]_-]*$";
         junos:pattern-message "Must be a string beginning with a number or letter and consisting of letters, numbers, dashes and underscores.";
       }
     }
     uses apply-advanced;
     container dns-filter {
       description "DNS filter information";
       uses dns-filter-object;
     }
     leaf-list client-interfaces {
       ordered-by user;
       description "Client facing interfaces on which the dns filtering is applied";
       type union {
         type jt:interface-unit;
         type string {
           pattern "<.*>|$.*";
         }
       }
       max-elements 64;
     }
     leaf-list server-interfaces {
       ordered-by user;
       description "Server facing interfaces to which traffic destined to";
       type union {
         type jt:interface-unit;
         type string {
           pattern "<.*>|$.*";
         }
       }
       max-elements 64;
     }
     leaf client-routing-instance {
       description "Routing instance name";
       type string;
     }
     leaf server-routing-instance {
       description "Routing instance name";
       type string;
     }
     list term {
       key name;
       ordered-by user;
       description "Define a DNS filtering term";
       max-elements 64;
       leaf name {
         description "Term name";
         type string {
           length "1 .. 64";
           junos:posix-pattern "^[[:alnum:]][[:alnum:]/.:_-]*$";
           junos:pattern-message "Must be a string beginning with a number or letter and consisting of letters, numbers, dashes, underscores, forward slashes, colons and dots.";
         }
       }
       uses apply-advanced;
       container from {
         description "Define match criteria";
         uses dnsf-match-object;
       }
       container then {
         presence "enable then";
         description "Action to take if the 'from' condition is matched";
         uses apply-advanced;
         choice dns-filter-action {
           case case_1 {
             leaf dns-sinkhole {
               description "DNS sinkhole";
               type empty;
             }
           }
         }
       }
     }
   }
   grouping dnsf-match-object {
     uses apply-advanced;
     leaf-list src-ip-prefix {
       ordered-by user;
       description "Source IP Prefix list specification";
       type jt:ipprefix;
       max-elements 64;
     }
   }
   grouping threat-level-object {
     leaf name {
       description "Threat level value";
       type union {
         type string {
           pattern "<.*>|$.*";
         }
         type uint32 {
           range "1 .. 10";
         }
       }
     }
     uses apply-advanced;
     container threat-action {
       presence "enable threat-action";
       description "Action to be taken for the given threat level ";
       uses apply-advanced;
       choice secintl-action {
         case case_1 {
           leaf accept {
             description "Accept";
             type empty;
           }
         }
         case case_2 {
           leaf log {
             description "Log";
             type empty;
           }
         }
         case case_3 {
           leaf drop {
             description "Drop";
             type empty;
           }
         }
         case case_4 {
           leaf drop-and-log {
             description "Drop and log";
             type empty;
           }
         }
       }
     }
   }
   grouping urlf-template-object {
     leaf name {
       description "Name of template";
       type string {
         length "1 .. 64";
         junos:posix-pattern "^[[:alnum:]][[:alnum:]_-]*$";
         junos:pattern-message "Must be a string beginning with a number or letter and consisting of letters, numbers, dashes and underscores.";
       }
     }
     uses apply-advanced;
     leaf-list client-interfaces {
       ordered-by user;
       description "Client facing interfaces on which the url filtering is applied";
       type union {
         type jt:interface-unit;
         type string {
           pattern "<.*>|$.*";
         }
       }
       max-elements 64;
     }
     leaf-list server-interfaces {
       ordered-by user;
       description "Server facing interfaces to which traffic destined to";
       junos:must "(!(\".. ..  security-intelligence-policy\"))";
       junos:must-message "Not applicable for security intelligence based profiles";
       type union {
         type jt:interface-unit;
         type string {
           pattern "<.*>|$.*";
         }
       }
       max-elements 64;
     }
     leaf dns-source-interface {
       description "Interface on which the DNS queries are originated";
       junos:must "(!(\".. ..  security-intelligence-policy\"))";
       junos:must-message "Not applicable for security intelligence based profiles";
       type union {
         type jt:interface-unit;
         type string {
           pattern "<.*>|$.*";
         }
       }
     }
     leaf dns-routing-instance {
       description "Routing instance for DNS queries";
       junos:must "(!(\".. ..  security-intelligence-policy\"))";
       junos:must-message "Not applicable for security intelligence based profiles";
       type string;
     }
     leaf client-routing-instance {
       description "Routing instance name";
       type string;
     }
     leaf-list dns-server {
       ordered-by user;
       description "One or more DNS servers addresses";
       junos:must "(!(\".. ..  security-intelligence-policy\"))";
       junos:must-message "DNS server must not be configured for security intelligence based profiles";
       type jt:ipaddr;
       max-elements 2;
     }
     leaf dns-resolution-interval {
       description "DNS resolution timer in minutes";
       default "1440";
       units "minutes";
       junos:must "(!(\".. ..  security-intelligence-policy\"))";
       junos:must-message "Not applicable for security intelligence based profiles";
       type union {
         type string {
           pattern "<.*>|$.*";
         }
         type uint32 {
           range "60 .. 1440";
         }
       }
     }
     leaf dns-retries {
       description "DNS resolution attempts";
       default "3";
       junos:must "(!(\".. ..  security-intelligence-policy\"))";
       junos:must-message "Not applicable for security intelligence based profiles";
       type union {
         type string {
           pattern "<.*>|$.*";
         }
         type uint32 {
           range "1 .. 5";
         }
       }
     }
     leaf dns-resolution-rate {
       description "DNS resolution rate per chunk interval";
       default "50";
       junos:must "(!(\".. ..  security-intelligence-policy\"))";
       junos:must-message "Not applicable for security intelligence based profiles";
       type union {
         type string {
           pattern "<.*>|$.*";
         }
         type uint32 {
           range "50 .. 100";
         }
       }
     }
     leaf url-filter-database {
       description "Full path of the file";
       junos:must "(!(\".. ..  security-intelligence-policy\"))";
       junos:must-message "Not applicable for security intelligence based profiles";
       type string {
         length "1 .. 1024";
       }
     }
     leaf disable-url-ip-filtering {
       description "Disable filtering of IPs belonging to blocklisted domains";
       junos:must "(!(\".. ..  security-intelligence-policy\"))";
       junos:must-message "Not applicable for security intelligence based profiles";
       type empty;
     }
     list term {
       key name;
       ordered-by user;
       description "Define a url filtering term";
       max-elements 8;
       leaf name {
         description "Term name";
         type string {
           length "1 .. 64";
           junos:posix-pattern "^[[:alnum:]][[:alnum:]/.:_-]*$";
           junos:pattern-message "Must be a string beginning with a number or letter and consisting of letters, numbers, dashes, underscores, forward slashes, colons and dots.";
         }
       }
       uses apply-advanced;
       container from {
         description "Define match criteria";
         uses urlf-match-object;
       }
       container then {
         presence "enable then";
         description "Action to take if the 'from' condition is matched";
         uses apply-advanced;
         choice url-filter-action {
           case case_1 {
             leaf redirect-url {
               description "Redirect URL";
               type string {
                 length "1 .. 1024";
               }
             }
           }
           case case_2 {
             leaf custom-page {
               description "Custome page string";
               type string {
                 length "1 .. 128";
               }
             }
           }
           case case_3 {
             leaf http-status-code {
               description "HTTP status code value";
               type union {
                 type string {
                   pattern "<.*>|$.*";
                 }
                 type uint16 {
                   range "400 .. 599";
                 }
               }
             }
           }
           case case_4 {
             leaf tcp-reset {
               description "TCP Reset";
               type empty;
             }
           }
           case case_5 {
             leaf accept {
               description "Accept";
               type empty;
             }
           }
         }
       }
     }
   }
   grouping urlf-match-object {
     uses apply-advanced;
     leaf-list src-ip-prefix {
       ordered-by user;
       description "Source IP Prefix list specification";
       type jt:ipprefix;
       max-elements 10;
     }
     leaf-list dest-ports {
       ordered-by user;
       description " Destination port list specification";
       type union {
         type string {
           pattern "<.*>|$.*";
         }
         type uint16 {
           range "1 .. 65535";
         }
       }
       max-elements 10;
     }
   }
   grouping urlf-traceoptions-object {
     description "URL filtering trace options";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing flag parameters";
       leaf name {
         type enumeration {
           enum "normal" {
             description "Trace normal events";
           }
           enum "config" {
             description "Trace url filtering config events";
           }
           enum "dns" {
             description "Trace url filtering DNS crawler events";
           }
           enum "timer" {
             description "Trace url filtering timer events";
           }
           enum "connect" {
             description "Trace url filtering ipc events";
           }
           enum "parse" {
             description "Trace url filtering parse events";
           }
           enum "statistics" {
             description "Trace url filtering statistics events";
           }
           enum "system" {
             description "Trace url filtering system events";
           }
           enum "operational-commands" {
             description "Trace url filtering show events";
           }
           enum "filter" {
             description "Trace url filtering filter programming events";
           }
           enum "gencfg" {
             description "Trace url filtering gencfg events";
           }
           enum "routing" {
             description "Trace url filtering route programming events";
           }
           enum "snmp" {
             description "Trace url filtering snmp events";
           }
           enum "all" {
             description "Trace everything";
           }
         }
       }
     }
   }
   grouping user-group-mapping-type {
     uses apply-advanced;
     container ldap {
       description "LDAP";
       uses apply-advanced;
       leaf authentication-algorithm {
         description "Authentication-algorithm";
         type enumeration {
           enum "simple" {
             description "Simple authentication";
           }
         }
       }
       leaf ssl {
         description "SSL";
         type empty;
       }
       leaf base {
         description "Base distinguished name";
         type string {
           length "1 .. 128";
         }
       }
       container user {
         description "User name";
         uses apply-advanced;
         leaf user-name {
           description "User name";
           type string {
             length "1 .. 64";
             junos:posix-pattern "^[[:alnum:]._-]+$|^\\\\*$";
             junos:pattern-message "Must be a string consisting of letters, numbers, dashes, underscores and dots";
           }
         }
         leaf password {
           description "Password string";
           type string {
             length "1 .. 128";
           }
         }
       }
       list address {
         key name;
         ordered-by user;
         description "Address of LDAP server";
         leaf name {
           description "Address";
           type jt:ipaddr;
         }
         uses apply-advanced;
         leaf port {
           description "LDAP port";
           type union {
             type string {
               pattern "<.*>|$.*";
             }
             type uint16 {
               range "1 .. 65535";
             }
           }
         }
       }
     }
   }
   grouping version-ipfix-template {
     description "One or more version-ipfix  templates for flow monitoring";
     leaf name {
       description "Name of template";
       type string;
     }
     uses apply-advanced;
     leaf flow-active-timeout {
       description "Interval after which active flow is exported";
       default "60";
       type union {
         type string {
           pattern "<.*>|$.*";
         }
         type uint32 {
           range "10 .. 600";
         }
       }
     }
     leaf flow-inactive-timeout {
       description "Period of inactivity that marks a flow inactive";
       default "60";
       type union {
         type string {
           pattern "<.*>|$.*";
         }
         type uint32 {
           range "10 .. 600";
         }
       }
     }
     leaf template-id {
       description "Template id";
       type union {
         type string {
           pattern "<.*>|$.*";
         }
         type uint32 {
           range "1024 .. 65535";
         }
       }
     }
     leaf option-template-id {
       description "Options template id";
       type union {
         type string {
           pattern "<.*>|$.*";
         }
         type uint32 {
           range "1024 .. 65535";
         }
       }
     }
     leaf observation-domain-id {
       description "Observation Domain Id";
       default "0";
       type union {
         type string {
           pattern "<.*>|$.*";
         }
         type uint32 {
           range "0 .. 255";
         }
       }
     }
     container nexthop-learning {
       presence "enable nexthop-learning";
       description "Nexthop learning parameter. Valid ONLY for INLINE-JFLOW";
       uses apply-advanced;
       choice enable-disable {
         case case_1 {
           leaf enable {
             description "Enable nexthop learning";
             type empty;
           }
         }
         case case_2 {
           leaf disable {
             description "Disable nexthop learning";
             type empty;
           }
         }
       }
     }
     container template-refresh-rate {
       presence "enable template-refresh-rate";
       description "Template refresh rate";
       uses apply-advanced;
       leaf packets {
         description "In number of packets";
         default "4800";
         type union {
           type string {
             pattern "<.*>|$.*";
           }
           type uint32 {
             range "1 .. 480000";
           }
         }
       }
       leaf seconds {
         description "In number of seconds";
         type union {
           type string {
             pattern "<.*>|$.*";
           }
           type uint32 {
             range "10 .. 600";
           }
         }
       }
     }
     container option-refresh-rate {
       presence "enable option-refresh-rate";
       description "Option template refresh rate";
       uses apply-advanced;
       leaf packets {
         description "In number of packets";
         default "4800";
         type union {
           type string {
             pattern "<.*>|$.*";
           }
           type uint32 {
             range "1 .. 480000";
           }
         }
       }
       leaf seconds {
         description "In number of seconds";
         type union {
           type string {
             pattern "<.*>|$.*";
           }
           type uint32 {
             range "10 .. 600";
           }
         }
       }
     }
     choice template-types {
       case case_1 {
       }
       case case_2 {
       }
       case case_3 {
       }
       case case_4 {
       }
       case case_5 {
       }
       case case_6 {
       }
     }
     container tunnel-observation {
       junos:must "((\".. ipv4-template\" || (\".. mpls-ipvx-template\" || \".. mpls-template\")))";
       junos:must-message "Tunnel observation must be configured only for ipv4,mpls and mpls-ipvx templates";
       description "Tunnel observation";
       uses apply-advanced;
       leaf ipv4 {
         description "IPv4";
         junos:must "(\".. .. mpls-template\")";
         junos:must-message "Tunnel observation must be set to ipv4 only for mpls template";
         type empty;
       }
       leaf ipv6 {
         description "IPv6";
         junos:must "(\".. .. mpls-template\")";
         junos:must-message "Tunnel observation must be set to ipv6 only for mpls template";
         type empty;
       }
     }
     container flow-key {
       description "Flow key for the template. Valid ONLY for INLINE-JFLOW";
       uses apply-advanced;
       leaf flow-direction {
         description "Include flow direction";
         type empty;
       }
       leaf vlan-id {
         description "Include vlan ID";
         type empty;
       }
       leaf output-interface {
         description "Include output interface";
         junos:must "((\".. .. vpls-template\" || \".. .. bridge-template\"))";
         junos:must-message "Flow-key output interafce must be configured for bridge/vpls template";
         type empty;
       }
     }
   }
   grouping version9-template {
     description "One or more version 9 templates for flow monitoring";
     leaf name {
       description "Name of template";
       type string;
     }
     uses apply-advanced;
     leaf flow-active-timeout {
       description "Interval after which active flow is exported";
       default "60";
       type union {
         type string {
           pattern "<.*>|$.*";
         }
         type uint32 {
           range "10 .. 600";
         }
       }
     }
     leaf flow-inactive-timeout {
       description "Period of inactivity that marks a flow inactive";
       default "60";
       type union {
         type string {
           pattern "<.*>|$.*";
         }
         type uint32 {
           range "10 .. 600";
         }
       }
     }
     leaf template-id {
       description "Template id";
       type union {
         type string {
           pattern "<.*>|$.*";
         }
         type uint32 {
           range "1024 .. 65535";
         }
       }
     }
     leaf option-template-id {
       description "Options template id";
       type union {
         type string {
           pattern "<.*>|$.*";
         }
         type uint32 {
           range "1024 .. 65535";
         }
       }
     }
     leaf source-id {
       description "Source Id";
       default "0";
       type union {
         type string {
           pattern "<.*>|$.*";
         }
         type uint32 {
           range "0 .. 255";
         }
       }
     }
     container nexthop-learning {
       description "Nexthop learning parameter. Valid ONLY for INLINE-JFLOW";
       uses apply-advanced;
       choice enable-disable {
         case case_1 {
           leaf enable {
             description "Enable nexthop learning";
             type empty;
           }
         }
         case case_2 {
           leaf disable {
             description "Disable nexthop learning";
             type empty;
           }
         }
       }
     }
     container template-refresh-rate {
       presence "enable template-refresh-rate";
       description "Template refresh rate";
       uses apply-advanced;
       leaf packets {
         description "In number of packets";
         default "4800";
         type union {
           type string {
             pattern "<.*>|$.*";
           }
           type uint32 {
             range "1 .. 480000";
           }
         }
       }
       leaf seconds {
         description "In number of seconds";
         type union {
           type string {
             pattern "<.*>|$.*";
           }
           type uint32 {
             range "10 .. 600";
           }
         }
       }
     }
     container option-refresh-rate {
       presence "enable option-refresh-rate";
       description "Option template refresh rate";
       uses apply-advanced;
       leaf packets {
         description "In number of packets";
         default "4800";
         type union {
           type string {
             pattern "<.*>|$.*";
           }
           type uint32 {
             range "1 .. 480000";
           }
         }
       }
       leaf seconds {
         description "In number of seconds";
         type union {
           type string {
             pattern "<.*>|$.*";
           }
           type uint32 {
             range "10 .. 600";
           }
         }
       }
     }
     choice template-types {
       case case_1 {
       }
       case case_2 {
       }
       case case_3 {
         container ipv6-template {
           presence "enable ipv6-template";
           description "IPv6 template configuration";
           uses apply-advanced;
           list export-extension {
             key name;
             ordered-by user;
             description "IPv6 template configuration with extra fields added to the template";
             leaf name {
               type enumeration {
                 enum "flow-dir" {
                   description "Applicationid field type";
                 }
                 enum "app-id" {
                   description "Applicationid field type";
                 }
               }
             }
             uses apply-advanced;
           }
           container nexthop-options {
             presence "enable nexthop-options";
             description "Additional information retrieved from nexthop";
             uses apply-advanced;
             choice nexthop-types {
               case case_1 {
                 container mpls {
                   presence "enable mpls";
                   description "MPLS information retrieved from nexthop";
                   uses apply-advanced;
                   leaf-list label-position {
                     ordered-by user;
                     description "One or more MPLS label positions";
                     type union {
                       type string {
                         pattern "<.*>|$.*";
                       }
                       type uint8 {
                         range "1 .. 3";
                       }
                     }
                     max-elements 3;
                   }
                 }
               }
             }
           }
         }
       }
       case case_4 {
         container peer-as-billing-template {
           presence "enable peer-as-billing-template";
           description "Peer AS billing template configuration";
         }
       }
       case case_5 {
         container ipv4-template {
           presence "enable ipv4-template";
           description "IPv4 template configuration";
           uses apply-advanced;
           list export-extension {
             key name;
             ordered-by user;
             description "IPv4 template configuration with extra fields added to the template";
             leaf name {
               type enumeration {
                 enum "flow-dir" {
                   description "Applicationid field type";
                 }
                 enum "app-id" {
                   description "Applicationid field type";
                 }
               }
             }
             uses apply-advanced;
           }
         }
       }
       case case_6 {
       }
       case case_7 {
       }
     }
     container tunnel-observation {
       junos:must "((\".. ipv4-template\" || (\".. mpls-ipvx-template\" || \".. mpls-template\")))";
       junos:must-message "Tunnel observation must be configured only for ipv4,mpls and mpls-ipvx templates";
       description "Tunnel observation";
       uses apply-advanced;
       leaf ipv4 {
         description "IPv4";
         junos:must "(\".. .. mpls-template\")";
         junos:must-message "Tunnel observation must be set to ipv4 only for mpls template";
         type empty;
       }
       leaf ipv6 {
         description "IPv6";
         junos:must "(\".. .. mpls-template\")";
         junos:must-message "Tunnel observation must be set to ipv6 only for mpls template";
         type empty;
       }
     }
     container flow-key {
       description "Flow key for the template. Valid ONLY for INLINE-JFLOW";
       uses apply-advanced;
       leaf flow-direction {
         description "Include flow direction";
         type empty;
       }
       leaf vlan-id {
         description "Include vlan ID";
         type empty;
       }
       leaf output-interface {
         description "Include output interface";
         junos:must "((\".. .. vpls-template\" || \".. .. bridge-template\"))";
         junos:must-message "Flow-key output interafce must be configured for bridge/vpls template";
         type empty;
       }
     }
   }
 }
