/*
 * Copyright (c) 2019 Juniper Networks, Inc.
 * All rights reserved.
 */
 module junos-conf-firewall {
   namespace "http://yang.juniper.net/junos/conf/firewall";

   prefix jc-firewall;

   import junos-common-ddl-extensions {
     prefix junos;
   }

   import junos-common-types {
     prefix jt;
   }

   import junos-conf-root {
     prefix jc;
   }

   organization "Juniper Networks, Inc.";

   contact "yang-support@juniper.net";

   description "Junos firewall configuration module";

   revision 2019-01-01 {
     description "Junos: 18.4R2.7";
   }

   augment /jc:configuration {
     uses firewall-group;
   }
   augment /jc:configuration/jc:groups {
     uses firewall-group;
   }
   grouping firewall-group {
     container firewall {
       description "Define a firewall configuration";
       uses apply-advanced;
       container family {
         description "Protocol family";
         container inet {
           description "Protocol family IPv4 for firewall filter";
           uses apply-advanced;
           list dialer-filter {
             key name;
             ordered-by user;
             description "Define an IPv4 dialer filter";
             uses inet_dialer_filter;
           }
           list prefix-action {
             key name;
             ordered-by user;
             description "Define a prefix action";
             uses prefix_action;
           }
           list filter {
             key name;
             ordered-by user;
             description "Define an IPv4 firewall filter";
             uses inet_filter;
           }
           list simple-filter {
             key name;
             ordered-by user;
             description "Define an IPv4 firewall simple filter";
             uses inet_simple_filter;
           }
           list service-filter {
             key name;
             ordered-by user;
             description "One or more IPv4 service filters";
             uses inet_service_filter;
           }
           list fast-update-filter {
             key name;
             ordered-by user;
             description "One or more fast update filters";
             uses inet_fuf;
           }
         }
         container inet6 {
           description "Protocol family IPv6 for firewall filter";
           uses apply-advanced;
           list dialer-filter {
             key name;
             ordered-by user;
             description "Define an IPv6 dialer filter";
             uses inet6_dialer_filter;
           }
           list filter {
             key name;
             ordered-by user;
             description "Define an IPv6 firewall filter";
             uses inet6_filter;
           }
           list service-filter {
             key name;
             ordered-by user;
             description "One or more IPv6 service filters";
             uses inet6_service_filter;
           }
           list fast-update-filter {
             key name;
             ordered-by user;
             description "One or more fast update filters";
             uses inet6_fuf;
           }
         }
         container mpls {
           description "Protocol family MPLS for firewall filter";
           uses apply-advanced;
           list dialer-filter {
             key name;
             ordered-by user;
             description "Define an mpls dialer filter";
             uses mpls_dialer_filter;
           }
           list filter {
             key name;
             ordered-by user;
             uses mpls_filter;
           }
         }
         container vpls {
           description "Protocol family VPLS for firewall filter";
           uses apply-advanced;
           list filter {
             key name;
             ordered-by user;
             uses vpls_filter;
           }
         }
         container evpn {
           description "Protocol family EVPN for firewall filter";
           uses apply-advanced;
           list filter {
             key name;
             ordered-by user;
             uses vpls_filter;
           }
         }
         container bridge {
           description "Protocol family BRIDGE for firewall filter";
           uses apply-advanced;
           list filter {
             key name;
             ordered-by user;
             uses bridge_filter;
           }
         }
         container ccc {
           description "Protocol family CCC for firewall filter";
           uses apply-advanced;
           list filter {
             key name;
             ordered-by user;
             uses ccc_filter;
           }
         }
         container any {
           description "Protocol-independent filter";
           uses apply-advanced;
           list filter {
             key name;
             ordered-by user;
             description "Define a protocol independent filter";
             uses any_filter;
           }
         }
         container ethernet-switching {
           description "Protocol family Ethernet Switching for firewall filter";
           uses apply-advanced;
           list filter {
             key name;
             ordered-by user;
             description "Define an Ethernet Switching firewall filter";
             uses es_filter;
           }
         }
       }
       list policer {
         key name;
         ordered-by user;
         description "Policer template definition";
         uses firewall_policer;
       }
       list flexible-match {
         key name;
         ordered-by user;
         description "Flexible packet match template definition";
         uses firewall_flexible_match;
       }
       list tunnel-end-point {
         key name;
         ordered-by user;
         description "Tunnel end-point template definition";
         uses tunnel_end_point;
       }
       list hierarchical-policer {
         key name;
         ordered-by user;
         description "Hierarchical policer template definition";
         uses firewall_hierpolicer;
       }
       list interface-set {
         key name;
         ordered-by user;
         description "Interface set definition";
         uses interface_set_type;
       }
       list load-balance-group {
         key name;
         ordered-by user;
         description "Load-balance group definition";
         uses firewall_load_balance_group;
       }
       list atm-policer {
         key name;
         ordered-by user;
         description "Atm policer";
         uses atm-policer-type;
       }
       list three-color-policer {
         key name;
         ordered-by user;
         description "Three-color policer";
         uses three-color-policer-type;
       }
       list filter {
         key name;
         ordered-by user;
         description "Define an IPv4 firewall filter";
         uses inet_filter;
       }
     }
   }
   grouping any_filter {
     leaf name {
       description "Filter name";
       type string {
         junos:posix-pattern "!^((__.*)|(.{65,}))$";
         junos:pattern-message "Must be a non-reserved string of 64 characters or less";
       }
     }
     uses apply-advanced;
     leaf interface-specific {
       description "Defined counters are interface specific";
       type empty;
     }
     leaf interface-shared {
       description "Filter is interface-shared";
       junos:must "(!(\".. interface-specific\"))";
       junos:must-message "Cannot be both interface-specific and interface-shared";
       type empty;
     }
     list term {
       key name;
       ordered-by user;
       description "Define a firewall term";
       leaf name {
         description "Term name";
         type string {
           junos:posix-pattern "!^((__.*)|(.{65,}))$";
           junos:pattern-message "Must be a non-reserved string of 64 characters or less";
         }
       }
       uses apply-advanced;
       container from {
         description "Define match criteria";
         uses apply-advanced;
         list interface {
           key name;
           ordered-by user;
           description "Match interface name";
           uses match_interface_object_oam;
         }
         list interface-set {
           key name;
           ordered-by user;
           description "Match interface in set";
           uses match_interface_set_object;
         }
         choice packet-length_choice {
           case case_1 {
             leaf-list packet-length {
               ordered-by user;
               description "Range of values";
               type string {
                 junos:posix-pattern "^([0-9]{1,4}|[1-5][0-9][0-9][0-9][0-9]|[6][0-4][0-9][0-9][0-9]|65[0-4][0-9][0-9]|655[0-2][0-9]|6553[0-5]|0x[0-f][0-f][0-f][0-f]|0x[0-f]|0x[0-f][0-f]|0x[0-f][0-f][0-f])(-([0-9]{1,4}|[1-5][0-9][0-9][0-9][0-9]|[6][0-4][0-9][0-9][0-9]|65[0-4][0-9][0-9]|655[0-2][0-9]|6553[0-5]|0x[0-f][0-f][0-f][0-f]|0x[0-f]|0x[0-f][0-f]|0x[0-f][0-f][0-f]))?$";
                 junos:pattern-message "Must be a numeric value or a range between 0-65535";
               }
             }
           }
           case case_2 {
             leaf-list packet-length-except {
               ordered-by user;
               description "Range of values";
               type string {
                 junos:posix-pattern "^([0-9]{1,4}|[1-5][0-9][0-9][0-9][0-9]|[6][0-4][0-9][0-9][0-9]|65[0-4][0-9][0-9]|655[0-2][0-9]|6553[0-5]|0x[0-f][0-f][0-f][0-f]|0x[0-f]|0x[0-f][0-f]|0x[0-f][0-f][0-f])(-([0-9]{1,4}|[1-5][0-9][0-9][0-9][0-9]|[6][0-4][0-9][0-9][0-9]|65[0-4][0-9][0-9]|655[0-2][0-9]|6553[0-5]|0x[0-f][0-f][0-f][0-f]|0x[0-f]|0x[0-f][0-f]|0x[0-f][0-f][0-f]))?$";
                 junos:pattern-message "Must be a numeric value or a range between 0-65535";
               }
             }
           }
         }
         choice forwarding-class_choice {
           case case_1 {
             leaf-list forwarding-class {
               ordered-by user;
               description "String name";
               type string {
                 junos:posix-pattern "^.{1,64}$";
                 junos:pattern-message "Must be string of 64 characters or less";
               }
             }
           }
           case case_2 {
             leaf-list forwarding-class-except {
               ordered-by user;
               description "String name";
               type string {
                 junos:posix-pattern "^.{1,64}$";
                 junos:pattern-message "Must be string of 64 characters or less";
               }
             }
           }
         }
         choice loss-priority_choice {
           case case_1 {
             leaf-list loss-priority {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
           case case_2 {
             leaf-list loss-priority-except {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
         }
         choice policy-map_choice {
           case case_1 {
             leaf-list policy-map {
               ordered-by user;
               description "String name";
               junos:must "(\"class-of-service policy-map $$\")";
               junos:must-message "Undefined policy-map instance";
               type string {
                 length "1 .. 64";
                 junos:posix-pattern "!^((__.*)|(.{65,}))$";
                 junos:pattern-message "Must be a non-reserved string of 64 characters or less";
               }
             }
           }
           case case_2 {
             leaf-list policy-map-except {
               ordered-by user;
               description "String name";
               junos:must "(\"class-of-service policy-map $$\")";
               junos:must-message "Undefined policy-map instance";
               type string {
                 length "1 .. 64";
                 junos:posix-pattern "!^((__.*)|(.{65,}))$";
                 junos:pattern-message "Must be a non-reserved string of 64 characters or less";
               }
             }
           }
         }
         leaf service-filter-hit {
           description "Match if service-filter-hit is set";
           type empty;
         }
       }
       container then {
         description "Action to take if the 'from' condition is matched";
         uses apply-advanced;
         choice policer-choice {
           case case_1 {
             leaf policer {
               description "Name of policer to use to rate-limit traffic";
               junos:must "(!(\"firewall policer $$ aggregate\"))";
               junos:must-message "Cannot attach a aggregate policer to filter";
               type string {
                 junos:posix-pattern "!^((__.*)|(.{65,}))$";
                 junos:pattern-message "Must be a non-reserved string of 64 characters or less";
               }
             }
           }
           case case_2 {
             container three-color-policer {
               description "Police the packet using a three-color-policer";
               uses apply-advanced;
               choice type-choice {
                 case case_1 {
                   leaf single-rate {
                     description "Name of single-rate three-color policer to use to rate-limit traffic";
                     junos:must "(\"firewall three-color-policer $$ single-rate\")";
                     junos:must-message "Referenced single-rate policer does not exist";
                     type string {
                       junos:posix-pattern "!^((__.*)|(.{65,}))$";
                       junos:pattern-message "Must be a non-reserved string of 64 characters or less";
                     }
                   }
                 }
                 case case_2 {
                   leaf single-packet-rate {
                     description "Name of single-packet-rate three-color policer to use to rate-limit traffic";
                     junos:must "(\"firewall three-color-policer $$ single-packet-rate\")";
                     junos:must-message "Referenced single-packet-rate policer does not exist";
                     type string {
                       junos:posix-pattern "!^((__.*)|(.{65,}))$";
                       junos:pattern-message "Must be a non-reserved string of 64 characters or less";
                     }
                   }
                 }
                 case case_3 {
                   leaf two-rate {
                     description "Name of two-rate three-color policer to use to rate-limit traffic";
                     junos:must "(\"firewall three-color-policer $$ two-rate\")";
                     junos:must-message "Referenced two-rate policer does not exist";
                     type string {
                       junos:posix-pattern "!^((__.*)|(.{65,}))$";
                       junos:pattern-message "Must be a non-reserved string of 64 characters or less";
                     }
                   }
                 }
                 case case_4 {
                   leaf two-packet-rate {
                     description "Name of two-packet-rate three-color policer to use to rate-limit traffic";
                     junos:must "(\"firewall three-color-policer $$ two-packet-rate\")";
                     junos:must-message "Referenced two-packet-rate policer does not exist";
                     type string {
                       junos:posix-pattern "!^((__.*)|(.{65,}))$";
                       junos:pattern-message "Must be a non-reserved string of 64 characters or less";
                     }
                   }
                 }
               }
             }
           }
           case case_3 {
             leaf hierarchical-policer {
               description "Name of hierarchical policer to use to rate-limit traffic";
               type string {
                 junos:posix-pattern "!^((__.*)|(.{65,}))$";
                 junos:pattern-message "Must be a non-reserved string of 64 characters or less";
               }
             }
           }
         }
         choice policy-map-choice {
           case case_1 {
             leaf clear-policy-map {
               description "Clear the policy marking";
               type empty;
             }
           }
           case case_2 {
             leaf policy-map {
               description "Policy map action";
               junos:must "(\"class-of-service policy-map $$\")";
               junos:must-message "referenced policy map must be defined";
               type string {
                 junos:posix-pattern "!^((__.*)|(.{65,}))$";
                 junos:pattern-message "Must be a non-reserved string of 64 characters or less";
               }
             }
           }
         }
         leaf count {
           description "Count the packet in the named counter";
           type string {
             junos:posix-pattern "!^((__.*)|(.{65,}))$";
             junos:pattern-message "Must be a non-reserved string of 64 characters or less";
           }
         }
         leaf service-accounting {
           description "Count the packets for service accounting";
           junos:must "(!(\".. service-accounting-deferred\"))";
           junos:must-message "'service-accounting-deferred' and 'service-accounting' cannot coexist";
           junos:must "(!(\".. count\"))";
           junos:must-message "'count' and 'service-accounting' cannot coexist";
           type empty;
         }
         leaf service-accounting-deferred {
           description "Count the packets for deferred service accounting";
           junos:must "(!(\".. service-accounting\"))";
           junos:must-message "Cannot be both 'service-accounting' and 'service-accounting-deferred'";
           junos:must "(!(\".. count\"))";
           junos:must-message "'count' and 'service-accounting-deferred' cannot coexist";
           type empty;
         }
         leaf service-filter-hit {
           description "Signal subsequent filters in the chain that packet was processed";
           type empty;
         }
         leaf force-premium {
           description "Process packets as premium traffic by subsequent hierarchical policers";
           type empty;
         }
         leaf loss-priority {
           description "Classify packet to loss-priority";
           type enumeration {
             enum "low" {
               description "Loss priority low";
             }
             enum "high" {
               description "Loss priority high";
             }
             enum "medium-low" {
               description "Loss priority medium-low";
             }
             enum "medium-high" {
               description "Loss priority medium-high";
             }
           }
         }
         leaf port-mirror-instance {
           description "Port-mirror the packet to specified instance";
           junos:must "(\"forwarding-options port-mirroring instance $$\")";
           junos:must-message "Referenced port-mirroring instance does not exist";
           type string {
             junos:posix-pattern "!^((__.*)|(.{65,}))$";
             junos:pattern-message "Must be a non-reserved string of 64 characters or less";
           }
         }
         leaf port-mirror {
           description "Port-mirror the packet";
           junos:must "(!(\".. port-mirror-instance\"))";
           junos:must-message "'port-mirror' and 'port-mirror-instance' are mutually exclusive";
           type empty;
         }
         leaf forwarding-class {
           description "Classify packet to forwarding class";
           type string {
             junos:posix-pattern "^.{1,64}$";
             junos:pattern-message "Must be string of 64 characters or less";
           }
         }
         choice designation {
           case case_1 {
             container encapsulate {
               presence "enable encapsulate";
               description "Send to a tunnel";
               leaf tunnel-end-point {
                 description "Name of the tunnel end point";
                 junos:must "(\"firewall tunnel-end-point $$\")";
                 junos:must-message "referenced firewall tunnel-end-point must be defined";
                 type string {
                   junos:posix-pattern "!^((__.*)|(.{65,}))$";
                   junos:pattern-message "Must be a non-reserved string of 64 characters or less";
                 }
               }
             }
           }
           case case_2 {
             leaf accept {
               description "Accept the packet";
               type empty;
             }
           }
           case case_3 {
             leaf discard {
               description "Discard the packet";
               type empty;
             }
           }
           case case_4 {
             leaf next {
               description "Continue to next term in a filter";
               type enumeration {
                 enum "term" {
                   description "Continue to next term in a filter";
                 }
               }
             }
           }
         }
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping atm-policer-type {
     description "Atm policer";
     leaf name {
       description "Policer name";
       type string {
         junos:posix-pattern "!^((__.*)|(.{65,}))$";
         junos:pattern-message "Must be a non-reserved string of 64 characters or less";
       }
     }
     uses apply-advanced;
     leaf logical-interface-policer {
       description "Policer is logical interface policer";
       type empty;
     }
     leaf atm-service {
       description "ATM service category";
       type enumeration {
         enum "cbr" {
           description "Constant bit rate";
         }
         enum "rtvbr" {
           description "Real-time variable bit rate";
         }
         enum "nrtvbr" {
           description "Non-real-time variable bit rate";
         }
         enum "ubr" {
           description "Unspecified bit rate";
         }
       }
     }
     leaf peak-rate {
       description "ATM Peak Cell Rate (PCR)";
       units "cps";
       type string;
     }
     leaf sustained-rate {
       description "ATM Sustained Cell Rate (SCR)";
       units "cps";
       type string;
     }
     leaf max-burst-size {
       description "ATM Maximum Burst Size (MBS)";
       units "cells";
       type union {
         type string {
           pattern "<.*>|$.*";
         }
         type uint64 {
           range "1 .. 4000";
         }
       }
     }
     leaf cdvt {
       description "Cell Delay Variation Tolerance";
       units "microseconds";
       type string;
     }
     leaf policing-action {
       description "Policing action";
       type enumeration {
         enum "count" {
           description "Update counters";
         }
         enum "discard" {
           description "Discard non-conforming cells (CBR.1/VBR.1/UBR.1)";
         }
         enum "discard-tag" {
           description "Discard PCR non-conforming and tag SCR non-conforming cells (VBR.3/UBR.2)";
         }
       }
     }
   }
   grouping bridge_filter {
     description "Define a BRIDGE firewall filter";
     leaf name {
       description "Filter name";
       type string {
         junos:posix-pattern "!^((__.*)|(.{65,}))$";
         junos:pattern-message "Must be a non-reserved string of 64 characters or less";
       }
     }
     uses apply-advanced;
     leaf-list accounting-profile {
       ordered-by user;
       description "Accounting profile name";
       junos:must "(\"accounting-options filter-profile\")";
       junos:must-message "referenced accounting profile must be defined";
       type string;
     }
     leaf interface-specific {
       description "Defined counters are interface specific";
       type empty;
     }
     leaf physical-interface-filter {
       description "Filter is physical interface filter";
       type empty;
     }
     leaf instance-shared {
       description "Filter is routing-instance shared";
       junos:must "(\"chassis network-services enhanced-ip\")";
       junos:must-message "instance-shared filter available only in enhanced-ip mode";
       junos:must "(!(\".. physical-interface-filter\"))";
       junos:must-message "Cannot be both physical-interface-filter and instance-shared";
       junos:must "(!(\".. interface-specific\"))";
       junos:must-message "Cannot be both interface-specific and instance-shared";
       type empty;
     }
     list term {
       key name;
       ordered-by user;
       description "Define a firewall term";
       leaf name {
         description "Term name";
         type string {
           junos:posix-pattern "!^((__.*)|(.{65,}))$";
           junos:pattern-message "Must be a non-reserved string of 64 characters or less";
         }
       }
       uses apply-advanced;
       leaf filter {
         description "Filter to include";
         junos:must "(\"firewall family bridge filter $$\")";
         junos:must-message "Referenced filter is not defined";
         junos:must "((!(\".. from\") && !(\".. then\")))";
         junos:must-message "Not compatible with 'from or then'";
         type string {
           junos:posix-pattern "!^((__.*)|(.{65,}))$";
           junos:pattern-message "Must be a non-reserved string of 64 characters or less";
         }
       }
       container from {
         description "Define match criteria";
         uses apply-advanced;
         choice interface-group_choice {
           case case_1 {
             leaf-list interface-group {
               ordered-by user;
               description "Range of values";
               type string;
             }
           }
           case case_2 {
             leaf-list interface-group-except {
               ordered-by user;
               description "Range of values";
               type string;
             }
           }
         }
         choice ether-type_choice {
           case case_1 {
             leaf-list ether-type {
               ordered-by user;
               type string;
             }
           }
           case case_2 {
             leaf-list ether-type-except {
               ordered-by user;
               type string;
             }
           }
         }
         choice vlan-ether-type_choice {
           case case_1 {
             leaf-list vlan-ether-type {
               ordered-by user;
               type string;
             }
           }
           case case_2 {
             leaf-list vlan-ether-type-except {
               ordered-by user;
               type string;
             }
           }
         }
         list destination-mac-address {
           key name;
           ordered-by user;
           description "Destination MAC address";
           uses firewall_mac_addr_object;
         }
         list source-mac-address {
           key name;
           ordered-by user;
           description "Source MAC address";
           uses firewall_mac_addr_object;
         }
         choice forwarding-class_choice {
           case case_1 {
             leaf-list forwarding-class {
               ordered-by user;
               description "String name";
               type string {
                 junos:posix-pattern "^.{1,64}$";
                 junos:pattern-message "Must be string of 64 characters or less";
               }
             }
           }
           case case_2 {
             leaf-list forwarding-class-except {
               ordered-by user;
               description "String name";
               type string {
                 junos:posix-pattern "^.{1,64}$";
                 junos:pattern-message "Must be string of 64 characters or less";
               }
             }
           }
         }
         choice loss-priority_choice {
           case case_1 {
             leaf-list loss-priority {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
           case case_2 {
             leaf-list loss-priority-except {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
         }
         choice learn-vlan-id_choice {
           case case_1 {
             leaf-list learn-vlan-id {
               ordered-by user;
               description "Range of values";
               type string;
             }
           }
           case case_2 {
             leaf-list learn-vlan-id-except {
               ordered-by user;
               description "Range of values";
               type string;
             }
           }
         }
         choice learn-vlan-1p-priority_choice {
           case case_1 {
             leaf-list learn-vlan-1p-priority {
               ordered-by user;
               description "802.1p priority value 0-7";
               type union {
                 type string {
                   pattern "<.*>|$.*";
                 }
                 type uint32 {
                   range "0 .. 7";
                 }
               }
             }
           }
           case case_2 {
             leaf-list learn-vlan-1p-priority-except {
               ordered-by user;
               description "802.1p priority value 0-7";
               type union {
                 type string {
                   pattern "<.*>|$.*";
                 }
                 type uint32 {
                   range "0 .. 7";
                 }
               }
             }
           }
         }
         choice user-vlan-id_choice {
           case case_1 {
             leaf-list user-vlan-id {
               ordered-by user;
               description "Range of values";
               type string;
             }
           }
           case case_2 {
             leaf-list user-vlan-id-except {
               ordered-by user;
               description "Range of values";
               type string;
             }
           }
         }
         choice user-vlan-1p-priority_choice {
           case case_1 {
             leaf-list user-vlan-1p-priority {
               ordered-by user;
               description "802.1p priority value 0-7";
               type union {
                 type string {
                   pattern "<.*>|$.*";
                 }
                 type uint32 {
                   range "0 .. 7";
                 }
               }
             }
           }
           case case_2 {
             leaf-list user-vlan-1p-priority-except {
               ordered-by user;
               description "802.1p priority value 0-7";
               type union {
                 type string {
                   pattern "<.*>|$.*";
                 }
                 type uint32 {
                   range "0 .. 7";
                 }
               }
             }
           }
         }
         choice learn-vlan-dei_choice {
           case case_1 {
             leaf-list learn-vlan-dei {
               ordered-by user;
               description "DEI value 0-1";
               type union {
                 type string {
                   pattern "<.*>|$.*";
                 }
                 type uint32 {
                   range "0 .. 1";
                 }
               }
             }
           }
           case case_2 {
             leaf-list learn-vlan-dei-except {
               ordered-by user;
               description "DEI value 0-1";
               type union {
                 type string {
                   pattern "<.*>|$.*";
                 }
                 type uint32 {
                   range "0 .. 1";
                 }
               }
             }
           }
         }
         choice traffic-type_choice {
           case case_1 {
             leaf-list traffic-type {
               ordered-by user;
               type enumeration {
                 enum "broadcast" {
                   description "Packets with broadcast ethernet address";
                 }
                 enum "multicast" {
                   description "Packets with multicast ethernet address";
                 }
                 enum "unknown-unicast" {
                   description "Packets for which destination ethernet address has not been learnt";
                 }
                 enum "known-unicast" {
                   description "Packets for which destination ethernet address has been learnt";
                 }
               }
             }
           }
           case case_2 {
             leaf-list traffic-type-except {
               ordered-by user;
               type enumeration {
                 enum "broadcast" {
                   description "Packets with broadcast ethernet address";
                 }
                 enum "multicast" {
                   description "Packets with multicast ethernet address";
                 }
                 enum "unknown-unicast" {
                   description "Packets for which destination ethernet address has not been learnt";
                 }
                 enum "known-unicast" {
                   description "Packets for which destination ethernet address has been learnt";
                 }
               }
             }
           }
         }
         list ip-source-address {
           key name;
           ordered-by user;
           description "Match IP source address";
           uses firewall_addr_object;
         }
         list ip-destination-address {
           key name;
           ordered-by user;
           description "Match IP destination address";
           uses firewall_addr_object;
         }
         list ip-address {
           key name;
           ordered-by user;
           description "Match IP source or destination address";
           uses firewall_addr_object;
         }
         choice ip-protocol_choice {
           case case_1 {
             leaf-list ip-protocol {
               ordered-by user;
               type string;
             }
           }
           case case_2 {
             leaf-list ip-protocol-except {
               ordered-by user;
               type string;
             }
           }
         }
         choice dscp_choice {
           case case_1 {
             leaf-list dscp {
               ordered-by user;
               type string;
             }
           }
           case case_2 {
             leaf-list dscp-except {
               ordered-by user;
               type string;
             }
           }
         }
         choice ip-precedence_choice {
           case case_1 {
             leaf-list ip-precedence {
               ordered-by user;
               type string;
             }
           }
           case case_2 {
             leaf-list ip-precedence-except {
               ordered-by user;
               type string;
             }
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice port_choice {
           case case_1 {
             leaf-list port {
               ordered-by user;
               type string;
             }
           }
           case case_2 {
             leaf-list port-except {
               ordered-by user;
               type string;
             }
           }
         }
         leaf tcp-flags {
           description "Match TCP flags";
           type string;
         }
         choice icmp-type_choice {
           case case_1 {
             leaf-list icmp-type {
               ordered-by user;
               type string;
             }
           }
           case case_2 {
             leaf-list icmp-type-except {
               ordered-by user;
               type string;
             }
           }
         }
         choice icmp-code_choice {
           case case_1 {
             leaf-list icmp-code {
               ordered-by user;
               type string;
             }
           }
           case case_2 {
             leaf-list icmp-code-except {
               ordered-by user;
               type string;
             }
           }
         }
         list interface {
           key name;
           ordered-by user;
           description "Match interface name";
           uses match_interface_object;
         }
         list interface-set {
           key name;
           ordered-by user;
           description "Match interface in set";
           uses match_interface_set_object;
         }
         list source-prefix-list {
           key name;
           ordered-by user;
           description "Match IP source prefixes in named list";
           uses firewall_prefix_list;
         }
         list destination-prefix-list {
           key name;
           ordered-by user;
           description "Match IP destination prefixes in named list";
           uses firewall_prefix_list;
         }
         list prefix-list {
           key name;
           ordered-by user;
           description "Match IP source or destination prefixes in named list";
           uses firewall_prefix_list;
         }
         list ipv6-destination-address {
           key name;
           ordered-by user;
           description "Match IPv6 destination address";
           uses firewall_addr6_object;
         }
         list ipv6-source-address {
           key name;
           ordered-by user;
           description "Match IPv6 source address";
           uses firewall_addr6_object;
         }
         list ipv6-address {
           key name;
           ordered-by user;
           description "Match IPv6 address";
           uses firewall_addr6_object;
         }
         choice ipv6-next-header_choice {
           case case_1 {
             leaf-list ipv6-next-header {
               ordered-by user;
               type string;
             }
           }
           case case_2 {
             leaf-list ipv6-next-header-except {
               ordered-by user;
               type string;
             }
           }
         }
         choice ipv6-payload-protocol_choice {
           case case_1 {
             leaf-list ipv6-payload-protocol {
               ordered-by user;
               type string;
             }
           }
           case case_2 {
             leaf-list ipv6-payload-protocol-except {
               ordered-by user;
               type string;
             }
           }
         }
         choice ipv6-traffic-class_choice {
           case case_1 {
             leaf-list ipv6-traffic-class {
               ordered-by user;
               type string;
             }
           }
           case case_2 {
             leaf-list ipv6-traffic-class-except {
               ordered-by user;
               type string;
             }
           }
         }
         list ipv6-source-prefix-list {
           key name;
           ordered-by user;
           description "Match IPV6 source prefixes in named list";
           uses firewall_prefix_list;
         }
         list ipv6-destination-prefix-list {
           key name;
           ordered-by user;
           description "Match IPV6 destination prefixes in named list";
           uses firewall_prefix_list;
         }
         list ipv6-prefix-list {
           key name;
           ordered-by user;
           description "Match IP source or destination prefixes in named list";
           uses firewall_prefix_list;
         }
         choice flex-mask_choice {
           case case_1 {
             container flexible-match-mask {
               description "Match flexible mask";
               uses match_L2_flexible_mask;
             }
           }
         }
         choice flex-range_choice {
           case case_1 {
             container flexible-match-range {
               description "Match flexible range";
               uses match_L2_flexible_range;
             }
           }
         }
         choice policy-map_choice {
           case case_1 {
             leaf-list policy-map {
               ordered-by user;
               description "String name";
               junos:must "(\"class-of-service policy-map $$\")";
               junos:must-message "Undefined policy-map instance";
               type string {
                 length "1 .. 64";
                 junos:posix-pattern "!^((__.*)|(.{65,}))$";
                 junos:pattern-message "Must be a non-reserved string of 64 characters or less";
               }
             }
           }
           case case_2 {
             leaf-list policy-map-except {
               ordered-by user;
               description "String name";
               junos:must "(\"class-of-service policy-map $$\")";
               junos:must-message "Undefined policy-map instance";
               type string {
                 length "1 .. 64";
                 junos:posix-pattern "!^((__.*)|(.{65,}))$";
                 junos:pattern-message "Must be a non-reserved string of 64 characters or less";
               }
             }
           }
         }
         choice isid_choice {
           case case_1 {
             leaf-list isid {
               ordered-by user;
               description "Range of values";
               type string;
             }
           }
           case case_2 {
             leaf-list isid-except {
               ordered-by user;
               description "Range of values";
               type string;
             }
           }
         }
         choice isid-priority-code-point_choice {
           case case_1 {
             leaf-list isid-priority-code-point {
               ordered-by user;
               description "802.1p priority value 0-7";
               type union {
                 type string {
                   pattern "<.*>|$.*";
                 }
                 type uint32 {
                   range "0 .. 7";
                 }
               }
             }
           }
           case case_2 {
             leaf-list isid-priority-code-point-except {
               ordered-by user;
               description "802.1p priority value 0-7";
               type union {
                 type string {
                   pattern "<.*>|$.*";
                 }
                 type uint32 {
                   range "0 .. 7";
                 }
               }
             }
           }
         }
         choice isid-dei_choice {
           case case_1 {
             leaf-list isid-dei {
               ordered-by user;
               description "DEI value 0-1";
               type union {
                 type string {
                   pattern "<.*>|$.*";
                 }
                 type uint32 {
                   range "0 .. 1";
                 }
               }
             }
           }
           case case_2 {
             leaf-list isid-dei-except {
               ordered-by user;
               description "DEI value 0-1";
               type union {
                 type string {
                   pattern "<.*>|$.*";
                 }
                 type uint32 {
                   range "0 .. 1";
                 }
               }
             }
           }
         }
       }
       container then {
         description "Action to take if the 'from' condition is matched";
         uses apply-advanced;
         choice policer-choice {
           case case_1 {
             leaf policer {
               description "Name of policer to use to rate-limit traffic";
               junos:must "(!(\"firewall policer $$ aggregate\"))";
               junos:must-message "Cannot attach a aggregate policer to filter";
               type string {
                 junos:posix-pattern "!^((__.*)|(.{65,}))$";
                 junos:pattern-message "Must be a non-reserved string of 64 characters or less";
               }
             }
           }
           case case_2 {
             container three-color-policer {
               description "Police the packet using a three-color-policer";
               uses apply-advanced;
               choice type-choice {
                 case case_1 {
                   leaf single-rate {
                     description "Name of single-rate three-color policer to use to rate-limit traffic";
                     junos:must "(\"firewall three-color-policer $$ single-rate\")";
                     junos:must-message "Referenced single-rate policer does not exist";
                     type string {
                       junos:posix-pattern "!^((__.*)|(.{65,}))$";
                       junos:pattern-message "Must be a non-reserved string of 64 characters or less";
                     }
                   }
                 }
                 case case_2 {
                   leaf single-packet-rate {
                     description "Name of single-packet-rate three-color policer to use to rate-limit traffic";
                     junos:must "(\"firewall three-color-policer $$ single-packet-rate\")";
                     junos:must-message "Referenced single-packet-rate policer does not exist";
                     type string {
                       junos:posix-pattern "!^((__.*)|(.{65,}))$";
                       junos:pattern-message "Must be a non-reserved string of 64 characters or less";
                     }
                   }
                 }
                 case case_3 {
                   leaf two-rate {
                     description "Name of two-rate three-color policer to use to rate-limit traffic";
                     junos:must "(\"firewall three-color-policer $$ two-rate\")";
                     junos:must-message "Referenced two-rate policer does not exist";
                     type string {
                       junos:posix-pattern "!^((__.*)|(.{65,}))$";
                       junos:pattern-message "Must be a non-reserved string of 64 characters or less";
                     }
                   }
                 }
                 case case_4 {
                   leaf two-packet-rate {
                     description "Name of two-packet-rate three-color policer to use to rate-limit traffic";
                     junos:must "(\"firewall three-color-policer $$ two-packet-rate\")";
                     junos:must-message "Referenced two-packet-rate policer does not exist";
                     type string {
                       junos:posix-pattern "!^((__.*)|(.{65,}))$";
                       junos:pattern-message "Must be a non-reserved string of 64 characters or less";
                     }
                   }
                 }
               }
             }
           }
           case case_3 {
             leaf hierarchical-policer {
               description "Name of hierarchical policer to use to rate-limit traffic";
               type string {
                 junos:posix-pattern "!^((__.*)|(.{65,}))$";
                 junos:pattern-message "Must be a non-reserved string of 64 characters or less";
               }
             }
           }
         }
         choice policy-map-choice {
           case case_1 {
             leaf clear-policy-map {
               description "Clear the policy marking";
               type empty;
             }
           }
           case case_2 {
             leaf policy-map {
               description "Policy map action";
               junos:must "(\"class-of-service policy-map $$\")";
               junos:must-message "referenced policy map must be defined";
               type string {
                 junos:posix-pattern "!^((__.*)|(.{65,}))$";
                 junos:pattern-message "Must be a non-reserved string of 64 characters or less";
               }
             }
           }
         }
         leaf count {
           description "Count the packet in the named counter";
           type string {
             junos:posix-pattern "!^((__.*)|(.{65,}))$";
             junos:pattern-message "Must be a non-reserved string of 64 characters or less";
           }
         }
         leaf loss-priority {
           description "Packet's loss priority";
           type enumeration {
             enum "low" {
               description "Loss priority low";
             }
             enum "high" {
               description "Loss priority high";
             }
             enum "medium-low" {
               description "Loss priority medium-low";
             }
             enum "medium-high" {
               description "Loss priority medium-high";
             }
           }
         }
         leaf forwarding-class {
           description "Classify packet to forwarding class";
           type string {
             junos:posix-pattern "^.{1,64}$";
             junos:pattern-message "Must be string of 64 characters or less";
           }
         }
         choice designation {
           case case_1 {
             leaf accept {
               description "Accept the packet";
               type empty;
             }
           }
           case case_2 {
             leaf discard {
               description "Discard the packet";
               type empty;
             }
           }
           case case_3 {
             leaf next {
               description "Continue to next term in a filter";
               type enumeration {
                 enum "term" {
                   description "Continue to next term in a filter";
                 }
               }
             }
           }
         }
         leaf port-mirror-instance {
           description "Port-mirror the packet to specified instance";
           junos:must "(\"forwarding-options port-mirroring instance $$\")";
           junos:must-message "Referenced port-mirroring instance does not exist";
           type string {
             junos:posix-pattern "!^((__.*)|(.{65,}))$";
             junos:pattern-message "Must be a non-reserved string of 64 characters or less";
           }
         }
         leaf port-mirror {
           description "Port-mirror the packet";
           junos:must "(!(\".. port-mirror-instance\"))";
           junos:must-message "'port-mirror' and 'port-mirror-instance' are mutually exclusive";
           junos:must "(\"forwarding-options port-mirroring\")";
           junos:must-message "Configure 'port-mirroring' under 'forwarding-options'";
           type empty;
         }
         leaf next-hop-group {
           description "Use specified next-hop group";
           type string;
         }
         leaf sample {
           description "Sample the packet";
           junos:must "(any \"forwarding-options sampling instance <*> family bridge\")";
           junos:must-message "Configure family bridge under forwarding-options sampling";
           type empty;
         }
         leaf log {
           description "Log the packet";
           type empty;
         }
         leaf syslog {
           description "System log (syslog) information about the packet";
           type empty;
         }
         container forwarding-policy {
           description "Specify forwarding policy for extended port";
           uses apply-advanced;
           leaf uplink-select {
             description "Specify port group for uplink selection";
             type string;
           }
         }
       }
     }
   }
   grouping ccc_filter {
     description "Define a CCC firewall filter";
     leaf name {
       description "Filter name";
       type string {
         junos:posix-pattern "!^((__.*)|(.{65,}))$";
         junos:pattern-message "Must be a non-reserved string of 64 characters or less";
       }
     }
     uses apply-advanced;
     leaf-list accounting-profile {
       ordered-by user;
       description "Accounting profile name";
       junos:must "(\"accounting-options filter-profile\")";
       junos:must-message "referenced accounting profile must be defined";
       type string;
     }
     leaf interface-specific {
       description "Any counters defined will be interface specific";
       type empty;
     }
     leaf physical-interface-filter {
       description "Filter is physical interface filter";
       type empty;
     }
     list term {
       key name;
       ordered-by user;
       description "Define a firewall term";
       leaf name {
         description "Term name";
         type string {
           junos:posix-pattern "!^((__.*)|(.{65,}))$";
           junos:pattern-message "Must be a non-reserved string of 64 characters or less";
         }
       }
       uses apply-advanced;
       leaf filter {
         description "Filter to include";
         junos:must "(\"firewall family ccc filter $$\")";
         junos:must-message "Referenced filter is not defined";
         junos:must "((!(\".. from\") && !(\".. then\")))";
         junos:must-message "Not compatible with 'from or then'";
         type string {
           junos:posix-pattern "!^((__.*)|(.{65,}))$";
           junos:pattern-message "Must be a non-reserved string of 64 characters or less";
         }
       }
       container from {
         description "Define match criteria";
         uses apply-advanced;
         choice interface-group_choice {
           case case_1 {
             leaf-list interface-group {
               ordered-by user;
               description "Range of values";
               type string;
             }
           }
           case case_2 {
             leaf-list interface-group-except {
               ordered-by user;
               description "Range of values";
               type string;
             }
           }
         }
         choice forwarding-class_choice {
           case case_1 {
             leaf-list forwarding-class {
               ordered-by user;
               description "String name";
               type string {
                 junos:posix-pattern "^.{1,64}$";
                 junos:pattern-message "Must be string of 64 characters or less";
               }
             }
           }
           case case_2 {
             leaf-list forwarding-class-except {
               ordered-by user;
               description "String name";
               type string {
                 junos:posix-pattern "^.{1,64}$";
                 junos:pattern-message "Must be string of 64 characters or less";
               }
             }
           }
         }
         choice loss-priority_choice {
           case case_1 {
             leaf-list loss-priority {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
           case case_2 {
             leaf-list loss-priority-except {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
         }
         choice learn-vlan-1p-priority_choice {
           case case_1 {
             leaf-list learn-vlan-1p-priority {
               ordered-by user;
               description "802.1p priority value 0-7";
               type union {
                 type string {
                   pattern "<.*>|$.*";
                 }
                 type uint32 {
                   range "0 .. 7";
                 }
               }
             }
           }
           case case_2 {
             leaf-list learn-vlan-1p-priority-except {
               ordered-by user;
               description "802.1p priority value 0-7";
               type union {
                 type string {
                   pattern "<.*>|$.*";
                 }
                 type uint32 {
                   range "0 .. 7";
                 }
               }
             }
           }
         }
         choice user-vlan-1p-priority_choice {
           case case_1 {
             leaf-list user-vlan-1p-priority {
               ordered-by user;
               description "802.1p priority value 0-7";
               type union {
                 type string {
                   pattern "<.*>|$.*";
                 }
                 type uint32 {
                   range "0 .. 7";
                 }
               }
             }
           }
           case case_2 {
             leaf-list user-vlan-1p-priority-except {
               ordered-by user;
               description "802.1p priority value 0-7";
               type union {
                 type string {
                   pattern "<.*>|$.*";
                 }
                 type uint32 {
                   range "0 .. 7";
                 }
               }
             }
           }
         }
         list destination-mac-address {
           key name;
           ordered-by user;
           description "Destination MAC address";
           uses firewall_mac_addr_object;
         }
         leaf is-host-packet {
           description "Match if packet is host generated";
           type empty;
         }
         list source-mac-address {
           key name;
           ordered-by user;
           description "Source MAC address";
           uses firewall_mac_addr_object;
         }
         list ip-source-address {
           key name;
           ordered-by user;
           description "Match IP source address";
           uses firewall_addr_object;
         }
         list ip-destination-address {
           key name;
           ordered-by user;
           description "Match IP destination address";
           uses firewall_addr_object;
         }
         choice dscp_choice {
           case case_1 {
             leaf-list dscp {
               ordered-by user;
               type string;
             }
           }
           case case_2 {
             leaf-list dscp-except {
               ordered-by user;
               type string;
             }
           }
         }
         choice ip-precedence_choice {
           case case_1 {
             leaf-list ip-precedence {
               ordered-by user;
               type string;
             }
           }
           case case_2 {
             leaf-list ip-precedence-except {
               ordered-by user;
               type string;
             }
           }
         }
         choice ip-protocol_choice {
           case case_1 {
             leaf-list ip-protocol {
               ordered-by user;
               type string;
             }
           }
           case case_2 {
             leaf-list ip-protocol-except {
               ordered-by user;
               type string;
             }
           }
         }
         choice icmp-type_choice {
           case case_1 {
             leaf-list icmp-type {
               ordered-by user;
               type string;
             }
           }
           case case_2 {
             leaf-list icmp-type-except {
               ordered-by user;
               type string;
             }
           }
         }
         choice icmp-code_choice {
           case case_1 {
             leaf-list icmp-code {
               ordered-by user;
               type string;
             }
           }
           case case_2 {
             leaf-list icmp-code-except {
               ordered-by user;
               type string;
             }
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice policy-map_choice {
           case case_1 {
             leaf-list policy-map {
               ordered-by user;
               description "String name";
               junos:must "(\"class-of-service policy-map $$\")";
               junos:must-message "Undefined policy-map instance";
               type string {
                 length "1 .. 64";
                 junos:posix-pattern "!^((__.*)|(.{65,}))$";
                 junos:pattern-message "Must be a non-reserved string of 64 characters or less";
               }
             }
           }
           case case_2 {
             leaf-list policy-map-except {
               ordered-by user;
               description "String name";
               junos:must "(\"class-of-service policy-map $$\")";
               junos:must-message "Undefined policy-map instance";
               type string {
                 length "1 .. 64";
                 junos:posix-pattern "!^((__.*)|(.{65,}))$";
                 junos:pattern-message "Must be a non-reserved string of 64 characters or less";
               }
             }
           }
         }
         choice flex-mask_choice {
           case case_1 {
             container flexible-match-mask {
               description "Match flexible mask";
               uses match_L2_flexible_mask;
             }
           }
         }
         choice flex-range_choice {
           case case_1 {
             container flexible-match-range {
               description "Match flexible range";
               uses match_L2_flexible_range;
             }
           }
         }
         choice user-vlan-id_choice {
           case case_1 {
           }
           case case_2 {
             leaf-list user-vlan-id-except {
               ordered-by user;
               description "Range of values";
               type string;
             }
           }
         }
       }
       container then {
         description "Action to take if the 'from' condition is matched";
         uses apply-advanced;
         choice policer-choice {
           case case_1 {
             leaf policer {
               description "Name of policer to use to rate-limit traffic";
               junos:must "(!(\"firewall policer $$ aggregate\"))";
               junos:must-message "Cannot attach a aggregate policer to filter";
               type string {
                 junos:posix-pattern "!^((__.*)|(.{65,}))$";
                 junos:pattern-message "Must be a non-reserved string of 64 characters or less";
               }
             }
           }
           case case_2 {
             container three-color-policer {
               description "Police the packet using a three-color-policer";
               uses apply-advanced;
               choice type-choice {
                 case case_1 {
                   leaf single-rate {
                     description "Name of single-rate three-color policer to use to rate-limit traffic";
                     junos:must "(\"firewall three-color-policer $$ single-rate\")";
                     junos:must-message "Referenced single-rate policer does not exist";
                     type string {
                       junos:posix-pattern "!^((__.*)|(.{65,}))$";
                       junos:pattern-message "Must be a non-reserved string of 64 characters or less";
                     }
                   }
                 }
                 case case_2 {
                   leaf single-packet-rate {
                     description "Name of single-packet-rate three-color policer to use to rate-limit traffic";
                     junos:must "(\"firewall three-color-policer $$ single-packet-rate\")";
                     junos:must-message "Referenced single-packet-rate policer does not exist";
                     type string {
                       junos:posix-pattern "!^((__.*)|(.{65,}))$";
                       junos:pattern-message "Must be a non-reserved string of 64 characters or less";
                     }
                   }
                 }
                 case case_3 {
                   leaf two-rate {
                     description "Name of two-rate three-color policer to use to rate-limit traffic";
                     junos:must "(\"firewall three-color-policer $$ two-rate\")";
                     junos:must-message "Referenced two-rate policer does not exist";
                     type string {
                       junos:posix-pattern "!^((__.*)|(.{65,}))$";
                       junos:pattern-message "Must be a non-reserved string of 64 characters or less";
                     }
                   }
                 }
                 case case_4 {
                   leaf two-packet-rate {
                     description "Name of two-packet-rate three-color policer to use to rate-limit traffic";
                     junos:must "(\"firewall three-color-policer $$ two-packet-rate\")";
                     junos:must-message "Referenced two-packet-rate policer does not exist";
                     type string {
                       junos:posix-pattern "!^((__.*)|(.{65,}))$";
                       junos:pattern-message "Must be a non-reserved string of 64 characters or less";
                     }
                   }
                 }
               }
             }
           }
           case case_3 {
             leaf hierarchical-policer {
               description "Name of hierarchical policer to use to rate-limit traffic";
               type string {
                 junos:posix-pattern "!^((__.*)|(.{65,}))$";
                 junos:pattern-message "Must be a non-reserved string of 64 characters or less";
               }
             }
           }
         }
         choice policy-map-choice {
           case case_1 {
             leaf clear-policy-map {
               description "Clear the policy marking";
               type empty;
             }
           }
           case case_2 {
             leaf policy-map {
               description "Policy map action";
               junos:must "(\"class-of-service policy-map $$\")";
               junos:must-message "referenced policy map must be defined";
               type string {
                 junos:posix-pattern "!^((__.*)|(.{65,}))$";
                 junos:pattern-message "Must be a non-reserved string of 64 characters or less";
               }
             }
           }
         }
         leaf count {
           description "Count the packet in the named counter";
           type string {
             junos:posix-pattern "!^((__.*)|(.{65,}))$";
             junos:pattern-message "Must be a non-reserved string of 64 characters or less";
           }
         }
         leaf loss-priority {
           description "Packet's loss priority";
           type enumeration {
             enum "low" {
               description "Loss priority low";
             }
             enum "high" {
               description "Loss priority high";
             }
             enum "medium-low" {
               description "Loss priority medium-low";
             }
             enum "medium-high" {
               description "Loss priority medium-high";
             }
           }
         }
         leaf forwarding-class {
           description "Classify packet to forwarding class";
           type string {
             junos:posix-pattern "^.{1,64}$";
             junos:pattern-message "Must be string of 64 characters or less";
           }
         }
         leaf port-mirror-instance {
           description "Port-mirror the packet to the specified instance";
           junos:must "(\"forwarding-options port-mirroring instance $$\")";
           junos:must-message "Referenced port-mirroring instance does not exist";
           type string {
             junos:posix-pattern "!^((__.*)|(.{65,}))$";
             junos:pattern-message "Must be a non-reserved string of 64 characters or less";
           }
         }
         leaf next-hop-group {
           description "Use specified next-hop group";
           type string;
         }
         leaf port-mirror {
           description "Port-mirror the packet";
           junos:must "(!(\".. port-mirror-instance\"))";
           junos:must-message "'port-mirror' and 'port-mirror-instance' are mutually exclusive";
           junos:must "(\"forwarding-options port-mirroring\")";
           junos:must-message "Configure 'port-mirroring' under 'forwarding-options'";
           type empty;
         }
         leaf packet-mode {
           description "Bypass flow mode for the packet";
           type empty;
         }
         leaf force-premium {
           description "Convert traffic-class to premium";
           type empty;
         }
         leaf log {
           description "Log the packet";
           type empty;
         }
         leaf syslog {
           description "System log (syslog) information about the packet";
           type empty;
         }
         choice designation {
           case case_1 {
             container encapsulate {
               presence "enable encapsulate";
               description "Send to a tunnel";
               leaf tunnel-end-point {
                 description "Name of the tunnel end point";
                 junos:must "(\"firewall tunnel-end-point $$\")";
                 junos:must-message "referenced firewall tunnel-end-point must be defined";
                 type string {
                   junos:posix-pattern "!^((__.*)|(.{65,}))$";
                   junos:pattern-message "Must be a non-reserved string of 64 characters or less";
                 }
               }
             }
           }
           case case_2 {
             leaf accept {
               description "Accept the packet";
               type empty;
             }
           }
           case case_3 {
             leaf discard {
               description "Discard the packet";
               type empty;
             }
           }
           case case_4 {
             leaf next {
               description "Continue to next term in a filter";
               type enumeration {
                 enum "term" {
                   description "Continue to next term in a filter";
                 }
               }
             }
           }
         }
       }
     }
   }
   grouping es_filter {
     leaf name {
       description "Filter name";
       type string {
         junos:posix-pattern "!^((__.*)|(.{65,}))$";
         junos:pattern-message "Must be a non-reserved string of 64 characters or less";
       }
     }
     uses apply-advanced;
     leaf interface-specific {
       description "Defined counters are interface specific";
       type empty;
     }
     leaf physical-interface-filter {
       description "Filter is physical interface filter";
       type empty;
     }
     list term {
       key name;
       ordered-by user;
       description "Define a firewall term";
       leaf name {
         description "Term name";
         type string {
           junos:posix-pattern "!^((__.*)|(.{65,}))$";
           junos:pattern-message "Must be a non-reserved string of 64 characters or less";
         }
       }
       uses apply-advanced;
       container from {
         description "Define match criteria";
         uses apply-advanced;
         list interface {
           key name;
           ordered-by user;
           description "Match interface name";
           uses match_interface_object;
         }
         list source-mac-address {
           key name;
           ordered-by user;
           description "Match MAC source address";
           uses firewall_mac_addr_object;
         }
         list destination-mac-address {
           key name;
           ordered-by user;
           description "Match MAC destination address";
           uses firewall_mac_addr_object;
         }
         choice ether-type_choice {
           case case_1 {
             leaf-list ether-type {
               ordered-by user;
               type string;
             }
           }
           case case_2 {
             leaf-list ether-type-except {
               ordered-by user;
               type string;
             }
           }
         }
         choice l2-encap-type_choice {
           case case_1 {
             leaf-list l2-encap-type {
               ordered-by user;
               type string;
             }
           }
           case case_2 {
             leaf-list l2-encap-type-except {
               ordered-by user;
               type string;
             }
           }
         }
         choice vlan_choice {
           case case_1 {
           }
           case case_2 {
             leaf-list vlan-except {
               ordered-by user;
               description "VLAN name or ID";
               type string;
             }
           }
         }
         choice dot1q-tag_choice {
           case case_1 {
           }
           case case_2 {
             leaf-list dot1q-tag-except {
               ordered-by user;
               description "Range of values";
               type string {
                 junos:posix-pattern "^([0-9]{1,3}|[1-3][0-9][0-9][0-9]|40[0-8][0-9]|409[0-5])(-([0-9]{1,3}|[1-3][0-9][0-9][0-9]|40[0-8][0-9]|409[0-5]))?$";
                 junos:pattern-message "Must be a numerical value or range between 0-4095";
               }
             }
           }
         }
         choice dot1q-user-priority_choice {
           case case_1 {
           }
           case case_2 {
             leaf-list dot1q-user-priority-except {
               ordered-by user;
               type string;
             }
           }
         }
         list address {
           key name;
           ordered-by user;
           description "Match IP source or destination address";
           uses firewall_addr_object;
         }
         list source-address {
           key name;
           ordered-by user;
           description "Match IP source address";
           uses firewall_addr_object;
         }
         list destination-address {
           key name;
           ordered-by user;
           description "Match IP destination address";
           uses firewall_addr_object;
         }
         choice dscp_choice {
           case case_1 {
             leaf-list dscp {
               ordered-by user;
               type string;
             }
           }
           case case_2 {
             leaf-list dscp-except {
               ordered-by user;
               type string;
             }
           }
         }
         choice precedence_choice {
           case case_1 {
           }
           case case_2 {
             leaf-list precedence-except {
               ordered-by user;
               type string;
             }
           }
         }
         choice ip-options_choice {
           case case_1 {
             leaf-list ip-options {
               ordered-by user;
               type enumeration {
                 enum "any" {
                   description "Any IP option";
                 }
               }
             }
           }
           case case_2 {
             leaf-list ip-options-except {
               ordered-by user;
               type enumeration {
                 enum "any" {
                   description "Any IP option";
                 }
               }
             }
           }
         }
         leaf fragment-flags {
           description "Match fragment flags (in symbolic or hex formats) - (Ingress only)";
           type string;
         }
         leaf is-fragment {
           description "Match if packet is a fragment";
           type empty;
         }
         choice protocol_choice {
           case case_1 {
           }
           case case_2 {
             leaf-list protocol-except {
               ordered-by user;
               type string;
             }
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice port_choice {
           case case_1 {
             leaf-list port {
               ordered-by user;
               type string;
             }
           }
           case case_2 {
             leaf-list port-except {
               ordered-by user;
               type string;
             }
           }
         }
         leaf tcp-flags {
           description "Match TCP flags (in symbolic or hex formats)";
           type string;
         }
         leaf tcp-initial {
           description "Match initial packet of a TCP connection";
           type empty;
         }
         leaf tcp-established {
           description "Match packet of an established TCP connection";
           type empty;
         }
         choice icmp-type_choice {
           case case_1 {
             leaf-list icmp-type {
               ordered-by user;
               type string;
             }
           }
           case case_2 {
             leaf-list icmp-type-except {
               ordered-by user;
               type string;
             }
           }
         }
         choice icmp-code_choice {
           case case_1 {
             leaf-list icmp-code {
               ordered-by user;
               type string;
             }
           }
           case case_2 {
             leaf-list icmp-code-except {
               ordered-by user;
               type string;
             }
           }
         }
         list source-prefix-list {
           key name;
           ordered-by user;
           description "Match IP source prefixes in named list";
           uses firewall_prefix_list;
         }
         list destination-prefix-list {
           key name;
           ordered-by user;
           description "Match IP destination prefixes in named list";
           uses firewall_prefix_list;
         }
         list ip-source-address {
           key name;
           ordered-by user;
           description "Match IP source address";
           uses firewall_addr_object;
         }
         list ip-destination-address {
           key name;
           ordered-by user;
           description "Match IP destination address";
           uses firewall_addr_object;
         }
         choice ip-protocol_choice {
           case case_1 {
             leaf-list ip-protocol {
               ordered-by user;
               type string;
             }
           }
           case case_2 {
             leaf-list ip-protocol-except {
               ordered-by user;
               type string;
             }
           }
         }
         choice ip-precedence_choice {
           case case_1 {
             leaf-list ip-precedence {
               ordered-by user;
               type string;
             }
           }
           case case_2 {
             leaf-list ip-precedence-except {
               ordered-by user;
               type string;
             }
           }
         }
         list ipv6-destination-address {
           key name;
           ordered-by user;
           description "Match IPv6 destination address";
           uses firewall_addr6_object;
         }
         list ipv6-source-address {
           key name;
           ordered-by user;
           description "Match IPv6 source address";
           uses firewall_addr6_object;
         }
         list ipv6-address {
           key name;
           ordered-by user;
           description "Match IPv6 address";
           uses firewall_addr6_object;
         }
         choice ipv6-next-header_choice {
           case case_1 {
             leaf-list ipv6-next-header {
               ordered-by user;
               type string;
             }
           }
           case case_2 {
             leaf-list ipv6-next-header-except {
               ordered-by user;
               type string;
             }
           }
         }
         choice ipv6-payload-protocol_choice {
           case case_1 {
             leaf-list ipv6-payload-protocol {
               ordered-by user;
               type string;
             }
           }
           case case_2 {
             leaf-list ipv6-payload-protocol-except {
               ordered-by user;
               type string;
             }
           }
         }
         choice ipv6-traffic-class_choice {
           case case_1 {
             leaf-list ipv6-traffic-class {
               ordered-by user;
               type string;
             }
           }
           case case_2 {
             leaf-list ipv6-traffic-class-except {
               ordered-by user;
               type string;
             }
           }
         }
         list ipv6-source-prefix-list {
           key name;
           ordered-by user;
           description "Match IPV6 source prefixes in named list";
           uses firewall_prefix_list;
         }
         list ipv6-destination-prefix-list {
           key name;
           ordered-by user;
           description "Match IPV6 destination prefixes in named list";
           uses firewall_prefix_list;
         }
         list ipv6-prefix-list {
           key name;
           ordered-by user;
           description "Match IP source or destination prefixes in named list";
           uses firewall_prefix_list;
         }
         choice interface-group_choice {
           case case_1 {
             leaf-list interface-group {
               ordered-by user;
               description "Range of values";
               type string;
             }
           }
           case case_2 {
             leaf-list interface-group-except {
               ordered-by user;
               description "Range of values";
               type string;
             }
           }
         }
         choice vlan-ether-type_choice {
           case case_1 {
             leaf-list vlan-ether-type {
               ordered-by user;
               type string;
             }
           }
           case case_2 {
             leaf-list vlan-ether-type-except {
               ordered-by user;
               type string;
             }
           }
         }
         choice loss-priority_choice {
           case case_1 {
             leaf-list loss-priority {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
           case case_2 {
             leaf-list loss-priority-except {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
         }
         choice learn-vlan-id_choice {
           case case_1 {
             leaf-list learn-vlan-id {
               ordered-by user;
               description "Range of values";
               type string;
             }
           }
           case case_2 {
             leaf-list learn-vlan-id-except {
               ordered-by user;
               description "Range of values";
               type string;
             }
           }
         }
         choice learn-vlan-1p-priority_choice {
           case case_1 {
             leaf-list learn-vlan-1p-priority {
               ordered-by user;
               description "802.1p priority value 0-7";
               type union {
                 type string {
                   pattern "<.*>|$.*";
                 }
                 type uint32 {
                   range "0 .. 7";
                 }
               }
             }
           }
           case case_2 {
             leaf-list learn-vlan-1p-priority-except {
               ordered-by user;
               description "802.1p priority value 0-7";
               type union {
                 type string {
                   pattern "<.*>|$.*";
                 }
                 type uint32 {
                   range "0 .. 7";
                 }
               }
             }
           }
         }
         choice learn-vlan-dei_choice {
           case case_1 {
             leaf-list learn-vlan-dei {
               ordered-by user;
               description "DEI value 0-1";
               type union {
                 type string {
                   pattern "<.*>|$.*";
                 }
                 type uint32 {
                   range "0 .. 1";
                 }
               }
             }
           }
           case case_2 {
             leaf-list learn-vlan-dei-except {
               ordered-by user;
               description "DEI value 0-1";
               type union {
                 type string {
                   pattern "<.*>|$.*";
                 }
                 type uint32 {
                   range "0 .. 1";
                 }
               }
             }
           }
         }
         choice user-vlan-id_choice {
           case case_1 {
             leaf-list user-vlan-id {
               ordered-by user;
               description "Range of values";
               type string;
             }
           }
           case case_2 {
             leaf-list user-vlan-id-except {
               ordered-by user;
               description "Range of values";
               type string;
             }
           }
         }
         choice user-vlan-1p-priority_choice {
           case case_1 {
             leaf-list user-vlan-1p-priority {
               ordered-by user;
               description "802.1p priority value 0-7";
               type union {
                 type string {
                   pattern "<.*>|$.*";
                 }
                 type uint32 {
                   range "0 .. 7";
                 }
               }
             }
           }
           case case_2 {
             leaf-list user-vlan-1p-priority-except {
               ordered-by user;
               description "802.1p priority value 0-7";
               type union {
                 type string {
                   pattern "<.*>|$.*";
                 }
                 type uint32 {
                   range "0 .. 7";
                 }
               }
             }
           }
         }
         choice traffic-type_choice {
           case case_1 {
             leaf-list traffic-type {
               ordered-by user;
               type enumeration {
                 enum "broadcast" {
                   description "Packets with broadcast ethernet address";
                 }
                 enum "multicast" {
                   description "Packets with multicast ethernet address";
                 }
                 enum "unknown-unicast" {
                   description "Packets for which destination ethernet address has not been learnt";
                 }
                 enum "known-unicast" {
                   description "Packets for which destination ethernet address has been learnt";
                 }
               }
             }
           }
           case case_2 {
             leaf-list traffic-type-except {
               ordered-by user;
               type enumeration {
                 enum "broadcast" {
                   description "Packets with broadcast ethernet address";
                 }
                 enum "multicast" {
                   description "Packets with multicast ethernet address";
                 }
                 enum "unknown-unicast" {
                   description "Packets for which destination ethernet address has not been learnt";
                 }
                 enum "known-unicast" {
                   description "Packets for which destination ethernet address has been learnt";
                 }
               }
             }
           }
         }
         list ip-address {
           key name;
           ordered-by user;
           description "Match IP source or destination address";
           uses firewall_addr_object;
         }
         list interface-set {
           key name;
           ordered-by user;
           description "Match interface in set";
           uses match_interface_set_object;
         }
         list prefix-list {
           key name;
           ordered-by user;
           description "Match IP source or destination prefixes in named list";
           uses firewall_prefix_list;
         }
         choice isid_choice {
           case case_1 {
             leaf-list isid {
               ordered-by user;
               description "Range of values";
               type string;
             }
           }
           case case_2 {
             leaf-list isid-except {
               ordered-by user;
               description "Range of values";
               type string;
             }
           }
         }
         choice isid-priority-code-point_choice {
           case case_1 {
             leaf-list isid-priority-code-point {
               ordered-by user;
               description "802.1p priority value 0-7";
               type union {
                 type string {
                   pattern "<.*>|$.*";
                 }
                 type uint32 {
                   range "0 .. 7";
                 }
               }
             }
           }
           case case_2 {
             leaf-list isid-priority-code-point-except {
               ordered-by user;
               description "802.1p priority value 0-7";
               type union {
                 type string {
                   pattern "<.*>|$.*";
                 }
                 type uint32 {
                   range "0 .. 7";
                 }
               }
             }
           }
         }
         choice isid-dei_choice {
           case case_1 {
             leaf-list isid-dei {
               ordered-by user;
               description "DEI value 0-1";
               type union {
                 type string {
                   pattern "<.*>|$.*";
                 }
                 type uint32 {
                   range "0 .. 1";
                 }
               }
             }
           }
           case case_2 {
             leaf-list isid-dei-except {
               ordered-by user;
               description "DEI value 0-1";
               type union {
                 type string {
                   pattern "<.*>|$.*";
                 }
                 type uint32 {
                   range "0 .. 1";
                 }
               }
             }
           }
         }
         choice forwarding-class_choice {
           case case_1 {
             leaf-list forwarding-class {
               ordered-by user;
               description "String name";
               type string {
                 junos:posix-pattern "^.{1,64}$";
                 junos:pattern-message "Must be string of 64 characters or less";
               }
             }
           }
           case case_2 {
             leaf-list forwarding-class-except {
               ordered-by user;
               description "String name";
               type string {
                 junos:posix-pattern "^.{1,64}$";
                 junos:pattern-message "Must be string of 64 characters or less";
               }
             }
           }
         }
         choice arp-type_choice {
           case case_1 {
             leaf-list arp-type {
               ordered-by user;
               type string;
             }
           }
         }
         choice flex-mask_choice {
           case case_1 {
             container flexible-match-mask {
               description "Match flexible mask";
               uses match_L2_flexible_mask;
             }
           }
         }
         choice flex-range_choice {
           case case_1 {
             container flexible-match-range {
               description "Match flexible range";
               uses match_L2_flexible_range;
             }
           }
         }
         container ip-version {
           description "Define IP version";
           uses apply-advanced;
           container ipv4 {
             junos:must "(!(\".. ipv6\"))";
             junos:must-message "Same term cannot have both IPv4 & IPv6 IP version";
             description "Define L3/L4 match items to match IPv4 packets";
             uses apply-advanced;
             list address {
               key name;
               ordered-by user;
               description "Match IP source or destination address";
               uses firewall_addr_object;
             }
             choice dscp_choice {
               case case_1 {
                 leaf-list dscp {
                   ordered-by user;
                   type string;
                 }
               }
               case case_2 {
                 leaf-list dscp-except {
                   ordered-by user;
                   type string;
                 }
               }
             }
             choice precedence_choice {
               case case_1 {
               }
               case case_2 {
                 leaf-list precedence-except {
                   ordered-by user;
                   type string;
                 }
               }
             }
             choice ip-options_choice {
               case case_1 {
                 leaf-list ip-options {
                   ordered-by user;
                   type enumeration {
                     enum "any" {
                       description "Any IP option";
                     }
                   }
                 }
               }
               case case_2 {
                 leaf-list ip-options-except {
                   ordered-by user;
                   type enumeration {
                     enum "any" {
                       description "Any IP option";
                     }
                   }
                 }
               }
             }
             leaf fragment-flags {
               description "Match fragment flags (in symbolic or hex formats) - (Ingress only)";
               type string;
             }
             leaf is-fragment {
               description "Match if packet is a fragment";
               type empty;
             }
             choice protocol_choice {
               case case_1 {
               }
               case case_2 {
                 leaf-list protocol-except {
                   ordered-by user;
                   type string;
                 }
               }
             }
             choice source-port_choice {
               case case_1 {
                 leaf-list source-port {
                   ordered-by user;
                   type string;
                 }
               }
               case case_2 {
                 leaf-list source-port-except {
                   ordered-by user;
                   type string;
                 }
               }
             }
             choice destination-port_choice {
               case case_1 {
                 leaf-list destination-port {
                   ordered-by user;
                   type string;
                 }
               }
               case case_2 {
                 leaf-list destination-port-except {
                   ordered-by user;
                   type string;
                 }
               }
             }
             choice port_choice {
               case case_1 {
                 leaf-list port {
                   ordered-by user;
                   type string;
                 }
               }
               case case_2 {
                 leaf-list port-except {
                   ordered-by user;
                   type string;
                 }
               }
             }
             leaf tcp-flags {
               description "Match TCP flags (in symbolic or hex formats) - (Ingress only)";
               type string;
             }
             leaf tcp-initial {
               description "Match initial packet of a TCP connection - (Ingress only)";
               type empty;
             }
             leaf tcp-established {
               description "Match packet of an established TCP connection";
               type empty;
             }
             choice icmp-type_choice {
               case case_1 {
                 leaf-list icmp-type {
                   ordered-by user;
                   type string;
                 }
               }
               case case_2 {
                 leaf-list icmp-type-except {
                   ordered-by user;
                   type string;
                 }
               }
             }
             choice icmp-code_choice {
               case case_1 {
                 leaf-list icmp-code {
                   ordered-by user;
                   type string;
                 }
               }
               case case_2 {
                 leaf-list icmp-code-except {
                   ordered-by user;
                   type string;
                 }
               }
             }
             list source-prefix-list {
               key name;
               ordered-by user;
               description "Match IP source prefixes in named list";
               uses firewall_prefix_list;
             }
             list destination-prefix-list {
               key name;
               ordered-by user;
               description "Match IP destination prefixes in named list";
               uses firewall_prefix_list;
             }
             list ip-source-address {
               key name;
               ordered-by user;
               description "Match IP source address";
               uses firewall_addr_object;
             }
             list ip-destination-address {
               key name;
               ordered-by user;
               description "Match IP destination address";
               uses firewall_addr_object;
             }
             choice ip-protocol_choice {
               case case_1 {
                 leaf-list ip-protocol {
                   ordered-by user;
                   type string;
                 }
               }
               case case_2 {
                 leaf-list ip-protocol-except {
                   ordered-by user;
                   type string;
                 }
               }
             }
             choice ip-precedence_choice {
               case case_1 {
                 leaf-list ip-precedence {
                   ordered-by user;
                   type string;
                 }
               }
               case case_2 {
                 leaf-list ip-precedence-except {
                   ordered-by user;
                   type string;
                 }
               }
             }
           }
           container ipv6 {
             junos:must "(!(\".. ipv4\"))";
             junos:must-message "Same term cannot have both IPv4 & IPv6 IP version";
             description "Define L3/L4 match items to match IPv6 packets";
             uses apply-advanced;
             choice traffic-class_choice {
               case case_1 {
                 leaf-list traffic-class {
                   ordered-by user;
                   type string;
                 }
               }
               case case_2 {
                 leaf-list traffic-class-except {
                   ordered-by user;
                   type string;
                 }
               }
             }
             choice next-header_choice {
               case case_1 {
                 leaf-list next-header {
                   ordered-by user;
                   type string;
                 }
               }
               case case_2 {
                 leaf-list next-header-except {
                   ordered-by user;
                   type string;
                 }
               }
             }
             choice payload-protocol_choice {
               case case_1 {
                 leaf-list payload-protocol {
                   ordered-by user;
                   type string;
                 }
               }
               case case_2 {
                 leaf-list payload-protocol-except {
                   ordered-by user;
                   type string;
                 }
               }
             }
             choice source-port_choice {
               case case_1 {
                 leaf-list source-port {
                   ordered-by user;
                   type string;
                 }
               }
               case case_2 {
                 leaf-list source-port-except {
                   ordered-by user;
                   type string;
                 }
               }
             }
             choice destination-port_choice {
               case case_1 {
                 leaf-list destination-port {
                   ordered-by user;
                   type string;
                 }
               }
               case case_2 {
                 leaf-list destination-port-except {
                   ordered-by user;
                   type string;
                 }
               }
             }
             choice port_choice {
               case case_1 {
                 leaf-list port {
                   ordered-by user;
                   type string;
                 }
               }
               case case_2 {
                 leaf-list port-except {
                   ordered-by user;
                   type string;
                 }
               }
             }
             choice extension-header_choice {
               case case_1 {
                 leaf-list extension-header {
                   ordered-by user;
                   type string;
                 }
               }
               case case_2 {
                 leaf-list extension-header-except {
                   ordered-by user;
                   type string;
                 }
               }
             }
             leaf tcp-flags {
               description "Match TCP flags (in symbolic or hex formats)";
               junos:must "((\".. next-header tcp\" || (\".. next-header 6\" || \".. payload-protocol tcp\")))";
               junos:must-message "next-header tcp or next-header 6 or payload-protocol tcp must be defined in the same clause";
               type string;
             }
             leaf tcp-initial {
               description "Match initial packet of a TCP connection";
               junos:must "((\".. next-header tcp\" || (\".. next-header 6\" || \".. payload-protocol tcp\")))";
               junos:must-message "next-header tcp or next-header 6 or payload-protocol tcp must be defined in the same clause";
               type empty;
             }
             leaf tcp-established {
               description "Match packet of an established TCP connection";
               junos:must "((\".. next-header tcp\" || (\".. next-header 6\" || \".. payload-protocol tcp\")))";
               junos:must-message "next-header tcp or next-header 6 or payload-protocol tcp must be defined in the same clause";
               type empty;
             }
             choice icmp-type_choice {
               case case_1 {
                 leaf-list icmp-type {
                   ordered-by user;
                   type string;
                 }
               }
               case case_2 {
                 leaf-list icmp-type-except {
                   ordered-by user;
                   type string;
                 }
               }
             }
             choice icmp-code_choice {
               case case_1 {
                 leaf-list icmp-code {
                   ordered-by user;
                   type string;
                 }
               }
               case case_2 {
                 leaf-list icmp-code-except {
                   ordered-by user;
                   type string;
                 }
               }
             }
             list source-prefix-list {
               key name;
               ordered-by user;
               description "Match IP source prefixes in named list";
               uses firewall_prefix_list;
             }
             list destination-prefix-list {
               key name;
               ordered-by user;
               description "Match IP destination prefixes in named list";
               uses firewall_prefix_list;
             }
             list ip6-source-address {
               key name;
               ordered-by user;
               description "Match source address";
               uses firewall_addr6_object;
             }
             list ip6-destination-address {
               key name;
               ordered-by user;
               description "Match destination address";
               uses firewall_addr6_object;
             }
           }
         }
         container vxlan {
           description "Define vxlan match items";
           uses apply-advanced;
           choice vni_choice {
             case case_1 {
               leaf-list vni {
                 ordered-by user;
                 description "Range of values";
                 type string {
                   junos:posix-pattern "^([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f])(-([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f]))?$";
                   junos:pattern-message "Must be a numeric value or a range between 0-16777215";
                 }
               }
             }
             case case_2 {
               leaf-list vni-except {
                 ordered-by user;
                 description "Range of values";
                 type string {
                   junos:posix-pattern "^([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f])(-([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f]))?$";
                   junos:pattern-message "Must be a numeric value or a range between 0-16777215";
                 }
               }
             }
           }
           choice rsvd1_choice {
             case case_1 {
               leaf-list rsvd1 {
                 ordered-by user;
                 description "Range of values";
                 type string {
                   junos:posix-pattern "^([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f])(-([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f]))?$";
                   junos:pattern-message "Must be a numeric value or a range between 0-16777215";
                 }
               }
             }
             case case_2 {
               leaf-list rsvd1-except {
                 ordered-by user;
                 description "Range of values";
                 type string {
                   junos:posix-pattern "^([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f])(-([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f]))?$";
                   junos:pattern-message "Must be a numeric value or a range between 0-16777215";
                 }
               }
             }
           }
           choice rsvd2_choice {
             case case_1 {
               leaf-list rsvd2 {
                 ordered-by user;
                 description "Range of values";
                 type string {
                   junos:posix-pattern "^([0-9]|[1-9][0-9]|1[0-9][0-9]|2[0-4][0-9]|25[0-5]|0x[0-f]|0x[0-f][0-f])(-([0-9]|[1-9][0-9]|1[0-9][0-9]|2[0-4][0-9]|25[0-5]|0x[0-f]|0x[0-f][0-f]))?$";
                   junos:pattern-message "Must be a numeric value or a range between 0-255";
                 }
               }
             }
             case case_2 {
               leaf-list rsvd2-except {
                 ordered-by user;
                 description "Range of values";
                 type string {
                   junos:posix-pattern "^([0-9]|[1-9][0-9]|1[0-9][0-9]|2[0-4][0-9]|25[0-5]|0x[0-f]|0x[0-f][0-f])(-([0-9]|[1-9][0-9]|1[0-9][0-9]|2[0-4][0-9]|25[0-5]|0x[0-f]|0x[0-f][0-f]))?$";
                   junos:pattern-message "Must be a numeric value or a range between 0-255";
                 }
               }
             }
           }
           container flags {
             description "Match VXlan flag field";
             uses match_flags_value;
           }
         }
       }
       container then {
         description "Action to take if the 'from' condition is matched";
         uses apply-advanced;
         choice designation {
           case case_1 {
             leaf accept {
               description "Accept the packet";
               type empty;
             }
           }
           case case_2 {
             leaf discard {
               description "Discard the packet";
               type empty;
             }
           }
           case case_3 {
             leaf next {
               description "Continue to next term in a filter";
               type enumeration {
                 enum "term" {
                   description "Continue to next term in a filter";
                 }
               }
             }
           }
         }
         leaf log {
           description "Log the packet";
           type empty;
         }
         leaf syslog {
           description "System log (syslog) information about the packet";
           type empty;
         }
         leaf forwarding-class {
           description "Classify packet to forwarding class";
           type string {
             junos:posix-pattern "^.{1,64}$";
             junos:pattern-message "Must be string of 64 characters or less";
           }
         }
         leaf analyzer {
           description "Name of analyzer - (Ingress only)";
           junos:must "(\"ethernet-switching-options analyzer $$\")";
           junos:must-message "Named Analyzer must be set";
           type string {
             junos:posix-pattern "!^((__.*)|(.{65,}))$";
             junos:pattern-message "Must be a non-reserved string of 64 characters or less";
           }
         }
         leaf port-mirror-instance {
           description "Port-mirror the packet to specified instance";
           junos:must "(\"forwarding-options port-mirroring instance $$\")";
           junos:must-message "Referenced port-mirroring instance does not exist";
           type string {
             junos:posix-pattern "!^((__.*)|(.{65,}))$";
             junos:pattern-message "Must be a non-reserved string of 64 characters or less";
           }
         }
         leaf port-mirror {
           description "Port-mirror the packet";
           junos:must "(!(\".. port-mirror-instance\"))";
           junos:must-message "'port-mirror' and 'port-mirror-instance' are mutually exclusive";
           junos:must "(\"forwarding-options port-mirroring\")";
           junos:must-message "Configure 'port-mirroring' under 'forwarding-options'";
           type empty;
         }
         leaf next-hop-group {
           description "Use specified next-hop group";
           junos:must "(\"forwarding-options next-hop-group $$\")";
           junos:must-message "Referenced next-hop group is not defined";
           type string;
         }
         leaf loss-priority {
           description "Packet's loss priority";
           type enumeration {
             enum "low" {
               description "Loss priority low";
             }
             enum "high" {
               description "Loss priority high";
             }
             enum "medium-low" {
               description "Loss priority medium-low";
             }
             enum "medium-high" {
               description "Loss priority medium-high";
             }
           }
         }
         leaf count {
           description "Count the packet in the named counter";
           type string {
             junos:posix-pattern "!^((__.*)|(.{65,}))$";
             junos:pattern-message "Must be a non-reserved string of 64 characters or less";
           }
         }
         choice policer-choice {
           case case_1 {
             leaf policer {
               description "Name of policer to use to rate-limit traffic";
               junos:must "(!(\"firewall policer $$ aggregate\"))";
               junos:must-message "Cannot attach a aggregate policer to filter";
               type string {
                 junos:posix-pattern "!^((__.*)|(.{65,}))$";
                 junos:pattern-message "Must be a non-reserved string of 64 characters or less";
               }
             }
           }
           case case_2 {
             container three-color-policer {
               description "Police the packet using a three-color-policer";
               uses apply-advanced;
               choice type-choice {
                 case case_1 {
                   leaf single-rate {
                     description "Name of single-rate three-color policer to use to rate-limit traffic";
                     junos:must "(\"firewall three-color-policer $$ single-rate\")";
                     junos:must-message "Referenced single-rate policer does not exist";
                     type string {
                       junos:posix-pattern "!^((__.*)|(.{65,}))$";
                       junos:pattern-message "Must be a non-reserved string of 64 characters or less";
                     }
                   }
                 }
                 case case_2 {
                   leaf single-packet-rate {
                     description "Name of single-packet-rate three-color policer to use to rate-limit traffic";
                     junos:must "(\"firewall three-color-policer $$ single-packet-rate\")";
                     junos:must-message "Referenced single-packet-rate policer does not exist";
                     type string {
                       junos:posix-pattern "!^((__.*)|(.{65,}))$";
                       junos:pattern-message "Must be a non-reserved string of 64 characters or less";
                     }
                   }
                 }
                 case case_3 {
                   leaf two-rate {
                     description "Name of two-rate three-color policer to use to rate-limit traffic";
                     junos:must "(\"firewall three-color-policer $$ two-rate\")";
                     junos:must-message "Referenced two-rate policer does not exist";
                     type string {
                       junos:posix-pattern "!^((__.*)|(.{65,}))$";
                       junos:pattern-message "Must be a non-reserved string of 64 characters or less";
                     }
                   }
                 }
                 case case_4 {
                   leaf two-packet-rate {
                     description "Name of two-packet-rate three-color policer to use to rate-limit traffic";
                     junos:must "(\"firewall three-color-policer $$ two-packet-rate\")";
                     junos:must-message "Referenced two-packet-rate policer does not exist";
                     type string {
                       junos:posix-pattern "!^((__.*)|(.{65,}))$";
                       junos:pattern-message "Must be a non-reserved string of 64 characters or less";
                     }
                   }
                 }
               }
             }
           }
           case case_3 {
             leaf hierarchical-policer {
               description "Name of hierarchical policer to use to rate-limit traffic";
               type string {
                 junos:posix-pattern "!^((__.*)|(.{65,}))$";
                 junos:pattern-message "Must be a non-reserved string of 64 characters or less";
               }
             }
           }
         }
         leaf vlan {
           description "Name of VLAN - (Ingress only)";
           junos:must "((\"vlans $$\" && !(\"vlans $$ vlan-range\")))";
           junos:must-message "Named or Non-range vlan must be set";
           type string;
         }
         leaf interface {
           description "Switch traffic to the specified interface by-passing switching lookup - (Ingress only)";
           type union {
             type jt:interface-unit;
             type string {
               pattern "<.*>|$.*";
             }
           }
         }
         container vxlan {
           description "Vxlan related data";
           uses apply-advanced;
           leaf flags {
             description "Set vxlan flags value (8..255 or 0x08..0xFF)";
             type string {
               junos:posix-pattern "^([8-9]|[1-9][0-9]|1[0-9][0-9]|2[0-4][0-9]|25[0-5]|0x[8-f]|0x0[8-f]|0x[1-f][0-f])(-([8-9]|[1-9][0-9]|1[0-9][0-9]|2[0-4][0-9]|25[0-5]|0x[8-f]|0x0[8-f]|0x[1-f][0-f]))?$";
               junos:pattern-message "Must be a numeric value or a range between 8-255";
             }
           }
           leaf rsvd1 {
             description "Set vxlan reserved-1 value";
             type string {
               junos:posix-pattern "^([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f])(-([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f]))?$";
               junos:pattern-message "Must be a numeric value or a range between 0-16777215";
             }
           }
           leaf rsvd2 {
             description "Set vxlan reserved-2 value";
             type string {
               junos:posix-pattern "^([0-9]|[1-9][0-9]|1[0-9][0-9]|2[0-4][0-9]|25[0-5]|0x[0-f]|0x[0-f][0-f])(-([0-9]|[1-9][0-9]|1[0-9][0-9]|2[0-4][0-9]|25[0-5]|0x[0-f]|0x[0-f][0-f]))?$";
               junos:pattern-message "Must be a numeric value or a range between 0-255";
             }
           }
         }
       }
     }
   }
   grouping firewall_addr6_object {
     leaf name {
       description "Prefix to match";
       type jt:ipv6prefix;
     }
     leaf except {
       description "Match address not in this prefix";
       type empty;
     }
   }
   grouping firewall_addr_object {
     leaf name {
       description "Prefix to match";
       type jt:ipv4prefix;
     }
     leaf except {
       description "Match address not in this prefix";
       type empty;
     }
   }
   grouping firewall_flexible_match {
     description "Define a flexible match";
     leaf name {
       description "Flex match template name";
       type string {
         junos:posix-pattern "!^((__.*)|(.{65,}))$";
         junos:pattern-message "Must be a non-reserved string of 64 characters or less";
       }
     }
     uses apply-advanced;
     leaf match-start {
       description "Start point to match in packet";
       type enumeration {
         enum "layer-2" {
           description "Layer-2 match start";
         }
         enum "layer-3" {
           description "Layer-3 match start";
         }
         enum "layer-4" {
           description "Layer-4 match start";
         }
         enum "payload" {
           description "Payload match start";
         }
       }
     }
     leaf byte-offset {
       description "Byte offset after the match start point";
       type union {
         type uint32;
         type string {
           pattern "<.*>|$.*";
         }
       }
     }
     leaf bit-offset {
       description "Bit offset after the (match-start + byte) offset";
       type union {
         type string {
           pattern "<.*>|$.*";
         }
         type uint32 {
           range "0 .. 7";
         }
       }
     }
     leaf bit-length {
       description "Length of the data to be matched in bits, not needed for string input";
       type union {
         type string {
           pattern "<.*>|$.*";
         }
         type uint32 {
           range "1 .. 128";
         }
       }
     }
   }
   grouping firewall_hierpolicer {
     description "Define a hierarchical policer";
     leaf name {
       description "Hierarchical Policer name";
       type string {
         junos:posix-pattern "!^((__.*)|(.{65,}))$";
         junos:pattern-message "Must be a non-reserved string of 64 characters or less";
       }
     }
     choice sharing {
       case case_1 {
         leaf logical-interface-policer {
           description "Hierarchical policer is a logical interface policer";
           type empty;
         }
       }
       case case_2 {
         leaf physical-interface-policer {
           description "Hierarchical policer is a physical interface policer";
           type empty;
         }
       }
     }
     leaf shared-bandwidth-policer {
       description "Share policer bandwidth among bundle links";
       type empty;
     }
     leaf filter-specific {
       description "Hierarchical policer is filter-specific";
       type empty;
     }
     container aggregate {
       description "Aggregate definition";
       uses hierarchical-policer-aggregate-bucket;
     }
     container premium {
       description "Premium definition";
       uses hierarchical-policer-premium-bucket;
     }
   }
   grouping firewall_load_balance_group {
     description "Define group of destinations for load balancing";
     leaf name {
       description "Load balance group name";
       type string {
         junos:posix-pattern "!^((__.*)|(.{65,}))$";
         junos:pattern-message "Must be a non-reserved string of 64 characters or less";
       }
     }
     uses apply-advanced;
     leaf-list next-hop-group {
       ordered-by user;
       description "Use specified next-hop group";
       type string;
     }
   }
   grouping firewall_mac_addr_object {
     leaf name {
       description "MAC address to match";
       type jt:mac-addr-prefix;
     }
     leaf except {
       description "Match MAC address not in this range";
       type empty;
     }
   }
   grouping firewall_policer {
     description "Define a policer";
     leaf name {
       description "Policer name";
       type string {
         junos:posix-pattern "!^((__.*)|(.{65,}))$";
         junos:pattern-message "Must be a non-reserved string of 64 characters or less";
       }
     }
     uses apply-advanced;
     leaf filter-specific {
       description "Policer is filter-specific";
       type empty;
     }
     leaf logical-interface-policer {
       description "Policer is logical interface policer";
       type empty;
     }
     leaf physical-interface-policer {
       description "Policer is physical interface policer";
       type empty;
     }
     leaf logical-bandwidth-policer {
       description "Policer uses logical interface bandwidth";
       type empty;
     }
     leaf shared-bandwidth-policer {
       description "Share policer bandwidth among bundle links";
       type empty;
     }
     choice exceeding {
       case case_1 {
         container if-exceeding {
           presence "enable if-exceeding";
           description "Define rate limits";
           uses apply-advanced;
           choice bandwidth {
             case case_1 {
               leaf bandwidth-limit {
                 description "Bandwidth limit";
                 units "bits per second";
                 type string;
               }
             }
             case case_2 {
               leaf bandwidth-percent {
                 description "Bandwidth limit in percentage";
                 units "percent";
                 type union {
                   type string {
                     pattern "<.*>|$.*";
                   }
                   type uint32 {
                     range "1 .. 100";
                   }
                 }
               }
             }
           }
           leaf burst-size-limit {
             description "Burst size limit";
             units "bytes";
             type string;
           }
           container aggregate-policing {
             presence "enable aggregate-policing";
             description "Configure Aggregate Policer";
             uses apply-advanced;
             list policer {
               key name;
               ordered-by user;
               description "Two-color policer to be used as aggregate";
               max-elements 1;
               leaf name {
                 description "Name of two-color policer to use to aggregate police";
                 junos:must "(\"firewall policer $$ aggregate\")";
                 junos:must-message "Referenced policer must be of type 'aggregate'";
                 junos:must "(\"firewall policer $$\")";
                 junos:must-message "Referenced aggregate policer is not defined";
                 type string;
               }
               uses apply-advanced;
               leaf aggregate-sharing-mode {
                 description "Hierarchical Metering model";
                 type enumeration {
                   enum "guarantee" {
                     description "Child policer rates are guaranteed rates for member flow";
                   }
                   enum "peak" {
                     description "Child policer rates are peak rates for member flow";
                   }
                 }
               }
             }
           }
         }
       }
       case case_2 {
         container if-exceeding-pps {
           presence "enable if-exceeding-pps";
           description "Define pps limits";
           uses apply-advanced;
           choice pps {
             case case_1 {
               leaf pps-limit {
                 description "PPS limit";
                 units "packets per second";
                 type string;
               }
             }
           }
           leaf packet-burst {
             description "PPS burst size limit";
             units "packets";
             type string;
           }
         }
       }
     }
     container then {
       description "Action to take if the rate limits are exceeded";
       uses apply-advanced;
       leaf discard {
         description "Discard the packet";
         type empty;
       }
       leaf loss-priority {
         description "Packet's loss priority";
         type enumeration {
           enum "low" {
             description "Loss priority low";
           }
           enum "high" {
             description "Loss priority high";
           }
           enum "medium-low" {
             description "Loss priority medium-low";
           }
           enum "medium-high" {
             description "Loss priority medium-high";
           }
         }
       }
       leaf forwarding-class {
         description "Classify packet to forwarding class";
         type string {
           junos:posix-pattern "^.{1,64}$";
           junos:pattern-message "Must be string of 64 characters or less";
         }
       }
       leaf out-of-profile {
         description "Discard packets only if both congested and over threshold";
         type empty;
       }
     }
     container aggregate {
       presence "enable aggregate";
       junos:must "(!(\".. if-exceeding aggregate-policing\"))";
       junos:must-message "Cannot use same template as both child and parent policer";
       junos:must "(!(\".. filter-specific\"))";
       junos:must-message "'filter-specific' not valid for aggregate policers; Use 'aggregate instantiation' ";
       description "Aggregate policer used in Extended Hierarchical Policers";
       uses apply-advanced;
       leaf instantiation {
         description "Specify instantiation semantics of aggregate policer";
         type enumeration {
           enum "global" {
             description "Single global instance of aggregate policer";
           }
         }
       }
     }
   }
   grouping firewall_prefix_list {
     leaf name {
       description "Prefix list to match";
       type string;
     }
     leaf except {
       description "Match addresses not in this prefix list";
       type empty;
     }
   }
   grouping hierarchical-policer-aggregate-bucket {
     uses apply-advanced;
     choice hp-aggregate-exceeding {
       case case_1 {
         container if-exceeding {
           presence "enable if-exceeding";
           description "Define rate limits";
           uses apply-advanced;
           choice bandwidth {
             case case_1 {
               leaf bandwidth-limit {
                 description "Bandwidth limit";
                 units "bits per second";
                 type string;
               }
             }
           }
           leaf burst-size-limit {
             description "Burst size limit";
             units "bytes";
             type string;
           }
         }
       }
       case case_2 {
         container if-exceeding-pps {
           presence "enable if-exceeding-pps";
           description "Define pps limits";
           uses apply-advanced;
           choice pps {
             case case_1 {
               leaf pps-limit {
                 description "PPS limit";
                 units "packets per second";
                 type string;
               }
             }
           }
           leaf packet-burst {
             description "PPS burst size limit";
             units "packets";
             type string;
           }
         }
       }
     }
     container then {
       description "Action to take if the rate limits are exceeded";
       uses apply-advanced;
       choice hierarchical-policer-action {
         case case_1 {
           leaf discard {
             description "Discard the packet";
             type empty;
           }
         }
         case case_2 {
           leaf loss-priority {
             description "Packet's loss priority";
             junos:must "(!(\".. forwarding-class\"))";
             junos:must-message "Cannot configure loss-priority with forwarding-class";
             type enumeration {
               enum "low" {
                 description "Loss priority low";
               }
               enum "high" {
                 description "Loss priority high";
               }
               enum "medium-low" {
                 description "Loss priority medium-low";
               }
               enum "medium-high" {
                 description "Loss priority medium-high";
               }
             }
           }
         }
         case case_3 {
           leaf forwarding-class {
             description "Classify packet to forwarding class";
             junos:must "(!(\".. loss-priority\"))";
             junos:must-message "Cannot configure forwarding-class with loss-priority";
             type string {
               junos:posix-pattern "^.{1,64}$";
               junos:pattern-message "Must be string of 64 characters or less";
             }
           }
         }
       }
     }
   }
   grouping hierarchical-policer-premium-bucket {
     uses apply-advanced;
     choice hp-premium-exceeding {
       case case_1 {
         container if-exceeding {
           presence "enable if-exceeding";
           description "Define rate limits";
           uses apply-advanced;
           choice bandwidth {
             case case_1 {
               leaf bandwidth-limit {
                 description "Bandwidth limit";
                 units "bits per second";
                 type string;
               }
             }
           }
           leaf burst-size-limit {
             description "Burst size limit";
             units "bytes";
             type string;
           }
         }
       }
       case case_2 {
         container if-exceeding-pps {
           presence "enable if-exceeding-pps";
           description "Define pps limits";
           uses apply-advanced;
           choice pps {
             case case_1 {
               leaf pps-limit {
                 description "PPS limit";
                 units "packets per second";
                 type string;
               }
             }
           }
           leaf packet-burst {
             description "PPS burst size limit";
             units "packets";
             type string;
           }
         }
       }
     }
     container then {
       description "Action to take if the rate limits are exceeded";
       uses apply-advanced;
       choice hierarchical-policer-action {
         case case_1 {
           leaf discard {
             description "Discard the packet";
             type empty;
           }
         }
       }
     }
   }
   grouping inet6_dialer_filter {
     description "Define an IPv6 dialer filter";
     leaf name {
       description "Filter name";
       type string {
         junos:posix-pattern "!^((__.*)|(.{65,}))$";
         junos:pattern-message "Must be a non-reserved string of 64 characters or less";
       }
     }
     uses apply-advanced;
     leaf-list accounting-profile {
       ordered-by user;
       description "Accounting profile name";
       junos:must "(\"accounting-options filter-profile\")";
       junos:must-message "referenced accounting profile must be defined";
       type string;
     }
     list term {
       key name;
       ordered-by user;
       description "Define a firewall term";
       leaf name {
         description "Term name";
         type string {
           junos:posix-pattern "!^((__.*)|(.{65,}))$";
           junos:pattern-message "Must be a non-reserved string of 64 characters or less";
         }
       }
       uses apply-advanced;
       container from {
         description "Define match criteria";
         uses apply-advanced;
         list source-address {
           key name;
           ordered-by user;
           description "Match source address";
           uses firewall_addr6_object;
         }
         list destination-address {
           key name;
           ordered-by user;
           description "Match destination address";
           uses firewall_addr6_object;
         }
         list address {
           key name;
           ordered-by user;
           description "Match source or destination address";
           uses firewall_addr6_object;
         }
         list source-prefix-list {
           key name;
           ordered-by user;
           description "Match source prefixes in named list";
           uses firewall_prefix_list;
         }
         list destination-prefix-list {
           key name;
           ordered-by user;
           description "Match destination prefixes in named list";
           uses firewall_prefix_list;
         }
         list prefix-list {
           key name;
           ordered-by user;
           description "Match source or destination prefixes in named list";
           uses firewall_prefix_list;
         }
         choice packet-length_choice {
           case case_1 {
             leaf-list packet-length {
               ordered-by user;
               description "Range of values";
               type string;
             }
           }
           case case_2 {
             leaf-list packet-length-except {
               ordered-by user;
               description "Range of values";
               type string;
             }
           }
         }
         choice next-header_choice {
           case case_1 {
             leaf-list next-header {
               ordered-by user;
               type string;
             }
           }
           case case_2 {
             leaf-list next-header-except {
               ordered-by user;
               type string;
             }
           }
         }
         choice icmp-type_choice {
           case case_1 {
             leaf-list icmp-type {
               ordered-by user;
               type string;
             }
           }
           case case_2 {
             leaf-list icmp-type-except {
               ordered-by user;
               type string;
             }
           }
         }
         choice icmp-code_choice {
           case case_1 {
             leaf-list icmp-code {
               ordered-by user;
               type string;
             }
           }
           case case_2 {
             leaf-list icmp-code-except {
               ordered-by user;
               type string;
             }
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice port_choice {
           case case_1 {
             leaf-list port {
               ordered-by user;
               type string;
             }
           }
           case case_2 {
             leaf-list port-except {
               ordered-by user;
               type string;
             }
           }
         }
       }
       container then {
         description "Action to take if the 'from' condition is matched";
         uses apply-advanced;
         leaf log {
           description "Log the packet";
           type empty;
         }
         leaf syslog {
           description "System log (syslog) information about the packet";
           type empty;
         }
         leaf sample {
           description "Sample the packet";
           type empty;
         }
         choice designation {
           case case_1 {
             leaf note {
               description "Interested ISDN packet";
               type empty;
             }
           }
           case case_2 {
             leaf ignore {
               description "Non-interested ISDN packet";
               type empty;
             }
           }
         }
       }
     }
   }
   grouping inet6_filter {
     description "Define an IPv6 firewall filter";
     leaf name {
       description "Filter name";
       type string {
         junos:posix-pattern "!^((__.*)|(.{65,}))$";
         junos:pattern-message "Must be a non-reserved string of 64 characters or less";
       }
     }
     uses apply-advanced;
     leaf promote {
       description "Promote a firewall match to PFM";
       type enumeration {
         enum "gre-key" {
           description "Promote GRE Key to PFM";
         }
         enum "traffic-class" {
           description "Promote traffic-class to PFM";
         }
       }
     }
     leaf-list accounting-profile {
       ordered-by user;
       description "Accounting profile name";
       junos:must "(\"accounting-options filter-profile\")";
       junos:must-message "referenced accounting profile must be defined";
       type string;
     }
     leaf interface-specific {
       description "Defined counters are interface specific";
       type empty;
     }
     leaf scale-optimized {
       description "Improve filter prefix scale";
       type empty;
     }
     leaf enhanced-mode {
       description "Define filter for chassis network-services enhanced mode";
       junos:must "(!(\".. enhanced-mode-override\"))";
       junos:must-message "Cannot configure filter for both enhanced-mode and enhanced-mode-override";
       type empty;
     }
     leaf interface-shared {
       description "Filter is interface-shared";
       junos:must "(!(\".. physical-interface-filter\"))";
       junos:must-message "Cannot be both physical-interface-filter and interface-shared";
       junos:must "(!(\".. interface-specific\"))";
       junos:must-message "Cannot be both interface-specific and interface-shared";
       type empty;
     }
     leaf enhanced-mode-override {
       description "Override the default chassis network-services enhanced mode for dynamic filter";
       junos:must "(!(\".. enhanced-mode\"))";
       junos:must-message "Cannot configure filter for both enhanced-mode-override and enhanced-mode";
       type empty;
     }
     leaf physical-interface-filter {
       description "Filter is physical interface filter";
       type empty;
     }
     leaf fast-lookup-filter {
       description "Configure filter in the fast lookup hardware block";
       type empty;
     }
     leaf instance-shared {
       description "Filter is routing-instance shared";
       junos:must "(\"chassis network-services enhanced-ip\")";
       junos:must-message "instance-shared filter available only in enhanced-ip mode";
       junos:must "(!(\".. physical-interface-filter\"))";
       junos:must-message "Cannot be both physical-interface-filter and instance-shared";
       junos:must "(!(\".. interface-specific\"))";
       junos:must-message "Cannot be both interface-specific and instance-shared";
       type empty;
     }
     list term {
       key name;
       ordered-by user;
       description "Define a firewall term";
       leaf name {
         description "Term name";
         type string {
           junos:posix-pattern "!^((__.*)|(.{65,}))$";
           junos:pattern-message "Must be a non-reserved string of 64 characters or less";
         }
       }
       uses apply-advanced;
       leaf filter {
         description "Filter to include";
         junos:must "(\"firewall family inet6 filter $$\")";
         junos:must-message "Referenced filter is not defined";
         junos:must "((!(\".. from\") && !(\".. then\")))";
         junos:must-message "Not compatible with 'from or then'";
         type string {
           junos:posix-pattern "!^((__.*)|(.{65,}))$";
           junos:pattern-message "Must be a non-reserved string of 64 characters or less";
         }
       }
       container from {
         description "Define match criteria";
         uses apply-advanced;
         choice destination-class_choice {
           case case_1 {
             leaf-list destination-class {
               ordered-by user;
               description "String name";
               type string;
             }
           }
           case case_2 {
             leaf-list destination-class-except {
               ordered-by user;
               description "String name";
               type string;
             }
           }
         }
         choice source-class_choice {
           case case_1 {
             leaf-list source-class {
               ordered-by user;
               description "String name";
               type string;
             }
           }
           case case_2 {
             leaf-list source-class-except {
               ordered-by user;
               description "String name";
               type string;
             }
           }
         }
         choice interface-group_choice {
           case case_1 {
             leaf-list interface-group {
               ordered-by user;
               description "Range of values";
               type string;
             }
           }
           case case_2 {
             leaf-list interface-group-except {
               ordered-by user;
               description "Range of values";
               type string;
             }
           }
         }
         list source-address {
           key name;
           ordered-by user;
           description "Match  source address";
           uses firewall_addr6_object;
         }
         list destination-address {
           key name;
           ordered-by user;
           description "Match destination address";
           uses firewall_addr6_object;
         }
         list address {
           key name;
           ordered-by user;
           description "Match source or destination address";
           uses firewall_addr6_object;
         }
         list source-prefix-list {
           key name;
           ordered-by user;
           description "Match source prefixes in named list";
           uses firewall_prefix_list;
         }
         list destination-prefix-list {
           key name;
           ordered-by user;
           description "Match destination prefixes in named list";
           uses firewall_prefix_list;
         }
         list prefix-list {
           key name;
           ordered-by user;
           description "Match source or destination prefixes in named list";
           uses firewall_prefix_list;
         }
         choice next-header_choice {
           case case_1 {
             leaf-list next-header {
               ordered-by user;
               type string;
             }
           }
           case case_2 {
             leaf-list next-header-except {
               ordered-by user;
               type string;
             }
           }
         }
         choice payload-protocol_choice {
           case case_1 {
             leaf-list payload-protocol {
               ordered-by user;
               type string;
             }
           }
           case case_2 {
             leaf-list payload-protocol-except {
               ordered-by user;
               type string;
             }
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice port_choice {
           case case_1 {
             leaf-list port {
               ordered-by user;
               type string;
             }
           }
           case case_2 {
             leaf-list port-except {
               ordered-by user;
               type string;
             }
           }
         }
         choice extension-header_choice {
           case case_1 {
             leaf-list extension-header {
               ordered-by user;
               type string;
             }
           }
           case case_2 {
             leaf-list extension-header-except {
               ordered-by user;
               type string;
             }
           }
         }
         choice packet-length_choice {
           case case_1 {
             leaf-list packet-length {
               ordered-by user;
               description "Range of values";
               type string {
                 junos:posix-pattern "^([0-9]{1,4}|[1-5][0-9][0-9][0-9][0-9]|[6][0-4][0-9][0-9][0-9]|65[0-4][0-9][0-9]|655[0-2][0-9]|6553[0-5]|0x[0-f][0-f][0-f][0-f]|0x[0-f]|0x[0-f][0-f]|0x[0-f][0-f][0-f])(-([0-9]{1,4}|[1-5][0-9][0-9][0-9][0-9]|[6][0-4][0-9][0-9][0-9]|65[0-4][0-9][0-9]|655[0-2][0-9]|6553[0-5]|0x[0-f][0-f][0-f][0-f]|0x[0-f]|0x[0-f][0-f]|0x[0-f][0-f][0-f]))?$";
                 junos:pattern-message "Must be a numeric value or a range between 0-65535";
               }
             }
           }
           case case_2 {
             leaf-list packet-length-except {
               ordered-by user;
               description "Range of values";
               type string {
                 junos:posix-pattern "^([0-9]{1,4}|[1-5][0-9][0-9][0-9][0-9]|[6][0-4][0-9][0-9][0-9]|65[0-4][0-9][0-9]|655[0-2][0-9]|6553[0-5]|0x[0-f][0-f][0-f][0-f]|0x[0-f]|0x[0-f][0-f]|0x[0-f][0-f][0-f])(-([0-9]{1,4}|[1-5][0-9][0-9][0-9][0-9]|[6][0-4][0-9][0-9][0-9]|65[0-4][0-9][0-9]|655[0-2][0-9]|6553[0-5]|0x[0-f][0-f][0-f][0-f]|0x[0-f]|0x[0-f][0-f]|0x[0-f][0-f][0-f]))?$";
                 junos:pattern-message "Must be a numeric value or a range between 0-65535";
               }
             }
           }
         }
         choice traffic-class_choice {
           case case_1 {
             leaf-list traffic-class {
               ordered-by user;
               type string;
             }
           }
           case case_2 {
             leaf-list traffic-class-except {
               ordered-by user;
               type string;
             }
           }
         }
         choice icmp-type_choice {
           case case_1 {
             leaf-list icmp-type {
               ordered-by user;
               type string;
             }
           }
           case case_2 {
             leaf-list icmp-type-except {
               ordered-by user;
               type string;
             }
           }
         }
         choice icmp-code_choice {
           case case_1 {
             leaf-list icmp-code {
               ordered-by user;
               type string;
             }
           }
           case case_2 {
             leaf-list icmp-code-except {
               ordered-by user;
               type string;
             }
           }
         }
         leaf tcp-initial {
           description "Match initial packet of a TCP connection";
           junos:must "((\".. next-header tcp\" || (\".. next-header 6\" || \".. payload-protocol tcp\")))";
           junos:must-message "next-header tcp or next-header 6 or payload-protocol tcp must be defined in the same clause";
           type empty;
         }
         leaf tcp-established {
           description "Match packet of an established TCP connection";
           junos:must "((\".. next-header tcp\" || (\".. next-header 6\" || \".. payload-protocol tcp\")))";
           junos:must-message "next-header tcp or next-header 6 or payload-protocol tcp must be defined in the same clause";
           type empty;
         }
         leaf tcp-flags {
           description "Match TCP flags (in symbolic or hex formats)";
           junos:must "((\".. next-header tcp\" || (\".. next-header 6\" || \".. payload-protocol tcp\")))";
           junos:must-message "next-header tcp or next-header 6 or payload-protocol tcp must be defined in the same clause";
           type string;
         }
         list interface {
           key name;
           ordered-by user;
           description "Match interface name";
           uses match_interface_object;
         }
         list interface-set {
           key name;
           ordered-by user;
           description "Match interface in set";
           uses match_interface_set_object;
         }
         choice forwarding-class_choice {
           case case_1 {
             leaf-list forwarding-class {
               ordered-by user;
               description "String name";
               type string {
                 junos:posix-pattern "^.{1,64}$";
                 junos:pattern-message "Must be string of 64 characters or less";
               }
             }
           }
           case case_2 {
             leaf-list forwarding-class-except {
               ordered-by user;
               description "String name";
               type string {
                 junos:posix-pattern "^.{1,64}$";
                 junos:pattern-message "Must be string of 64 characters or less";
               }
             }
           }
         }
         choice loss-priority_choice {
           case case_1 {
             leaf-list loss-priority {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
           case case_2 {
             leaf-list loss-priority-except {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
         }
         leaf service-filter-hit {
           description "Match if service-filter-hit is set";
           type empty;
         }
         choice hop-limit_choice {
           case case_1 {
             leaf-list hop-limit {
               ordered-by user;
               description "Range of values";
               type string {
                 junos:posix-pattern "^([0-9]|[1-9][0-9]|1[0-9][0-9]|2[0-4][0-9]|25[0-5]|0x[0-f]|0x[0-f][0-f])(-([0-9]|[1-9][0-9]|1[0-9][0-9]|2[0-4][0-9]|25[0-5]|0x[0-f]|0x[0-f][0-f]))?$";
                 junos:pattern-message "Must be a numerical hop-limit value or range between 0-255";
               }
             }
           }
           case case_2 {
             leaf-list hop-limit-except {
               ordered-by user;
               description "Range of values";
               type string {
                 junos:posix-pattern "^([0-9]|[1-9][0-9]|1[0-9][0-9]|2[0-4][0-9]|25[0-5]|0x[0-f]|0x[0-f][0-f])(-([0-9]|[1-9][0-9]|1[0-9][0-9]|2[0-4][0-9]|25[0-5]|0x[0-f]|0x[0-f][0-f]))?$";
                 junos:pattern-message "Must be a numerical hop-limit value or range between 0-255";
               }
             }
           }
         }
         leaf is-fragment {
           description "Match if packet is a fragment";
           type empty;
         }
         leaf first-fragment {
           description "Match if packet is first fragment";
           type empty;
         }
         leaf last-fragment {
           description "Match if packet is last fragment";
           type empty;
         }
         choice flex-mask_choice {
           case case_1 {
             container flexible-match-mask {
               description "Match flexible mask";
               uses match_L3_flexible_mask;
             }
           }
         }
         choice flex-range_choice {
           case case_1 {
             container flexible-match-range {
               description "Match flexible range";
               uses match_L3_flexible_range;
             }
           }
         }
         choice gre-key_choice {
           case case_1 {
             leaf-list gre-key {
               ordered-by user;
               description "Range of values";
               type string;
             }
           }
           case case_2 {
             leaf-list gre-key-except {
               ordered-by user;
               description "Range of values";
               type string;
             }
           }
         }
         choice policy-map_choice {
           case case_1 {
             leaf-list policy-map {
               ordered-by user;
               description "String name";
               junos:must "(\"class-of-service policy-map $$\")";
               junos:must-message "Undefined policy-map instance";
               type string {
                 length "1 .. 64";
                 junos:posix-pattern "!^((__.*)|(.{65,}))$";
                 junos:pattern-message "Must be a non-reserved string of 64 characters or less";
               }
             }
           }
           case case_2 {
             leaf-list policy-map-except {
               ordered-by user;
               description "String name";
               junos:must "(\"class-of-service policy-map $$\")";
               junos:must-message "Undefined policy-map instance";
               type string {
                 length "1 .. 64";
                 junos:posix-pattern "!^((__.*)|(.{65,}))$";
                 junos:pattern-message "Must be a non-reserved string of 64 characters or less";
               }
             }
           }
         }
       }
       container then {
         description "Action to take if the 'from' condition is matched";
         uses apply-advanced;
         choice policer-choice {
           case case_1 {
             leaf policer {
               description "Name of policer to use to rate-limit traffic";
               junos:must "(!(\"firewall policer $$ aggregate\"))";
               junos:must-message "Cannot attach a aggregate policer to filter";
               type string {
                 junos:posix-pattern "!^((__.*)|(.{65,}))$";
                 junos:pattern-message "Must be a non-reserved string of 64 characters or less";
               }
             }
           }
           case case_2 {
             container three-color-policer {
               description "Police the packet using a three-color-policer";
               uses apply-advanced;
               choice type-choice {
                 case case_1 {
                   leaf single-rate {
                     description "Name of single-rate three-color policer to use to rate-limit traffic";
                     junos:must "(\"firewall three-color-policer $$ single-rate\")";
                     junos:must-message "Referenced single-rate policer does not exist";
                     type string {
                       junos:posix-pattern "!^((__.*)|(.{65,}))$";
                       junos:pattern-message "Must be a non-reserved string of 64 characters or less";
                     }
                   }
                 }
                 case case_2 {
                   leaf single-packet-rate {
                     description "Name of single-packet-rate three-color policer to use to rate-limit traffic";
                     junos:must "(\"firewall three-color-policer $$ single-packet-rate\")";
                     junos:must-message "Referenced single-packet-rate policer does not exist";
                     type string {
                       junos:posix-pattern "!^((__.*)|(.{65,}))$";
                       junos:pattern-message "Must be a non-reserved string of 64 characters or less";
                     }
                   }
                 }
                 case case_3 {
                   leaf two-rate {
                     description "Name of two-rate three-color policer to use to rate-limit traffic";
                     junos:must "(\"firewall three-color-policer $$ two-rate\")";
                     junos:must-message "Referenced two-rate policer does not exist";
                     type string {
                       junos:posix-pattern "!^((__.*)|(.{65,}))$";
                       junos:pattern-message "Must be a non-reserved string of 64 characters or less";
                     }
                   }
                 }
                 case case_4 {
                   leaf two-packet-rate {
                     description "Name of two-packet-rate three-color policer to use to rate-limit traffic";
                     junos:must "(\"firewall three-color-policer $$ two-packet-rate\")";
                     junos:must-message "Referenced two-packet-rate policer does not exist";
                     type string {
                       junos:posix-pattern "!^((__.*)|(.{65,}))$";
                       junos:pattern-message "Must be a non-reserved string of 64 characters or less";
                     }
                   }
                 }
               }
             }
           }
           case case_3 {
             leaf hierarchical-policer {
               description "Name of hierarchical policer to use to rate-limit traffic";
               type string {
                 junos:posix-pattern "!^((__.*)|(.{65,}))$";
                 junos:pattern-message "Must be a non-reserved string of 64 characters or less";
               }
             }
           }
         }
         choice policy-map-choice {
           case case_1 {
             leaf clear-policy-map {
               description "Clear the policy marking";
               type empty;
             }
           }
           case case_2 {
             leaf policy-map {
               description "Policy map action";
               junos:must "(\"class-of-service policy-map $$\")";
               junos:must-message "referenced policy map must be defined";
               type string {
                 junos:posix-pattern "!^((__.*)|(.{65,}))$";
                 junos:pattern-message "Must be a non-reserved string of 64 characters or less";
               }
             }
           }
         }
         choice inet6cnt {
           case case_1 {
             leaf traffic-class-count {
               description "Count the packet in the named traffic-class counter";
               type string {
                 junos:posix-pattern "!^((__.*)|(.{65,}))$";
                 junos:pattern-message "Must be a non-reserved string of 64 characters or less";
               }
             }
           }
           case case_2 {
             leaf count {
               description "Count the packet in the named counter";
               type string {
                 junos:posix-pattern "!^((__.*)|(.{65,}))$";
                 junos:pattern-message "Must be a non-reserved string of 64 characters or less";
               }
             }
           }
         }
         leaf service-accounting {
           description "Count the packets for service accounting";
           junos:must "(!(\".. service-accounting-deferred\"))";
           junos:must-message "'service-accounting-deferred' and 'service-accounting' cannot coexist";
           junos:must "(!(\".. count\"))";
           junos:must-message "'count' and 'service-accounting' cannot coexist";
           type empty;
         }
         leaf service-accounting-deferred {
           description "Count the packets for deferred service accounting";
           junos:must "(!(\".. service-accounting\"))";
           junos:must-message "Cannot be both 'service-accounting' and 'service-accounting-deferred'";
           junos:must "(!(\".. count\"))";
           junos:must-message "'count' and 'service-accounting-deferred' cannot coexist";
           type empty;
         }
         leaf log {
           description "Log the packet";
           type empty;
         }
         leaf syslog {
           description "System log (syslog) information about the packet";
           type empty;
         }
         leaf sample {
           description "Sample the packet";
           junos:must "((\"forwarding-options sampling family inet6\" || (\"forwarding-options packet-capture\" || any \"forwarding-options sampling instance <*> family inet6\")))";
           junos:must-message "Requires forwarding-options sampling or packet-capture config";
           type empty;
         }
         leaf port-mirror-instance {
           description "Port-mirror the packet to specified instance";
           junos:must "(\"forwarding-options port-mirroring instance $$\")";
           junos:must-message "Referenced port-mirroring instance does not exist";
           type string {
             junos:posix-pattern "!^((__.*)|(.{65,}))$";
             junos:pattern-message "Must be a non-reserved string of 64 characters or less";
           }
         }
         leaf port-mirror {
           description "Port-mirror the packet";
           junos:must "(!(\".. port-mirror-instance\"))";
           junos:must-message "'port-mirror' and 'port-mirror-instance' are mutually exclusive";
           type empty;
         }
         leaf loss-priority {
           description "Packet's loss priority";
           type enumeration {
             enum "low" {
               description "Loss priority low";
             }
             enum "high" {
               description "Loss priority high";
             }
             enum "medium-low" {
               description "Loss priority medium-low";
             }
             enum "medium-high" {
               description "Loss priority medium-high";
             }
           }
         }
         leaf forwarding-class {
           description "Classify packet to forwarding class";
           type string {
             junos:posix-pattern "^.{1,64}$";
             junos:pattern-message "Must be string of 64 characters or less";
           }
         }
         leaf traffic-class {
           description "Set traffic-class code point";
           type string;
         }
         leaf skip-services {
           description "Skip the services";
           type empty;
         }
         leaf service-filter-hit {
           description "Marked when packet processing by the current type of chained filters is done, the packet is directed to the next type of filters";
           type empty;
         }
         leaf force-premium {
           description "When this bit is marked, traffic is considered as premium by the following hierarchical policer";
           type empty;
         }
         leaf exclude-accounting {
           description "When this is marked, traffic is excluded from accurate accounting";
           type empty;
         }
         choice designation {
           case case_1 {
             container decapsulate {
               presence "enable decapsulate";
               description "Terminate a tunnel";
               choice tunnel-protocol {
                 case case_1 {
                   container gre {
                     presence "enable gre";
                     description "GRE protocol";
                     uses apply-advanced;
                     leaf-list sample {
                       ordered-by user;
                       description "Sample the packet";
                       junos:must "(!(\".. sampling-instance\"))";
                       junos:must-message "'sampling' and 'sampling-instance' are mutually exclusive";
                       type enumeration {
                         enum "inet" {
                           description "IPV4 protocol";
                           junos:must "((\"forwarding-options sampling family inet\" || (\"forwarding-options packet-capture\" || any \"forwarding-options sampling instance <*> family inet\")))";
                           junos:must-message "Requires forwarding-options sampling or packet-capture config";
                         }
                         enum "inet6" {
                           description "IPV6 protocol";
                           junos:must "((\"forwarding-options sampling family inet6\" || (\"forwarding-options packet-capture\" || any \"forwarding-options sampling instance <*> family inet6\")))";
                           junos:must-message "Requires forwarding-options sampling or packet-capture config";
                         }
                         enum "mpls" {
                           description "MPLS protocol";
                           junos:must "(!(\".. .. sample mpls-ipvx-payload\"))";
                           junos:must-message "Cannot configure both sample mpls and sample mpls-ipvx-payload";
                           junos:must "((\"forwarding-options sampling family mpls\" || (\"forwarding-options packet-capture\" || any \"forwarding-options sampling instance <*> family mpls\")))";
                           junos:must-message "Requires forwarding-options sampling or packet-capture config";
                         }
                       }
                     }
                     leaf no-decrement-ttl {
                       description "Do not decrement TTL";
                       type empty;
                     }
                     leaf forwarding-class {
                       description "Classify packet to forwarding class";
                       type string {
                         junos:posix-pattern "^.{1,64}$";
                         junos:pattern-message "Must be string of 64 characters or less";
                       }
                     }
                     leaf interface-group {
                       description "Set the interface group";
                       type union {
                         type string {
                           pattern "<.*>|$.*";
                         }
                         type uint32 {
                           range "0 .. 255";
                         }
                       }
                     }
                     choice destination {
                       case case_1 {
                         container routing-instance {
                           description "Packets are directed to specified routing instance";
                           leaf routing-instance-name {
                             description "Name of routing instance";
                             junos:must "(\"routing-instances $$\")";
                             junos:must-message "referenced routing instance must be defined";
                             type string {
                               junos:posix-pattern "!^((__.*__)|(all)|(.*[ ].*)|(\"\")|(.{129,}))$";
                               junos:pattern-message "Must be a non-reserved string of 128 characters or less with no spaces.";
                             }
                           }
                         }
                       }
                     }
                   }
                 }
                 case case_2 {
                   container gre-in-udp {
                     presence "enable gre-in-udp";
                     description "GRE-in-UDP protocol";
                     uses apply-advanced;
                     leaf-list sample {
                       ordered-by user;
                       description "Sample the packet";
                       junos:must "(!(\".. sampling-instance\"))";
                       junos:must-message "'sampling' and 'sampling-instance' are mutually exclusive";
                       type enumeration {
                         enum "inet" {
                           description "IPV4 protocol";
                           junos:must "((\"forwarding-options sampling family inet\" || (\"forwarding-options packet-capture\" || any \"forwarding-options sampling instance <*> family inet\")))";
                           junos:must-message "Requires forwarding-options sampling or packet-capture config";
                         }
                         enum "inet6" {
                           description "IPV6 protocol";
                           junos:must "((\"forwarding-options sampling family inet6\" || (\"forwarding-options packet-capture\" || any \"forwarding-options sampling instance <*> family inet6\")))";
                           junos:must-message "Requires forwarding-options sampling or packet-capture config";
                         }
                         enum "mpls" {
                           description "MPLS protocol";
                           junos:must "(!(\".. .. sample mpls-ipvx-payload\"))";
                           junos:must-message "Cannot configure both sample mpls and sample mpls-ipvx-payload";
                           junos:must "((\"forwarding-options sampling family mpls\" || (\"forwarding-options packet-capture\" || any \"forwarding-options sampling instance <*> family mpls\")))";
                           junos:must-message "Requires forwarding-options sampling or packet-capture config";
                         }
                       }
                     }
                     leaf no-decrement-ttl {
                       description "Do not decrement TTL";
                       type empty;
                     }
                     leaf forwarding-class {
                       description "Classify packet to forwarding class";
                       type string {
                         junos:posix-pattern "^.{1,64}$";
                         junos:pattern-message "Must be string of 64 characters or less";
                       }
                     }
                     leaf interface-group {
                       description "Set the interface group";
                       type union {
                         type string {
                           pattern "<.*>|$.*";
                         }
                         type uint32 {
                           range "0 .. 255";
                         }
                       }
                     }
                     choice destination {
                       case case_1 {
                         container routing-instance {
                           description "Packets are directed to specified routing instance";
                           leaf routing-instance-name {
                             description "Name of routing instance";
                             junos:must "(\"routing-instances $$\")";
                             junos:must-message "referenced routing instance must be defined";
                             type string {
                               junos:posix-pattern "!^((__.*__)|(all)|(.*[ ].*)|(\"\")|(.{129,}))$";
                               junos:pattern-message "Must be a non-reserved string of 128 characters or less with no spaces.";
                             }
                           }
                         }
                       }
                     }
                   }
                 }
                 case case_3 {
                   container mpls-in-udp {
                     presence "enable mpls-in-udp";
                     description "MPLS-in-UDP protocol";
                     uses apply-advanced;
                     leaf-list sample {
                       ordered-by user;
                       description "Sample the packet";
                       junos:must "(!(\".. sampling-instance\"))";
                       junos:must-message "'sampling' and 'sampling-instance' are mutually exclusive";
                       type enumeration {
                         enum "inet" {
                           description "IPV4 protocol";
                           junos:must "((\"forwarding-options sampling family inet\" || (\"forwarding-options packet-capture\" || any \"forwarding-options sampling instance <*> family inet\")))";
                           junos:must-message "Requires forwarding-options sampling or packet-capture config";
                         }
                         enum "inet6" {
                           description "IPV6 protocol";
                           junos:must "((\"forwarding-options sampling family inet6\" || (\"forwarding-options packet-capture\" || any \"forwarding-options sampling instance <*> family inet6\")))";
                           junos:must-message "Requires forwarding-options sampling or packet-capture config";
                         }
                         enum "mpls" {
                           description "MPLS protocol";
                           junos:must "(!(\".. .. sample mpls-ipvx-payload\"))";
                           junos:must-message "Cannot configure both sample mpls and sample mpls-ipvx-payload";
                           junos:must "((\"forwarding-options sampling family mpls\" || (\"forwarding-options packet-capture\" || any \"forwarding-options sampling instance <*> family mpls\")))";
                           junos:must-message "Requires forwarding-options sampling or packet-capture config";
                         }
                       }
                     }
                     leaf no-decrement-ttl {
                       description "Do not decrement TTL";
                       type empty;
                     }
                     leaf forwarding-class {
                       description "Classify packet to forwarding class";
                       type string {
                         junos:posix-pattern "^.{1,64}$";
                         junos:pattern-message "Must be string of 64 characters or less";
                       }
                     }
                     leaf interface-group {
                       description "Set the interface group";
                       type union {
                         type string {
                           pattern "<.*>|$.*";
                         }
                         type uint32 {
                           range "0 .. 255";
                         }
                       }
                     }
                     choice destination {
                       case case_1 {
                         container routing-instance {
                           description "Packets are directed to specified routing instance";
                           leaf routing-instance-name {
                             description "Name of routing instance";
                             junos:must "(\"routing-instances $$\")";
                             junos:must-message "referenced routing instance must be defined";
                             type string {
                               junos:posix-pattern "!^((__.*__)|(all)|(.*[ ].*)|(\"\")|(.{129,}))$";
                               junos:pattern-message "Must be a non-reserved string of 128 characters or less with no spaces.";
                             }
                           }
                         }
                       }
                     }
                   }
                 }
                 case case_4 {
                   container l2tp {
                     description "L2TP protocol";
                     uses apply-advanced;
                     leaf-list sample {
                       ordered-by user;
                       description "Sample the packet";
                       junos:must "(!(\".. sampling-instance\"))";
                       junos:must-message "'sampling' and 'sampling-instance' are mutually exclusive";
                       type enumeration {
                         enum "inet" {
                           description "IPV4 protocol";
                           junos:must "((\"forwarding-options sampling family inet\" || (\"forwarding-options packet-capture\" || any \"forwarding-options sampling instance <*> family inet\")))";
                           junos:must-message "Requires forwarding-options sampling or packet-capture config";
                         }
                         enum "inet6" {
                           description "IPV6 protocol";
                           junos:must "((\"forwarding-options sampling family inet6\" || (\"forwarding-options packet-capture\" || any \"forwarding-options sampling instance <*> family inet6\")))";
                           junos:must-message "Requires forwarding-options sampling or packet-capture config";
                         }
                         enum "mpls" {
                           description "MPLS protocol";
                           junos:must "(!(\".. .. sample mpls-ipvx-payload\"))";
                           junos:must-message "Cannot configure both sample mpls and sample mpls-ipvx-payload";
                           junos:must "((\"forwarding-options sampling family mpls\" || (\"forwarding-options packet-capture\" || any \"forwarding-options sampling instance <*> family mpls\")))";
                           junos:must-message "Requires forwarding-options sampling or packet-capture config";
                         }
                       }
                     }
                     leaf no-decrement-ttl {
                       description "Do not decrement TTL";
                       type empty;
                     }
                     leaf forwarding-class {
                       description "Classify packet to forwarding class";
                       type string {
                         junos:posix-pattern "^.{1,64}$";
                         junos:pattern-message "Must be string of 64 characters or less";
                       }
                     }
                     leaf interface-group {
                       description "Set the interface group";
                       type union {
                         type string {
                           pattern "<.*>|$.*";
                         }
                         type uint32 {
                           range "0 .. 255";
                         }
                       }
                     }
                     leaf-list cookie {
                       ordered-by user;
                       description "L2TPv3 cookie";
                       type string {
                         length "1 .. 32";
                       }
                     }
                     choice destination {
                       case case_1 {
                         leaf output-interface {
                           description "Interface name";
                           junos:must "(\"interfaces $$\")";
                           junos:must-message "Interface must be defined in the interfaces hierarchy";
                           type union {
                             type jt:interface-unit;
                             type string {
                               pattern "<.*>|$.*";
                             }
                           }
                         }
                       }
                     }
                   }
                 }
               }
             }
           }
           case case_2 {
             container encapsulate {
               presence "enable encapsulate";
               description "Send to a tunnel";
               leaf tunnel-end-point {
                 description "Name of the tunnel end point";
                 junos:must "(\"firewall tunnel-end-point $$\")";
                 junos:must-message "referenced firewall tunnel-end-point must be defined";
                 type string {
                   junos:posix-pattern "!^((__.*)|(.{65,}))$";
                   junos:pattern-message "Must be a non-reserved string of 64 characters or less";
                 }
               }
             }
           }
           case case_3 {
             leaf accept {
               description "Accept the packet";
               type empty;
             }
           }
           case case_4 {
             leaf discard {
               description "Discard the packet";
               type empty;
             }
           }
           case case_5 {
             leaf next {
               description "Continue to next term in a filter";
               type enumeration {
                 enum "term" {
                   description "Continue to next term in a filter";
                 }
               }
             }
           }
           case case_6 {
             leaf next-hop-group {
               description "Use specified next-hop group";
               type string;
             }
           }
           case case_7 {
             list logical-system {
               key logical-system-name;
               ordered-by user;
               description "Packets are directed to specified logical system";
               max-elements 1;
               leaf logical-system-name {
                 description "Name of logical system";
                 type string {
                   junos:posix-pattern "^[a-zA-Z0-9_-]{1,63}$";
                   junos:pattern-message "Logical-system name is a string consisting of up to 63 letters, numbers, dashes and underscores";
                 }
               }
               container routing-instance {
                 description "Packets are directed to specified routing instance";
                 leaf routing-instance-name {
                   description "Name of routing instance";
                   type string {
                     junos:posix-pattern "!^((__.*__)|(all)|(.*[ ].*)|(\"\")|(.{129,}))$";
                     junos:pattern-message "Must be a non-reserved string of 128 characters or less with no spaces.";
                   }
                 }
                 leaf topology {
                   description "Packets are directed to specified topology";
                   type string {
                     junos:posix-pattern "!^((.*:.*)|(.{129,}))$";
                     junos:pattern-message "Must be a non-reserved string of 128 characters or less";
                   }
                 }
               }
               leaf topology {
                 description "Packets are directed to specified topology";
                 type string {
                   junos:posix-pattern "!^((.*:.*)|(.{129,}))$";
                   junos:pattern-message "Must be a non-reserved string of 128 characters or less";
                 }
               }
             }
           }
           case case_8 {
             container routing-instance {
               description "Packets are directed to specified routing instance";
               leaf routing-instance-name {
                 description "Name of routing instance";
                 type string {
                   junos:posix-pattern "!^((__.*__)|(all)|(.*[ ].*)|(\"\")|(.{129,}))$";
                   junos:pattern-message "Must be a non-reserved string of 128 characters or less with no spaces.";
                 }
               }
               leaf topology {
                 description "Packets are directed to specified topology";
                 type string {
                   junos:posix-pattern "!^((.*:.*)|(.{129,}))$";
                   junos:pattern-message "Must be a non-reserved string of 128 characters or less";
                 }
               }
             }
           }
           case case_9 {
             leaf topology {
               description "Packets are directed to specified topology";
               type string {
                 junos:posix-pattern "!^((.*:.*)|(.{129,}))$";
                 junos:pattern-message "Must be a non-reserved string of 128 characters or less";
               }
             }
           }
           case case_10 {
             container next-ip6 {
               description "Packets are directed to specified the specified ipv6 address";
               leaf address {
                 description "Address to route";
                 type jt:ipv6prefix;
               }
               container routing-instance {
                 description "Packets are directed to specified routing instance";
                 leaf routing-instance-name {
                   description "Name of routing instance";
                   type string {
                     junos:posix-pattern "!^((__.*__)|(all)|(.*[ ].*)|(\"\")|(.{129,}))$";
                     junos:pattern-message "Must be a non-reserved string of 128 characters or less with no spaces.";
                   }
                 }
                 leaf topology {
                   description "Packets are directed to specified topology";
                   type string {
                     junos:posix-pattern "!^((.*:.*)|(.{129,}))$";
                     junos:pattern-message "Must be a non-reserved string of 128 characters or less";
                   }
                 }
               }
             }
           }
           case case_11 {
             container next-interface {
               presence "enable next-interface";
               description "Packets are to be routed through the specified interface";
               uses apply-advanced;
               leaf interface-name {
                 description "Interface name";
                 type string {
                   length "1 .. 127";
                   junos:posix-pattern "^((ge-)|(mge-)|(xe-)|(et-)|(gr-)|(ae)|(irb))";
                   junos:pattern-message "Only ge, mge, xe, et, ae, irb and point-to-point gr tunnel intefaces are supported";
                 }
               }
               container routing-instance {
                 description "Packets are directed to specified routing instance";
                 leaf routing-instance-name {
                   description "Name of routing instance";
                   type string {
                     junos:posix-pattern "!^((__.*__)|(all)|(.*[ ].*)|(\"\")|(.{129,}))$";
                     junos:pattern-message "Must be a non-reserved string of 128 characters or less with no spaces.";
                   }
                 }
                 leaf topology {
                   description "Packets are directed to specified topology";
                   type string {
                     junos:posix-pattern "!^((.*:.*)|(.{129,}))$";
                     junos:pattern-message "Must be a non-reserved string of 128 characters or less";
                   }
                 }
               }
               choice designation {
                 case case_1 {
                   leaf accept {
                     description "Accept the packet";
                     type empty;
                   }
                 }
                 case case_2 {
                   leaf next {
                     description "Continue to next term in a filter";
                     type enumeration {
                       enum "term" {
                         description "Continue to next term in a filter";
                       }
                     }
                   }
                 }
               }
             }
           }
           case case_12 {
             container reject {
               presence "enable reject";
               description "Reject the packet";
               choice style {
                 case case_1 {
                   leaf no-route {
                     description "Send ICMPv6 No Route message";
                     type empty;
                   }
                 }
                 case case_2 {
                   leaf administratively-prohibited {
                     description "Send ICMPv6 Administratively Prohibited message";
                     type empty;
                   }
                 }
                 case case_3 {
                   leaf beyond-scope {
                     description "Send ICMPv6 Beyond Scope of Source Address message";
                     type empty;
                   }
                 }
                 case case_4 {
                   leaf address-unreachable {
                     description "Send ICMPv6 Address Unreachable message";
                     type empty;
                   }
                 }
                 case case_5 {
                   leaf port-unreachable {
                     description "Send ICMPv6 Port Unreachable message";
                     type empty;
                   }
                 }
                 case case_6 {
                   leaf policy-failed {
                     description "Source address failed ingress/egress policy";
                     type empty;
                   }
                 }
                 case case_7 {
                   leaf reject-route {
                     description "Reject route to destination";
                     type empty;
                   }
                 }
                 case case_8 {
                   leaf tcp-reset {
                     description "Send TCP Reset message";
                     type empty;
                   }
                 }
                 case case_9 {
                   leaf network-unreachable {
                     description "Send ICMPv4 Network Unreachable message";
                     status deprecated;
                     type empty;
                   }
                 }
                 case case_10 {
                   leaf host-unreachable {
                     description "Send ICMPv4 Host Unreachable message";
                     status deprecated;
                     type empty;
                   }
                 }
                 case case_11 {
                   leaf protocol-unreachable {
                     description "Send ICMPv4 Protocol Unreachable message";
                     status deprecated;
                     type empty;
                   }
                 }
                 case case_12 {
                   leaf source-route-failed {
                     description "Send ICMPv4 Source Route Failed message";
                     status deprecated;
                     type empty;
                   }
                 }
                 case case_13 {
                   leaf network-unknown {
                     description "Send ICMPv4 Network Unknown message";
                     status deprecated;
                     type empty;
                   }
                 }
                 case case_14 {
                   leaf host-unknown {
                     description "Send ICMPv4 Host Unknown message";
                     status deprecated;
                     type empty;
                   }
                 }
                 case case_15 {
                   leaf source-host-isolated {
                     description "Send ICMPv4 Source Host Isolated message";
                     status deprecated;
                     type empty;
                   }
                 }
                 case case_16 {
                   leaf network-prohibited {
                     description "Send ICMPv4 Network Prohibited message";
                     status deprecated;
                     type empty;
                   }
                 }
                 case case_17 {
                   leaf host-prohibited {
                     description "Send ICMPv4 Host Prohibited message";
                     status deprecated;
                     type empty;
                   }
                 }
                 case case_18 {
                   leaf bad-network-tos {
                     description "Send ICMPv4 Bad Network ToS message";
                     status deprecated;
                     type empty;
                   }
                 }
                 case case_19 {
                   leaf bad-host-tos {
                     description "Send ICMPv4 Bad Host ToS message";
                     status deprecated;
                     type empty;
                   }
                 }
                 case case_20 {
                   leaf precedence-violation {
                     description "Send ICMPv4 Precedence Violation message";
                     status deprecated;
                     type empty;
                   }
                 }
                 case case_21 {
                   leaf precedence-cutoff {
                     description "Send ICMPv4 Precedence Cutoff message";
                     status deprecated;
                     type empty;
                   }
                 }
               }
             }
           }
         }
       }
     }
   }
   grouping inet6_fuf {
     leaf name {
       description "Name of fast update filter";
       junos:must "(unique \"firewall family <*> filter $$\")";
       junos:must-message "Fast update filter can not have the same name as firewall family filter";
       type string {
         junos:posix-pattern "!^((__.*)|(.{65,}))$";
         junos:pattern-message "Must be a non-reserved string of 64 characters or less";
       }
     }
     uses apply-advanced;
     leaf interface-specific {
       description "Defined counters are interface specific";
       type empty;
     }
     leaf-list match-order {
       ordered-by user;
       type enumeration {
         enum "next-header" {
           description "Include next header protocol in match set";
         }
         enum "payload-protocol" {
           description "Include payload protocol in match set";
         }
         enum "source-address" {
           description "Include source-address in match set";
         }
         enum "destination-address" {
           description "Include destination-address in match set";
         }
         enum "source-port" {
           description "Include source-port in match set";
         }
         enum "destination-port" {
           description "Include destination-port in match set";
         }
         enum "traffic-class" {
           description "Include traffic-class (DSCP) in match set";
         }
       }
     }
     list term {
       key name;
       ordered-by user;
       description "One or more firewall terms";
       leaf name {
         description "Term name";
         type string {
           junos:posix-pattern "!^((__.*)|(.{65,}))$";
           junos:pattern-message "Must be a non-reserved string of 64 characters or less";
         }
       }
       uses apply-advanced;
       leaf only-at-create {
         description "Add term only when filter is first created.";
         type empty;
       }
       container from {
         description "Match criteria";
         uses apply-advanced;
         container source-address {
           description "Match source IP address";
           uses firewall_addr6_simple_object;
         }
         container destination-address {
           description "Match destination IP address";
           uses firewall_addr6_simple_object;
         }
         choice source-port_choice {
           case case_1 {
             container source-port {
               description "Match TCP/UDP source port";
               uses match_simple_port_value;
             }
           }
         }
         choice destination-port_choice {
           case case_1 {
             container destination-port {
               description "Match TCP/UDP destination port";
               uses match_simple_port_value;
             }
           }
         }
         choice next-header_choice {
           case case_1 {
             container next-header {
               description "Match next header protocol type";
               uses match_simple_protocol_value;
             }
           }
         }
         choice payload-protocol_choice {
           case case_1 {
             container payload-protocol {
               description "Match payload protocol type";
               uses match_simple_payload_protocol_value;
             }
           }
         }
         choice traffic-class_choice {
           case case_1 {
             container traffic-class {
               description "Match Differentiated Services (DiffServ) code point";
               uses match_simple_dscp_value;
             }
           }
         }
         leaf match-terms {
           description "Dynamically supplied list of match criteria";
           type string;
         }
       }
       container then {
         description "Action to take if the 'from' condition is matched";
         uses apply-advanced;
         choice policer-choice {
           case case_1 {
             leaf policer {
               description "Name of policer to use to rate-limit traffic";
               type string {
                 junos:posix-pattern "!^((__.*)|(.{65,}))$";
                 junos:pattern-message "Must be a non-reserved string of 64 characters or less";
               }
             }
           }
         }
         leaf count {
           description "Count the packet in the named counter";
           type string {
             junos:posix-pattern "!^((__.*)|(.{65,}))$";
             junos:pattern-message "Must be a non-reserved string of 64 characters or less";
           }
         }
         leaf service-accounting {
           description "Count the packets for service accounting";
           junos:must "(!(\".. count\"))";
           junos:must-message "'count' and 'service-accounting' cannot coexist";
           type empty;
         }
         leaf log {
           description "Log the packet";
           type empty;
         }
         leaf port-mirror {
           description "Port-mirror the packet";
           type empty;
         }
         leaf loss-priority {
           description "Packet's loss priority";
           junos:must "(!(\".. three-color-policer\"))";
           junos:must-message "Configuring loss-priority is incompatible with configuring three-color-policer";
           type enumeration {
             enum "low" {
               description "Loss priority low";
             }
             enum "high" {
               description "Loss priority high";
             }
             enum "medium-low" {
               description "Loss priority medium-low";
             }
             enum "medium-high" {
               description "Loss priority medium-high";
             }
           }
         }
         leaf forwarding-class {
           description "Classify packet to forwarding class";
           type string {
             junos:posix-pattern "^.{1,64}$";
             junos:pattern-message "Must be string of 64 characters or less";
           }
         }
         leaf action-terms {
           description "Dynamically supplied list of actions";
           type string;
         }
         choice designation {
           case case_1 {
             leaf accept {
               description "Accept the packet";
               type empty;
             }
           }
           case case_2 {
             leaf discard {
               description "Discard the packet";
               type empty;
             }
           }
           case case_3 {
             container routing-instance {
               description "Packets are directed to specified routing instance";
               leaf routing-instance-name {
                 description "Name of routing instance";
                 type string {
                   junos:posix-pattern "!^((__.*__)|(all)|(.*[ ].*)|(\"\")|(.{129,}))$";
                   junos:pattern-message "Must be a non-reserved string of 128 characters or less with no spaces.";
                 }
               }
               leaf topology {
                 description "Packets are directed to specified topology";
                 type string {
                   junos:posix-pattern "!^((.*:.*)|(.{129,}))$";
                   junos:pattern-message "Must be a non-reserved string of 128 characters or less";
                 }
               }
             }
           }
         }
       }
     }
   }
   grouping firewall_addr6_simple_object {
     uses apply-advanced;
     leaf address {
       description "Prefix to match";
       type jt:ipv6prefix;
     }
   }
   grouping inet6_service_filter {
     leaf name {
       description "Filter name";
       type string {
         junos:posix-pattern "!^((__.*)|(.{65,}))$";
         junos:pattern-message "Must be a non-reserved string of 64 characters or less";
       }
     }
     uses apply-advanced;
     list term {
       key name;
       ordered-by user;
       description "Service filter term";
       leaf name {
         description "Term name";
         type string {
           junos:posix-pattern "!^((__.*)|(.{65,}))$";
           junos:pattern-message "Must be a non-reserved string of 64 characters or less";
         }
       }
       uses apply-advanced;
       container from {
         description "Match criteria";
         uses apply-advanced;
         choice interface-group_choice {
           case case_1 {
             leaf-list interface-group {
               ordered-by user;
               description "Range of values";
               type string;
             }
           }
           case case_2 {
             leaf-list interface-group-except {
               ordered-by user;
               description "Range of values";
               type string;
             }
           }
         }
         list source-address {
           key name;
           ordered-by user;
           description "Match  source address";
           uses firewall_addr6_object;
         }
         list destination-address {
           key name;
           ordered-by user;
           description "Match destination address";
           uses firewall_addr6_object;
         }
         list address {
           key name;
           ordered-by user;
           description "Match source or destination address";
           uses firewall_addr6_object;
         }
         list source-prefix-list {
           key name;
           ordered-by user;
           description "Match source prefixes in named list";
           uses firewall_prefix_list;
         }
         list destination-prefix-list {
           key name;
           ordered-by user;
           description "Match destination prefixes in named list";
           uses firewall_prefix_list;
         }
         list prefix-list {
           key name;
           ordered-by user;
           description "Match source or destination prefixes in named list";
           uses firewall_prefix_list;
         }
         choice next-header_choice {
           case case_1 {
             leaf-list next-header {
               ordered-by user;
               type string;
             }
           }
           case case_2 {
             leaf-list next-header-except {
               ordered-by user;
               type string;
             }
           }
         }
         choice payload-protocol_choice {
           case case_1 {
             leaf-list payload-protocol {
               ordered-by user;
               type string;
             }
           }
           case case_2 {
             leaf-list payload-protocol-except {
               ordered-by user;
               type string;
             }
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice port_choice {
           case case_1 {
             leaf-list port {
               ordered-by user;
               type string;
             }
           }
           case case_2 {
             leaf-list port-except {
               ordered-by user;
               type string;
             }
           }
         }
         choice extension-header_choice {
           case case_1 {
             leaf-list extension-header {
               ordered-by user;
               type string;
             }
           }
           case case_2 {
             leaf-list extension-header-except {
               ordered-by user;
               type string;
             }
           }
         }
         choice esp-spi_choice {
           case case_1 {
             leaf-list esp-spi {
               ordered-by user;
               description "Range of values";
               type string;
             }
           }
           case case_2 {
             leaf-list esp-spi-except {
               ordered-by user;
               description "Range of values";
               type string;
             }
           }
         }
         choice ah-spi_choice {
           case case_1 {
             leaf-list ah-spi {
               ordered-by user;
               description "Range of values";
               type string;
             }
           }
           case case_2 {
             leaf-list ah-spi-except {
               ordered-by user;
               description "Range of values";
               type string;
             }
           }
         }
         leaf tcp-flags {
           description "Match TCP flags (in symbolic or hex formats)";
           type string;
         }
         choice loss-priority_choice {
           case case_1 {
             leaf-list loss-priority {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
           case case_2 {
             leaf-list loss-priority-except {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
         }
         choice forwarding-class_choice {
           case case_1 {
             leaf-list forwarding-class {
               ordered-by user;
               description "String name";
               type string {
                 junos:posix-pattern "^.{1,64}$";
                 junos:pattern-message "Must be string of 64 characters or less";
               }
             }
           }
           case case_2 {
             leaf-list forwarding-class-except {
               ordered-by user;
               description "String name";
               type string {
                 junos:posix-pattern "^.{1,64}$";
                 junos:pattern-message "Must be string of 64 characters or less";
               }
             }
           }
         }
       }
       container then {
         description "Action to take if the 'from' condition is matched";
         uses apply-advanced;
         leaf count {
           description "Count the packet in the named counter";
           type string {
             junos:posix-pattern "!^((__.*)|(.{65,}))$";
             junos:pattern-message "Must be a non-reserved string of 64 characters or less";
           }
         }
         leaf log {
           description "Log the packet";
           type empty;
         }
         leaf sample {
           description "Sample the packet";
           type empty;
         }
         leaf port-mirror {
           description "Port-mirror the packet";
           type empty;
         }
         choice designation {
           case case_1 {
             leaf service {
               description "Forward packets to service processing";
               type empty;
             }
           }
           case case_2 {
             leaf skip {
               description "Skip service processing";
               type empty;
             }
           }
           case case_3 {
             leaf accept {
               description "Accept the packet";
               type empty;
             }
           }
         }
       }
     }
   }
   grouping inet_dialer_filter {
     leaf name {
       description "Filter name";
       type string {
         junos:posix-pattern "!^((__.*)|(.{65,}))$";
         junos:pattern-message "Must be a non-reserved string of 64 characters or less";
       }
     }
     uses apply-advanced;
     leaf-list accounting-profile {
       ordered-by user;
       description "Accounting profile name";
       junos:must "(\"accounting-options filter-profile\")";
       junos:must-message "referenced accounting profile must be defined";
       type string;
     }
     list term {
       key name;
       ordered-by user;
       description "Define a firewall term";
       leaf name {
         description "Term name";
         type string {
           junos:posix-pattern "!^((__.*)|(.{65,}))$";
           junos:pattern-message "Must be a non-reserved string of 64 characters or less";
         }
       }
       uses apply-advanced;
       container from {
         description "Define match criteria";
         uses apply-advanced;
         list source-address {
           key name;
           ordered-by user;
           description "Match IP source address";
           uses firewall_addr_object;
         }
         list destination-address {
           key name;
           ordered-by user;
           description "Match IP destination address";
           uses firewall_addr_object;
         }
         list address {
           key name;
           ordered-by user;
           description "Match IP source or destination address";
           uses firewall_addr_object;
         }
         list source-prefix-list {
           key name;
           ordered-by user;
           description "Match IP source prefixes in named list";
           uses firewall_prefix_list;
         }
         list destination-prefix-list {
           key name;
           ordered-by user;
           description "Match IP destination prefixes in named list";
           uses firewall_prefix_list;
         }
         list prefix-list {
           key name;
           ordered-by user;
           description "Match IP source or destination prefixes in named list";
           uses firewall_prefix_list;
         }
         choice packet-length_choice {
           case case_1 {
             leaf-list packet-length {
               ordered-by user;
               description "Range of values";
               type string {
                 junos:posix-pattern "^([0-9]{1,4}|[1-5][0-9][0-9][0-9][0-9]|[6][0-4][0-9][0-9][0-9]|65[0-4][0-9][0-9]|655[0-2][0-9]|6553[0-5]|0x[0-f][0-f][0-f][0-f]|0x[0-f]|0x[0-f][0-f]|0x[0-f][0-f][0-f])(-([0-9]{1,4}|[1-5][0-9][0-9][0-9][0-9]|[6][0-4][0-9][0-9][0-9]|65[0-4][0-9][0-9]|655[0-2][0-9]|6553[0-5]|0x[0-f][0-f][0-f][0-f]|0x[0-f]|0x[0-f][0-f]|0x[0-f][0-f][0-f]))?$";
                 junos:pattern-message "Must be a numeric value or a range between 0-65535";
               }
             }
           }
           case case_2 {
             leaf-list packet-length-except {
               ordered-by user;
               description "Range of values";
               type string {
                 junos:posix-pattern "^([0-9]{1,4}|[1-5][0-9][0-9][0-9][0-9]|[6][0-4][0-9][0-9][0-9]|65[0-4][0-9][0-9]|655[0-2][0-9]|6553[0-5]|0x[0-f][0-f][0-f][0-f]|0x[0-f]|0x[0-f][0-f]|0x[0-f][0-f][0-f])(-([0-9]{1,4}|[1-5][0-9][0-9][0-9][0-9]|[6][0-4][0-9][0-9][0-9]|65[0-4][0-9][0-9]|655[0-2][0-9]|6553[0-5]|0x[0-f][0-f][0-f][0-f]|0x[0-f]|0x[0-f][0-f]|0x[0-f][0-f][0-f]))?$";
                 junos:pattern-message "Must be a numeric value or a range between 0-65535";
               }
             }
           }
         }
         choice precedence_choice {
           case case_1 {
             leaf-list precedence {
               ordered-by user;
               type string;
             }
           }
           case case_2 {
             leaf-list precedence-except {
               ordered-by user;
               type string;
             }
           }
         }
         choice dscp_choice {
           case case_1 {
             leaf-list dscp {
               ordered-by user;
               type string;
             }
           }
           case case_2 {
             leaf-list dscp-except {
               ordered-by user;
               type string;
             }
           }
         }
         choice ip-options_choice {
           case case_1 {
             leaf-list ip-options {
               ordered-by user;
               type string;
             }
           }
           case case_2 {
             leaf-list ip-options-except {
               ordered-by user;
               type string;
             }
           }
         }
         leaf is-fragment {
           description "Match if packet is a fragment";
           type empty;
         }
         leaf first-fragment {
           description "Match if packet is the first fragment";
           type empty;
         }
         choice fragment-offset_choice {
           case case_1 {
             leaf-list fragment-offset {
               ordered-by user;
               description "Range of values";
               type string {
                 junos:posix-pattern "^[[:digit:]]+(-[[:digit:]]+)?$";
                 junos:pattern-message "Must be a in form of number or a range in the form '<minimum-value>-<maximum-value>'";
               }
             }
           }
           case case_2 {
             leaf-list fragment-offset-except {
               ordered-by user;
               description "Range of values";
               type string {
                 junos:posix-pattern "^[[:digit:]]+(-[[:digit:]]+)?$";
                 junos:pattern-message "Must be a in form of number or a range in the form '<minimum-value>-<maximum-value>'";
               }
             }
           }
         }
         leaf fragment-flags {
           description "Match fragment flags";
           type string;
         }
         choice protocol_choice {
           case case_1 {
             leaf-list protocol {
               ordered-by user;
               type string;
             }
           }
           case case_2 {
             leaf-list protocol-except {
               ordered-by user;
               type string;
             }
           }
         }
         choice ttl_choice {
           case case_1 {
             leaf-list ttl {
               ordered-by user;
               description "Range of values";
               type string {
                 junos:posix-pattern "^([0-9]|[1-9][0-9]|1[0-9][0-9]|2[0-4][0-9]|25[0-5]|0x[0-f]|0x[0-f][0-f])(-([0-9]|[1-9][0-9]|1[0-9][0-9]|2[0-4][0-9]|25[0-5]|0x[0-f]|0x[0-f][0-f]))?$";
                 junos:pattern-message "Must be a numerical TTL value or range between 0-255";
               }
             }
           }
           case case_2 {
             leaf-list ttl-except {
               ordered-by user;
               description "Range of values";
               type string {
                 junos:posix-pattern "^([0-9]|[1-9][0-9]|1[0-9][0-9]|2[0-4][0-9]|25[0-5]|0x[0-f]|0x[0-f][0-f])(-([0-9]|[1-9][0-9]|1[0-9][0-9]|2[0-4][0-9]|25[0-5]|0x[0-f]|0x[0-f][0-f]))?$";
                 junos:pattern-message "Must be a numerical TTL value or range between 0-255";
               }
             }
           }
         }
         choice icmp-type_choice {
           case case_1 {
             leaf-list icmp-type {
               ordered-by user;
               type string;
             }
           }
           case case_2 {
             leaf-list icmp-type-except {
               ordered-by user;
               type string;
             }
           }
         }
         choice icmp-code_choice {
           case case_1 {
             leaf-list icmp-code {
               ordered-by user;
               type string;
             }
           }
           case case_2 {
             leaf-list icmp-code-except {
               ordered-by user;
               type string;
             }
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice port_choice {
           case case_1 {
             leaf-list port {
               ordered-by user;
               type string;
             }
           }
           case case_2 {
             leaf-list port-except {
               ordered-by user;
               type string;
             }
           }
         }
         leaf tcp-initial {
           description "Match initial packet of a TCP connection";
           type empty;
         }
         leaf tcp-established {
           description "Match packet of an established TCP connection";
           type empty;
         }
         leaf tcp-flags {
           description "Match TCP flags (in symbolic or hex formats)";
           type string;
         }
         choice esp-spi_choice {
           case case_1 {
             leaf-list esp-spi {
               ordered-by user;
               description "Range of values";
               type string;
             }
           }
           case case_2 {
             leaf-list esp-spi-except {
               ordered-by user;
               description "Range of values";
               type string;
             }
           }
         }
         choice ah-spi_choice {
           case case_1 {
             leaf-list ah-spi {
               ordered-by user;
               description "Range of values";
               type string;
             }
           }
           case case_2 {
             leaf-list ah-spi-except {
               ordered-by user;
               description "Range of values";
               type string;
             }
           }
         }
       }
       container then {
         description "Action to take if the 'from' condition is matched";
         uses apply-advanced;
         leaf log {
           description "Log the packet";
           type empty;
         }
         leaf syslog {
           description "System log (syslog) information about the packet";
           type empty;
         }
         leaf sample {
           description "Sample the packet";
           type empty;
         }
         choice designation {
           case case_1 {
             leaf note {
               description "Interested ISDN packet";
               type empty;
             }
           }
           case case_2 {
             leaf ignore {
               description "Non-interested ISDN packet";
               type empty;
             }
           }
         }
       }
     }
   }
   grouping inet_filter {
     leaf name {
       description "Filter name";
       type string {
         junos:posix-pattern "!^((__.*)|(.{65,}))$";
         junos:pattern-message "Must be a non-reserved string of 64 characters or less";
       }
     }
     uses apply-advanced;
     leaf promote {
       description "Promote a firewall match to PFM";
       type enumeration {
         enum "gre-key" {
           description "Promote GRE Key to PFM";
         }
         enum "dscp" {
           description "Promote DSCP to PFM";
         }
       }
     }
     leaf-list accounting-profile {
       ordered-by user;
       description "Accounting profile name";
       junos:must "(\"accounting-options filter-profile\")";
       junos:must-message "referenced accounting profile must be defined";
       type string;
     }
     leaf interface-specific {
       description "Defined counters are interface specific";
       type empty;
     }
     leaf scale-optimized {
       description "Improve filter prefix scale";
       type empty;
     }
     leaf physical-interface-filter {
       description "Filter is physical interface filter";
       type empty;
     }
     leaf enhanced-mode {
       description "Define filter for chassis network-services enhanced mode";
       junos:must "(!(\".. enhanced-mode-override\"))";
       junos:must-message "Cannot configure filter for both enhanced-mode and enhanced-mode-override";
       type empty;
     }
     leaf interface-shared {
       description "Filter is interface-shared";
       junos:must "(!(\".. physical-interface-filter\"))";
       junos:must-message "Cannot be both physical-interface-filter and interface-shared";
       junos:must "(!(\".. interface-specific\"))";
       junos:must-message "Cannot be both interface-specific and interface-shared";
       type empty;
     }
     leaf enhanced-mode-override {
       description "Override the default chassis network-services enhanced mode for dynamic filter";
       junos:must "(!(\".. enhanced-mode\"))";
       junos:must-message "Cannot configure filter for both enhanced-mode-override and enhanced-mode";
       type empty;
     }
     leaf instance-shared {
       description "Filter is routing-instance shared";
       junos:must "(\"chassis network-services enhanced-ip\")";
       junos:must-message "instance-shared filter available only in enhanced-ip mode";
       junos:must "(!(\".. physical-interface-filter\"))";
       junos:must-message "Cannot be both physical-interface-filter and instance-shared";
       junos:must "(!(\".. interface-specific\"))";
       junos:must-message "Cannot be both interface-specific and instance-shared";
       type empty;
     }
     leaf fast-lookup-filter {
       description "Configure filter in the fast lookup hardware block";
       type empty;
     }
     list term {
       key name;
       ordered-by user;
       description "Define a firewall term";
       leaf name {
         description "Term name";
         type string {
           junos:posix-pattern "!^((__.*)|(.{65,}))$";
           junos:pattern-message "Must be a non-reserved string of 64 characters or less";
         }
       }
       uses apply-advanced;
       leaf filter {
         description "Filter to include";
         junos:must "((\"firewall filter $$\" || \"firewall family inet filter $$\"))";
         junos:must-message "Referenced filter is not defined";
         junos:must "((!(\".. from\") && !(\".. then\")))";
         junos:must-message "Not compatible with 'from or then'";
         type string {
           junos:posix-pattern "!^((__.*)|(.{65,}))$";
           junos:pattern-message "Must be a non-reserved string of 64 characters or less";
         }
       }
       container from {
         description "Define match criteria";
         uses apply-advanced;
         choice destination-class_choice {
           case case_1 {
             leaf-list destination-class {
               ordered-by user;
               description "String name";
               type string;
             }
           }
           case case_2 {
             leaf-list destination-class-except {
               ordered-by user;
               description "String name";
               type string;
             }
           }
         }
         choice source-class_choice {
           case case_1 {
             leaf-list source-class {
               ordered-by user;
               description "String name";
               type string;
             }
           }
           case case_2 {
             leaf-list source-class-except {
               ordered-by user;
               description "String name";
               type string;
             }
           }
         }
         choice interface-group_choice {
           case case_1 {
             leaf-list interface-group {
               ordered-by user;
               description "Range of values";
               type string;
             }
           }
           case case_2 {
             leaf-list interface-group-except {
               ordered-by user;
               description "Range of values";
               type string;
             }
           }
         }
         list source-address {
           key name;
           ordered-by user;
           description "Match IP source address";
           uses firewall_addr_object;
         }
         list destination-address {
           key name;
           ordered-by user;
           description "Match IP destination address";
           uses firewall_addr_object;
         }
         list address {
           key name;
           ordered-by user;
           description "Match IP source or destination address";
           uses firewall_addr_object;
         }
         list source-prefix-list {
           key name;
           ordered-by user;
           description "Match IP source prefixes in named list";
           uses firewall_prefix_list;
         }
         list destination-prefix-list {
           key name;
           ordered-by user;
           description "Match IP destination prefixes in named list";
           uses firewall_prefix_list;
         }
         list prefix-list {
           key name;
           ordered-by user;
           description "Match IP source or destination prefixes in named list";
           uses firewall_prefix_list;
         }
         choice packet-length_choice {
           case case_1 {
             leaf-list packet-length {
               ordered-by user;
               description "Range of values";
               type string {
                 junos:posix-pattern "^([0-9]{1,4}|[1-5][0-9][0-9][0-9][0-9]|[6][0-4][0-9][0-9][0-9]|65[0-4][0-9][0-9]|655[0-2][0-9]|6553[0-5]|0x[0-f][0-f][0-f][0-f]|0x[0-f]|0x[0-f][0-f]|0x[0-f][0-f][0-f])(-([0-9]{1,4}|[1-5][0-9][0-9][0-9][0-9]|[6][0-4][0-9][0-9][0-9]|65[0-4][0-9][0-9]|655[0-2][0-9]|6553[0-5]|0x[0-f][0-f][0-f][0-f]|0x[0-f]|0x[0-f][0-f]|0x[0-f][0-f][0-f]))?$";
                 junos:pattern-message "Must be a numeric value or a range between 0-65535";
               }
             }
           }
           case case_2 {
             leaf-list packet-length-except {
               ordered-by user;
               description "Range of values";
               type string {
                 junos:posix-pattern "^([0-9]{1,4}|[1-5][0-9][0-9][0-9][0-9]|[6][0-4][0-9][0-9][0-9]|65[0-4][0-9][0-9]|655[0-2][0-9]|6553[0-5]|0x[0-f][0-f][0-f][0-f]|0x[0-f]|0x[0-f][0-f]|0x[0-f][0-f][0-f])(-([0-9]{1,4}|[1-5][0-9][0-9][0-9][0-9]|[6][0-4][0-9][0-9][0-9]|65[0-4][0-9][0-9]|655[0-2][0-9]|6553[0-5]|0x[0-f][0-f][0-f][0-f]|0x[0-f]|0x[0-f][0-f]|0x[0-f][0-f][0-f]))?$";
                 junos:pattern-message "Must be a numeric value or a range between 0-65535";
               }
             }
           }
         }
         choice dscp_choice {
           case case_1 {
             leaf-list dscp {
               ordered-by user;
               type string;
             }
           }
           case case_2 {
             leaf-list dscp-except {
               ordered-by user;
               type string;
             }
           }
         }
         choice precedence_choice {
           case case_1 {
             leaf-list precedence {
               ordered-by user;
               type string;
             }
           }
           case case_2 {
             leaf-list precedence-except {
               ordered-by user;
               type string;
             }
           }
         }
         choice ip-options_choice {
           case case_1 {
             leaf-list ip-options {
               ordered-by user;
               type string;
             }
           }
           case case_2 {
             leaf-list ip-options-except {
               ordered-by user;
               type string;
             }
           }
         }
         leaf is-fragment {
           description "Match if packet is a fragment";
           type empty;
         }
         leaf first-fragment {
           description "Match if packet is the first fragment";
           type empty;
         }
         leaf service-filter-hit {
           description "Match if service-filter-hit is set";
           type empty;
         }
         choice fragment-offset_choice {
           case case_1 {
             leaf-list fragment-offset {
               ordered-by user;
               description "Range of values";
               type string {
                 junos:posix-pattern "^[[:digit:]]+(-[[:digit:]]+)?$";
                 junos:pattern-message "Must be a in form of number or a range in the form '<minimum-value>-<maximum-value>'";
               }
             }
           }
           case case_2 {
             leaf-list fragment-offset-except {
               ordered-by user;
               description "Range of values";
               type string {
                 junos:posix-pattern "^[[:digit:]]+(-[[:digit:]]+)?$";
                 junos:pattern-message "Must be a in form of number or a range in the form '<minimum-value>-<maximum-value>'";
               }
             }
           }
         }
         leaf fragment-flags {
           description "Match fragment flags (in symbolic or hex formats) - (Ingress only)";
           type string;
         }
         choice protocol_choice {
           case case_1 {
             leaf-list protocol {
               ordered-by user;
               type string;
             }
           }
           case case_2 {
             leaf-list protocol-except {
               ordered-by user;
               type string;
             }
           }
         }
         choice ttl_choice {
           case case_1 {
             leaf-list ttl {
               ordered-by user;
               description "Range of values";
               type string {
                 junos:posix-pattern "^([0-9]|[1-9][0-9]|1[0-9][0-9]|2[0-4][0-9]|25[0-5]|0x[0-f]|0x[0-f][0-f])(-([0-9]|[1-9][0-9]|1[0-9][0-9]|2[0-4][0-9]|25[0-5]|0x[0-f]|0x[0-f][0-f]))?$";
                 junos:pattern-message "Must be a numerical TTL value or range between 0-255";
               }
             }
           }
           case case_2 {
             leaf-list ttl-except {
               ordered-by user;
               description "Range of values";
               type string {
                 junos:posix-pattern "^([0-9]|[1-9][0-9]|1[0-9][0-9]|2[0-4][0-9]|25[0-5]|0x[0-f]|0x[0-f][0-f])(-([0-9]|[1-9][0-9]|1[0-9][0-9]|2[0-4][0-9]|25[0-5]|0x[0-f]|0x[0-f][0-f]))?$";
                 junos:pattern-message "Must be a numerical TTL value or range between 0-255";
               }
             }
           }
         }
         choice icmp-type_choice {
           case case_1 {
             leaf-list icmp-type {
               ordered-by user;
               type string;
             }
           }
           case case_2 {
             leaf-list icmp-type-except {
               ordered-by user;
               type string;
             }
           }
         }
         choice icmp-code_choice {
           case case_1 {
             leaf-list icmp-code {
               ordered-by user;
               type string;
             }
           }
           case case_2 {
             leaf-list icmp-code-except {
               ordered-by user;
               type string;
             }
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice port_choice {
           case case_1 {
             leaf-list port {
               ordered-by user;
               type string;
             }
           }
           case case_2 {
             leaf-list port-except {
               ordered-by user;
               type string;
             }
           }
         }
         leaf tcp-initial {
           description "Match initial packet of a TCP connection";
           type empty;
         }
         leaf tcp-established {
           description "Match packet of an established TCP connection";
           type empty;
         }
         leaf tcp-flags {
           description "Match TCP flags (in symbolic or hex formats)";
           type string;
         }
         choice esp-spi_choice {
           case case_1 {
             leaf-list esp-spi {
               ordered-by user;
               description "Range of values";
               type string;
             }
           }
           case case_2 {
             leaf-list esp-spi-except {
               ordered-by user;
               description "Range of values";
               type string;
             }
           }
         }
         choice ah-spi_choice {
           case case_1 {
             leaf-list ah-spi {
               ordered-by user;
               description "Range of values";
               type string;
             }
           }
           case case_2 {
             leaf-list ah-spi-except {
               ordered-by user;
               description "Range of values";
               type string;
             }
           }
         }
         list interface {
           key name;
           ordered-by user;
           description "Match interface name";
           uses match_interface_object;
         }
         list interface-set {
           key name;
           ordered-by user;
           description "Match interface in set";
           uses match_interface_set_object;
         }
         choice forwarding-class_choice {
           case case_1 {
             leaf-list forwarding-class {
               ordered-by user;
               description "String name";
               type string {
                 junos:posix-pattern "^.{1,64}$";
                 junos:pattern-message "Must be string of 64 characters or less";
               }
             }
           }
           case case_2 {
             leaf-list forwarding-class-except {
               ordered-by user;
               description "String name";
               type string {
                 junos:posix-pattern "^.{1,64}$";
                 junos:pattern-message "Must be string of 64 characters or less";
               }
             }
           }
         }
         choice loss-priority_choice {
           case case_1 {
             leaf-list loss-priority {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
           case case_2 {
             leaf-list loss-priority-except {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
         }
         choice rat-type_choice {
           case case_1 {
             leaf-list rat-type {
               ordered-by user;
               type string;
             }
           }
           case case_2 {
             leaf-list rat-type-except {
               ordered-by user;
               type string;
             }
           }
         }
         choice redirect-reason_choice {
           case case_1 {
             leaf-list redirect-reason {
               ordered-by user;
               type enumeration {
                 enum "aoc" {
                   description "Advice of Charge";
                 }
                 enum "aolb" {
                   description "Advice of Low Balance";
                 }
                 enum "dpi" {
                   description "Layer7 match required";
                 }
               }
             }
           }
           case case_2 {
             leaf-list redirect-reason-except {
               ordered-by user;
               type enumeration {
                 enum "aoc" {
                   description "Advice of Charge";
                 }
                 enum "aolb" {
                   description "Advice of Low Balance";
                 }
                 enum "dpi" {
                   description "Layer7 match required";
                 }
               }
             }
           }
         }
         choice gre-key_choice {
           case case_1 {
             leaf-list gre-key {
               ordered-by user;
               description "Range of values";
               type string;
             }
           }
           case case_2 {
             leaf-list gre-key-except {
               ordered-by user;
               description "Range of values";
               type string;
             }
           }
         }
         choice flex-mask_choice {
           case case_1 {
             container flexible-match-mask {
               description "Match flexible mask";
               uses match_L3_flexible_mask;
             }
           }
         }
         choice flex-range_choice {
           case case_1 {
             container flexible-match-range {
               description "Match flexible range";
               uses match_L3_flexible_range;
             }
           }
         }
         choice policy-map_choice {
           case case_1 {
             leaf-list policy-map {
               ordered-by user;
               description "String name";
               junos:must "(\"class-of-service policy-map $$\")";
               junos:must-message "Undefined policy-map instance";
               type string {
                 length "1 .. 64";
                 junos:posix-pattern "!^((__.*)|(.{65,}))$";
                 junos:pattern-message "Must be a non-reserved string of 64 characters or less";
               }
             }
           }
           case case_2 {
             leaf-list policy-map-except {
               ordered-by user;
               description "String name";
               junos:must "(\"class-of-service policy-map $$\")";
               junos:must-message "Undefined policy-map instance";
               type string {
                 length "1 .. 64";
                 junos:posix-pattern "!^((__.*)|(.{65,}))$";
                 junos:pattern-message "Must be a non-reserved string of 64 characters or less";
               }
             }
           }
         }
         container vxlan {
           description "Define vxlan match items";
           uses apply-advanced;
           choice vni_choice {
             case case_1 {
               leaf-list vni {
                 ordered-by user;
                 description "Range of values";
                 type string {
                   junos:posix-pattern "^([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f])(-([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f]))?$";
                   junos:pattern-message "Must be a numeric value or a range between 0-16777215";
                 }
               }
             }
             case case_2 {
               leaf-list vni-except {
                 ordered-by user;
                 description "Range of values";
                 type string {
                   junos:posix-pattern "^([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f])(-([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f]))?$";
                   junos:pattern-message "Must be a numeric value or a range between 0-16777215";
                 }
               }
             }
           }
           choice rsvd1_choice {
             case case_1 {
               leaf-list rsvd1 {
                 ordered-by user;
                 description "Range of values";
                 type string {
                   junos:posix-pattern "^([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f])(-([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f]))?$";
                   junos:pattern-message "Must be a numeric value or a range between 0-16777215";
                 }
               }
             }
             case case_2 {
               leaf-list rsvd1-except {
                 ordered-by user;
                 description "Range of values";
                 type string {
                   junos:posix-pattern "^([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f])(-([0-9]{1,7}|1[0-5][0-9][0-9][0-9][0-9][0-9][0-9]|16[0-6][0-9][0-9][0-9][0-9][0-9]|167[0-6][0-9][0-9][0-9][0-9]|1677[0-6][0-9]0-9][0-9]|16777[0-1][0-9][0-9]|1677721[0-5]|0x[0-f]|0x[0-f][0-f]|0x[0-f][0-f][0-f]|0x[0-f][0-f][0-f][0-f]|0x[0-f][0-f][0-f][0-f][0-f]|0x[0-f][0-f][0-f][0-f][0-f][0-f]))?$";
                   junos:pattern-message "Must be a numeric value or a range between 0-16777215";
                 }
               }
             }
           }
           choice rsvd2_choice {
             case case_1 {
               leaf-list rsvd2 {
                 ordered-by user;
                 description "Range of values";
                 type string {
                   junos:posix-pattern "^([0-9]|[1-9][0-9]|1[0-9][0-9]|2[0-4][0-9]|25[0-5]|0x[0-f]|0x[0-f][0-f])(-([0-9]|[1-9][0-9]|1[0-9][0-9]|2[0-4][0-9]|25[0-5]|0x[0-f]|0x[0-f][0-f]))?$";
                   junos:pattern-message "Must be a numeric value or a range between 0-255";
                 }
               }
             }
             case case_2 {
               leaf-list rsvd2-except {
                 ordered-by user;
                 description "Range of values";
                 type string {
                   junos:posix-pattern "^([0-9]|[1-9][0-9]|1[0-9][0-9]|2[0-4][0-9]|25[0-5]|0x[0-f]|0x[0-f][0-f])(-([0-9]|[1-9][0-9]|1[0-9][0-9]|2[0-4][0-9]|25[0-5]|0x[0-f]|0x[0-f][0-f]))?$";
                   junos:pattern-message "Must be a numeric value or a range between 0-255";
                 }
               }
             }
           }
           container flags {
             description "Match VXlan flag field";
             uses match_flags_value;
           }
         }
       }
       container then {
         description "Action to take if the 'from' condition is matched";
         uses apply-advanced;
         choice policer-choice {
           case case_1 {
             leaf policer {
               description "Name of policer to use to rate-limit traffic";
               junos:must "(!(\"firewall policer $$ aggregate\"))";
               junos:must-message "Cannot attach a aggregate policer to filter";
               type string {
                 junos:posix-pattern "!^((__.*)|(.{65,}))$";
                 junos:pattern-message "Must be a non-reserved string of 64 characters or less";
               }
             }
           }
           case case_2 {
             container three-color-policer {
               description "Police the packet using a three-color-policer";
               uses apply-advanced;
               choice type-choice {
                 case case_1 {
                   leaf single-rate {
                     description "Name of single-rate three-color policer to use to rate-limit traffic";
                     junos:must "(\"firewall three-color-policer $$ single-rate\")";
                     junos:must-message "Referenced single-rate policer does not exist";
                     type string {
                       junos:posix-pattern "!^((__.*)|(.{65,}))$";
                       junos:pattern-message "Must be a non-reserved string of 64 characters or less";
                     }
                   }
                 }
                 case case_2 {
                   leaf single-packet-rate {
                     description "Name of single-packet-rate three-color policer to use to rate-limit traffic";
                     junos:must "(\"firewall three-color-policer $$ single-packet-rate\")";
                     junos:must-message "Referenced single-packet-rate policer does not exist";
                     type string {
                       junos:posix-pattern "!^((__.*)|(.{65,}))$";
                       junos:pattern-message "Must be a non-reserved string of 64 characters or less";
                     }
                   }
                 }
                 case case_3 {
                   leaf two-rate {
                     description "Name of two-rate three-color policer to use to rate-limit traffic";
                     junos:must "(\"firewall three-color-policer $$ two-rate\")";
                     junos:must-message "Referenced two-rate policer does not exist";
                     type string {
                       junos:posix-pattern "!^((__.*)|(.{65,}))$";
                       junos:pattern-message "Must be a non-reserved string of 64 characters or less";
                     }
                   }
                 }
                 case case_4 {
                   leaf two-packet-rate {
                     description "Name of two-packet-rate three-color policer to use to rate-limit traffic";
                     junos:must "(\"firewall three-color-policer $$ two-packet-rate\")";
                     junos:must-message "Referenced two-packet-rate policer does not exist";
                     type string {
                       junos:posix-pattern "!^((__.*)|(.{65,}))$";
                       junos:pattern-message "Must be a non-reserved string of 64 characters or less";
                     }
                   }
                 }
               }
             }
           }
           case case_3 {
             leaf hierarchical-policer {
               description "Name of hierarchical policer to use to rate-limit traffic";
               type string {
                 junos:posix-pattern "!^((__.*)|(.{65,}))$";
                 junos:pattern-message "Must be a non-reserved string of 64 characters or less";
               }
             }
           }
         }
         choice policy-map-choice {
           case case_1 {
             leaf clear-policy-map {
               description "Clear the policy marking";
               type empty;
             }
           }
           case case_2 {
             leaf policy-map {
               description "Policy map action";
               junos:must "(\"class-of-service policy-map $$\")";
               junos:must-message "referenced policy map must be defined";
               type string {
                 junos:posix-pattern "!^((__.*)|(.{65,}))$";
                 junos:pattern-message "Must be a non-reserved string of 64 characters or less";
               }
             }
           }
         }
         choice inetcnt {
           case case_1 {
             leaf traffic-class-count {
               description "Count the packet in the named traffic-class counter";
               type string {
                 junos:posix-pattern "!^((__.*)|(.{65,}))$";
                 junos:pattern-message "Must be a non-reserved string of 64 characters or less";
               }
             }
           }
           case case_2 {
             leaf count {
               description "Count the packet in the named counter";
               type string {
                 junos:posix-pattern "!^((__.*)|(.{65,}))$";
                 junos:pattern-message "Must be a non-reserved string of 64 characters or less";
               }
             }
           }
         }
         leaf service-accounting {
           description "Count the packets for service accounting";
           junos:must "(!(\".. service-accounting-deferred\"))";
           junos:must-message "'service-accounting-deferred' and 'service-accounting' cannot coexist";
           junos:must "(!(\".. count\"))";
           junos:must-message "'count' and 'service-accounting' cannot coexist";
           type empty;
         }
         leaf skip-services {
           description "Skip the services";
           type empty;
         }
         leaf service-accounting-deferred {
           description "Count the packets for deferred service accounting";
           junos:must "(!(\".. service-accounting\"))";
           junos:must-message "Cannot be both 'service-accounting' and 'service-accounting-deferred'";
           junos:must "(!(\".. count\"))";
           junos:must-message "'count' and 'service-accounting-deferred' cannot coexist";
           type empty;
         }
         leaf log {
           description "Log the packet";
           type empty;
         }
         leaf packet-mode {
           description "Bypass flow mode for the packet";
           type empty;
         }
         leaf syslog {
           description "System log (syslog) information about the packet";
           type empty;
         }
         leaf sample {
           description "Sample the packet";
           junos:must "(!(\".. sampling-instance\"))";
           junos:must-message "'sampling' and 'sampling-instance' are mutually exclusive";
           junos:must "((\"forwarding-options sampling family inet\" || (\"forwarding-options packet-capture\" || any \"forwarding-options sampling instance <*> family inet\")))";
           junos:must-message "Requires forwarding-options sampling or packet-capture config";
           type empty;
         }
         leaf port-mirror-instance {
           description "Port-mirror the packet to specified instance";
           junos:must "(\"forwarding-options port-mirroring instance $$\")";
           junos:must-message "Referenced port-mirroring instance does not exist";
           type string {
             junos:posix-pattern "!^((__.*)|(.{65,}))$";
             junos:pattern-message "Must be a non-reserved string of 64 characters or less";
           }
         }
         leaf port-mirror {
           description "Port-mirror the packet";
           junos:must "(!(\".. port-mirror-instance\"))";
           junos:must-message "'port-mirror' and 'port-mirror-instance' are mutually exclusive";
           type empty;
         }
         leaf loss-priority {
           description "Packet's loss priority";
           junos:must "(!(\".. three-color-policer\"))";
           junos:must-message "Configuring loss-priority is incompatible with configuring three-color-policer";
           type enumeration {
             enum "low" {
               description "Loss priority low";
             }
             enum "high" {
               description "Loss priority high";
             }
             enum "medium-low" {
               description "Loss priority medium-low";
             }
             enum "medium-high" {
               description "Loss priority medium-high";
             }
           }
         }
         leaf forwarding-class {
           description "Classify packet to forwarding class";
           type string {
             junos:posix-pattern "^.{1,64}$";
             junos:pattern-message "Must be string of 64 characters or less";
           }
         }
         leaf service-filter-hit {
           description "Marked when packet processing by the current type of chained filters is done, the packet is directed to the next type of filters";
           type empty;
         }
         leaf force-premium {
           description "When this bit is marked, traffic is considered as premium by the following hierarchical policer";
           type empty;
         }
         leaf exclude-accounting {
           description "When this is marked, traffic is excluded from accurate accounting";
           type empty;
         }
         leaf virtual-channel {
           description "Set the output interface virtual channel";
           junos:must "(\"class-of-service virtual-channels $$\")";
           junos:must-message "Referenced virtual channel is not defined";
           type string {
             junos:posix-pattern "!^((__.*)|(.{65,}))$";
             junos:pattern-message "Must be a non-reserved string of 64 characters or less";
           }
         }
         choice designation {
           case case_1 {
             leaf accept {
               description "Accept the packet";
               type empty;
             }
           }
           case case_2 {
             container discard {
               presence "enable discard";
               description "Discard the packet";
               uses apply-advanced;
               leaf accounting {
                 description "Named discard collector for packet";
                 type string;
               }
             }
           }
           case case_3 {
             leaf next {
               description "Continue to next term in a filter";
               type enumeration {
                 enum "term" {
                   description "Continue to next term in a filter";
                 }
               }
             }
           }
           case case_4 {
             list logical-system {
               key logical-system-name;
               ordered-by user;
               description "Packets are directed to specified logical system";
               max-elements 1;
               leaf logical-system-name {
                 description "Name of logical system";
                 type string {
                   junos:posix-pattern "^[a-zA-Z0-9_-]{1,63}$";
                   junos:pattern-message "Logical-system name is a string consisting of up to 63 letters, numbers, dashes and underscores";
                 }
               }
               container routing-instance {
                 description "Packets are directed to specified routing instance";
                 leaf routing-instance-name {
                   description "Name of routing instance";
                   type string {
                     junos:posix-pattern "!^((__.*__)|(all)|(.*[ ].*)|(\"\")|(.{129,}))$";
                     junos:pattern-message "Must be a non-reserved string of 128 characters or less with no spaces.";
                   }
                 }
                 leaf topology {
                   description "Packets are directed to specified topology";
                   type string {
                     junos:posix-pattern "!^((.*:.*)|(.{129,}))$";
                     junos:pattern-message "Must be a non-reserved string of 128 characters or less";
                   }
                 }
               }
               leaf topology {
                 description "Packets are directed to specified topology";
                 type string {
                   junos:posix-pattern "!^((.*:.*)|(.{129,}))$";
                   junos:pattern-message "Must be a non-reserved string of 128 characters or less";
                 }
               }
             }
           }
           case case_5 {
             container routing-instance {
               description "Packets are directed to specified routing instance";
               leaf routing-instance-name {
                 description "Name of routing instance";
                 type string {
                   junos:posix-pattern "!^((__.*__)|(all)|(.*[ ].*)|(\"\")|(.{129,}))$";
                   junos:pattern-message "Must be a non-reserved string of 128 characters or less with no spaces.";
                 }
               }
               leaf topology {
                 description "Packets are directed to specified topology";
                 type string {
                   junos:posix-pattern "!^((.*:.*)|(.{129,}))$";
                   junos:pattern-message "Must be a non-reserved string of 128 characters or less";
                 }
               }
             }
           }
           case case_6 {
             leaf topology {
               description "Packets are directed to specified topology";
               type string {
                 junos:posix-pattern "!^((.*:.*)|(.{129,}))$";
                 junos:pattern-message "Must be a non-reserved string of 128 characters or less";
               }
             }
           }
           case case_7 {
             container next-ip {
               description "Packets are directed to specified the specified ipv4 address";
               leaf address {
                 description "Address to route";
                 type jt:ipv4prefix;
               }
               container routing-instance {
                 description "Packets are directed to specified routing instance";
                 leaf routing-instance-name {
                   description "Name of routing instance";
                   type string {
                     junos:posix-pattern "!^((__.*__)|(all)|(.*[ ].*)|(\"\")|(.{129,}))$";
                     junos:pattern-message "Must be a non-reserved string of 128 characters or less with no spaces.";
                   }
                 }
                 leaf topology {
                   description "Packets are directed to specified topology";
                   type string {
                     junos:posix-pattern "!^((.*:.*)|(.{129,}))$";
                     junos:pattern-message "Must be a non-reserved string of 128 characters or less";
                   }
                 }
               }
             }
           }
           case case_8 {
             container next-interface {
               presence "enable next-interface";
               description "Packets are to be routed through the specified interface";
               uses apply-advanced;
               leaf interface-name {
                 description "Interface name";
                 type string {
                   length "1 .. 127";
                   junos:posix-pattern "^((ge-)|(mge-)|(xe-)|(et-)|(gr-)|(ae)|(irb))";
                   junos:pattern-message "Only ge, mge, xe, et, ae, irb and point-to-point gr tunnel intefaces are supported";
                 }
               }
               container routing-instance {
                 description "Packets are directed to specified routing instance";
                 leaf routing-instance-name {
                   description "Name of routing instance";
                   type string {
                     junos:posix-pattern "!^((__.*__)|(all)|(.*[ ].*)|(\"\")|(.{129,}))$";
                     junos:pattern-message "Must be a non-reserved string of 128 characters or less with no spaces.";
                   }
                 }
                 leaf topology {
                   description "Packets are directed to specified topology";
                   type string {
                     junos:posix-pattern "!^((.*:.*)|(.{129,}))$";
                     junos:pattern-message "Must be a non-reserved string of 128 characters or less";
                   }
                 }
               }
               choice designation {
                 case case_1 {
                   leaf accept {
                     description "Accept the packet";
                     type empty;
                   }
                 }
                 case case_2 {
                   leaf next {
                     description "Continue to next term in a filter";
                     type enumeration {
                       enum "term" {
                         description "Continue to next term in a filter";
                       }
                     }
                   }
                 }
               }
             }
           }
           case case_9 {
             leaf ipsec-sa {
               description "Use specified IPSec security association";
               type string;
             }
           }
           case case_10 {
             leaf next-hop-group {
               description "Use specified next-hop group";
               type string;
             }
           }
           case case_11 {
             container decapsulate {
               presence "enable decapsulate";
               description "Terminate a tunnel";
               choice tunnel-protocol {
                 case case_1 {
                   container gre {
                     presence "enable gre";
                     description "GRE protocol";
                     uses apply-advanced;
                     leaf-list sample {
                       ordered-by user;
                       description "Sample the packet";
                       junos:must "(!(\".. sampling-instance\"))";
                       junos:must-message "'sampling' and 'sampling-instance' are mutually exclusive";
                       type enumeration {
                         enum "inet" {
                           description "IPV4 protocol";
                           junos:must "((\"forwarding-options sampling family inet\" || (\"forwarding-options packet-capture\" || any \"forwarding-options sampling instance <*> family inet\")))";
                           junos:must-message "Requires forwarding-options sampling or packet-capture config";
                         }
                         enum "inet6" {
                           description "IPV6 protocol";
                           junos:must "((\"forwarding-options sampling family inet6\" || (\"forwarding-options packet-capture\" || any \"forwarding-options sampling instance <*> family inet6\")))";
                           junos:must-message "Requires forwarding-options sampling or packet-capture config";
                         }
                         enum "mpls" {
                           description "MPLS protocol";
                           junos:must "(!(\".. .. sample mpls-ipvx-payload\"))";
                           junos:must-message "Cannot configure both sample mpls and sample mpls-ipvx-payload";
                           junos:must "((\"forwarding-options sampling family mpls\" || (\"forwarding-options packet-capture\" || any \"forwarding-options sampling instance <*> family mpls\")))";
                           junos:must-message "Requires forwarding-options sampling or packet-capture config";
                         }
                       }
                     }
                     leaf no-decrement-ttl {
                       description "Do not decrement TTL";
                       type empty;
                     }
                     leaf forwarding-class {
                       description "Classify packet to forwarding class";
                       type string {
                         junos:posix-pattern "^.{1,64}$";
                         junos:pattern-message "Must be string of 64 characters or less";
                       }
                     }
                     leaf interface-group {
                       description "Set the interface group";
                       type union {
                         type string {
                           pattern "<.*>|$.*";
                         }
                         type uint32 {
                           range "0 .. 255";
                         }
                       }
                     }
                     choice destination {
                       case case_1 {
                         container routing-instance {
                           description "Packets are directed to specified routing instance";
                           leaf routing-instance-name {
                             description "Name of routing instance";
                             junos:must "(\"routing-instances $$\")";
                             junos:must-message "referenced routing instance must be defined";
                             type string {
                               junos:posix-pattern "!^((__.*__)|(all)|(.*[ ].*)|(\"\")|(.{129,}))$";
                               junos:pattern-message "Must be a non-reserved string of 128 characters or less with no spaces.";
                             }
                           }
                         }
                       }
                     }
                   }
                 }
                 case case_2 {
                   container gre-in-udp {
                     presence "enable gre-in-udp";
                     description "GRE-in-UDP protocol";
                     uses apply-advanced;
                     leaf-list sample {
                       ordered-by user;
                       description "Sample the packet";
                       junos:must "(!(\".. sampling-instance\"))";
                       junos:must-message "'sampling' and 'sampling-instance' are mutually exclusive";
                       type enumeration {
                         enum "inet" {
                           description "IPV4 protocol";
                           junos:must "((\"forwarding-options sampling family inet\" || (\"forwarding-options packet-capture\" || any \"forwarding-options sampling instance <*> family inet\")))";
                           junos:must-message "Requires forwarding-options sampling or packet-capture config";
                         }
                         enum "inet6" {
                           description "IPV6 protocol";
                           junos:must "((\"forwarding-options sampling family inet6\" || (\"forwarding-options packet-capture\" || any \"forwarding-options sampling instance <*> family inet6\")))";
                           junos:must-message "Requires forwarding-options sampling or packet-capture config";
                         }
                         enum "mpls" {
                           description "MPLS protocol";
                           junos:must "(!(\".. .. sample mpls-ipvx-payload\"))";
                           junos:must-message "Cannot configure both sample mpls and sample mpls-ipvx-payload";
                           junos:must "((\"forwarding-options sampling family mpls\" || (\"forwarding-options packet-capture\" || any \"forwarding-options sampling instance <*> family mpls\")))";
                           junos:must-message "Requires forwarding-options sampling or packet-capture config";
                         }
                       }
                     }
                     leaf no-decrement-ttl {
                       description "Do not decrement TTL";
                       type empty;
                     }
                     leaf forwarding-class {
                       description "Classify packet to forwarding class";
                       type string {
                         junos:posix-pattern "^.{1,64}$";
                         junos:pattern-message "Must be string of 64 characters or less";
                       }
                     }
                     leaf interface-group {
                       description "Set the interface group";
                       type union {
                         type string {
                           pattern "<.*>|$.*";
                         }
                         type uint32 {
                           range "0 .. 255";
                         }
                       }
                     }
                     choice destination {
                       case case_1 {
                         container routing-instance {
                           description "Packets are directed to specified routing instance";
                           leaf routing-instance-name {
                             description "Name of routing instance";
                             junos:must "(\"routing-instances $$\")";
                             junos:must-message "referenced routing instance must be defined";
                             type string {
                               junos:posix-pattern "!^((__.*__)|(all)|(.*[ ].*)|(\"\")|(.{129,}))$";
                               junos:pattern-message "Must be a non-reserved string of 128 characters or less with no spaces.";
                             }
                           }
                         }
                       }
                     }
                   }
                 }
                 case case_3 {
                   container mpls-in-udp {
                     presence "enable mpls-in-udp";
                     description "MPLS-in-UDP protocol";
                     uses apply-advanced;
                     leaf-list sample {
                       ordered-by user;
                       description "Sample the packet";
                       junos:must "(!(\".. sampling-instance\"))";
                       junos:must-message "'sampling' and 'sampling-instance' are mutually exclusive";
                       type enumeration {
                         enum "inet" {
                           description "IPV4 protocol";
                           junos:must "((\"forwarding-options sampling family inet\" || (\"forwarding-options packet-capture\" || any \"forwarding-options sampling instance <*> family inet\")))";
                           junos:must-message "Requires forwarding-options sampling or packet-capture config";
                         }
                         enum "inet6" {
                           description "IPV6 protocol";
                           junos:must "((\"forwarding-options sampling family inet6\" || (\"forwarding-options packet-capture\" || any \"forwarding-options sampling instance <*> family inet6\")))";
                           junos:must-message "Requires forwarding-options sampling or packet-capture config";
                         }
                         enum "mpls" {
                           description "MPLS protocol";
                           junos:must "(!(\".. .. sample mpls-ipvx-payload\"))";
                           junos:must-message "Cannot configure both sample mpls and sample mpls-ipvx-payload";
                           junos:must "((\"forwarding-options sampling family mpls\" || (\"forwarding-options packet-capture\" || any \"forwarding-options sampling instance <*> family mpls\")))";
                           junos:must-message "Requires forwarding-options sampling or packet-capture config";
                         }
                       }
                     }
                     leaf no-decrement-ttl {
                       description "Do not decrement TTL";
                       type empty;
                     }
                     leaf forwarding-class {
                       description "Classify packet to forwarding class";
                       type string {
                         junos:posix-pattern "^.{1,64}$";
                         junos:pattern-message "Must be string of 64 characters or less";
                       }
                     }
                     leaf interface-group {
                       description "Set the interface group";
                       type union {
                         type string {
                           pattern "<.*>|$.*";
                         }
                         type uint32 {
                           range "0 .. 255";
                         }
                       }
                     }
                     choice destination {
                       case case_1 {
                         container routing-instance {
                           description "Packets are directed to specified routing instance";
                           leaf routing-instance-name {
                             description "Name of routing instance";
                             junos:must "(\"routing-instances $$\")";
                             junos:must-message "referenced routing instance must be defined";
                             type string {
                               junos:posix-pattern "!^((__.*__)|(all)|(.*[ ].*)|(\"\")|(.{129,}))$";
                               junos:pattern-message "Must be a non-reserved string of 128 characters or less with no spaces.";
                             }
                           }
                         }
                       }
                     }
                   }
                 }
                 case case_4 {
                   container l2tp {
                     description "L2TP protocol";
                     uses apply-advanced;
                     leaf-list sample {
                       ordered-by user;
                       description "Sample the packet";
                       junos:must "(!(\".. sampling-instance\"))";
                       junos:must-message "'sampling' and 'sampling-instance' are mutually exclusive";
                       type enumeration {
                         enum "inet" {
                           description "IPV4 protocol";
                           junos:must "((\"forwarding-options sampling family inet\" || (\"forwarding-options packet-capture\" || any \"forwarding-options sampling instance <*> family inet\")))";
                           junos:must-message "Requires forwarding-options sampling or packet-capture config";
                         }
                         enum "inet6" {
                           description "IPV6 protocol";
                           junos:must "((\"forwarding-options sampling family inet6\" || (\"forwarding-options packet-capture\" || any \"forwarding-options sampling instance <*> family inet6\")))";
                           junos:must-message "Requires forwarding-options sampling or packet-capture config";
                         }
                         enum "mpls" {
                           description "MPLS protocol";
                           junos:must "(!(\".. .. sample mpls-ipvx-payload\"))";
                           junos:must-message "Cannot configure both sample mpls and sample mpls-ipvx-payload";
                           junos:must "((\"forwarding-options sampling family mpls\" || (\"forwarding-options packet-capture\" || any \"forwarding-options sampling instance <*> family mpls\")))";
                           junos:must-message "Requires forwarding-options sampling or packet-capture config";
                         }
                       }
                     }
                     leaf no-decrement-ttl {
                       description "Do not decrement TTL";
                       type empty;
                     }
                     leaf forwarding-class {
                       description "Classify packet to forwarding class";
                       type string {
                         junos:posix-pattern "^.{1,64}$";
                         junos:pattern-message "Must be string of 64 characters or less";
                       }
                     }
                     leaf interface-group {
                       description "Set the interface group";
                       type union {
                         type string {
                           pattern "<.*>|$.*";
                         }
                         type uint32 {
                           range "0 .. 255";
                         }
                       }
                     }
                     leaf-list cookie {
                       ordered-by user;
                       description "L2TPv3 cookie";
                       type string {
                         length "1 .. 32";
                       }
                     }
                     choice destination {
                       case case_1 {
                         leaf output-interface {
                           description "Interface name";
                           junos:must "(\"interfaces $$\")";
                           junos:must-message "Interface must be defined in the interfaces hierarchy";
                           type union {
                             type jt:interface-unit;
                             type string {
                               pattern "<.*>|$.*";
                             }
                           }
                         }
                       }
                     }
                   }
                 }
               }
             }
           }
           case case_12 {
             container encapsulate {
               presence "enable encapsulate";
               description "Send to a tunnel";
               leaf tunnel-end-point {
                 description "Name of the tunnel end point";
                 junos:must "(\"firewall tunnel-end-point $$\")";
                 junos:must-message "referenced firewall tunnel-end-point must be defined";
                 type string {
                   junos:posix-pattern "!^((__.*)|(.{65,}))$";
                   junos:pattern-message "Must be a non-reserved string of 64 characters or less";
                 }
               }
             }
           }
           case case_13 {
             container reject {
               presence "enable reject";
               description "Reject the packet";
               choice style {
                 case case_1 {
                   leaf network-unreachable {
                     description "Send ICMP Network Unreachable message";
                     type empty;
                   }
                 }
                 case case_2 {
                   leaf host-unreachable {
                     description "Send ICMP Host Unreachable message";
                     type empty;
                   }
                 }
                 case case_3 {
                   leaf protocol-unreachable {
                     description "Send ICMP Protocol Unreachable message";
                     type empty;
                   }
                 }
                 case case_4 {
                   leaf port-unreachable {
                     description "Send ICMP Port Unreachable message";
                     type empty;
                   }
                 }
                 case case_5 {
                   leaf fragmentation-needed {
                     description "Send ICMP Fragmentation Needed message";
                     type empty;
                   }
                 }
                 case case_6 {
                   leaf source-route-failed {
                     description "Send ICMP Source Route Failed message";
                     type empty;
                   }
                 }
                 case case_7 {
                   leaf network-unknown {
                     description "Send ICMP Network Unknown message";
                     type empty;
                   }
                 }
                 case case_8 {
                   leaf host-unknown {
                     description "Send ICMP Host Unknown message";
                     type empty;
                   }
                 }
                 case case_9 {
                   leaf source-host-isolated {
                     description "Send ICMP Source Host Isolated message";
                     type empty;
                   }
                 }
                 case case_10 {
                   leaf network-prohibited {
                     description "Send ICMP Network Prohibited message";
                     type empty;
                   }
                 }
                 case case_11 {
                   leaf host-prohibited {
                     description "Send ICMP Host Prohibited message";
                     type empty;
                   }
                 }
                 case case_12 {
                   leaf bad-network-tos {
                     description "Send ICMP Bad Network ToS message";
                     type empty;
                   }
                 }
                 case case_13 {
                   leaf bad-host-tos {
                     description "Send ICMP Bad Host ToS message";
                     type empty;
                   }
                 }
                 case case_14 {
                   leaf administratively-prohibited {
                     description "Send ICMP Administratively Prohibited message";
                     type empty;
                   }
                 }
                 case case_15 {
                   leaf precedence-violation {
                     description "Send ICMP Precedence Violation message";
                     type empty;
                   }
                 }
                 case case_16 {
                   leaf precedence-cutoff {
                     description "Send ICMP Precedence Cutoff message";
                     type empty;
                   }
                 }
                 case case_17 {
                   leaf tcp-reset {
                     description "Send TCP Reset message";
                     type empty;
                   }
                 }
               }
             }
           }
           case case_14 {
             leaf load-balance {
               description "Use specified load balancing group";
               junos:must "(\"firewall load-balance-group $$\")";
               junos:must-message "Referenced load-balance group is not defined";
               type string {
                 junos:posix-pattern "!^((__.*)|(.{65,}))$";
                 junos:pattern-message "Must be a non-reserved string of 64 characters or less";
               }
             }
           }
         }
         leaf dscp {
           description "Set Differentiated Services (DiffServ) code point";
           type string;
         }
         leaf dont-fragment {
           description "Set or clear the DF bit flag of the IP header (ingress only)";
           type enumeration {
             enum "clear" {
               description "Clear DF bit flag";
             }
             enum "set" {
               description "Set DF bit flag";
             }
           }
         }
         leaf prefix-action {
           description "Police or count packets using named prefix action";
           type string {
             junos:posix-pattern "!^((__.*)|(.{65,}))$";
             junos:pattern-message "Must be a non-reserved string of 64 characters or less";
           }
         }
       }
     }
   }
   grouping inet_fuf {
     leaf name {
       description "Name of fast update filter";
       junos:must "(unique \"firewall family <*> filter $$\")";
       junos:must-message "Fast update filter can not have the same name as firewall family filter";
       type string {
         junos:posix-pattern "!^((__.*)|(.{65,}))$";
         junos:pattern-message "Must be a non-reserved string of 64 characters or less";
       }
     }
     uses apply-advanced;
     leaf interface-specific {
       description "Defined counters are interface specific";
       type empty;
     }
     leaf-list match-order {
       ordered-by user;
       type enumeration {
         enum "protocol" {
           description "Include IP protocol in match set";
         }
         enum "source-address" {
           description "Include source-address in match set";
         }
         enum "destination-address" {
           description "Include destination-address in match set";
         }
         enum "source-port" {
           description "Include source-port in match set";
         }
         enum "destination-port" {
           description "Include destination-port in match set";
         }
         enum "dscp" {
           description "Include Differentiated Services (DiffServ) code point in match set";
         }
       }
     }
     list term {
       key name;
       ordered-by user;
       description "One or more firewall terms";
       leaf name {
         description "Term name";
         type string {
           junos:posix-pattern "!^((__.*)|(.{65,}))$";
           junos:pattern-message "Must be a non-reserved string of 64 characters or less";
         }
       }
       uses apply-advanced;
       leaf only-at-create {
         description "Add term only when filter is first created.";
         type empty;
       }
       container from {
         description "Match criteria";
         uses apply-advanced;
         container source-address {
           description "Match source IP address";
           uses firewall_addr_simple_object;
         }
         container destination-address {
           description "Match destination IP address";
           uses firewall_addr_simple_object;
         }
         choice source-port_choice {
           case case_1 {
             container source-port {
               description "Match TCP/UDP source port";
               uses match_simple_port_value;
             }
           }
         }
         choice destination-port_choice {
           case case_1 {
             container destination-port {
               description "Match TCP/UDP destination port";
               uses match_simple_port_value;
             }
           }
         }
         choice protocol_choice {
           case case_1 {
             container protocol {
               description "Match IP protocol type";
               uses match_simple_protocol_value;
             }
           }
         }
         choice dscp_choice {
           case case_1 {
             container dscp {
               description "Match Differentiated Services (DiffServ) code point";
               uses match_simple_dscp_value;
             }
           }
         }
         leaf match-terms {
           description "Dynamically supplied list of match criteria";
           type string;
         }
       }
       container then {
         description "Action to take if the 'from' condition is matched";
         uses apply-advanced;
         choice policer-choice {
           case case_1 {
             leaf policer {
               description "Name of policer to use to rate-limit traffic";
               type string {
                 junos:posix-pattern "!^((__.*)|(.{65,}))$";
                 junos:pattern-message "Must be a non-reserved string of 64 characters or less";
               }
             }
           }
         }
         leaf count {
           description "Count the packet in the named counter";
           type string {
             junos:posix-pattern "!^((__.*)|(.{65,}))$";
             junos:pattern-message "Must be a non-reserved string of 64 characters or less";
           }
         }
         leaf service-accounting {
           description "Count the packets for service accounting";
           junos:must "(!(\".. count\"))";
           junos:must-message "'count' and 'service-accounting' cannot coexist";
           type empty;
         }
         leaf log {
           description "Log the packet";
           type empty;
         }
         leaf port-mirror {
           description "Port-mirror the packet";
           type empty;
         }
         leaf loss-priority {
           description "Packet's loss priority";
           junos:must "(!(\".. three-color-policer\"))";
           junos:must-message "Configuring loss-priority is incompatible with configuring three-color-policer";
           type enumeration {
             enum "low" {
               description "Loss priority low";
             }
             enum "high" {
               description "Loss priority high";
             }
             enum "medium-low" {
               description "Loss priority medium-low";
             }
             enum "medium-high" {
               description "Loss priority medium-high";
             }
           }
         }
         leaf forwarding-class {
           description "Classify packet to forwarding class";
           type string {
             junos:posix-pattern "^.{1,64}$";
             junos:pattern-message "Must be string of 64 characters or less";
           }
         }
         leaf action-terms {
           description "Dynamically supplied list of actions";
           type string;
         }
         choice designation {
           case case_1 {
             leaf accept {
               description "Accept the packet";
               type empty;
             }
           }
           case case_2 {
             leaf discard {
               description "Discard the packet";
               type empty;
             }
           }
           case case_3 {
             container routing-instance {
               description "Packets are directed to specified routing instance";
               leaf routing-instance-name {
                 description "Name of routing instance";
                 type string {
                   junos:posix-pattern "!^((__.*__)|(all)|(.*[ ].*)|(\"\")|(.{129,}))$";
                   junos:pattern-message "Must be a non-reserved string of 128 characters or less with no spaces.";
                 }
               }
               leaf topology {
                 description "Packets are directed to specified topology";
                 type string {
                   junos:posix-pattern "!^((.*:.*)|(.{129,}))$";
                   junos:pattern-message "Must be a non-reserved string of 128 characters or less";
                 }
               }
             }
           }
         }
       }
     }
   }
   grouping firewall_addr_simple_object {
     uses apply-advanced;
     leaf address {
       description "Prefix to match";
       type jt:ipv4prefix;
     }
   }
   grouping inet_service_filter {
     leaf name {
       description "Filter name";
       type string {
         junos:posix-pattern "!^((__.*)|(.{65,}))$";
         junos:pattern-message "Must be a non-reserved string of 64 characters or less";
       }
     }
     uses apply-advanced;
     list term {
       key name;
       ordered-by user;
       description "Service filter term";
       leaf name {
         description "Term name";
         type string {
           junos:posix-pattern "!^((__.*)|(.{65,}))$";
           junos:pattern-message "Must be a non-reserved string of 64 characters or less";
         }
       }
       uses apply-advanced;
       container from {
         description "Match criteria";
         uses apply-advanced;
         choice interface-group_choice {
           case case_1 {
             leaf-list interface-group {
               ordered-by user;
               description "Range of values";
               type string;
             }
           }
           case case_2 {
             leaf-list interface-group-except {
               ordered-by user;
               description "Range of values";
               type string;
             }
           }
         }
         list source-address {
           key name;
           ordered-by user;
           description "Match IP source address";
           uses firewall_addr_object;
         }
         list destination-address {
           key name;
           ordered-by user;
           description "Match IP destination address";
           uses firewall_addr_object;
         }
         list address {
           key name;
           ordered-by user;
           description "Match IP source or destination address";
           uses firewall_addr_object;
         }
         list source-prefix-list {
           key name;
           ordered-by user;
           description "Match IP source prefixes in named list";
           uses firewall_prefix_list;
         }
         list destination-prefix-list {
           key name;
           ordered-by user;
           description "Match IP destination prefixes in named list";
           uses firewall_prefix_list;
         }
         list prefix-list {
           key name;
           ordered-by user;
           description "Match IP source or destination prefixes in named list";
           uses firewall_prefix_list;
         }
         choice protocol_choice {
           case case_1 {
             leaf-list protocol {
               ordered-by user;
               type string;
             }
           }
           case case_2 {
             leaf-list protocol-except {
               ordered-by user;
               type string;
             }
           }
         }
         choice ip-options_choice {
           case case_1 {
             leaf-list ip-options {
               ordered-by user;
               type enumeration {
                 enum "any" {
                   description "Any IP option";
                 }
               }
             }
           }
           case case_2 {
             leaf-list ip-options-except {
               ordered-by user;
               type enumeration {
                 enum "any" {
                   description "Any IP option";
                 }
               }
             }
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice port_choice {
           case case_1 {
             leaf-list port {
               ordered-by user;
               type string;
             }
           }
           case case_2 {
             leaf-list port-except {
               ordered-by user;
               type string;
             }
           }
         }
         choice esp-spi_choice {
           case case_1 {
             leaf-list esp-spi {
               ordered-by user;
               description "Range of values";
               type string;
             }
           }
           case case_2 {
             leaf-list esp-spi-except {
               ordered-by user;
               description "Range of values";
               type string;
             }
           }
         }
         leaf is-fragment {
           description "Match if packet is a fragment";
           type empty;
         }
         leaf first-fragment {
           description "Match if packet is the first fragment";
           type empty;
         }
         choice fragment-offset_choice {
           case case_1 {
             leaf-list fragment-offset {
               ordered-by user;
               description "Range of values";
               type string {
                 junos:posix-pattern "^[[:digit:]]+(-[[:digit:]]+)?$";
                 junos:pattern-message "Must be a in form of number or a range in the form '<minimum-value>-<maximum-value>'";
               }
             }
           }
           case case_2 {
             leaf-list fragment-offset-except {
               ordered-by user;
               description "Range of values";
               type string {
                 junos:posix-pattern "^[[:digit:]]+(-[[:digit:]]+)?$";
                 junos:pattern-message "Must be a in form of number or a range in the form '<minimum-value>-<maximum-value>'";
               }
             }
           }
         }
         leaf fragment-flags {
           description "Match fragment flags";
           type string;
         }
         leaf tcp-flags {
           description "Match TCP flags (in symbolic or hex formats)";
           type string;
         }
         choice ah-spi_choice {
           case case_1 {
             leaf-list ah-spi {
               ordered-by user;
               description "Range of values";
               type string;
             }
           }
           case case_2 {
             leaf-list ah-spi-except {
               ordered-by user;
               description "Range of values";
               type string;
             }
           }
         }
         choice loss-priority_choice {
           case case_1 {
             leaf-list loss-priority {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
           case case_2 {
             leaf-list loss-priority-except {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
         }
         choice forwarding-class_choice {
           case case_1 {
             leaf-list forwarding-class {
               ordered-by user;
               description "String name";
               type string {
                 junos:posix-pattern "^.{1,64}$";
                 junos:pattern-message "Must be string of 64 characters or less";
               }
             }
           }
           case case_2 {
             leaf-list forwarding-class-except {
               ordered-by user;
               description "String name";
               type string {
                 junos:posix-pattern "^.{1,64}$";
                 junos:pattern-message "Must be string of 64 characters or less";
               }
             }
           }
         }
         choice redirect-reason_choice {
           case case_1 {
             leaf-list redirect-reason {
               ordered-by user;
               type enumeration {
                 enum "aoc" {
                   description "Advice of Charge";
                 }
                 enum "aolb" {
                   description "Advice of Low Balance";
                 }
                 enum "dpi" {
                   description "Layer7 match required";
                 }
               }
             }
           }
           case case_2 {
             leaf-list redirect-reason-except {
               ordered-by user;
               type enumeration {
                 enum "aoc" {
                   description "Advice of Charge";
                 }
                 enum "aolb" {
                   description "Advice of Low Balance";
                 }
                 enum "dpi" {
                   description "Layer7 match required";
                 }
               }
             }
           }
         }
       }
       container then {
         description "Action to take if the 'from' condition is matched";
         uses apply-advanced;
         leaf count {
           description "Count the packet in the named counter";
           type string {
             junos:posix-pattern "!^((__.*)|(.{65,}))$";
             junos:pattern-message "Must be a non-reserved string of 64 characters or less";
           }
         }
         leaf log {
           description "Log the packet";
           type empty;
         }
         leaf sample {
           description "Sample the packet";
           type empty;
         }
         leaf port-mirror {
           description "Port-mirror the packet";
           type empty;
         }
         choice designation {
           case case_1 {
             leaf service {
               description "Forward packets to service processing";
               type empty;
             }
           }
           case case_2 {
             leaf skip {
               description "Skip service processing";
               type empty;
             }
           }
           case case_3 {
             leaf accept {
               description "Accept the packet";
               type empty;
             }
           }
         }
       }
     }
   }
   grouping inet_simple_filter {
     leaf name {
       description "Name of simple filter";
       type string {
         junos:posix-pattern "!^((__.*)|(.{65,}))$";
         junos:pattern-message "Must be a non-reserved string of 64 characters or less";
       }
     }
     uses apply-advanced;
     leaf interface-specific {
       description "Defined counters are interface specific";
       status deprecated;
       type empty;
     }
     list term {
       key name;
       ordered-by user;
       description "One or more firewall terms";
       leaf name {
         description "Term name";
         type string {
           junos:posix-pattern "!^((__.*)|(.{65,}))$";
           junos:pattern-message "Must be a non-reserved string of 64 characters or less";
         }
       }
       uses apply-advanced;
       container from {
         description "Match criteria";
         uses apply-advanced;
         container source-address {
           description "Source IP address";
           uses firewall_addr_simple_object;
         }
         container destination-address {
           description "Destination IP address";
           uses firewall_addr_simple_object;
         }
         choice protocol_choice {
           case case_1 {
             container protocol {
               description "Match IP protocol type";
               uses match_simple_protocol_value;
             }
           }
         }
         choice source-port_choice {
           case case_1 {
             container source-port {
               description "Match TCP/UDP source port";
               uses match_simple_port_value;
             }
           }
         }
         choice destination-port_choice {
           case case_1 {
             container destination-port {
               description "Match TCP/UDP destination port";
               uses match_simple_port_value;
             }
           }
         }
         choice forwarding-class_choice {
           case case_1 {
             leaf-list forwarding-class {
               ordered-by user;
               description "String name";
               type string {
                 junos:posix-pattern "^.{1,64}$";
                 junos:pattern-message "Must be string of 64 characters or less";
               }
             }
           }
         }
       }
       container then {
         description "Action to take if the 'from' condition is matched";
         uses apply-advanced;
         choice policer-choice {
           case case_1 {
             leaf policer {
               description "Name of policer to use to rate-limit traffic";
               type string {
                 junos:posix-pattern "!^((__.*)|(.{65,}))$";
                 junos:pattern-message "Must be a non-reserved string of 64 characters or less";
               }
             }
           }
           case case_2 {
             container three-color-policer {
               description "Police the packet using a three-color-policer";
               uses apply-advanced;
               choice type-choice {
                 case case_1 {
                   leaf single-rate {
                     description "Name of single-rate three-color policer to use to rate-limit traffic";
                     junos:must "(\"firewall three-color-policer $$ single-rate\")";
                     junos:must-message "Referenced single-rate policer does not exist";
                     type string {
                       junos:posix-pattern "!^((__.*)|(.{65,}))$";
                       junos:pattern-message "Must be a non-reserved string of 64 characters or less";
                     }
                   }
                 }
                 case case_2 {
                   leaf two-rate {
                     description "Name of two-rate three-color policer to use to rate-limit traffic";
                     junos:must "(\"firewall three-color-policer $$ two-rate\")";
                     junos:must-message "Referenced two-rate policer does not exist";
                     type string {
                       junos:posix-pattern "!^((__.*)|(.{65,}))$";
                       junos:pattern-message "Must be a non-reserved string of 64 characters or less";
                     }
                   }
                 }
               }
             }
           }
         }
         leaf loss-priority {
           description "Packet's loss priority";
           type enumeration {
             enum "low" {
               description "Low loss priority";
             }
             enum "medium-high" {
               description "Medium-high loss priority";
             }
             enum "medium-low" {
               description "Medium-low loss priority";
             }
             enum "high" {
               description "High loss priority";
             }
           }
         }
         leaf forwarding-class {
           description "Classify packet to forwarding class";
           type string {
             junos:posix-pattern "^.{1,64}$";
             junos:pattern-message "Must be string of 64 characters or less";
           }
         }
         leaf discard {
           description "Discard the packet";
           type empty;
         }
         leaf accept {
           description "Accept the packet";
           type empty;
         }
       }
     }
   }
   grouping interface_set_type {
     leaf name {
       description "Interface set name";
       type string {
         junos:posix-pattern "!^((__.*)|(.{65,}))$";
         junos:pattern-message "Must be a non-reserved string of 64 characters or less";
       }
     }
     uses apply-advanced;
     list interface-list {
       key name;
       ordered-by user;
       description "Interface list";
       leaf name {
         description "Interface name";
         type union {
           type jt:interface-wildcard;
           type string {
             pattern "<.*>|$.*";
           }
         }
       }
       uses apply-advanced;
     }
   }
   grouping macro-data-type {
     leaf name {
       description "Keyword part of the keyword-value pair";
       type string;
     }
     leaf value {
       description "Value part of the keyword-value pair";
       type string;
     }
   }
   grouping match_L2_flexible_mask {
     description "Define a flexible match";
     uses apply-advanced;
     leaf match-start {
       description "Start point to match in packet";
       type enumeration {
         enum "layer-2" {
           description "Layer-2 match start";
         }
         enum "layer-3" {
           description "Layer-3 match start";
         }
         enum "layer-4" {
           description "Layer-4 match start";
         }
         enum "payload" {
           description "Payload match start";
         }
       }
     }
     leaf byte-offset {
       description "Byte offset after the match start point";
       type union {
         type uint32;
         type string {
           pattern "<.*>|$.*";
         }
       }
     }
     leaf bit-offset {
       description "Bit offset after the (match-start + byte) offset";
       type union {
         type string {
           pattern "<.*>|$.*";
         }
         type uint32 {
           range "0 .. 7";
         }
       }
     }
     leaf bit-length {
       description "Length of the data to be matched in bits, not needed for string input";
       type union {
         type string {
           pattern "<.*>|$.*";
         }
         type uint32 {
           range "1 .. 128";
         }
       }
     }
     leaf mask-in-hex {
       description "Mask out bits in the packet data to be matched";
       type string {
         junos:posix-pattern "(^(0[xX])?[A-Fa-f0-9]{0,8}$)";
       }
     }
     leaf prefix {
       description "Value data/string to be matched";
       junos:must "((\".. flexible-mask-name\" || \".. match-start\"))";
       junos:must-message "To configure prefix, 'flexible-mask-name' or 'match-start' must be configured";
       type string {
         junos:posix-pattern "!^((__.*)|(.{65,}))$";
         junos:pattern-message "Must be a non-reserved string of 64 characters or less";
       }
     }
     leaf flexible-mask-name {
       description "Select a flexible match from predefined template field";
       junos:must "((!(\".. byte-offset\") && (!(\".. bit-offset\") && (!(\".. bit-length\") && !(\".. match-start\")))))";
       junos:must-message "To refer configured template, only prefix or prefix along with mask can be configured";
       type string;
     }
   }
   grouping match_L2_flexible_range {
     description "Define a flexible match";
     uses apply-advanced;
     leaf match-start {
       description "Start point to match in packet";
       type enumeration {
         enum "layer-2" {
           description "Layer-2 match start";
         }
         enum "layer-3" {
           description "Layer-3 match start";
         }
         enum "layer-4" {
           description "Layer-4 match start";
         }
         enum "payload" {
           description "Payload match start";
         }
       }
     }
     leaf byte-offset {
       description "Byte offset after the match start point";
       type union {
         type uint32;
         type string {
           pattern "<.*>|$.*";
         }
       }
     }
     leaf bit-offset {
       description "Bit offset after the (match-start + byte) offset";
       type union {
         type string {
           pattern "<.*>|$.*";
         }
         type uint32 {
           range "0 .. 7";
         }
       }
     }
     leaf bit-length {
       description "Length of the data to be matched in bits";
       type union {
         type string {
           pattern "<.*>|$.*";
         }
         type uint32 {
           range "1 .. 32";
         }
       }
     }
     choice range_choice {
       case case_1 {
         leaf range {
           description "Range of values to be matched";
           junos:must "((\".. flexible-range-name\" || (\".. match-start\" && \".. bit-length\")))";
           junos:must-message "To configure range, 'flexible-range-name' or 'match-start & bit-length' must be configured";
           type string;
         }
       }
       case case_2 {
         leaf range-except {
           description "Range of values to be not matched";
           junos:must "((\".. flexible-range-name\" || (\".. match-start\" && \".. bit-length\")))";
           junos:must-message "To configure range-except, 'flexible-range-name' or 'match-start & bit-length' must be configured";
           type string;
         }
       }
     }
     leaf flexible-range-name {
       description "Select a flexible match from predefined template field";
       junos:must "((!(\".. byte-offset\") && (!(\".. bit-offset\") && (!(\".. bit-length\") && !(\".. match-start\")))))";
       junos:must-message "To refer configured template, only range or range-except can be configured";
       type string;
     }
   }
   grouping match_L3_flexible_mask {
     description "Define a flexible match";
     uses apply-advanced;
     leaf match-start {
       description "Start point to match in packet";
       type enumeration {
         enum "layer-3" {
           description "Layer-3 match start";
         }
         enum "layer-4" {
           description "Layer-4 match start";
         }
         enum "payload" {
           description "Payload match start";
         }
       }
     }
     leaf byte-offset {
       description "Byte offset after the match start point";
       type union {
         type uint32;
         type string {
           pattern "<.*>|$.*";
         }
       }
     }
     leaf bit-offset {
       description "Bit offset after the (match-start + byte) offset";
       type union {
         type string {
           pattern "<.*>|$.*";
         }
         type uint32 {
           range "0 .. 7";
         }
       }
     }
     leaf bit-length {
       description "Length of the data to be matched in bits, not needed for string input";
       type union {
         type string {
           pattern "<.*>|$.*";
         }
         type uint32 {
           range "1 .. 128";
         }
       }
     }
     leaf mask-in-hex {
       description "Mask out bits in the packet data to be matched";
       type string {
         junos:posix-pattern "(^(0[xX])?[A-Fa-f0-9]{0,8}$)";
       }
     }
     leaf prefix {
       description "Value data/string to be matched";
       junos:must "((\".. flexible-mask-name\" || \".. match-start\"))";
       junos:must-message "To configure prefix, 'flexible-mask-name' or 'match-start' must be configured";
       type string {
         junos:posix-pattern "!^((__.*)|(.{65,}))$";
         junos:pattern-message "Must be a non-reserved string of 64 characters or less";
       }
     }
     leaf flexible-mask-name {
       description "Select a flexible match from predefined template field";
       junos:must "((!(\".. byte-offset\") && (!(\".. bit-offset\") && (!(\".. bit-length\") && !(\".. match-start\")))))";
       junos:must-message "To refer configured template, only prefix or prefix along with mask can be configured";
       type string;
     }
   }
   grouping match_L3_flexible_range {
     description "Define a flexible match";
     uses apply-advanced;
     leaf match-start {
       description "Start point to match in packet";
       type enumeration {
         enum "layer-3" {
           description "Layer-3 match start";
         }
         enum "layer-4" {
           description "Layer-4 match start";
         }
         enum "payload" {
           description "Payload match start";
         }
       }
     }
     leaf byte-offset {
       description "Byte offset after the match start point";
       type union {
         type uint32;
         type string {
           pattern "<.*>|$.*";
         }
       }
     }
     leaf bit-offset {
       description "Bit offset after the (match-start + byte) offset";
       type union {
         type string {
           pattern "<.*>|$.*";
         }
         type uint32 {
           range "0 .. 7";
         }
       }
     }
     leaf bit-length {
       description "Length of the data to be matched in bits";
       type union {
         type string {
           pattern "<.*>|$.*";
         }
         type uint32 {
           range "1 .. 32";
         }
       }
     }
     choice range_choice {
       case case_1 {
         leaf range {
           description "Range of values to be matched";
           junos:must "((\".. flexible-range-name\" || (\".. match-start\" && \".. bit-length\")))";
           junos:must-message "To configure range, 'flexible-range-name' or 'match-start & bit-length' must be configured";
           type string;
         }
       }
       case case_2 {
         leaf range-except {
           description "Range of values to be not matched";
           junos:must "((\".. flexible-range-name\" || (\".. match-start\" && \".. bit-length\")))";
           junos:must-message "To configure range-except, 'flexible-range-name' or 'match-start & bit-length' must be configured";
           type string;
         }
       }
     }
     leaf flexible-range-name {
       description "Select a flexible match from predefined template field";
       junos:must "((!(\".. byte-offset\") && (!(\".. bit-offset\") && (!(\".. bit-length\") && !(\".. match-start\")))))";
       junos:must-message "To refer configured template, only range or range-except can be configured";
       type string;
     }
   }
   grouping match_flags_value {
     description "Define a vxlan flag";
     uses apply-advanced;
     leaf value {
       description "Value data to be matched";
       junos:must "(\".. mask-in-hex\")";
       junos:must-message "mask-in-hex must be set for vxlan flag";
       type string {
         junos:posix-pattern "^([0-9]|[1-9][0-9]|1[0-9][0-9]|2[0-4][0-9]|25[0-5]|0x[0-f]|0x[0-f][0-f])$";
         junos:pattern-message "Must be a numeric value";
       }
     }
     leaf mask-in-hex {
       description "Mask out bits in the packet data to be matched";
       type string {
         junos:posix-pattern "^([0-9]|[1-9][0-9]|1[0-9][0-9]|2[0-4][0-9]|25[0-5]|0x[0-f]|0x[0-f][0-f])$";
         junos:pattern-message "Must be a numeric value";
       }
     }
   }
   grouping match_interface_object {
     leaf name {
       description "Interface to match";
       type union {
         type jt:interface-wildcard;
         type string {
           pattern "<.*>|$.*";
         }
       }
     }
   }
   grouping match_interface_object_oam {
     leaf name {
       description "Interface to match";
       type union {
         type jt:interface-wildcard;
         type string {
           pattern "<.*>|$.*";
         }
       }
     }
   }
   grouping match_interface_set_object {
     leaf name {
       description "Interface set to match";
       type string;
     }
   }
   grouping match_simple_dscp_value {
     uses apply-advanced;
     leaf value_keyword {
       type string;
     }
   }
   grouping match_simple_payload_protocol_value {
     uses apply-advanced;
     leaf value_keyword {
       type string;
     }
   }
   grouping match_simple_port_value {
     uses apply-advanced;
     leaf value_keyword {
       type string;
     }
   }
   grouping match_simple_protocol_value {
     uses apply-advanced;
     leaf value_keyword {
       type string;
     }
   }
   grouping mpls_dialer_filter {
     description "Define an MPLS DIALER filter";
     leaf name {
       description "Filter name";
       type string {
         junos:posix-pattern "!^((__.*)|(.{65,}))$";
         junos:pattern-message "Must be a non-reserved string of 64 characters or less";
       }
     }
     uses apply-advanced;
     leaf-list accounting-profile {
       ordered-by user;
       description "Accounting profile name";
       junos:must "(\"accounting-options filter-profile\")";
       junos:must-message "referenced accounting profile must be defined";
       type string;
     }
     list term {
       key name;
       ordered-by user;
       description "Define a firewall term";
       leaf name {
         description "Term name";
         type string {
           junos:posix-pattern "!^((__.*)|(.{65,}))$";
           junos:pattern-message "Must be a non-reserved string of 64 characters or less";
         }
       }
       uses apply-advanced;
       container from {
         description "Define match criteria";
         uses apply-advanced;
         choice exp_choice {
           case case_1 {
             leaf-list exp {
               ordered-by user;
               description "Range of values";
               type string;
             }
           }
           case case_2 {
             leaf-list exp-except {
               ordered-by user;
               description "Range of values";
               type string;
             }
           }
         }
       }
       container then {
         description "Action to take if the 'from' condition is matched";
         uses apply-advanced;
         leaf log {
           description "Log the packet";
           type empty;
         }
         leaf syslog {
           description "System log (syslog) information about the packet";
           type empty;
         }
         leaf sample {
           description "Sample the packet";
           type empty;
         }
         choice designation {
           case case_1 {
             leaf note {
               description "Interested ISDN packet";
               type empty;
             }
           }
           case case_2 {
             leaf ignore {
               description "Non-interested ISDN packet";
               type empty;
             }
           }
         }
       }
     }
   }
   grouping mpls_filter {
     description "Define an MPLS firewall filter";
     leaf name {
       description "Filter name";
       type string {
         junos:posix-pattern "!^((__.*)|(.{65,}))$";
         junos:pattern-message "Must be a non-reserved string of 64 characters or less";
       }
     }
     uses apply-advanced;
     leaf-list accounting-profile {
       ordered-by user;
       description "Accounting profile name";
       junos:must "(\"accounting-options filter-profile\")";
       junos:must-message "referenced accounting profile must be defined";
       type string;
     }
     leaf interface-specific {
       description "Defined counters are interface specific";
       type empty;
     }
     leaf physical-interface-filter {
       description "Filter is physical interface filter";
       type empty;
     }
     leaf instance-shared {
       description "Filter is routing-instance shared";
       junos:must "(\"chassis network-services enhanced-ip\")";
       junos:must-message "instance-shared filter available only in enhanced-ip mode";
       junos:must "(!(\".. physical-interface-filter\"))";
       junos:must-message "Cannot be both physical-interface-filter and instance-shared";
       junos:must "(!(\".. interface-specific\"))";
       junos:must-message "Cannot be both interface-specific and instance-shared";
       type empty;
     }
     list term {
       key name;
       ordered-by user;
       description "Define a firewall term";
       leaf name {
         description "Term name";
         type string {
           junos:posix-pattern "!^((__.*)|(.{65,}))$";
           junos:pattern-message "Must be a non-reserved string of 64 characters or less";
         }
       }
       uses apply-advanced;
       leaf filter {
         description "Filter to include";
         junos:must "(\"firewall family mpls filter $$\")";
         junos:must-message "Referenced filter is not defined";
         junos:must "((!(\".. from\") && !(\".. then\")))";
         junos:must-message "Not compatible with 'from or then'";
         type string {
           junos:posix-pattern "!^((__.*)|(.{65,}))$";
           junos:pattern-message "Must be a non-reserved string of 64 characters or less";
         }
       }
       container from {
         description "Define match criteria";
         uses apply-advanced;
         choice interface-group_choice {
           case case_1 {
             leaf-list interface-group {
               ordered-by user;
               description "Range of values";
               type string;
             }
           }
           case case_2 {
             leaf-list interface-group-except {
               ordered-by user;
               description "Range of values";
               type string;
             }
           }
         }
         container ip-version {
           description "Specify inner IP version";
           uses apply-advanced;
           container ipv4 {
             presence "enable ipv4";
             junos:must "(!(\".. ipv6\"))";
             junos:must-message "Same term cannot have both IPv4 & IPv6 IP version";
             description "Define L3/L4 match items to match IPv4 packets";
             uses apply-advanced;
             list protocol {
               key name;
               ordered-by user;
               description "Specify inner IPv4 protocol";
               max-elements 1;
               leaf name {
                 description "IP protocol choices";
                 type string;
               }
               uses apply-advanced;
               choice source-port_choice {
                 case case_1 {
                   leaf-list source-port {
                     ordered-by user;
                     type string;
                   }
                 }
                 case case_2 {
                   leaf-list source-port-except {
                     ordered-by user;
                     type string;
                   }
                 }
               }
               choice destination-port_choice {
                 case case_1 {
                   leaf-list destination-port {
                     ordered-by user;
                     type string;
                   }
                 }
                 case case_2 {
                   leaf-list destination-port-except {
                     ordered-by user;
                     type string;
                   }
                 }
               }
             }
             list source-address {
               key name;
               ordered-by user;
               description "Match IPv4 source address";
               uses firewall_addr_object;
             }
             list destination-address {
               key name;
               ordered-by user;
               description "Match IPv4 destination address";
               uses firewall_addr_object;
             }
             list source-prefix-list {
               key name;
               ordered-by user;
               description "Match IPv4 source prefixes in named list";
               uses firewall_prefix_list;
             }
             list destination-prefix-list {
               key name;
               ordered-by user;
               description "Match IPv4 destination prefixes in named list";
               uses firewall_prefix_list;
             }
           }
           container ipv6 {
             presence "enable ipv6";
             junos:must "(!(\".. ipv4\"))";
             junos:must-message "Same term cannot have both IPv4 & IPv6 IP version";
             description "Define L3/L4 match items to match IPv6 packets";
             uses apply-advanced;
             list protocol {
               key name;
               ordered-by user;
               description "Specify inner IPv6 next-header";
               max-elements 1;
               leaf name {
                 description "IP protocol choices";
                 type string;
               }
               uses apply-advanced;
               choice source-port_choice {
                 case case_1 {
                   leaf-list source-port {
                     ordered-by user;
                     type string;
                   }
                 }
                 case case_2 {
                   leaf-list source-port-except {
                     ordered-by user;
                     type string;
                   }
                 }
               }
               choice destination-port_choice {
                 case case_1 {
                   leaf-list destination-port {
                     ordered-by user;
                     type string;
                   }
                 }
                 case case_2 {
                   leaf-list destination-port-except {
                     ordered-by user;
                     type string;
                   }
                 }
               }
             }
             list source-address {
               key name;
               ordered-by user;
               description "Match IPv6 source address";
               uses firewall_addr6_object;
             }
             list destination-address {
               key name;
               ordered-by user;
               description "Match IPv6 destination address";
               uses firewall_addr6_object;
             }
             list source-prefix-list {
               key name;
               ordered-by user;
               description "Match IPv6 source prefixes in named list";
               uses firewall_prefix_list;
             }
             list destination-prefix-list {
               key name;
               ordered-by user;
               description "Match IPv6 destination prefixes in named list";
               uses firewall_prefix_list;
             }
           }
         }
         choice exp_choice {
           case case_1 {
             leaf-list exp {
               ordered-by user;
               description "Range of values between 0 and 7 in decimal, binary or hex";
               type string;
             }
           }
           case case_2 {
             leaf-list exp-except {
               ordered-by user;
               description "Range of values between 0 and 7 in decimal, binary or hex";
               type string;
             }
           }
         }
         list interface {
           key name;
           ordered-by user;
           description "Match interface name";
           uses match_interface_object;
         }
         list interface-set {
           key name;
           ordered-by user;
           description "Match interface in set";
           uses match_interface_set_object;
         }
         choice forwarding-class_choice {
           case case_1 {
             leaf-list forwarding-class {
               ordered-by user;
               description "String name";
               type string {
                 junos:posix-pattern "^.{1,64}$";
                 junos:pattern-message "Must be string of 64 characters or less";
               }
             }
           }
           case case_2 {
             leaf-list forwarding-class-except {
               ordered-by user;
               description "String name";
               type string {
                 junos:posix-pattern "^.{1,64}$";
                 junos:pattern-message "Must be string of 64 characters or less";
               }
             }
           }
         }
         choice loss-priority_choice {
           case case_1 {
             leaf-list loss-priority {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
           case case_2 {
             leaf-list loss-priority-except {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
         }
         choice flex-mask_choice {
           case case_1 {
             container flexible-match-mask {
               description "Match flexible mask";
               uses match_mpls_flexible_mask;
             }
           }
         }
         choice flex-range_choice {
           case case_1 {
             container flexible-match-range {
               description "Match flexible range";
               uses match_mpls_flexible_range;
             }
           }
         }
         choice policy-map_choice {
           case case_1 {
             leaf-list policy-map {
               ordered-by user;
               description "String name";
               junos:must "(\"class-of-service policy-map $$\")";
               junos:must-message "Undefined policy-map instance";
               type string {
                 length "1 .. 64";
                 junos:posix-pattern "!^((__.*)|(.{65,}))$";
                 junos:pattern-message "Must be a non-reserved string of 64 characters or less";
               }
             }
           }
           case case_2 {
             leaf-list policy-map-except {
               ordered-by user;
               description "String name";
               junos:must "(\"class-of-service policy-map $$\")";
               junos:must-message "Undefined policy-map instance";
               type string {
                 length "1 .. 64";
                 junos:posix-pattern "!^((__.*)|(.{65,}))$";
                 junos:pattern-message "Must be a non-reserved string of 64 characters or less";
               }
             }
           }
         }
       }
       container then {
         description "Action to take if the 'from' condition is matched";
         uses apply-advanced;
         choice policer-choice {
           case case_1 {
             leaf policer {
               description "Name of policer to use to rate-limit traffic";
               junos:must "(!(\"firewall policer $$ aggregate\"))";
               junos:must-message "Cannot attach a aggregate policer to filter";
               type string {
                 junos:posix-pattern "!^((__.*)|(.{65,}))$";
                 junos:pattern-message "Must be a non-reserved string of 64 characters or less";
               }
             }
           }
           case case_2 {
             container three-color-policer {
               description "Police the packet using a three-color-policer";
               uses apply-advanced;
               choice type-choice {
                 case case_1 {
                   leaf single-rate {
                     description "Name of single-rate three-color policer to use to rate-limit traffic";
                     junos:must "(\"firewall three-color-policer $$ single-rate\")";
                     junos:must-message "Referenced single-rate policer does not exist";
                     type string {
                       junos:posix-pattern "!^((__.*)|(.{65,}))$";
                       junos:pattern-message "Must be a non-reserved string of 64 characters or less";
                     }
                   }
                 }
                 case case_2 {
                   leaf single-packet-rate {
                     description "Name of single-packet-rate three-color policer to use to rate-limit traffic";
                     junos:must "(\"firewall three-color-policer $$ single-packet-rate\")";
                     junos:must-message "Referenced single-packet-rate policer does not exist";
                     type string {
                       junos:posix-pattern "!^((__.*)|(.{65,}))$";
                       junos:pattern-message "Must be a non-reserved string of 64 characters or less";
                     }
                   }
                 }
                 case case_3 {
                   leaf two-rate {
                     description "Name of two-rate three-color policer to use to rate-limit traffic";
                     junos:must "(\"firewall three-color-policer $$ two-rate\")";
                     junos:must-message "Referenced two-rate policer does not exist";
                     type string {
                       junos:posix-pattern "!^((__.*)|(.{65,}))$";
                       junos:pattern-message "Must be a non-reserved string of 64 characters or less";
                     }
                   }
                 }
                 case case_4 {
                   leaf two-packet-rate {
                     description "Name of two-packet-rate three-color policer to use to rate-limit traffic";
                     junos:must "(\"firewall three-color-policer $$ two-packet-rate\")";
                     junos:must-message "Referenced two-packet-rate policer does not exist";
                     type string {
                       junos:posix-pattern "!^((__.*)|(.{65,}))$";
                       junos:pattern-message "Must be a non-reserved string of 64 characters or less";
                     }
                   }
                 }
               }
             }
           }
           case case_3 {
             leaf hierarchical-policer {
               description "Name of hierarchical policer to use to rate-limit traffic";
               type string {
                 junos:posix-pattern "!^((__.*)|(.{65,}))$";
                 junos:pattern-message "Must be a non-reserved string of 64 characters or less";
               }
             }
           }
         }
         choice policy-map-choice {
           case case_1 {
             leaf clear-policy-map {
               description "Clear the policy marking";
               type empty;
             }
           }
           case case_2 {
             leaf policy-map {
               description "Policy map action";
               junos:must "(\"class-of-service policy-map $$\")";
               junos:must-message "referenced policy map must be defined";
               type string {
                 junos:posix-pattern "!^((__.*)|(.{65,}))$";
                 junos:pattern-message "Must be a non-reserved string of 64 characters or less";
               }
             }
           }
         }
         choice mplscnt {
           case case_1 {
             leaf traffic-class-count {
               description "Count the packet in the named traffic-class counter";
               type string {
                 junos:posix-pattern "!^((__.*)|(.{65,}))$";
                 junos:pattern-message "Must be a non-reserved string of 64 characters or less";
               }
             }
           }
           case case_2 {
             leaf count {
               description "Count the packet in the named counter";
               type string {
                 junos:posix-pattern "!^((__.*)|(.{65,}))$";
                 junos:pattern-message "Must be a non-reserved string of 64 characters or less";
               }
             }
           }
         }
         leaf sample {
           description "Sample the packet";
           junos:must "((\"forwarding-options sampling family mpls\" || (\"forwarding-options packet-capture\" || any \"forwarding-options sampling instance <*> family mpls\")))";
           junos:must-message "Requires forwarding-options sampling or packet-capture config";
           type empty;
         }
         leaf loss-priority {
           description "Classify packet to loss-priority";
           type enumeration {
             enum "low" {
               description "Loss priority low";
             }
             enum "high" {
               description "Loss priority high";
             }
             enum "medium-low" {
               description "Loss priority medium-low";
             }
             enum "medium-high" {
               description "Loss priority medium-high";
             }
           }
         }
         leaf forwarding-class {
           description "Classify packet to forwarding class";
           type string {
             junos:posix-pattern "^.{1,64}$";
             junos:pattern-message "Must be string of 64 characters or less";
           }
         }
         leaf port-mirror-instance {
           description "Port-mirror the packet to specified instance";
           junos:must "(\"forwarding-options port-mirroring instance $$\")";
           junos:must-message "Referenced port-mirroring instance does not exist";
           type string {
             junos:posix-pattern "!^((__.*)|(.{65,}))$";
             junos:pattern-message "Must be a non-reserved string of 64 characters or less";
           }
         }
         leaf port-mirror {
           description "Port-mirror the packet";
           junos:must "(!(\".. port-mirror-instance\"))";
           junos:must-message "'port-mirror' and 'port-mirror-instance' are mutually exclusive";
           junos:must "(\"forwarding-options port-mirroring\")";
           junos:must-message "Configure 'port-mirroring' under 'forwarding-options'";
           type empty;
         }
         leaf packet-mode {
           description "Bypass flow mode for the packet";
           type empty;
         }
         choice designation {
           case case_1 {
             container encapsulate {
               presence "enable encapsulate";
               description "Send to a tunnel";
               leaf tunnel-end-point {
                 description "Name of the tunnel end point";
                 junos:must "(\"firewall tunnel-end-point $$\")";
                 junos:must-message "referenced firewall tunnel-end-point must be defined";
                 type string {
                   junos:posix-pattern "!^((__.*)|(.{65,}))$";
                   junos:pattern-message "Must be a non-reserved string of 64 characters or less";
                 }
               }
             }
           }
           case case_2 {
             leaf accept {
               description "Accept the packet";
               type empty;
             }
           }
           case case_3 {
             leaf discard {
               description "Discard the packet";
               type empty;
             }
           }
           case case_4 {
             leaf next {
               description "Continue to next term in a filter";
               type enumeration {
                 enum "term" {
                   description "Continue to next term in a filter";
                 }
               }
             }
           }
         }
       }
     }
   }
   grouping match_mpls_flexible_mask {
     description "Define a flexible match";
     uses apply-advanced;
     leaf match-start {
       description "Start point to match in packet";
       type enumeration {
         enum "layer-3" {
           description "Layer-3 match start";
         }
         enum "payload" {
           description "Payload match start";
         }
       }
     }
     leaf byte-offset {
       description "Byte offset after the match start point";
       type union {
         type uint32;
         type string {
           pattern "<.*>|$.*";
         }
       }
     }
     leaf bit-offset {
       description "Bit offset after the (match-start + byte) offset";
       type union {
         type string {
           pattern "<.*>|$.*";
         }
         type uint32 {
           range "0 .. 7";
         }
       }
     }
     leaf bit-length {
       description "Length of the data to be matched in bits, not needed for string input";
       type union {
         type string {
           pattern "<.*>|$.*";
         }
         type uint32 {
           range "1 .. 128";
         }
       }
     }
     leaf mask-in-hex {
       description "Mask out bits in the packet data to be matched";
       type string {
         junos:posix-pattern "(^(0[xX])?[A-Fa-f0-9]{0,8}$)";
       }
     }
     leaf prefix {
       description "Value data/string to be matched";
       junos:must "((\".. flexible-mask-name\" || \".. match-start\"))";
       junos:must-message "To configure prefix, 'flexible-mask-name' or 'match-start' must be configured";
       type string {
         junos:posix-pattern "!^((__.*)|(.{65,}))$";
         junos:pattern-message "Must be a non-reserved string of 64 characters or less";
       }
     }
     leaf flexible-mask-name {
       description "Select a flexible match from predefined template field";
       junos:must "((!(\".. byte-offset\") && (!(\".. bit-offset\") && (!(\".. bit-length\") && !(\".. match-start\")))))";
       junos:must-message "To refer configured template, only prefix or prefix along with mask can be configured";
       type string;
     }
   }
   grouping match_mpls_flexible_range {
     description "Define a flexible match";
     uses apply-advanced;
     leaf match-start {
       description "Start point to match in packet";
       type enumeration {
         enum "layer-3" {
           description "Layer-3 match start";
         }
         enum "payload" {
           description "Payload match start";
         }
       }
     }
     leaf byte-offset {
       description "Byte offset after the match start point";
       type union {
         type uint32;
         type string {
           pattern "<.*>|$.*";
         }
       }
     }
     leaf bit-offset {
       description "Bit offset after the (match-start + byte) offset";
       type union {
         type string {
           pattern "<.*>|$.*";
         }
         type uint32 {
           range "0 .. 7";
         }
       }
     }
     leaf bit-length {
       description "Length of the data to be matched in bits";
       type union {
         type string {
           pattern "<.*>|$.*";
         }
         type uint32 {
           range "1 .. 32";
         }
       }
     }
     choice range_choice {
       case case_1 {
         leaf range {
           description "Range of values to be matched";
           junos:must "((\".. flexible-range-name\" || (\".. match-start\" && \".. bit-length\")))";
           junos:must-message "To configure range, 'flexible-range-name' or 'match-start & bit-length' must be configured";
           type string;
         }
       }
       case case_2 {
         leaf range-except {
           description "Range of values to be not matched";
           junos:must "((\".. flexible-range-name\" || (\".. match-start\" && \".. bit-length\")))";
           junos:must-message "To configure range-except, 'flexible-range-name' or 'match-start & bit-length' must be configured";
           type string;
         }
       }
     }
     leaf flexible-range-name {
       description "Select a flexible match from predefined template field";
       junos:must "((!(\".. byte-offset\") && (!(\".. bit-offset\") && (!(\".. bit-length\") && !(\".. match-start\")))))";
       junos:must-message "To refer configured template, only range or range-except can be configured";
       type string;
     }
   }
   grouping prefix_action {
     leaf name {
       description "Prefix action name";
       type string {
         junos:posix-pattern "!^((__.*)|(.{65,}))$";
         junos:pattern-message "Must be a non-reserved string of 64 characters or less";
       }
     }
     uses apply-advanced;
     leaf policer {
       description "Police the packet using a set of named policer";
       type string {
         junos:posix-pattern "!^((__.*)|(.{65,}))$";
         junos:pattern-message "Must be a non-reserved string of 64 characters or less";
       }
     }
     leaf count {
       description "Enable counters";
       type empty;
     }
     leaf filter-specific {
       description "Filter specific, else term specific";
       type empty;
     }
     leaf subnet-prefix-length {
       description "Prefix length for the total address range";
       type union {
         type string {
           pattern "<.*>|$.*";
         }
         type uint32 {
           range "0 .. 32";
         }
       }
     }
     choice source_or_dest {
       case case_1 {
         leaf source-prefix-length {
           description "Source prefix range";
           type union {
             type string {
               pattern "<.*>|$.*";
             }
             type uint32 {
               range "0 .. 32";
             }
           }
         }
       }
       case case_2 {
         leaf destination-prefix-length {
           description "Destination prefix range";
           type union {
             type string {
               pattern "<.*>|$.*";
             }
             type uint32 {
               range "0 .. 32";
             }
           }
         }
       }
     }
   }
   grouping three-color-policer-type {
     description "Three-color policer";
     leaf name {
       description "Policer name";
       type string {
         junos:posix-pattern "!^((__.*)|(.{65,}))$";
         junos:pattern-message "Must be a non-reserved string of 64 characters or less";
       }
     }
     uses apply-advanced;
     leaf filter-specific {
       description "Three color policer is filter-specific";
       type empty;
     }
     leaf logical-interface-policer {
       description "Policer is logical interface policer";
       type empty;
     }
     leaf physical-interface-policer {
       description "Policer is physical interface policer";
       type empty;
     }
     leaf shared-bandwidth-policer {
       description "Share policer bandwidth among bundle links";
       type empty;
     }
     container action {
       description "Action for three-color policer";
       uses apply-advanced;
       list loss-priority {
         key name;
         ordered-by user;
         description "Loss priority for packet";
         uses three-color-policer-action;
       }
     }
     choice rate-type-choice {
       case case_1 {
         container single-rate {
           description "Single-rate policer";
           uses apply-advanced;
           choice mode-choice {
             case case_1 {
               leaf color-blind {
                 description "Color-blind mode";
                 type empty;
               }
             }
             case case_2 {
               leaf color-aware {
                 description "Color-aware mode";
                 type empty;
               }
             }
           }
           leaf committed-information-rate {
             description "Bandwidth allowed for committed traffic";
             units "bits per second";
             type string;
           }
           leaf committed-burst-size {
             description "Burst size allowed for committed traffic";
             units "bytes";
             type string;
           }
           leaf excess-burst-size {
             description "Burst size allowed for excess traffic";
             units "bytes";
             type string;
           }
         }
       }
       case case_2 {
         container single-packet-rate {
           presence "enable single-packet-rate";
           description "Single-rate packet policer";
           uses apply-advanced;
           choice mode-choice {
             case case_1 {
               leaf color-blind {
                 description "Color-blind mode";
                 type empty;
               }
             }
             case case_2 {
               leaf color-aware {
                 description "Color-aware mode";
                 type empty;
               }
             }
           }
           leaf committed-information-pps {
             description "PPS allowed for committed traffic";
             units "packets per second";
             type string;
           }
           leaf committed-packet-burst {
             description "Packet burst allowed for committed traffic";
             units "packets";
             type string;
           }
           leaf excess-packet-burst {
             description "Packet burst allowed for excess traffic";
             units "packets";
             type string;
           }
         }
       }
       case case_3 {
         container two-rate {
           presence "enable two-rate";
           description "Two-rate policer";
           uses apply-advanced;
           choice mode-choice {
             case case_1 {
               leaf color-blind {
                 description "Color-blind mode";
                 type empty;
               }
             }
             case case_2 {
               leaf color-aware {
                 description "Color-aware mode";
                 type empty;
               }
             }
           }
           leaf committed-information-rate {
             description "Bandwidth allowed for committed traffic";
             units "bits per second";
             type string;
           }
           leaf committed-burst-size {
             description "Burst size allowed for committed traffic  ";
             units "bytes";
             type string;
           }
           leaf peak-information-rate {
             description "Bandwidth allowed for peak traffic";
             units "bits per second";
             type string;
           }
           leaf peak-burst-size {
             description "Burst size allowed for peak traffic  ";
             units "bytes";
             type string;
           }
           container aggregate-policing {
             presence "enable aggregate-policing";
             description "Configure Aggregate Policer";
             uses apply-advanced;
             list policer {
               key name;
               ordered-by user;
               description "Two-color policer to be used as aggregate";
               max-elements 1;
               leaf name {
                 description "Name of two-color policer to use to aggregate police";
                 junos:must "(\"firewall policer $$\")";
                 junos:must-message "Referenced aggregate policer is not defined";
                 type string;
               }
               uses apply-advanced;
               leaf aggregate-sharing-mode {
                 description "Hierarchical Metering model";
                 type enumeration {
                   enum "hybrid" {
                     description "Child policer CIR rates are guaranteed rates and PIR rate are peak rates for member flow";
                   }
                 }
               }
             }
           }
         }
       }
       case case_4 {
         container two-packet-rate {
           presence "enable two-packet-rate";
           description "Two-rate packet policer";
           uses apply-advanced;
           choice mode-choice {
             case case_1 {
               leaf color-blind {
                 description "Color-blind mode";
                 type empty;
               }
             }
             case case_2 {
               leaf color-aware {
                 description "Color-aware mode";
                 type empty;
               }
             }
           }
           leaf committed-information-pps {
             description "PPS allowed for committed traffic";
             units "packets per second";
             type string;
           }
           leaf committed-packet-burst {
             description "Packet burst allowed for committed traffic  ";
             units "packets";
             type string;
           }
           leaf peak-information-pps {
             description "PPS allowed for peak traffic";
             units "packets per second";
             type string;
           }
           leaf peak-packet-burst {
             description "Packet burst allowed for peak traffic  ";
             units "packets";
             type string;
           }
         }
       }
     }
   }
   grouping three-color-policer-action {
     description "Action for three-color policer";
     leaf name {
       description "Loss priority for packet";
       type enumeration {
         enum "high" {
           description "High loss priority";
         }
       }
     }
     uses apply-advanced;
     container then {
       description "Action to take if the rate limits are exceeded";
       uses apply-advanced;
       leaf discard {
         description "Discard the packet";
         type empty;
       }
     }
   }
   grouping tunnel_end_point {
     description "Define a tunnel end point";
     leaf name {
       description "Tunnel end-point identifier (ASCII string)";
       type string {
         junos:posix-pattern "!^((__.*)|(.{65,}))$";
         junos:pattern-message "Must be a non-reserved string of 64 characters or less";
       }
     }
     uses apply-advanced;
     choice l3-protocol {
       case case_1 {
         container ipv6 {
           presence "enable ipv6";
           description "Enter an IPv6 tunnel";
           uses apply-advanced;
           leaf source-address {
             description "Tunnel source address";
             type jt:ipv6addr;
           }
           leaf destination-address {
             description "Tunnel destination address";
             type jt:ipv6prefix;
           }
         }
       }
       case case_2 {
         container ipv4 {
           presence "enable ipv4";
           description "Enter an IPv4 tunnel";
           uses apply-advanced;
           leaf source-address {
             description "Tunnel source address";
             type jt:ipv4addr;
           }
           leaf destination-address {
             description "Tunnel destination address";
             type jt:ipv4prefix;
           }
         }
       }
     }
     choice tunnel-protocol {
       case case_1 {
         container gre {
           presence "enable gre";
           description "Tunnel is GRE";
           uses apply-advanced;
           leaf key {
             description "Key for authentication";
             type union {
               type uint32;
               type string {
                 pattern "<.*>|$.*";
               }
             }
           }
         }
       }
       case case_2 {
         container gre-in-udp {
           presence "enable gre-in-udp";
           description "Tunnel is GRE-in-UDP";
           uses apply-advanced;
           leaf source-port {
             description "UDP source port";
             type union {
               type string {
                 pattern "<.*>|$.*";
               }
               type uint32 {
                 range "0 .. 65535";
               }
             }
           }
           leaf destination-port {
             description "UDP destination port";
             type union {
               type string {
                 pattern "<.*>|$.*";
               }
               type uint32 {
                 range "0 .. 65535";
               }
             }
           }
           leaf key {
             description "GRE key for authentication";
             type union {
               type uint32;
               type string {
                 pattern "<.*>|$.*";
               }
             }
           }
         }
       }
     }
   }
   grouping vpls_filter {
     description "Define an VPLS firewall filter";
     leaf name {
       description "Filter name";
       type string {
         junos:posix-pattern "!^((__.*)|(.{65,}))$";
         junos:pattern-message "Must be a non-reserved string of 64 characters or less";
       }
     }
     uses apply-advanced;
     leaf-list accounting-profile {
       ordered-by user;
       description "Accounting profile name";
       junos:must "(\"accounting-options filter-profile\")";
       junos:must-message "referenced accounting profile must be defined";
       type string;
     }
     leaf interface-specific {
       description "Defined counters are interface specific";
       type empty;
     }
     leaf physical-interface-filter {
       description "Filter is physical interface filter";
       type empty;
     }
     leaf instance-shared {
       description "Filter is routing-instance shared";
       junos:must "(\"chassis network-services enhanced-ip\")";
       junos:must-message "instance-shared filter available only in enhanced-ip mode";
       junos:must "(!(\".. physical-interface-filter\"))";
       junos:must-message "Cannot be both physical-interface-filter and instance-shared";
       junos:must "(!(\".. interface-specific\"))";
       junos:must-message "Cannot be both interface-specific and instance-shared";
       type empty;
     }
     list term {
       key name;
       ordered-by user;
       description "Define a firewall term";
       leaf name {
         description "Term name";
         type string {
           junos:posix-pattern "!^((__.*)|(.{65,}))$";
           junos:pattern-message "Must be a non-reserved string of 64 characters or less";
         }
       }
       uses apply-advanced;
       leaf filter {
         description "Filter to include";
         junos:must "(\"firewall family vpls filter $$\")";
         junos:must-message "Referenced filter is not defined";
         junos:must "((!(\".. from\") && !(\".. then\")))";
         junos:must-message "Not compatible with 'from or then'";
         type string {
           junos:posix-pattern "!^((__.*)|(.{65,}))$";
           junos:pattern-message "Must be a non-reserved string of 64 characters or less";
         }
       }
       container from {
         description "Define match criteria";
         uses apply-advanced;
         choice interface-group_choice {
           case case_1 {
             leaf-list interface-group {
               ordered-by user;
               description "Range of values";
               type string;
             }
           }
           case case_2 {
             leaf-list interface-group-except {
               ordered-by user;
               description "Range of values";
               type string;
             }
           }
         }
         choice ether-type_choice {
           case case_1 {
             leaf-list ether-type {
               ordered-by user;
               type string;
             }
           }
           case case_2 {
             leaf-list ether-type-except {
               ordered-by user;
               type string;
             }
           }
         }
         choice vlan-ether-type_choice {
           case case_1 {
             leaf-list vlan-ether-type {
               ordered-by user;
               type string;
             }
           }
           case case_2 {
             leaf-list vlan-ether-type-except {
               ordered-by user;
               type string;
             }
           }
         }
         list destination-mac-address {
           key name;
           ordered-by user;
           description "Destination MAC address";
           uses firewall_mac_addr_object;
         }
         list source-mac-address {
           key name;
           ordered-by user;
           description "Source MAC address";
           uses firewall_mac_addr_object;
         }
         choice forwarding-class_choice {
           case case_1 {
             leaf-list forwarding-class {
               ordered-by user;
               description "String name";
               type string {
                 junos:posix-pattern "^.{1,64}$";
                 junos:pattern-message "Must be string of 64 characters or less";
               }
             }
           }
           case case_2 {
             leaf-list forwarding-class-except {
               ordered-by user;
               description "String name";
               type string {
                 junos:posix-pattern "^.{1,64}$";
                 junos:pattern-message "Must be string of 64 characters or less";
               }
             }
           }
         }
         choice loss-priority_choice {
           case case_1 {
             leaf-list loss-priority {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
           case case_2 {
             leaf-list loss-priority-except {
               ordered-by user;
               type enumeration {
                 enum "low" {
                   description "Loss priority low";
                 }
                 enum "high" {
                   description "Loss priority high";
                 }
                 enum "medium-low" {
                   description "Loss priority medium-low";
                 }
                 enum "medium-high" {
                   description "Loss priority medium-high";
                 }
               }
             }
           }
         }
         choice learn-vlan-id_choice {
           case case_1 {
             leaf-list learn-vlan-id {
               ordered-by user;
               description "Range of values";
               type string;
             }
           }
           case case_2 {
             leaf-list learn-vlan-id-except {
               ordered-by user;
               description "Range of values";
               type string;
             }
           }
         }
         choice learn-vlan-1p-priority_choice {
           case case_1 {
             leaf-list learn-vlan-1p-priority {
               ordered-by user;
               description "802.1p priority value 0-7";
               type union {
                 type string {
                   pattern "<.*>|$.*";
                 }
                 type uint32 {
                   range "0 .. 7";
                 }
               }
             }
           }
           case case_2 {
             leaf-list learn-vlan-1p-priority-except {
               ordered-by user;
               description "802.1p priority value 0-7";
               type union {
                 type string {
                   pattern "<.*>|$.*";
                 }
                 type uint32 {
                   range "0 .. 7";
                 }
               }
             }
           }
         }
         choice user-vlan-id_choice {
           case case_1 {
             leaf-list user-vlan-id {
               ordered-by user;
               description "Range of values";
               type string;
             }
           }
           case case_2 {
             leaf-list user-vlan-id-except {
               ordered-by user;
               description "Range of values";
               type string;
             }
           }
         }
         choice user-vlan-1p-priority_choice {
           case case_1 {
             leaf-list user-vlan-1p-priority {
               ordered-by user;
               description "802.1p priority value 0-7";
               type union {
                 type string {
                   pattern "<.*>|$.*";
                 }
                 type uint32 {
                   range "0 .. 7";
                 }
               }
             }
           }
           case case_2 {
             leaf-list user-vlan-1p-priority-except {
               ordered-by user;
               description "802.1p priority value 0-7";
               type union {
                 type string {
                   pattern "<.*>|$.*";
                 }
                 type uint32 {
                   range "0 .. 7";
                 }
               }
             }
           }
         }
         choice learn-vlan-dei_choice {
           case case_1 {
             leaf-list learn-vlan-dei {
               ordered-by user;
               description "DEI value 0-1";
               type union {
                 type string {
                   pattern "<.*>|$.*";
                 }
                 type uint32 {
                   range "0 .. 1";
                 }
               }
             }
           }
           case case_2 {
             leaf-list learn-vlan-dei-except {
               ordered-by user;
               description "DEI value 0-1";
               type union {
                 type string {
                   pattern "<.*>|$.*";
                 }
                 type uint32 {
                   range "0 .. 1";
                 }
               }
             }
           }
         }
         choice traffic-type_choice {
           case case_1 {
             leaf-list traffic-type {
               ordered-by user;
               type enumeration {
                 enum "broadcast" {
                   description "Packets with broadcast ethernet address";
                 }
                 enum "multicast" {
                   description "Packets with multicast ethernet address";
                 }
                 enum "unknown-unicast" {
                   description "Packets for which destination ethernet address has not been learnt";
                 }
                 enum "known-unicast" {
                   description "Packets for which destination ethernet address has been learnt";
                 }
               }
             }
           }
           case case_2 {
             leaf-list traffic-type-except {
               ordered-by user;
               type enumeration {
                 enum "broadcast" {
                   description "Packets with broadcast ethernet address";
                 }
                 enum "multicast" {
                   description "Packets with multicast ethernet address";
                 }
                 enum "unknown-unicast" {
                   description "Packets for which destination ethernet address has not been learnt";
                 }
                 enum "known-unicast" {
                   description "Packets for which destination ethernet address has been learnt";
                 }
               }
             }
           }
         }
         list ip-source-address {
           key name;
           ordered-by user;
           description "Match IP source address";
           uses firewall_addr_object;
         }
         list ip-destination-address {
           key name;
           ordered-by user;
           description "Match IP destination address";
           uses firewall_addr_object;
         }
         list ip-address {
           key name;
           ordered-by user;
           description "Match IP source or destination address";
           uses firewall_addr_object;
         }
         choice ip-protocol_choice {
           case case_1 {
             leaf-list ip-protocol {
               ordered-by user;
               type string;
             }
           }
           case case_2 {
             leaf-list ip-protocol-except {
               ordered-by user;
               type string;
             }
           }
         }
         choice dscp_choice {
           case case_1 {
             leaf-list dscp {
               ordered-by user;
               type string;
             }
           }
           case case_2 {
             leaf-list dscp-except {
               ordered-by user;
               type string;
             }
           }
         }
         choice ip-precedence_choice {
           case case_1 {
             leaf-list ip-precedence {
               ordered-by user;
               type string;
             }
           }
           case case_2 {
             leaf-list ip-precedence-except {
               ordered-by user;
               type string;
             }
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice port_choice {
           case case_1 {
             leaf-list port {
               ordered-by user;
               type string;
             }
           }
           case case_2 {
             leaf-list port-except {
               ordered-by user;
               type string;
             }
           }
         }
         leaf tcp-flags {
           description "Match TCP flags";
           type string;
         }
         choice icmp-type_choice {
           case case_1 {
             leaf-list icmp-type {
               ordered-by user;
               type string;
             }
           }
           case case_2 {
             leaf-list icmp-type-except {
               ordered-by user;
               type string;
             }
           }
         }
         choice icmp-code_choice {
           case case_1 {
             leaf-list icmp-code {
               ordered-by user;
               type string;
             }
           }
           case case_2 {
             leaf-list icmp-code-except {
               ordered-by user;
               type string;
             }
           }
         }
         list interface {
           key name;
           ordered-by user;
           description "Match interface name";
           uses match_interface_object;
         }
         list interface-set {
           key name;
           ordered-by user;
           description "Match interface in set";
           uses match_interface_set_object;
         }
         list source-prefix-list {
           key name;
           ordered-by user;
           description "Match IP source prefixes in named list";
           uses firewall_prefix_list;
         }
         list destination-prefix-list {
           key name;
           ordered-by user;
           description "Match IP destination prefixes in named list";
           uses firewall_prefix_list;
         }
         list prefix-list {
           key name;
           ordered-by user;
           description "Match IP source or destination prefixes in named list";
           uses firewall_prefix_list;
         }
         list ipv6-destination-address {
           key name;
           ordered-by user;
           description "Match IPv6 destination address";
           uses firewall_addr6_object;
         }
         list ipv6-source-address {
           key name;
           ordered-by user;
           description "Match IPv6 source address";
           uses firewall_addr6_object;
         }
         list ipv6-address {
           key name;
           ordered-by user;
           description "Match IPv6 address";
           uses firewall_addr6_object;
         }
         choice ipv6-next-header_choice {
           case case_1 {
             leaf-list ipv6-next-header {
               ordered-by user;
               type string;
             }
           }
           case case_2 {
             leaf-list ipv6-next-header-except {
               ordered-by user;
               type string;
             }
           }
         }
         choice ipv6-payload-protocol_choice {
           case case_1 {
             leaf-list ipv6-payload-protocol {
               ordered-by user;
               type string;
             }
           }
           case case_2 {
             leaf-list ipv6-payload-protocol-except {
               ordered-by user;
               type string;
             }
           }
         }
         choice ipv6-traffic-class_choice {
           case case_1 {
             leaf-list ipv6-traffic-class {
               ordered-by user;
               type string;
             }
           }
           case case_2 {
             leaf-list ipv6-traffic-class-except {
               ordered-by user;
               type string;
             }
           }
         }
         list ipv6-source-prefix-list {
           key name;
           ordered-by user;
           description "Match IPV6 source prefixes in named list";
           uses firewall_prefix_list;
         }
         list ipv6-destination-prefix-list {
           key name;
           ordered-by user;
           description "Match IPV6 destination prefixes in named list";
           uses firewall_prefix_list;
         }
         list ipv6-prefix-list {
           key name;
           ordered-by user;
           description "Match IP source or destination prefixes in named list";
           uses firewall_prefix_list;
         }
         choice flex-mask_choice {
           case case_1 {
             container flexible-match-mask {
               description "Match flexible mask";
               uses match_L2_flexible_mask;
             }
           }
         }
         choice flex-range_choice {
           case case_1 {
             container flexible-match-range {
               description "Match flexible range";
               uses match_L2_flexible_range;
             }
           }
         }
         choice policy-map_choice {
           case case_1 {
             leaf-list policy-map {
               ordered-by user;
               description "String name";
               junos:must "(\"class-of-service policy-map $$\")";
               junos:must-message "Undefined policy-map instance";
               type string {
                 length "1 .. 64";
                 junos:posix-pattern "!^((__.*)|(.{65,}))$";
                 junos:pattern-message "Must be a non-reserved string of 64 characters or less";
               }
             }
           }
           case case_2 {
             leaf-list policy-map-except {
               ordered-by user;
               description "String name";
               junos:must "(\"class-of-service policy-map $$\")";
               junos:must-message "Undefined policy-map instance";
               type string {
                 length "1 .. 64";
                 junos:posix-pattern "!^((__.*)|(.{65,}))$";
                 junos:pattern-message "Must be a non-reserved string of 64 characters or less";
               }
             }
           }
         }
       }
       container then {
         description "Action to take if the 'from' condition is matched";
         uses apply-advanced;
         choice policer-choice {
           case case_1 {
             leaf policer {
               description "Name of policer to use to rate-limit traffic";
               junos:must "(!(\"firewall policer $$ aggregate\"))";
               junos:must-message "Cannot attach a aggregate policer to filter";
               type string {
                 junos:posix-pattern "!^((__.*)|(.{65,}))$";
                 junos:pattern-message "Must be a non-reserved string of 64 characters or less";
               }
             }
           }
           case case_2 {
             container three-color-policer {
               description "Police the packet using a three-color-policer";
               uses apply-advanced;
               choice type-choice {
                 case case_1 {
                   leaf single-rate {
                     description "Name of single-rate three-color policer to use to rate-limit traffic";
                     junos:must "(\"firewall three-color-policer $$ single-rate\")";
                     junos:must-message "Referenced single-rate policer does not exist";
                     type string {
                       junos:posix-pattern "!^((__.*)|(.{65,}))$";
                       junos:pattern-message "Must be a non-reserved string of 64 characters or less";
                     }
                   }
                 }
                 case case_2 {
                   leaf single-packet-rate {
                     description "Name of single-packet-rate three-color policer to use to rate-limit traffic";
                     junos:must "(\"firewall three-color-policer $$ single-packet-rate\")";
                     junos:must-message "Referenced single-packet-rate policer does not exist";
                     type string {
                       junos:posix-pattern "!^((__.*)|(.{65,}))$";
                       junos:pattern-message "Must be a non-reserved string of 64 characters or less";
                     }
                   }
                 }
                 case case_3 {
                   leaf two-rate {
                     description "Name of two-rate three-color policer to use to rate-limit traffic";
                     junos:must "(\"firewall three-color-policer $$ two-rate\")";
                     junos:must-message "Referenced two-rate policer does not exist";
                     type string {
                       junos:posix-pattern "!^((__.*)|(.{65,}))$";
                       junos:pattern-message "Must be a non-reserved string of 64 characters or less";
                     }
                   }
                 }
                 case case_4 {
                   leaf two-packet-rate {
                     description "Name of two-packet-rate three-color policer to use to rate-limit traffic";
                     junos:must "(\"firewall three-color-policer $$ two-packet-rate\")";
                     junos:must-message "Referenced two-packet-rate policer does not exist";
                     type string {
                       junos:posix-pattern "!^((__.*)|(.{65,}))$";
                       junos:pattern-message "Must be a non-reserved string of 64 characters or less";
                     }
                   }
                 }
               }
             }
           }
           case case_3 {
             leaf hierarchical-policer {
               description "Name of hierarchical policer to use to rate-limit traffic";
               type string {
                 junos:posix-pattern "!^((__.*)|(.{65,}))$";
                 junos:pattern-message "Must be a non-reserved string of 64 characters or less";
               }
             }
           }
         }
         choice policy-map-choice {
           case case_1 {
             leaf clear-policy-map {
               description "Clear the policy marking";
               type empty;
             }
           }
           case case_2 {
             leaf policy-map {
               description "Policy map action";
               junos:must "(\"class-of-service policy-map $$\")";
               junos:must-message "referenced policy map must be defined";
               type string {
                 junos:posix-pattern "!^((__.*)|(.{65,}))$";
                 junos:pattern-message "Must be a non-reserved string of 64 characters or less";
               }
             }
           }
         }
         leaf count {
           description "Count the packet in the named counter";
           type string {
             junos:posix-pattern "!^((__.*)|(.{65,}))$";
             junos:pattern-message "Must be a non-reserved string of 64 characters or less";
           }
         }
         leaf loss-priority {
           description "Packet's loss priority";
           type enumeration {
             enum "low" {
               description "Loss priority low";
             }
             enum "high" {
               description "Loss priority high";
             }
             enum "medium-low" {
               description "Loss priority medium-low";
             }
             enum "medium-high" {
               description "Loss priority medium-high";
             }
           }
         }
         leaf forwarding-class {
           description "Classify packet to forwarding class";
           type string {
             junos:posix-pattern "^.{1,64}$";
             junos:pattern-message "Must be string of 64 characters or less";
           }
         }
         choice designation {
           case case_1 {
             leaf accept {
               description "Accept the packet";
               type empty;
             }
           }
           case case_2 {
             leaf discard {
               description "Discard the packet";
               type empty;
             }
           }
           case case_3 {
             leaf next {
               description "Continue to next term in a filter";
               type enumeration {
                 enum "term" {
                   description "Continue to next term in a filter";
                 }
               }
             }
           }
         }
         leaf port-mirror-instance {
           description "Port-mirror the packet to specified instance";
           junos:must "(\"forwarding-options port-mirroring instance $$\")";
           junos:must-message "Referenced port-mirroring instance does not exist";
           type string {
             junos:posix-pattern "!^((__.*)|(.{65,}))$";
             junos:pattern-message "Must be a non-reserved string of 64 characters or less";
           }
         }
         leaf port-mirror {
           description "Port-mirror the packet";
           junos:must "(!(\".. port-mirror-instance\"))";
           junos:must-message "'port-mirror' and 'port-mirror-instance' are mutually exclusive";
           junos:must "(\"forwarding-options port-mirroring\")";
           junos:must-message "Configure 'port-mirroring' under 'forwarding-options'";
           type empty;
         }
         leaf next-hop-group {
           description "Use specified next-hop group";
           type string;
         }
         leaf sample {
           description "Sample the packet";
           junos:must "((any \"forwarding-options sampling instance <*> family vpls\" || any \"forwarding-options sampling instance <*> family bridge\"))";
           junos:must-message "Configure family either vpls or bridge under forwarding-options sampling";
           type empty;
         }
         leaf log {
           description "Log the packet";
           type empty;
         }
         leaf syslog {
           description "System log (syslog) information about the packet";
           type empty;
         }
       }
     }
   }
 }
