/*
 * Copyright (c) 2019 Juniper Networks, Inc.
 * All rights reserved.
 */
 module junos-rpc-services {
   namespace "http://yang.juniper.net/junos/rpc/services";

   prefix services;

   import junos-common-ddl-extensions {
     prefix junos;
   }

   import junos-common-odl-extensions {
     prefix junos-odl;
   }

   import junos-common-types {
     prefix jt;
   }

   organization "Juniper Networks, Inc.";

   contact "yang-support@juniper.net";

   description "Junos RPC YANG module for services command(s)";

   revision 2019-01-01 {
     description "Junos: 18.4R2.7";
   }

   rpc get-probe-results {
     description "Show probe results";
     input {
       leaf owner {
         description "Name of owner";
         type string {
           length "1 .. 32";
         }
       }
       leaf test {
         description "Name of test";
         type string {
           length "1 .. 32";
         }
       }
       leaf source-address {
         description "Filter results based on ipv4 or ipv6 source-address";
         type jt:ipaddr;
       }
       leaf target-address {
         description "Filter results based on ipv4 or ipv6 target-address";
         type jt:ipaddr;
       }
       leaf dst-interface {
         description "Filter results based on destination-interface";
         type union {
           type jt:interface-unit;
           type string {
             pattern "<.*>|$.*";
           }
         }
       }
       leaf status {
         description "Filter based on test status PASS or FAIL";
         type enumeration {
           enum "PASS" {
             description "Dump successful tests";
           }
           enum "FAIL" {
             description "Dump failed tests";
           }
         }
       }
       leaf terse {
         description "Terse output";
         type empty;
       }
       leaf limit {
         description "Dump specified number of results (default is 100)";
         default "100";
         type union {
           type string {
             pattern "<.*>|$.*";
           }
           type uint32 {
             range "1 .. 4294967295";
           }
         }
       }
     }
     output {
       choice output_c {
         case output-tag {
           leaf output {
             type string;
           }
         }
         case actual-tag {
           anyxml probe-results;
         }
         case multichassis-tag {
           anyxml multi-routing-engine-results;
         }
       }
     }
   }
   rpc get-history-results {
     description "Show history results";
     input {
       leaf verbosity_level {
         default "brief";
         type enumeration {
           enum "brief" {
             description "Display brief output (default)";
           }
           enum "detail" {
             description "Display detailed output";
           }
         }
       }
       leaf owner {
         description "Name of owner";
         type string {
           length "1 .. 32";
         }
         mandatory true;
       }
       leaf test {
         description "Name of test";
         type string {
           length "1 .. 32";
         }
       }
       leaf since {
         description "Show history since YYYY-MM-DD.HH:MM:SS";
         type jt:time;
       }
       leaf source-address {
         description "Filter history based on ipv4 or ipv6 source-address";
         type jt:ipaddr;
       }
       leaf target-address {
         description "Filter history based on ipv4 or ipv6 target-address";
         type jt:ipaddr;
       }
       leaf dst-interface {
         description "Filter based on destination-interface";
         type union {
           type jt:interface-unit;
           type string {
             pattern "<.*>|$.*";
           }
         }
       }
       leaf limit {
         description "Dump specified number of results (default is 100)";
         default "100";
         type union {
           type string {
             pattern "<.*>|$.*";
           }
           type uint32 {
             range "1 .. 4294967295";
           }
         }
       }
     }
     output {
       choice output_c {
         case output-tag {
           leaf output {
             type string;
           }
         }
         case actual-tag {
           anyxml history-results;
         }
         case multichassis-tag {
           anyxml multi-routing-engine-results;
         }
       }
     }
   }
   rpc get-active-servers {
     description "Show configured servers";
     output {
       choice output_c {
         case output-tag {
           leaf output {
             type string;
           }
         }
         case actual-tag {
           anyxml active-servers;
         }
         case multichassis-tag {
           anyxml multi-routing-engine-results;
         }
       }
     }
   }
   rpc twamp-information {
     description "Show TWAMP information";
     output {
       choice output_c {
         case output-tag {
           leaf output {
             type string;
           }
         }
         case multichassis-tag {
           anyxml multi-routing-engine-results;
         }
       }
     }
   }
   rpc twamp-client-information {
     description "Show TWAMP client information";
     output {
       choice output_c {
         case output-tag {
           leaf output {
             type string;
           }
         }
         case actual-tag {
           anyxml twamp-client-information;
         }
         case multichassis-tag {
           anyxml multi-routing-engine-results;
         }
       }
     }
   }
   rpc twamp-client-connection-information {
     description "Display connection information";
     input {
       leaf connection-name {
         description "Control connection name";
         default "all";
         type string;
       }
     }
     output {
       choice output_c {
         case output-tag {
           leaf output {
             type string;
           }
         }
         case multichassis-tag {
           anyxml multi-routing-engine-results;
         }
       }
     }
   }
   rpc twamp-client-test-session {
     description "Display test session information";
     input {
       leaf control-connection {
         description "Control connection name";
         type string {
           length "1 .. 32";
         }
       }
       leaf test-session {
         description "Test session name";
         type string {
           length "1 .. 32";
         }
       }
     }
     output {
       choice output_c {
         case output-tag {
           leaf output {
             type string;
           }
         }
         case multichassis-tag {
           anyxml multi-routing-engine-results;
         }
       }
     }
   }
   rpc twamp-get-probe-results {
     description "Display test session results";
     input {
       leaf control-connection {
         description "Control connection name";
         type string;
       }
       leaf test-session {
         description "Test session name";
         type string;
       }
     }
     output {
       choice output_c {
         case output-tag {
           leaf output {
             type string;
           }
         }
         case actual-tag {
           anyxml probe-results;
         }
         case multichassis-tag {
           anyxml multi-routing-engine-results;
         }
       }
     }
   }
   rpc twamp-get-history-results {
     description "Display test session history results";
     input {
       leaf verbosity_level {
         default "brief";
         type enumeration {
           enum "brief" {
             description "Display brief output (default)";
           }
           enum "detail" {
             description "Display detailed output";
           }
         }
       }
       leaf control-connection {
         description "Control connection name";
         type string;
       }
       leaf test-session {
         description "Test session name";
         type string;
       }
       leaf since {
         description "Show history since YYYY-MM-DD.HH:MM:SS";
         type jt:time;
       }
     }
     output {
       choice output_c {
         case output-tag {
           leaf output {
             type string;
           }
         }
         case actual-tag {
           anyxml history-results;
         }
         case multichassis-tag {
           anyxml multi-routing-engine-results;
         }
       }
     }
   }
   rpc twamp-server-information {
     description "Show TWAMP server information";
     output {
       choice output_c {
         case output-tag {
           leaf output {
             type string;
           }
         }
         case actual-tag {
           anyxml twamp-server-information;
         }
         case multichassis-tag {
           anyxml multi-routing-engine-results;
         }
       }
     }
   }
   rpc twamp-server-connection-information {
     description "Display connection information";
     input {
       leaf connection-id {
         description "Connection ID";
         default "all";
         type string;
       }
     }
     output {
       choice output_c {
         case output-tag {
           leaf output {
             type string;
           }
         }
         case multichassis-tag {
           anyxml multi-routing-engine-results;
         }
       }
     }
   }
   rpc twamp-server-session-information {
     description "Display session information";
     input {
       leaf session-id {
         description "Session ID";
         default "all";
         type string;
       }
     }
     output {
       choice output_c {
         case output-tag {
           leaf output {
             type string;
           }
         }
         case multichassis-tag {
           anyxml multi-routing-engine-results;
         }
       }
     }
   }
   rpc get-rfc2544-information {
     description "Show rfc2544 information";
     output {
       choice output_c {
         case output-tag {
           leaf output {
             type string;
           }
         }
         case actual-tag {
           anyxml rfc2544-information;
         }
         case multichassis-tag {
           anyxml multi-routing-engine-results;
         }
       }
     }
   }
   rpc get-test-id-information {
     description "Show rfc2544 test id";
     input {
       leaf verbosity_level {
         default "brief";
         type enumeration {
           enum "brief" {
             description "Display brief output (default)";
           }
           enum "detail" {
             description "Display detailed output";
           }
           enum "extensive" {
             description "Display extensive output";
           }
         }
       }
       leaf test-id {
         description "Test id";
         type union {
           type uint32;
           type string {
             pattern "<.*>|$.*";
           }
         }
       }
     }
     output {
       choice output_c {
         case output-tag {
           leaf output {
             type string;
           }
         }
         case actual-tag {
           anyxml rfc2544-test-id-information;
         }
         case multichassis-tag {
           anyxml multi-routing-engine-results;
         }
       }
     }
   }
   rpc get-active-tests-information {
     description "Show rfc2544 active tests";
     input {
       leaf verbosity_level {
         default "brief";
         type enumeration {
           enum "brief" {
             description "Display brief output (default)";
           }
           enum "detail" {
             description "Display detailed output";
           }
           enum "extensive" {
             description "Display extensive output";
           }
         }
       }
       leaf test-id {
         description "Test id";
         type union {
           type uint32;
           type string {
             pattern "<.*>|$.*";
           }
         }
       }
     }
     output {
       choice output_c {
         case output-tag {
           leaf output {
             type string;
           }
         }
         case actual-tag {
           anyxml rfc2544-active-tests-information;
         }
         case multichassis-tag {
           anyxml multi-routing-engine-results;
         }
       }
     }
   }
   rpc get-aborted-tests-information {
     description "Show rfc2544 aborted tests";
     input {
       leaf verbosity_level {
         default "brief";
         type enumeration {
           enum "brief" {
             description "Display brief output (default)";
           }
           enum "detail" {
             description "Display detailed output";
           }
           enum "extensive" {
             description "Display extensive output";
           }
         }
       }
       leaf test-id {
         description "Test id";
         type union {
           type uint32;
           type string {
             pattern "<.*>|$.*";
           }
         }
       }
     }
     output {
       choice output_c {
         case output-tag {
           leaf output {
             type string;
           }
         }
         case actual-tag {
           anyxml rfc2544-aborted-tests-information;
         }
         case multichassis-tag {
           anyxml multi-routing-engine-results;
         }
       }
     }
   }
   rpc get-completed-tests-information {
     description "Show rfc2544 completed tests";
     input {
       leaf verbosity_level {
         default "brief";
         type enumeration {
           enum "brief" {
             description "Display brief output (default)";
           }
           enum "detail" {
             description "Display detailed output";
           }
           enum "extensive" {
             description "Display extensive output";
           }
         }
       }
       leaf test-id {
         description "Test id";
         type union {
           type uint32;
           type string {
             pattern "<.*>|$.*";
           }
         }
       }
     }
     output {
       choice output_c {
         case output-tag {
           leaf output {
             type string;
           }
         }
         case actual-tag {
           anyxml rfc2544-completed-tests-information;
         }
         case multichassis-tag {
           anyxml multi-routing-engine-results;
         }
       }
     }
   }
   rpc get-rfc2544-summary-information {
     description "Show rfc2544 summary";
     output {
       choice output_c {
         case output-tag {
           leaf output {
             type string;
           }
         }
         case actual-tag {
           anyxml rfc2544-summary-information;
         }
         case multichassis-tag {
           anyxml multi-routing-engine-results;
         }
       }
     }
   }
   rpc get-pcef-subscribers {
     description "Show subscriber information";
     input {
       leaf address {
         description "IPv4 or IPv6 address of subscriber";
         type string;
       }
       leaf interface {
         description "Interface name, or with wildcards (e.g. fe-0/0/*, fe-0/*/*)";
         type union {
           type jt:interface-wildcard;
           type string {
             pattern "<.*>|$.*";
           }
         }
       }
       leaf physical-interface {
         description "Physical Interface name";
         type union {
           type jt:interface-wildcard;
           type string {
             pattern "<.*>|$.*";
           }
         }
       }
       leaf user-name {
         description "Username of subscriber";
         type string;
       }
       leaf logical-system {
         description "Logical system where subscriber resides";
         type string;
       }
       leaf routing-instance {
         description "Routing instance where subscriber resides";
         type string;
       }
       leaf profile-name {
         description "Profile with which subscriber has been activated";
         type string {
           length "1 .. 80";
         }
       }
       leaf agent-circuit-identifier {
         description "Display summary for specified agent circuit identifier";
         type string;
       }
       leaf aci-interface-set-name {
         description "Display summary for specified ACI interface set";
         type string;
       }
       leaf stacked-vlan-id {
         description "Stacked VLAN identifier of subscriber";
         type union {
           type string {
             pattern "<.*>|$.*";
           }
           type uint16 {
             range "0 .. 4094";
           }
         }
       }
       leaf vlan-id {
         description "VLAN identifier of subscriber";
         type union {
           type string {
             pattern "<.*>|$.*";
           }
           type uint16 {
             range "0 .. 4094";
           }
         }
       }
       leaf vpi {
         description "ATM VPI of subscriber";
         type union {
           type string {
             pattern "<.*>|$.*";
           }
           type uint16 {
             range "0 .. 255";
           }
         }
       }
       leaf vci {
         description "ATM VCI of subscriber";
         type union {
           type string {
             pattern "<.*>|$.*";
           }
           type uint16 {
             range "0 .. 65535";
           }
         }
       }
       leaf id {
         description "Identifier of subscriber";
         type string;
       }
       leaf mac-address {
         description "MAC address of subscriber";
         type jt:mac-addr;
       }
       leaf client-type {
         description "Client type of subscriber";
         type enumeration {
           enum "dhcp" {
             description "DHCP clients only";
           }
           enum "vlan" {
             description "VLAN clients only";
           }
           enum "ppp" {
             description "PPP clients only";
           }
           enum "pppoe" {
             description "PPPoE clients only";
           }
           enum "l2tp" {
             description "L2TP clients only";
           }
           enum "static" {
             description "Static clients only";
           }
           enum "vpls-pw" {
             description "VPLS-PW clients only";
           }
           enum "mlppp" {
             description "MLPPP clients only";
           }
           enum "xauth" {
             description "XAuth clients only";
           }
           enum "fwauth" {
             description "FwAuth clients only";
           }
           enum "dot1x" {
             description "Dot1x clients only";
           }
           enum "essm" {
             description "ESSM clients only";
           }
         }
       }
       leaf subscriber-state {
         description "State of subscriber";
         type enumeration {
           enum "init" {
             description "INIT state only";
           }
           enum "configured" {
             description "CONFIGURED state only";
           }
           enum "active" {
             description "ACTIVE state only";
           }
           enum "terminating" {
             description "TERMINATING state only";
           }
         }
       }
       leaf display {
         default "terse";
         type enumeration {
           enum "terse" {
             description "Display terse output";
           }
           enum "detail" {
             description "Display detailed output";
           }
           enum "extensive" {
             description "Display extensive output";
           }
           enum "count" {
             description "Display number of subscribers";
           }
         }
       }
     }
     output {
       choice output_c {
         case output-tag {
           leaf output {
             type string;
           }
         }
         case actual-tag {
           anyxml pcef-subscriber;
         }
         case multichassis-tag {
           anyxml multi-routing-engine-results;
         }
       }
     }
   }
   rpc get-pcef-subscribers-summary {
     description "Display pcef subscriber summary";
     input {
       leaf logical-system {
         description "Display summary for specified logical system";
         type string;
       }
       leaf routing-instance {
         description "Display summary for specified routing instance";
         type string;
       }
       leaf physical-interface {
         description "Physical Interface name";
         type union {
           type jt:interface-wildcard;
           type string {
             pattern "<.*>|$.*";
           }
         }
       }
       leaf port {
         description "Display full subscriber port summary";
         type empty;
       }
       leaf pic {
         description "Display full subscriber pic summary";
         type empty;
       }
       leaf slot {
         description "Display full subscriber slot summary";
         type empty;
       }
       leaf all {
         description "Display full subscriber summary";
         type empty;
       }
     }
     output {
       choice output_c {
         case output-tag {
           leaf output {
             type string;
           }
         }
         case actual-tag {
           anyxml pcef-subscriber;
         }
         case multichassis-tag {
           anyxml multi-routing-engine-results;
         }
       }
     }
   }
   rpc get-pcef-pic {
     description "Show physical interface card information";
     input {
       leaf fpc-slot {
         description "FPC slot number";
         type union {
           type string {
             pattern "<.*>|$.*";
           }
           type uint32;
         }
       }
       leaf pic-slot {
         description "PIC slot number";
         type union {
           type string {
             pattern "<.*>|$.*";
           }
           type uint32;
         }
       }
       leaf display {
         default "terse";
         type enumeration {
           enum "terse" {
             description "Display terse output";
           }
         }
       }
     }
     output {
       choice output_c {
         case output-tag {
           leaf output {
             type string;
           }
         }
         case actual-tag {
           anyxml pcef-pic;
         }
         case multichassis-tag {
           anyxml multi-routing-engine-results;
         }
       }
     }
   }
   rpc get-services-flow-collector-information {
     description "Show flow collector service information";
     input {
       leaf display {
         default "terse";
         type enumeration {
           enum "extensive" {
             description "Display extensive output";
           }
           enum "detail" {
             description "Display detailed output";
           }
           enum "terse" {
             description "Display terse output (default)";
           }
         }
       }
       leaf interface {
         description "Interface name";
         type string;
         mandatory true;
       }
     }
     output {
       choice output_c {
         case output-tag {
           leaf output {
             type string;
           }
         }
         case actual-tag {
           anyxml services-flow-collector-information;
         }
         case multichassis-tag {
           anyxml multi-routing-engine-results;
         }
       }
     }
   }
   rpc get-services-flow-collector-file-information {
     description "Show file status information";
     input {
       leaf interface {
         description "Interface name";
         type string;
         mandatory true;
       }
       leaf display {
         default "terse";
         type enumeration {
           enum "extensive" {
             description "Display extensive output";
           }
           enum "detail" {
             description "Display detailed output";
           }
           enum "terse" {
             description "Display terse output (default)";
           }
         }
       }
     }
     output {
       choice output_c {
         case output-tag {
           leaf output {
             type string;
           }
         }
         case actual-tag {
           anyxml services-flow-collector-file-information;
         }
         case multichassis-tag {
           anyxml multi-routing-engine-results;
         }
       }
     }
   }
   rpc get-services-flow-collector-input-information {
     description "Show input status information";
     input {
       leaf interface {
         description "Interface name";
         type string;
         mandatory true;
       }
       leaf display {
         default "terse";
         type enumeration {
           enum "extensive" {
             description "Display extensive output";
           }
           enum "detail" {
             description "Display detailed output";
           }
           enum "terse" {
             description "Display terse output (default)";
           }
         }
       }
     }
     output {
       choice output_c {
         case output-tag {
           leaf output {
             type string;
           }
         }
         case actual-tag {
           anyxml services-flow-collector-input-information;
         }
         case multichassis-tag {
           anyxml multi-routing-engine-results;
         }
       }
     }
   }
   rpc get-cpcd-pic-statistics {
     description "Show captive portal and content delivery statistics by PIC";
     input {
       leaf pic-name {
         type union {
           type jt:interface-name;
           type string {
             pattern "<.*>|$.*";
           }
         }
         mandatory true;
       }
     }
     output {
       choice output_c {
         case output-tag {
           leaf output {
             type string;
           }
         }
         case actual-tag {
           anyxml cpcd-pic-statistics;
         }
         case multichassis-tag {
           anyxml multi-routing-engine-results;
         }
       }
     }
   }
   rpc get-cpcd-profile {
     description "Show profile database";
     input {
       leaf profile-name {
         type string;
       }
     }
     output {
       choice output_c {
         case output-tag {
           leaf output {
             type string;
           }
         }
         case actual-tag {
           anyxml cpcd-profile;
         }
         case multichassis-tag {
           anyxml multi-routing-engine-results;
         }
       }
     }
   }
   rpc get-cpcd-rule {
     description "Show rule database";
     input {
       leaf rule-name {
         type string;
       }
       leaf term {
         description "Term name";
         type string;
       }
     }
     output {
       choice output_c {
         case output-tag {
           leaf output {
             type string;
           }
         }
         case actual-tag {
           anyxml cpcd-rule;
         }
         case multichassis-tag {
           anyxml multi-routing-engine-results;
         }
       }
     }
   }
   rpc get-cpcd-rule-set {
     description "Show rule set database";
     input {
       leaf ruleset-name {
         type string;
       }
     }
     output {
       choice output_c {
         case output-tag {
           leaf output {
             type string;
           }
         }
         case actual-tag {
           anyxml cpcd-rule-set;
         }
         case multichassis-tag {
           anyxml multi-routing-engine-results;
         }
       }
     }
   }
   rpc get-cpcd-pic-information {
     description "Show pic database";
     input {
       leaf pic-name {
         type union {
           type jt:interface-name;
           type string {
             pattern "<.*>|$.*";
           }
         }
       }
     }
     output {
       choice output_c {
         case output-tag {
           leaf output {
             type string;
           }
         }
         case actual-tag {
           anyxml cpcd-pic-information;
         }
         case multichassis-tag {
           anyxml multi-routing-engine-results;
         }
       }
     }
   }
   rpc get-cpcd-service-set {
     description "Show service set database";
     input {
       leaf sset-name {
         type string;
         mandatory true;
       }
       leaf level {
         default "brief";
         type enumeration {
           enum "brief" {
             description "Display brief output (default)";
           }
           enum "detail" {
             description "Display detailed output";
           }
           enum "summary" {
             description "Display summary output";
           }
         }
       }
     }
     output {
       choice output_c {
         case output-tag {
           leaf output {
             type string;
           }
         }
         case actual-tag {
           anyxml cpcd-service-set;
         }
         case multichassis-tag {
           anyxml multi-routing-engine-results;
         }
       }
     }
   }
   rpc get-services-dfc-statistics-information {
     description "Show capture group statistics";
     input {
       leaf capture-group {
         description "Capture group name";
         type string;
         mandatory true;
       }
       leaf per-protocol-details {
         description "Shows ipv4 ipv6 also";
         type empty;
       }
     }
     output {
       choice output_c {
         case output-tag {
           leaf output {
             type string;
           }
         }
         case actual-tag {
           anyxml dfc-statistics-information;
         }
         case multichassis-tag {
           anyxml multi-routing-engine-results;
         }
       }
     }
   }
   rpc get-services-dynamic-flow-capture-control-source-information {
     description "Show DFC control source information";
     input {
       leaf display {
         default "terse";
         type enumeration {
           enum "detail" {
             description "Display detailed output";
           }
           enum "terse" {
             description "Display terse output (default)";
           }
         }
       }
       leaf capture-group {
         description "Capture group name";
         type string;
         mandatory true;
       }
       leaf source-identifier {
         description "Control source identifier";
         type string;
         mandatory true;
       }
       leaf per-protocol-details {
         description "Shows ipv4 ipv6 also";
         type empty;
       }
     }
     output {
       choice output_c {
         case output-tag {
           leaf output {
             type string;
           }
         }
         case actual-tag {
           anyxml services-dynamic-flow-capture-control-source-information;
         }
         case multichassis-tag {
           anyxml multi-routing-engine-results;
         }
       }
     }
   }
   rpc get-services-dynamic-flow-capture-content-destination-information {
     description "Show DFC content destination information";
     input {
       leaf display {
         default "terse";
         type enumeration {
           enum "terse" {
             description "Display terse output (default)";
           }
         }
       }
       leaf capture-group {
         description "Capture group name";
         type string;
         mandatory true;
       }
       leaf destination-identifier {
         description "Content destination identifier";
         type string;
         mandatory true;
       }
     }
     output {
       choice output_c {
         case output-tag {
           leaf output {
             type string;
           }
         }
         case actual-tag {
           anyxml services-dynamic-flow-capture-content-destination-information;
         }
         case multichassis-tag {
           anyxml multi-routing-engine-results;
         }
       }
     }
   }
   rpc get-appid-application-signature-detail {
     description "Show application signature details";
     input {
       uses command-forwarding;
       leaf application-name {
         type string;
       }
       leaf start {
         description "Show application details from a given position";
         type union {
           type string {
             pattern "<.*>|$.*";
           }
           type uint32 {
             range "1 .. 65535";
           }
         }
       }
       leaf count {
         description "Number of applications to show";
         type union {
           type string {
             pattern "<.*>|$.*";
           }
           type uint32 {
             range "1 .. 65535";
           }
         }
       }
     }
     output {
       choice output_c {
         case output-tag {
           leaf output {
             type string;
           }
         }
         case actual-tag {
           anyxml appid-application-signature-detail;
         }
         case multichassis-tag {
           anyxml multi-routing-engine-results;
         }
       }
     }
   }
   rpc get-appid-application-signature-summary {
     description "Show application signature summary";
     output {
       choice output_c {
         case output-tag {
           leaf output {
             type string;
           }
         }
         case actual-tag {
           anyxml appid-application-signature-summary;
         }
         case multichassis-tag {
           anyxml multi-routing-engine-results;
         }
       }
     }
   }
   rpc get-appid-application-group-detail {
     description "Show application group details";
     input {
       uses command-forwarding;
       leaf group-name {
         type string;
       }
     }
     output {
       choice output_c {
         case output-tag {
           leaf output {
             type string;
           }
         }
         case actual-tag {
           anyxml appid-application-group-detail;
         }
         case multichassis-tag {
           anyxml multi-routing-engine-results;
         }
       }
     }
   }
   rpc get-appid-application-group-summary {
     description "Show application group summary";
     output {
       choice output_c {
         case output-tag {
           leaf output {
             type string;
           }
         }
         case actual-tag {
           anyxml appid-application-group-summary;
         }
         case multichassis-tag {
           anyxml multi-routing-engine-results;
         }
       }
     }
   }
   rpc get-appid-application-system-cache {
     description "Show application system cache";
     input {
       uses command-forwarding;
       leaf interface {
         description "Services interface to query";
         type string;
       }
     }
     output {
       choice output_c {
         case output-tag {
           leaf output {
             type string;
           }
         }
         case actual-tag {
           anyxml appid-application-system-cache-information;
         }
         case multichassis-tag {
           anyxml multi-routing-engine-results;
         }
       }
     }
   }
   rpc get-appid-counter {
     description "Show the application identification counters";
     input {
       uses command-forwarding;
       leaf interface {
         description "Services interface to query";
         type string;
       }
     }
     output {
       choice output_c {
         case output-tag {
           leaf output {
             type string;
           }
         }
         case actual-tag {
           anyxml appid-counter-information;
         }
         case multichassis-tag {
           anyxml multi-routing-engine-results;
         }
       }
     }
   }
   rpc get-commit-status {
     description "Show config commit status";
     output {
       choice output_c {
         case output-tag {
           leaf output {
             type string;
           }
         }
         case actual-tag {
           anyxml appid-commit-status;
         }
         case multichassis-tag {
           anyxml multi-routing-engine-results;
         }
       }
     }
   }
   rpc get-appid-application-statistics {
     description "Show the application statistics";
     output {
       choice output_c {
         case output-tag {
           leaf output {
             type string;
           }
         }
         case actual-tag {
           anyxml appid-application-statistics-information;
         }
         case multichassis-tag {
           anyxml multi-routing-engine-results;
         }
       }
     }
   }
   rpc get-appid-application-group-statistics {
     description "Show the application group statistics";
     output {
       choice output_c {
         case output-tag {
           leaf output {
             type string;
           }
         }
         case actual-tag {
           anyxml appid-application-group-statistics-information;
         }
         case multichassis-tag {
           anyxml multi-routing-engine-results;
         }
       }
     }
   }
   rpc get-application-id-status-information {
     description "Show the application identification status";
     output {
       choice output_c {
         case output-tag {
           leaf output {
             type string;
           }
         }
         case actual-tag {
           anyxml appid-status-information;
         }
         case multichassis-tag {
           anyxml multi-routing-engine-results;
         }
       }
     }
   }
   rpc get-appid-package-version {
     description "Show the current application package version";
     output {
       choice output_c {
         case output-tag {
           leaf output {
             type string;
           }
         }
         case actual-tag {
           anyxml appid-package-version;
         }
         case multichassis-tag {
           anyxml multi-routing-engine-results;
         }
       }
     }
   }
   rpc get-lrf-statistics {
     description "Show lrf statistics";
     output {
       choice output_c {
         case output-tag {
           leaf output {
             type string;
           }
         }
         case actual-tag {
           anyxml lrf-statistics-summary;
         }
         case multichassis-tag {
           anyxml multi-routing-engine-results;
         }
       }
     }
   }
   rpc get-lrf-collector-statistics {
     description "Show lrf collector statistics";
     input {
       leaf collector-name {
         description "Name of collector";
         type string;
       }
     }
     output {
       choice output_c {
         case output-tag {
           leaf output {
             type string;
           }
         }
         case actual-tag {
           anyxml lrf-collector-statistics-summary;
         }
         case multichassis-tag {
           anyxml multi-routing-engine-results;
         }
       }
     }
   }
   rpc get-lrf-rule-statistics {
     description "Show lrf rule statistics";
     input {
       leaf rule-name {
         description "Name of rule";
         type string;
       }
     }
     output {
       choice output_c {
         case output-tag {
           leaf output {
             type string;
           }
         }
         case actual-tag {
           anyxml lrf-rule-statistics-summary;
         }
         case multichassis-tag {
           anyxml multi-routing-engine-results;
         }
       }
     }
   }
   rpc get-lrf-template {
     description "Show lrf template";
     input {
       leaf template-type {
         description "Template type";
         type enumeration {
           enum "ipv4" {
             description "Ipv4 template type";
           }
           enum "ipv4-extended" {
             description "Ipv4 extended template type";
           }
           enum "ipv6" {
             description "Ipv6 template type";
           }
           enum "ipv6-extended" {
             description "Ipv6 extended template type";
           }
           enum "transport-layer" {
             description "Transport layer template type";
           }
           enum "flow-id" {
             description "Flow id template type";
           }
           enum "ipflow" {
             description "IPFlow type";
           }
           enum "ipflow-ts" {
             description "IPFlow TS type";
           }
           enum "ipflow-extended" {
             description "IPFlow extended type";
           }
           enum "device-data" {
             description "Device data template type";
           }
           enum "l7-app" {
             description "L7 APP template type";
           }
           enum "http" {
             description "HTTP type";
           }
           enum "mobile-subscriber" {
             description "Mobile subscriber type";
           }
           enum "subscriber-data" {
             description "Subscriber data type";
           }
           enum "ifl-subscriber" {
             description "IFL based subscriber type";
           }
           enum "wireline-subscriber" {
             description "Wireline subscriber type";
           }
           enum "ipflow-tcp-ts" {
             description "IPFLOW TCP timestamp type (IBM specific)";
           }
           enum "ipflow-tcp" {
             description "IPFLOW TCP type";
           }
           enum "video" {
             description "Video type";
           }
           enum "dns" {
             description "DNS type";
           }
           enum "status-code-distribution" {
             description "Status code distribution for HTTP and DNS";
           }
           enum "pcc" {
             description "PCC type";
           }
         }
         mandatory true;
       }
     }
     output {
       choice output_c {
         case output-tag {
           leaf output {
             type string;
           }
         }
         case actual-tag {
           anyxml lrf-template;
         }
         case multichassis-tag {
           anyxml multi-routing-engine-results;
         }
       }
     }
   }
   rpc get-service-accounting-information {
     description "Show sampled accounting service";
     output {
       choice output_c {
         case output-tag {
           leaf output {
             type string;
           }
         }
         case actual-tag {
           anyxml service-accounting-information;
         }
         case multichassis-tag {
           anyxml multi-routing-engine-results;
         }
       }
     }
   }
   rpc get-service-accounting-status-information {
     description "Show service accounting parameters";
     input {
       leaf status-information {
         description "Name of service, wildcard, or 'all'";
         type string;
       }
     }
     output {
       choice output_c {
         case output-tag {
           leaf output {
             type string;
           }
         }
         case actual-tag {
           anyxml service-accounting-status-information;
         }
         case multichassis-tag {
           anyxml multi-routing-engine-results;
         }
       }
     }
   }
   rpc get-service-accounting-status-inline-jflow-information {
     description "Show service accounting inline Jflow parameters";
     input {
       leaf inline-jflow-information {
         description "FPC Slot for inline Jflow";
         type union {
           type string {
             pattern "<.*>|$.*";
           }
           type uint32;
         }
       }
     }
     output {
       choice output_c {
         case output-tag {
           leaf output {
             type string;
           }
         }
         case actual-tag {
           anyxml service-accouting-inline-jflow-information;
         }
         case multichassis-tag {
           anyxml multi-routing-engine-results;
         }
       }
     }
   }
   rpc get-service-accounting-usage-information {
     description "Show CPU usage";
     input {
       leaf usage-information {
         description "Name of service, wildcard, or 'all'";
         type string;
       }
     }
     output {
       choice output_c {
         case output-tag {
           leaf output {
             type string;
           }
         }
         case actual-tag {
           anyxml service-accounting-usage-information;
         }
         case multichassis-tag {
           anyxml multi-routing-engine-results;
         }
       }
     }
   }
   rpc get-service-accounting-memory-information {
     description "Show memory information";
     input {
       leaf memory-information {
         description "Name of service, wildcard, or 'all'";
         type string;
       }
     }
     output {
       choice output_c {
         case output-tag {
           leaf output {
             type string;
           }
         }
         case actual-tag {
           anyxml service-accounting-memory-information;
         }
         case multichassis-tag {
           anyxml multi-routing-engine-results;
         }
       }
     }
   }
   rpc get-service-accounting-flow-information {
     description "Show flow information";
     input {
       leaf flow-information {
         description "Name of service, wildcard, or 'all'";
         type string;
       }
       leaf logical-system {
         description "Name of logical system";
         type string {
           junos:posix-pattern "^[a-zA-Z0-9_-]{1,63}$";
           junos:pattern-message "Logical-system name is a string consisting of up         to 63 letters, numbers, dashes and underscores";
         }
       }
     }
     output {
       choice output_c {
         case output-tag {
           leaf output {
             type string;
           }
         }
         case actual-tag {
           anyxml service-accounting-flow-information;
         }
         case multichassis-tag {
           anyxml multi-routing-engine-results;
         }
       }
     }
   }
   rpc get-service-accounting-status-inline-jflow-flow-information {
     description "Show service accounting inline Jflow flow information";
     input {
       leaf inline-jflow-flow-information {
         description "FPC Slot for inline Jflow";
         type union {
           type string {
             pattern "<.*>|$.*";
           }
           type uint32;
         }
       }
     }
     output {
       choice output_c {
         case output-tag {
           leaf output {
             type string;
           }
         }
         case actual-tag {
           anyxml service-accouting-inline-jflow-flow-infomation;
         }
         case multichassis-tag {
           anyxml multi-routing-engine-results;
         }
       }
     }
   }
   rpc get-service-accounting-flow-detail {
     description "Show flow detail";
     input {
       leaf flow-detail-information {
         description "Name of service, wildcard, or 'all'";
         type string;
       }
       leaf limit {
         description "Maximum number of flows to display";
         type union {
           type uint32;
           type string {
             pattern "<.*>|$.*";
           }
         }
       }
       leaf order {
         description "Order for displaying flows";
         type enumeration {
           enum "bytes" {
             description "Display largest number of bytes first";
           }
           enum "packets" {
             description "Display largest number of packets first";
           }
         }
       }
       leaf display {
         default "terse";
         type enumeration {
           enum "extensive" {
             description "Display extensive output";
           }
           enum "detail" {
             description "Display detailed output";
           }
           enum "terse" {
             description "Display terse output (default)";
           }
         }
       }
       leaf source-prefix {
         description "Filter term source prefix";
         type string;
       }
       leaf destination-prefix {
         description "Filter term destination prefix";
         type string;
       }
       leaf source-port {
         description "Filter term source port";
         type union {
           type uint32;
           type string {
             pattern "<.*>|$.*";
           }
         }
       }
       leaf destination-port {
         description "Filter term destination port";
         type union {
           type uint32;
           type string {
             pattern "<.*>|$.*";
           }
         }
       }
       leaf input-snmp-interface-index {
         description "Filter term input SNMP interface index";
         type union {
           type uint32;
           type string {
             pattern "<.*>|$.*";
           }
         }
       }
       leaf output-snmp-interface-index {
         description "Filter term output SNMP interface index";
         type union {
           type uint32;
           type string {
             pattern "<.*>|$.*";
           }
         }
       }
       leaf source-as {
         description "Filter term source AS";
         type union {
           type uint32;
           type string {
             pattern "<.*>|$.*";
           }
         }
       }
       leaf destination-as {
         description "Filter term destination AS";
         type union {
           type uint32;
           type string {
             pattern "<.*>|$.*";
           }
         }
       }
       leaf tos {
         description "Filter term ToS";
         type union {
           type uint32;
           type string {
             pattern "<.*>|$.*";
           }
         }
       }
       leaf proto {
         description "Filter term protocol";
         type union {
           type uint32;
           type string {
             pattern "<.*>|$.*";
           }
         }
       }
     }
     output {
       choice output_c {
         case output-tag {
           leaf output {
             type string;
           }
         }
         case actual-tag {
           anyxml service-accounting-flow-detail;
         }
         case multichassis-tag {
           anyxml multi-routing-engine-results;
         }
       }
     }
   }
   rpc get-service-accounting-aggregation-information {
     description "Show aggregation information";
     output {
       choice output_c {
         case output-tag {
           leaf output {
             type string;
           }
         }
         case actual-tag {
           anyxml service-accounting-aggregation-information;
         }
         case multichassis-tag {
           anyxml multi-routing-engine-results;
         }
       }
     }
   }
   rpc get-service-accounting-aggregation-as-information {
     description "Show aggregation type AS";
     input {
       leaf as-information {
         description "Name of service, wildcard, or 'all'";
         type string;
       }
       leaf limit {
         description "Maximum number of flows to display";
         type union {
           type uint32;
           type string {
             pattern "<.*>|$.*";
           }
         }
       }
       leaf order {
         description "Order for displaying flows";
         type enumeration {
           enum "bytes" {
             description "Display largest number of bytes first";
           }
           enum "packets" {
             description "Display largest number of packets first";
           }
         }
       }
       leaf display {
         default "terse";
         type enumeration {
           enum "extensive" {
             description "Display extensive output";
           }
           enum "detail" {
             description "Display detailed output";
           }
           enum "terse" {
             description "Display terse output (default)";
           }
         }
       }
       leaf source-as {
         description "Filter term source-as";
         type union {
           type uint32;
           type string {
             pattern "<.*>|$.*";
           }
         }
       }
       leaf destination-as {
         description "Filter term destination AS";
         type union {
           type uint32;
           type string {
             pattern "<.*>|$.*";
           }
         }
       }
       leaf input-snmp-interface-index {
         description "Filter term input SNMP interface index";
         type union {
           type uint32;
           type string {
             pattern "<.*>|$.*";
           }
         }
       }
       leaf output-snmp-interface-index {
         description "Filter term output SNMP interface index";
         type union {
           type uint32;
           type string {
             pattern "<.*>|$.*";
           }
         }
       }
     }
     output {
       choice output_c {
         case output-tag {
           leaf output {
             type string;
           }
         }
         case actual-tag {
           anyxml service-accounting-aggregation-as-information;
         }
         case multichassis-tag {
           anyxml multi-routing-engine-results;
         }
       }
     }
   }
   rpc get-service-accounting-aggregation-protocol-port-information {
     description "Show aggregation type protocol-port";
     input {
       leaf protocol-port-information {
         description "Name of service, wildcard, or 'all'";
         type string;
       }
       leaf limit {
         description "Maximum number of flows to display";
         type union {
           type uint32;
           type string {
             pattern "<.*>|$.*";
           }
         }
       }
       leaf order {
         description "Order for displaying flows";
         type enumeration {
           enum "bytes" {
             description "Display largest number of bytes first";
           }
           enum "packets" {
             description "Display largest number of packets first";
           }
         }
       }
       leaf display {
         default "terse";
         type enumeration {
           enum "extensive" {
             description "Display extensive output";
           }
           enum "detail" {
             description "Display detailed output";
           }
           enum "terse" {
             description "Display terse output (default)";
           }
         }
       }
       leaf proto {
         description "Filter term protocol";
         type union {
           type uint32;
           type string {
             pattern "<.*>|$.*";
           }
         }
       }
       leaf source-port {
         description "Filter term source port";
         type union {
           type uint32;
           type string {
             pattern "<.*>|$.*";
           }
         }
       }
       leaf destination-port {
         description "Filter term destination port";
         type union {
           type uint32;
           type string {
             pattern "<.*>|$.*";
           }
         }
       }
     }
     output {
       choice output_c {
         case output-tag {
           leaf output {
             type string;
           }
         }
         case actual-tag {
           anyxml service-accounting-aggregation-protocol-port-information;
         }
         case multichassis-tag {
           anyxml multi-routing-engine-results;
         }
       }
     }
   }
   rpc get-service-accounting-aggregation-source-prefix-information {
     description "Show aggregation type source-prefix";
     input {
       leaf source-prefix-information {
         description "Name of service, wildcard, or 'all'";
         type string;
       }
       leaf limit {
         description "Maximum number of flows to display";
         type union {
           type uint32;
           type string {
             pattern "<.*>|$.*";
           }
         }
       }
       leaf order {
         description "Order for displaying flows";
         type enumeration {
           enum "bytes" {
             description "Display largest number of bytes first";
           }
           enum "packets" {
             description "Display largest number of packets first";
           }
         }
       }
       leaf display {
         default "terse";
         type enumeration {
           enum "extensive" {
             description "Display extensive output";
           }
           enum "detail" {
             description "Display detailed output";
           }
           enum "terse" {
             description "Display terse output (default)";
           }
         }
       }
       leaf source-prefix {
         description "Filter term source prefix";
         type string;
       }
       leaf source-as {
         description "Filter term source-as";
         type union {
           type uint32;
           type string {
             pattern "<.*>|$.*";
           }
         }
       }
       leaf input-snmp-interface-index {
         description "Filter term input SNMP interface index";
         type union {
           type uint32;
           type string {
             pattern "<.*>|$.*";
           }
         }
       }
     }
     output {
       choice output_c {
         case output-tag {
           leaf output {
             type string;
           }
         }
         case actual-tag {
           anyxml service-accounting-aggregation-source-prefix-information;
         }
         case multichassis-tag {
           anyxml multi-routing-engine-results;
         }
       }
     }
   }
   rpc get-service-accounting-aggregation-destination-prefix-information {
     description "Show aggregation type destination-prefix";
     input {
       leaf destination-prefix-information {
         description "Name of service, wildcard, or 'all'";
         type string;
       }
       leaf limit {
         description "Maximum number of flows to display";
         type union {
           type uint32;
           type string {
             pattern "<.*>|$.*";
           }
         }
       }
       leaf order {
         description "Order for displaying flows";
         type enumeration {
           enum "bytes" {
             description "Display largest number of bytes first";
           }
           enum "packets" {
             description "Display largest number of packets first";
           }
         }
       }
       leaf display {
         default "terse";
         type enumeration {
           enum "extensive" {
             description "Display extensive output";
           }
           enum "detail" {
             description "Display detailed output";
           }
           enum "terse" {
             description "Display terse output (default)";
           }
         }
       }
       leaf destination-prefix {
         description "Filter term destination prefix";
         type string;
       }
       leaf destination-as {
         description "Filter term destination-as";
         type union {
           type uint32;
           type string {
             pattern "<.*>|$.*";
           }
         }
       }
       leaf output-snmp-interface-index {
         description "Filter term output SNMP interface index";
         type union {
           type uint32;
           type string {
             pattern "<.*>|$.*";
           }
         }
       }
     }
     output {
       choice output_c {
         case output-tag {
           leaf output {
             type string;
           }
         }
         case actual-tag {
           anyxml service-accounting-aggregation-destination-prefix-information;
         }
         case multichassis-tag {
           anyxml multi-routing-engine-results;
         }
       }
     }
   }
   rpc get-service-accounting-aggregation-source-destination-prefix-information {
     description "Show aggregation type source-destination-prefix";
     input {
       leaf source-destination-prefix-information {
         description "Name of service, wildcard, or 'all'";
         type string;
       }
       leaf limit {
         description "Maximum number of flows to display";
         type union {
           type uint32;
           type string {
             pattern "<.*>|$.*";
           }
         }
       }
       leaf order {
         description "Order for displaying flows";
         type enumeration {
           enum "bytes" {
             description "Display largest number of bytes first";
           }
           enum "packets" {
             description "Display largest number of packets first";
           }
         }
       }
       leaf display {
         default "terse";
         type enumeration {
           enum "extensive" {
             description "Display extensive output";
           }
           enum "detail" {
             description "Display detailed output";
           }
           enum "terse" {
             description "Display terse output (default)";
           }
         }
       }
       leaf source-prefix {
         description "Filter term source prefix";
         type string;
       }
       leaf source-as {
         description "Filter term source-as";
         type union {
           type uint32;
           type string {
             pattern "<.*>|$.*";
           }
         }
       }
       leaf input-snmp-interface-index {
         description "Filter term input SNMP interface index";
         type union {
           type uint32;
           type string {
             pattern "<.*>|$.*";
           }
         }
       }
       leaf destination-prefix {
         description "Filter term destination prefix";
         type string;
       }
       leaf destination-as {
         description "Filter term destination-as";
         type union {
           type uint32;
           type string {
             pattern "<.*>|$.*";
           }
         }
       }
       leaf output-snmp-interface-index {
         description "Filter term output SNMP interface index";
         type union {
           type uint32;
           type string {
             pattern "<.*>|$.*";
           }
         }
       }
     }
     output {
       choice output_c {
         case output-tag {
           leaf output {
             type string;
           }
         }
         case actual-tag {
           anyxml service-accounting-aggregation-source-destination-prefix-information;
         }
         case multichassis-tag {
           anyxml multi-routing-engine-results;
         }
       }
     }
   }
   rpc get-service-accounting-aggregation-template-information {
     description "Show aggregation type template";
     input {
       leaf template-name {
         description "Name of template";
         type string;
         mandatory true;
       }
       leaf logical-system {
         description "Name of logical system";
         type string {
           junos:posix-pattern "^[a-zA-Z0-9_-]{1,63}$";
           junos:pattern-message "Logical-system name is a string consisting of up         to 63 letters, numbers, dashes and underscores";
         }
       }
       leaf display {
         default "terse";
         type enumeration {
           enum "extensive" {
             description "Display extensive output";
           }
           enum "detail" {
             description "Display detailed output";
           }
           enum "terse" {
             description "Display terse output (default)";
           }
         }
       }
     }
     output {
       choice output_c {
         case output-tag {
           leaf output {
             type string;
           }
         }
         case actual-tag {
           anyxml service-accounting-aggregation-template-information;
         }
         case multichassis-tag {
           anyxml multi-routing-engine-results;
         }
       }
     }
   }
   rpc get-service-accounting-errors-information {
     description "Show error statistics";
     input {
       leaf error-information {
         description "Name of service, wildcard, or 'all'";
         type string;
       }
     }
     output {
       choice output_c {
         case output-tag {
           leaf output {
             type string;
           }
         }
         case actual-tag {
           anyxml service-accounting-errors-information;
         }
         case multichassis-tag {
           anyxml multi-routing-engine-results;
         }
       }
     }
   }
   rpc get-service-accounting-error-inline-jflow-information {
     description "Show service accounting inline Jflow error information";
     input {
       leaf inline-jflow-error-information {
         description "FPC Slot for inline Jflow";
         type union {
           type string {
             pattern "<.*>|$.*";
           }
           type uint32;
         }
       }
     }
     output {
       choice output_c {
         case output-tag {
           leaf output {
             type string;
           }
         }
         case actual-tag {
           anyxml service-accouting-inline-jflow-error-infomation;
         }
         case multichassis-tag {
           anyxml multi-routing-engine-results;
         }
       }
     }
   }
   rpc get-packet-distribution-information {
     description "Show packet size distribution";
     input {
       leaf packet-size-distribution-information {
         description "Name of service, wildcard, or 'all'";
         type string;
       }
     }
     output {
       choice output_c {
         case output-tag {
           leaf output {
             type string;
           }
         }
         case actual-tag {
           anyxml packet-distribution-information;
         }
         case multichassis-tag {
           anyxml multi-routing-engine-results;
         }
       }
     }
   }
   rpc get-service-video-monitoring-information {
     description "Show video-monitoring information";
     output {
       choice output_c {
         case output-tag {
           leaf output {
             type string;
           }
         }
         case actual-tag {
           anyxml service-video-monitoring-information;
         }
         case multichassis-tag {
           anyxml multi-routing-engine-results;
         }
       }
     }
   }
   rpc get-service-video-monitoring-mdi-information {
     description "Show MDI flows information";
     output {
       choice output_c {
         case output-tag {
           leaf output {
             type string;
           }
         }
         case actual-tag {
           anyxml service-video-monitoring-mdii-information;
         }
         case multichassis-tag {
           anyxml multi-routing-engine-results;
         }
       }
     }
   }
   rpc get-service-video-monitoring-mdi-stats-information {
     description "Show MDI flows stats information";
     input {
       leaf fpc-slot {
         description "FPC Slot number";
         type union {
           type string {
             pattern "<.*>|$.*";
           }
           type uint32;
         }
         mandatory true;
       }
     }
     output {
       choice output_c {
         case output-tag {
           leaf output {
             type string;
           }
         }
         case actual-tag {
           anyxml service-video-monitoring-mdi-stats-information;
         }
         case multichassis-tag {
           anyxml multi-routing-engine-results;
         }
       }
     }
   }
   rpc get-service-video-monitoring-mdi-errors-information {
     description "Show MDI flows error information";
     input {
       leaf fpc-slot {
         description "FPC Slot number";
         type union {
           type string {
             pattern "<.*>|$.*";
           }
           type uint32;
         }
         mandatory true;
       }
     }
     output {
       choice output_c {
         case output-tag {
           leaf output {
             type string;
           }
         }
         case actual-tag {
           anyxml service-video-monitoring-mdi-errors-information;
         }
         case multichassis-tag {
           anyxml multi-routing-engine-results;
         }
       }
     }
   }
   rpc get-service-video-monitoring-mdi-flows-information {
     description "Show MDI flows information";
     input {
       leaf fpc-slot {
         description "FPC Slot number";
         type union {
           type string {
             pattern "<.*>|$.*";
           }
           type uint32;
         }
         mandatory true;
       }
       leaf flow-count {
         description "Count of flows to display";
         type union {
           type string {
             pattern "<.*>|$.*";
           }
           type uint32 {
             range "1 .. 10000";
           }
         }
       }
       leaf flow-identifier {
         description "Flow Identifier";
         type union {
           type uint32;
           type string {
             pattern "<.*>|$.*";
           }
         }
       }
       leaf source-address {
         description "Source address of flow";
         type jt:ipprefix-optional;
       }
       leaf destination-address {
         description "Destination address of flow";
         type jt:ipprefix-optional;
       }
       leaf source-port {
         description "Source port of flow";
         type union {
           type uint32;
           type string {
             pattern "<.*>|$.*";
           }
         }
       }
       leaf destination-port {
         description "Destination port of flow";
         type union {
           type uint32;
           type string {
             pattern "<.*>|$.*";
           }
         }
       }
       leaf template-name {
         description "Template name";
         type string;
       }
       leaf ifl-name {
         description "Interface name";
         type union {
           type jt:interface-name;
           type string {
             pattern "<.*>|$.*";
           }
         }
       }
       leaf flow-direction {
         description "Direction of flow";
         type enumeration {
           enum "input" {
             description "Input flows";
           }
           enum "output" {
             description "Output flows";
           }
         }
       }
       leaf flow-type {
         description "Type of flow";
         type enumeration {
           enum "udp" {
             description "UDP flows";
           }
           enum "rtp" {
             description "RTP flows";
           }
         }
       }
       leaf flow-family-type {
         description "Type of flow";
         type enumeration {
           enum "flow-over-ipv4" {
             description "Flows over IPv4";
           }
           enum "flow-over-ipv4-over-mpls" {
             description "Flows over IPv4 over MPLS";
           }
           enum "flow-over-ipv6" {
             description "Flows over IPv6";
           }
           enum "flow-over-ipv6-over-mpls" {
             description "Flows over IPv6 over MPLS";
           }
         }
       }
       leaf flow-display {
         description "Display terse/details output";
         type enumeration {
           enum "detail" {
             description "Display detailed output";
           }
           enum "brief" {
             description "Display breif output (default)";
           }
         }
       }
     }
     output {
       choice output_c {
         case output-tag {
           leaf output {
             type string;
           }
         }
         case actual-tag {
           anyxml service-video-monitoring-mdi-flows-information;
         }
         case multichassis-tag {
           anyxml multi-routing-engine-results;
         }
       }
     }
   }
   rpc get-services-video-monitoring-mdi-alarms-information {
     description "Show Alarm information";
     output {
       choice output_c {
         case output-tag {
           leaf output {
             type string;
           }
         }
         case actual-tag {
           anyxml services-video-monitoring-mdi-alarms-information;
         }
         case multichassis-tag {
           anyxml multi-routing-engine-results;
         }
       }
     }
   }
   rpc get-services-video-monitoring-mdi-alarms-stats-information {
     description "Show MDI alarm stats information";
     input {
       leaf fpc-slot {
         description "FPC Slot number";
         type union {
           type string {
             pattern "<.*>|$.*";
           }
           type uint32;
         }
         mandatory true;
       }
     }
     output {
       choice output_c {
         case output-tag {
           leaf output {
             type string;
           }
         }
         case actual-tag {
           anyxml services-video-monitoring-mdi-alarms-stats-information;
         }
         case multichassis-tag {
           anyxml multi-routing-engine-results;
         }
       }
     }
   }
   rpc get-analytics-agent-information {
     description "Show analytics service agent information";
     input {
       leaf level {
         default "brief";
         type enumeration {
           enum "detail" {
             description "Display detailed data";
           }
           enum "brief" {
             description "Display brief data (default)";
           }
         }
       }
     }
     output {
       choice output_c {
         case output-tag {
           leaf output {
             type string;
           }
         }
         case actual-tag {
           anyxml analytics-agent-information;
         }
         case multichassis-tag {
           anyxml multi-routing-engine-results;
         }
       }
     }
   }
   rpc get-service-set-memory-statistics {
     description "Show service interface memory utilization";
     input {
       leaf service-set {
         description "Name of service set";
         type string;
       }
       leaf interface {
         description "Name of adaptive services interface";
         type string;
       }
     }
     output {
       choice output_c {
         case output-tag {
           leaf output {
             type string;
           }
         }
         case actual-tag {
           anyxml service-set-memory-statistics-information;
         }
         case multichassis-tag {
           anyxml multi-routing-engine-results;
         }
       }
     }
   }
   rpc get-service-set-cpu-statistics {
     description "Show service interface CPU utilization as a percentage";
     input {
       leaf service-set {
         description "Name of service set";
         type string;
       }
       leaf interface {
         description "Name of adaptive services interface";
         type string;
       }
     }
     output {
       choice output_c {
         case output-tag {
           leaf output {
             type string;
           }
         }
         case actual-tag {
           anyxml service-set-cpu-statistics-information;
         }
         case multichassis-tag {
           anyxml multi-routing-engine-results;
         }
       }
     }
   }
   rpc get-service-set-summary-information {
     description "Show service set summary information";
     input {
       leaf interface {
         description "Name of adaptive services interface";
         type string;
       }
     }
     output {
       choice output_c {
         case output-tag {
           leaf output {
             type string;
           }
         }
         case actual-tag {
           anyxml service-set-summary-information;
         }
         case multichassis-tag {
           anyxml multi-routing-engine-results;
         }
       }
     }
   }
   rpc get-service-set-packet-drop-statistics {
     description "Show service set packet drop statistics";
     input {
       leaf interface {
         description "Name of adaptive services interface";
         type string;
       }
     }
     output {
       choice output_c {
         case output-tag {
           leaf output {
             type string;
           }
         }
         case actual-tag {
           anyxml service-set-packet-drop-statistics;
         }
         case multichassis-tag {
           anyxml multi-routing-engine-results;
         }
       }
     }
   }
   rpc get-service-set-drop-flow-statistics {
     description "Show drop flow stats";
     input {
       leaf interface {
         description "Name of adaptive services interface";
         type string;
       }
     }
     output {
       choice output_c {
         case output-tag {
           leaf output {
             type string;
           }
         }
         case actual-tag {
           anyxml service-set-drop-flow-statistics;
         }
         case multichassis-tag {
           anyxml multi-routing-engine-results;
         }
       }
     }
   }
   rpc get-service-set-integrity-drops-statistics {
     description "Show header integrity drops";
     input {
       leaf service-set {
         description "Name of service set";
         type string;
       }
       leaf interface {
         description "Name of adaptive services interface";
         type string;
       }
     }
     output {
       choice output_c {
         case output-tag {
           leaf output {
             type string;
           }
         }
         case actual-tag {
           anyxml service-set-integrity-drops-statistics;
         }
         case multichassis-tag {
           anyxml multi-routing-engine-results;
         }
       }
     }
   }
   rpc get-service-set-tcp-tracker-statistics {
     description "Show tcp tracker statistics";
     input {
       leaf service-set {
         description "Name of service set";
         type string;
       }
       leaf interface {
         description "Name of adaptive services interface";
         type string;
       }
     }
     output {
       choice output_c {
         case output-tag {
           leaf output {
             type string;
           }
         }
         case actual-tag {
           anyxml msp-service-set-tcp-statistics;
         }
         case multichassis-tag {
           anyxml multi-routing-engine-results;
         }
       }
     }
   }
   rpc get-service-set-tcp-mss-statistics {
     description "Show service set TCP MSS statistics";
     input {
       leaf interface {
         description "Name of adaptive services interface";
         type string;
       }
     }
     output {
       choice output_c {
         case output-tag {
           leaf output {
             type string;
           }
         }
         case actual-tag {
           anyxml service-set-tcp-mss-statistics;
         }
         case multichassis-tag {
           anyxml multi-routing-engine-results;
         }
       }
     }
   }
   rpc get-service-set-syslog-statistics {
     description "Show service set syslog statistics";
     input {
       leaf host {
         description "Syslog host address";
         type string;
       }
       leaf service-set {
         description "Name of service set";
         type string;
       }
       leaf interface {
         description "Name of adaptive services interface";
         type string;
       }
       leaf display {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml syslog-stats-interface;
         }
         case multichassis-tag {
           anyxml multi-routing-engine-results;
         }
       }
     }
   }
   rpc get-service-set-jflow-log-statistics {
     description "Show service set jflow-log statistics";
     input {
       leaf service-set {
         description "Name of service set";
         type string;
       }
       leaf interface {
         description "Name of adaptive services interface";
         type string;
       }
       leaf display {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml jflow-log-stats-interface;
         }
         case multichassis-tag {
           anyxml multi-routing-engine-results;
         }
       }
     }
   }
   rpc get-service-set-ids-drops-statistics {
     description "Show service set IDS drops statistics";
     input {
       leaf service-set {
         description "Name of service set";
         type string;
       }
       leaf interface {
         description "Name of adaptive services interface";
         type string;
       }
     }
     output {
       choice output_c {
         case output-tag {
           leaf output {
             type string;
           }
         }
         case actual-tag {
           anyxml msp-service-set-ids-drops-statistics;
         }
         case multichassis-tag {
           anyxml multi-routing-engine-results;
         }
       }
     }
   }
   rpc get-ids-session-limits-counters-statistics {
     description "Show the session-limits counters";
     input {
       leaf service-set {
         description "Name of service set";
         type string;
       }
       leaf interface {
         description "Name of adaptive services interface";
         type string;
       }
     }
     output {
       choice output_c {
         case output-tag {
           leaf output {
             type string;
           }
         }
         case actual-tag {
           anyxml ids-session-limits-counters-statistics;
         }
         case multichassis-tag {
           anyxml multi-routing-engine-results;
         }
       }
     }
   }
   rpc get-service-set-plugin-summary {
     description "Show service set plugins summary";
     input {
       leaf interface {
         description "Name of extension provider interface";
         type string;
       }
     }
     output {
       choice output_c {
         case output-tag {
           leaf output {
             type string;
           }
         }
         case actual-tag {
           anyxml service-set-plugin-summary;
         }
         case multichassis-tag {
           anyxml multi-routing-engine-results;
         }
       }
     }
   }
   rpc get-services-match-policies {
     description "Show match-policy information";
     input {
       leaf service-set {
         description "Name of service set";
         type string;
       }
       leaf source-ip {
         description "Source address";
         type jt:ipprefix;
       }
       leaf source-port {
         description "Source port to use as match";
         type union {
           type uint16;
           type string {
             pattern "<.*>|$.*";
           }
         }
       }
       leaf destination-ip {
         description "Destination address";
         type jt:ipprefix;
       }
       leaf destination-port {
         description "Destination port to use as match";
         type union {
           type uint16;
           type string {
             pattern "<.*>|$.*";
           }
         }
       }
       leaf protocol {
         description "IP protocol name or number";
         type string;
       }
       leaf result-count {
         description "The number of policy matches to display";
         type union {
           type uint16;
           type string {
             pattern "<.*>|$.*";
           }
         }
       }
       leaf match-direction {
         description "Match direction";
         type enumeration {
           enum "input" {
             description "Direction input";
           }
           enum "output" {
             description "Direction output";
           }
         }
       }
     }
     output {
       choice output_c {
         case output-tag {
           leaf output {
             type string;
           }
         }
         case actual-tag {
           anyxml services-match-policies-information;
         }
         case multichassis-tag {
           anyxml multi-routing-engine-results;
         }
       }
     }
   }
   rpc get-service-nat-pool-information {
     description "Show NAT pools information";
     input {
       leaf pool-name {
         description "Name of pool";
         type string;
       }
       leaf display {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml service-nat-pool-information;
         }
         case multichassis-tag {
           anyxml multi-routing-engine-results;
         }
       }
     }
   }
   rpc get-service-detnat-information {
     description "Show deterministic NAT internal-host information";
     input {
       leaf nat-address {
         description "NAT address";
         type string;
         mandatory true;
       }
       leaf nat-port {
         description "NAT port";
         type string;
         mandatory true;
       }
     }
     output {
       choice output_c {
         case output-tag {
           leaf output {
             type string;
           }
         }
         case actual-tag {
           anyxml service-detnat-information;
         }
         case multichassis-tag {
           anyxml multi-routing-engine-results;
         }
       }
     }
   }
   rpc get-service-detnat-pb-information {
     description "Show deterministic NAT port blocks assigned to internal-host";
     input {
       leaf internal-address {
         description "Subscriber IP address";
         type string;
         mandatory true;
       }
     }
     output {
       choice output_c {
         case output-tag {
           leaf output {
             type string;
           }
         }
         case actual-tag {
           anyxml service-detnat-information;
         }
         case multichassis-tag {
           anyxml multi-routing-engine-results;
         }
       }
     }
   }
   rpc get-service-nat-ipv6-multicast-information {
     description "Show interfaces with IPv6 multicast filter";
     output {
       choice output_c {
         case output-tag {
           leaf output {
             type string;
           }
         }
         case actual-tag {
           anyxml service-nat-ipv6-multicast-interfaces-information;
         }
         case multichassis-tag {
           anyxml multi-routing-engine-results;
         }
       }
     }
   }
   rpc get-service-nat-mapping-address-pooling-paired {
     description "Show NAT Address Pooling Paired mapping";
     input {
       leaf private {
         description "Private IP/IPv6 prefix to use as filter";
         type string;
       }
       leaf public {
         description "Public IP/IPv6 prefix to use as filter";
         type string;
       }
     }
     output {
       choice output_c {
         case output-tag {
           leaf output {
             type string;
           }
         }
         case actual-tag {
           anyxml service-nat-mapping-address-pooling-paired;
         }
         case multichassis-tag {
           anyxml multi-routing-engine-results;
         }
       }
     }
   }
   rpc get-service-nat-mapping-endpoint-independent {
     description "Show NAT Endpoint Independent mapping";
     input {
       leaf private {
         description "Private IP/IPv6 prefix to use as filter";
         type string;
       }
       leaf public {
         description "Public IP prefix to use as filter";
         type string;
       }
     }
     output {
       choice output_c {
         case output-tag {
           leaf output {
             type string;
           }
         }
         case actual-tag {
           anyxml service-nat-mapping-endpoint-independent;
         }
         case multichassis-tag {
           anyxml multi-routing-engine-results;
         }
       }
     }
   }
   rpc get-service-nat-mapping-pcp {
     description "Show NAT PCP mapping";
     output {
       choice output_c {
         case output-tag {
           leaf output {
             type string;
           }
         }
         case actual-tag {
           anyxml service-nat-mapping-pcp;
         }
         case multichassis-tag {
           anyxml multi-routing-engine-results;
         }
       }
     }
   }
   rpc get-service-nat-mapping-summary {
     description "Show NAT mapping entries count";
     output {
       choice output_c {
         case output-tag {
           leaf output {
             type string;
           }
         }
         case actual-tag {
           anyxml service-nat-mapping-summary;
         }
         case multichassis-tag {
           anyxml multi-routing-engine-results;
         }
       }
     }
   }
   rpc get-service-nat-mapping-brief {
     description "Show NAT mapping brief";
     input {
       leaf pool-name {
         description "Name of pool";
         type string;
       }
     }
     output {
       choice output_c {
         case output-tag {
           leaf output {
             type string;
           }
         }
         case actual-tag {
           anyxml service-nat-mapping-address-pooling-paired;
         }
         case multichassis-tag {
           anyxml multi-routing-engine-results;
         }
       }
     }
   }
   rpc get-service-nat-mapping-detail {
     description "Show NAT mapping detail";
     input {
       leaf pool-name {
         description "Name of pool";
         type string;
       }
     }
     output {
       choice output_c {
         case output-tag {
           leaf output {
             type string;
           }
         }
         case actual-tag {
           anyxml service-nat-mapping-endpoint-independent;
         }
         case multichassis-tag {
           anyxml multi-routing-engine-results;
         }
       }
     }
   }
   rpc get-service-nat-mapping-nptv6 {
     description "Show nptv6 translated address";
     input {
       leaf address {
         description "IPV6 Address";
         type jt:ipv6addr;
         mandatory true;
       }
       leaf direction {
         type enumeration {
           enum "internal" {
             description "Internal-address";
           }
           enum "external" {
             description "External-address";
           }
         }
         mandatory true;
       }
     }
     output {
       choice output_c {
         case output-tag {
           leaf output {
             type string;
           }
         }
         case actual-tag {
           anyxml service-nat-mapping-nptv6;
         }
         case multichassis-tag {
           anyxml multi-routing-engine-results;
         }
       }
     }
   }
   rpc get-service-nat-statistics-information {
     description "Show NAT statistics";
     input {
       leaf interface {
         description "Name of extension provider interface";
         type string;
       }
     }
     output {
       choice output_c {
         case output-tag {
           leaf output {
             type string;
           }
         }
         case actual-tag {
           anyxml service-nat-statistics-information;
         }
         case multichassis-tag {
           anyxml multi-routing-engine-results;
         }
       }
     }
   }
   rpc get-service-cos-statistics-information {
     description "Show statistics";
     input {
       leaf display {
         default "brief";
         type enumeration {
           enum "brief" {
             description "Display brief output (default)";
           }
           enum "detail" {
             description "Display detailed output";
           }
           enum "extensive" {
             description "Display extensive output";
           }
           enum "summary" {
             description "Display summary output";
           }
         }
       }
       leaf service-set {
         description "Name of service set";
         type string;
       }
       leaf interface {
         description "Name of adaptive services interface";
         type string;
       }
     }
     output {
       choice output_c {
         case output-tag {
           leaf output {
             type string;
           }
         }
         case actual-tag {
           anyxml service-cos-statistics-information;
         }
         case multichassis-tag {
           anyxml multi-routing-engine-results;
         }
       }
     }
   }
   rpc get-service-cos-diffserv-statistics {
     description "Show Diffserv marking statistics";
     input {
       leaf display {
         default "brief";
         type enumeration {
           enum "brief" {
             description "Display brief output (default)";
           }
           enum "detail" {
             description "Display detailed output";
           }
           enum "extensive" {
             description "Display extensive output";
           }
           enum "summary" {
             description "Display summary output";
           }
         }
       }
     }
     output {
       choice output_c {
         case output-tag {
           leaf output {
             type string;
           }
         }
         case actual-tag {
           anyxml service-cos-diffserv-statistics;
         }
         case multichassis-tag {
           anyxml multi-routing-engine-results;
         }
       }
     }
   }
   rpc get-service-cos-forwarding-class-statistics {
     description "Show forwarding Class statistics";
     input {
       leaf display {
         default "brief";
         type enumeration {
           enum "brief" {
             description "Display brief output (default)";
           }
           enum "detail" {
             description "Display detailed output";
           }
           enum "extensive" {
             description "Display extensive output";
           }
           enum "summary" {
             description "Display summary output";
           }
         }
       }
     }
     output {
       choice output_c {
         case output-tag {
           leaf output {
             type string;
           }
         }
         case actual-tag {
           anyxml service-cos-forwarding-class-statistics;
         }
         case multichassis-tag {
           anyxml multi-routing-engine-results;
         }
       }
     }
   }
   rpc get-service-hcm-statistics-information {
     description "Show hcm statistics";
     input {
       leaf rule {
         description "Name of HCM tag rule";
         type string;
       }
     }
     output {
       choice output_c {
         case output-tag {
           leaf output {
             type string;
           }
         }
         case actual-tag {
           anyxml service-hcm-statistics-information;
         }
         case multichassis-tag {
           anyxml multi-routing-engine-results;
         }
       }
     }
   }
   rpc get-service-hcm-pic-statistics-information {
     description "Show hcm pic statistics";
     input {
       leaf interface {
         description "Name of extension provider interface";
         type string;
       }
     }
     output {
       choice output_c {
         case output-tag {
           leaf output {
             type string;
           }
         }
         case actual-tag {
           anyxml service-hcm-pic-statistics-information;
         }
         case multichassis-tag {
           anyxml multi-routing-engine-results;
         }
       }
     }
   }
   rpc get-service-mss-sessions-information {
     description "Show mobile subscriber data sessions";
     input {
       leaf imsi {
         description "IMSI of subscriber";
         type string {
           length "5 .. 15";
         }
       }
     }
     output {
       choice output_c {
         case output-tag {
           leaf output {
             type string;
           }
         }
         case actual-tag {
           anyxml service-mss-sessions-information;
         }
         case multichassis-tag {
           anyxml multi-routing-engine-results;
         }
       }
     }
   }
   rpc get-service-hcm-sessions-stats {
     description "Show hcm session statistics";
     input {
       leaf imsi {
         description "IMSI of subscriber";
         type string {
           length "5 .. 15";
         }
         mandatory true;
       }
     }
     output {
       choice output_c {
         case output-tag {
           leaf output {
             type string;
           }
         }
         case actual-tag {
           anyxml service-hcm-sessions-stats;
         }
         case multichassis-tag {
           anyxml multi-routing-engine-results;
         }
       }
     }
   }
   rpc get-service-tdf-sessions-information {
     description "Show traffic-detection-function subscriber data sessions";
     input {
       leaf routing-instance {
         description "Name of routing instance";
         type string;
         mandatory true;
       }
       leaf ipv4-address {
         description "Show sessions for matching IPv4 address";
         type string;
       }
       leaf ipv6-address {
         description "Show sessions for matching IPv6 address";
         type string;
       }
       leaf subscriber-name {
         description "Show sessions for matching Subscriber name";
         type string;
       }
     }
     output {
       choice output_c {
         case output-tag {
           leaf output {
             type string;
           }
         }
         case actual-tag {
           anyxml service-tdf-sessions-information;
         }
         case multichassis-tag {
           anyxml multi-routing-engine-results;
         }
       }
     }
   }
   rpc get-service-tdf-hcm-sessions-stats {
     description "Show hcm session statistics";
     input {
       leaf routing-instance {
         description "Name of routing instance";
         type string;
         mandatory true;
       }
       leaf ipv4-address {
         description "Show sessions for matching IPv4 address";
         type string;
       }
       leaf ipv6-address {
         description "Show sessions for matching IPv6 address";
         type string;
       }
       leaf subscriber-name {
         description "Show sessions for matching Subscriber name";
         type string;
       }
     }
     output {
       choice output_c {
         case output-tag {
           leaf output {
             type string;
           }
         }
         case actual-tag {
           anyxml service-tdf-hcm-sessions-stats;
         }
         case multichassis-tag {
           anyxml multi-routing-engine-results;
         }
       }
     }
   }
   rpc get-service-pgcp-flow-table-information {
     description "Show PGCP flow table entries";
     output {
       choice output_c {
         case output-tag {
           leaf output {
             type string;
           }
         }
         case actual-tag {
           anyxml service-pgcp-flow-table-information;
         }
         case multichassis-tag {
           anyxml multi-routing-engine-results;
         }
       }
     }
   }
   rpc get-service-pgcp-flow-table-information-gateway {
     description "Show packet-gateway-control-protocol information for gateway";
     input {
       leaf gateway-name {
         description "Gateway name";
         type string;
         mandatory true;
       }
       leaf gate-id {
         description "Gate id";
         type union {
           type uint64;
           type string {
             pattern "<.*>|$.*";
           }
         }
       }
       leaf service-set {
         description "Name of service set";
         type string;
       }
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf source-routing-instance {
         description "Source routing-instance";
         type string;
       }
       leaf destination-routing-instance {
         description "Destination routing-instance";
         type string;
       }
       leaf protocol {
         description "IP protocol type to use as filter";
         type string;
       }
       leaf get-service-pgcp-flow-count-information {
         description "Show count of matching entries";
         type empty;
       }
       leaf level {
         default "brief";
         type enumeration {
           enum "brief" {
             description "Display brief output";
           }
           enum "extensive" {
             description "Display extensive output";
           }
         }
       }
       leaf backup-data-pic {
         description "Show flows table by querying the backup Data-PIC";
         type empty;
       }
       leaf redundancy-option {
         default "master";
         type enumeration {
           enum "master" {
             description "Query the master RE or ms-pic (default)";
           }
           enum "backup" {
             description "Query the backup ms-pic";
           }
         }
       }
     }
     output {
       choice output_c {
         case output-tag {
           leaf output {
             type string;
           }
         }
         case actual-tag {
           anyxml service-pgcp-flow-table-gateway-information;
         }
         case multichassis-tag {
           anyxml multi-routing-engine-results;
         }
       }
     }
   }
   rpc get-service-pgcp-conversation-information {
     description "Show PGCP conversations";
     output {
       choice output_c {
         case output-tag {
           leaf output {
             type string;
           }
         }
         case actual-tag {
           anyxml service-pgcp-conversation-information;
         }
         case multichassis-tag {
           anyxml multi-routing-engine-results;
         }
       }
     }
   }
   rpc get-service-pgcp-conversation-information-gateway {
     description "Show PGCP conversations for gateway";
     input {
       leaf gateway-name {
         description "Gateway name";
         type string;
         mandatory true;
       }
       leaf service-set {
         description "Name of service set";
         type string;
       }
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf source-routing-instance {
         description "Source routing-instance";
         type string;
       }
       leaf destination-routing-instance {
         description "Destination routing-instance";
         type string;
       }
       leaf protocol {
         description "IP protocol type to use as filter";
         type string;
       }
       leaf level {
         default "brief";
         type enumeration {
           enum "brief" {
             description "Display brief output";
           }
           enum "extensive" {
             description "Display extensive output";
           }
         }
       }
       leaf backup-data-pic {
         description "Show conversations information by querying the backup Data-PIC";
         type empty;
       }
       leaf redundancy-option {
         default "master";
         type enumeration {
           enum "master" {
             description "Query the master RE or ms-pic (default)";
           }
           enum "backup" {
             description "Query the backup ms-pic";
           }
         }
       }
     }
     output {
       choice output_c {
         case output-tag {
           leaf output {
             type string;
           }
         }
         case actual-tag {
           anyxml service-pgcp-conversation-gateway-information;
         }
         case multichassis-tag {
           anyxml multi-routing-engine-results;
         }
       }
     }
   }
   rpc get-pgcpd-active-configuration {
     description "Show pgcpd active-configuration";
     output {
       choice output_c {
         case output-tag {
           leaf output {
             type string;
           }
         }
         case actual-tag {
           anyxml pgcpd-active-configuration;
         }
         case multichassis-tag {
           anyxml multi-routing-engine-results;
         }
       }
     }
   }
   rpc get-service-pgcp-active-configuration-gateway {
     description "Show gateway active configuration";
     input {
       leaf gateway-name {
         description "Gateway name";
         type string;
         mandatory true;
       }
       leaf redundancy-option {
         default "master";
         type enumeration {
           enum "master" {
             description "Query the master RE or ms-pic (default)";
           }
           enum "backup" {
             description "Query the backup ms-pic";
           }
         }
       }
     }
     output {
       choice output_c {
         case output-tag {
           leaf output {
             type string;
           }
         }
         case actual-tag {
           anyxml service-pgcp-active-configuration-gateway;
         }
         case multichassis-tag {
           anyxml multi-routing-engine-results;
         }
       }
     }
   }
   rpc get-service-pgcp-statistics {
     description "Show pgcpd statistics";
     output {
       choice output_c {
         case output-tag {
           leaf output {
             type string;
           }
         }
         case actual-tag {
           anyxml service-pgcp-statistics;
         }
         case multichassis-tag {
           anyxml multi-routing-engine-results;
         }
       }
     }
   }
   rpc get-service-pgcp-statistics-gateway {
     description "Show gateway statistics";
     input {
       leaf gateway-name {
         description "Gateway name";
         type string;
         mandatory true;
       }
       leaf display {
         default "brief";
         type enumeration {
           enum "brief" {
             description "Display brief output (default)";
           }
           enum "extensive" {
             description "Display extensive output";
           }
         }
       }
       leaf redundancy-option {
         default "master";
         type enumeration {
           enum "master" {
             description "Query the master RE or ms-pic (default)";
           }
           enum "backup" {
             description "Query the backup ms-pic";
           }
         }
       }
     }
     output {
       choice output_c {
         case output-tag {
           leaf output {
             type string;
           }
         }
         case actual-tag {
           anyxml service-pgcp-statistics-gateway;
         }
         case multichassis-tag {
           anyxml multi-routing-engine-results;
         }
       }
     }
   }
   rpc get-service-pgcp-terminations {
     description "Show list of terminations";
     output {
       choice output_c {
         case output-tag {
           leaf output {
             type string;
           }
         }
         case actual-tag {
           anyxml service-pgcp-terminations;
         }
         case multichassis-tag {
           anyxml multi-routing-engine-results;
         }
       }
     }
   }
   rpc get-service-pgcp-terminations-gateway {
     description "Show list of terminations for gateway";
     input {
       leaf gateway-name {
         description "Gateway name";
         type string;
         mandatory true;
       }
       leaf termination-prefix {
         description "Termination-prefix to use as filter, default * (all)";
         type string;
       }
       leaf display {
         default "brief";
         type enumeration {
           enum "h248" {
             description "Display H248 output format";
           }
           enum "brief" {
             description "Display brief output (default)";
           }
           enum "count" {
             description "Show count of matching entries";
           }
         }
       }
       leaf redundancy-option {
         default "master";
         type enumeration {
           enum "master" {
             description "Query the master RE or ms-pic (default)";
           }
           enum "backup" {
             description "Query the backup ms-pic";
           }
         }
       }
     }
     output {
       choice output_c {
         case output-tag {
           leaf output {
             type string;
           }
         }
         case actual-tag {
           anyxml service-pgcp-terminations-gateway;
         }
         case multichassis-tag {
           anyxml multi-routing-engine-results;
         }
       }
     }
   }
   rpc get-service-pgcp-gates {
     description "Show list of gates";
     output {
       choice output_c {
         case output-tag {
           leaf output {
             type string;
           }
         }
         case actual-tag {
           anyxml service-pgcp-gates;
         }
         case multichassis-tag {
           anyxml multi-routing-engine-results;
         }
       }
     }
   }
   rpc get-service-pgcp-gates-gateway {
     description "Show all gates for gateway";
     input {
       leaf gateway-name {
         description "Gateway name";
         type string;
         mandatory true;
       }
       leaf display {
         default "brief";
         type enumeration {
           enum "extensive" {
             description "Display extensive output";
           }
           enum "brief" {
             description "Display brief output (default)";
           }
           enum "count" {
             description "Show count of matching entries";
           }
         }
       }
       leaf source-routing-instance {
         description "Source routing-instance";
         type string;
       }
       leaf destination-routing-instance {
         description "Destination routing-instance";
         type string;
       }
       leaf redundancy-option {
         default "master";
         type enumeration {
           enum "master" {
             description "Query the master RE or ms-pic (default)";
           }
           enum "backup" {
             description "Query the backup ms-pic";
           }
         }
       }
     }
     output {
       choice output_c {
         case output-tag {
           leaf output {
             type string;
           }
         }
         case actual-tag {
           anyxml service-pgcp-gates-gateway;
         }
         case multichassis-tag {
           anyxml multi-routing-engine-results;
         }
       }
     }
   }
   rpc get-service-pgcp-gate {
     description "Show gate according to gate-id";
     output {
       choice output_c {
         case output-tag {
           leaf output {
             type string;
           }
         }
         case actual-tag {
           anyxml service-pgcp-gate;
         }
         case multichassis-tag {
           anyxml multi-routing-engine-results;
         }
       }
     }
   }
   rpc get-service-pgcp-gate-gateway {
     description "Show gate for gateway";
     input {
       leaf gateway-name {
         description "Gateway name";
         type string;
         mandatory true;
       }
       leaf gate-id {
         description "Gate id";
         type union {
           type uint64;
           type string {
             pattern "<.*>|$.*";
           }
         }
         mandatory true;
       }
       leaf display {
         default "brief";
         type enumeration {
           enum "extensive" {
             description "Display extensive output";
           }
           enum "brief" {
             description "Display brief output (default)";
           }
           enum "statistics" {
             description "Display statistics for gate";
           }
           enum "session-mirroring" {
             description "Display session mirroring for gate";
           }
         }
       }
       leaf redundancy-option {
         default "master";
         type enumeration {
           enum "master" {
             description "Query the master RE or ms-pic (default)";
           }
           enum "backup" {
             description "Query the backup ms-pic";
           }
         }
       }
     }
     output {
       choice output_c {
         case output-tag {
           leaf output {
             type string;
           }
         }
         case actual-tag {
           anyxml service-pgcp-gate-gateway;
         }
         case multichassis-tag {
           anyxml multi-routing-engine-results;
         }
       }
     }
   }
   rpc get-services-pgcpd-root-termination {
     description "Show root termination h248 information";
     output {
       choice output_c {
         case output-tag {
           leaf output {
             type string;
           }
         }
         case actual-tag {
           anyxml services-pgcpd-root-termination;
         }
         case multichassis-tag {
           anyxml multi-routing-engine-results;
         }
       }
     }
   }
   rpc get-services-pgcpd-root-termination-gateway {
     description "Show root termination h248 information for gateway";
     input {
       leaf gateway-name {
         description "Gateway name";
         type string;
         mandatory true;
       }
       leaf redundancy-option {
         default "master";
         type enumeration {
           enum "master" {
             description "Query the master RE or ms-pic (default)";
           }
           enum "backup" {
             description "Query the backup ms-pic";
           }
         }
       }
     }
     output {
       choice output_c {
         case output-tag {
           leaf output {
             type string;
           }
         }
         case actual-tag {
           anyxml services-pgcpd-root-termination-gateway;
         }
         case multichassis-tag {
           anyxml multi-routing-engine-results;
         }
       }
     }
   }
   rpc get-service-border-signaling-gateway-statistics-calls {
     description "Show border signaling gateway calls statistics";
     output {
       choice output_c {
         case output-tag {
           leaf output {
             type string;
           }
         }
         case actual-tag {
           anyxml bsg-statistics-calls-details;
         }
         case multichassis-tag {
           anyxml multi-routing-engine-results;
         }
       }
     }
   }
   rpc get-service-border-signaling-gateway-statistics-calls-by-sp {
     description "Show border signaling gateway calls statistics grouped by service-point";
     input {
       leaf service-point-name {
         description "Service point name or prefix";
         type string;
       }
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       choice output_c {
         case output-tag {
           leaf output {
             type string;
           }
         }
         case actual-tag {
           anyxml bsg-statistics-calls;
         }
         case multichassis-tag {
           anyxml multi-routing-engine-results;
         }
       }
     }
   }
   rpc get-service-border-signaling-gateway-statistics-calls-by-server {
     description "Show border signaling gateway calls statistics grouped by server";
     input {
       leaf server-name {
         description "Server name";
         type string;
       }
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       choice output_c {
         case output-tag {
           leaf output {
             type string;
           }
         }
         case actual-tag {
           anyxml bsg-statistics-calls;
         }
         case multichassis-tag {
           anyxml multi-routing-engine-results;
         }
       }
     }
   }
   rpc get-service-border-signaling-gateway-statistics-calls-duration-by-sp {
     description "Show border signaling gateway calls duration statistics grouped by service-point";
     input {
       leaf service-point-name {
         description "Service point name or prefix";
         type string;
       }
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       choice output_c {
         case output-tag {
           leaf output {
             type string;
           }
         }
         case actual-tag {
           anyxml bsg-calls-duration-detals;
         }
         case multichassis-tag {
           anyxml multi-routing-engine-results;
         }
       }
     }
   }
   rpc get-service-border-signaling-gateway-statistics-calls-duration-by-server {
     description "Show border signaling gateway calls duration statistics grouped by server";
     input {
       leaf server-name {
         description "Server name";
         type string;
       }
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       choice output_c {
         case output-tag {
           leaf output {
             type string;
           }
         }
         case actual-tag {
           anyxml bsg-calls-duration-detals;
         }
         case multichassis-tag {
           anyxml multi-routing-engine-results;
         }
       }
     }
   }
   rpc get-service-border-signaling-gateway-statistics-failed-calls-by-sp {
     description "Show border signaling gateway failed calls statistics grouped by service-point";
     input {
       leaf service-point-name {
         description "Service point name or prefix";
         type string;
       }
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       choice output_c {
         case output-tag {
           leaf output {
             type string;
           }
         }
         case actual-tag {
           anyxml bsg-statistics-calls-failed-details;
         }
         case multichassis-tag {
           anyxml multi-routing-engine-results;
         }
       }
     }
   }
   rpc get-service-border-signaling-gateway-statistics-failed-calls-by-server {
     description "Show border signaling gateway failed calls statistics grouped by server";
     input {
       leaf server-name {
         description "Server name";
         type string;
       }
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       choice output_c {
         case output-tag {
           leaf output {
             type string;
           }
         }
         case actual-tag {
           anyxml bsg-statistics-calls-failed-details;
         }
         case multichassis-tag {
           anyxml multi-routing-engine-results;
         }
       }
     }
   }
   rpc get-service-bsg-denied-messages {
     description "Show information about dropped messages";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       choice output_c {
         case output-tag {
           leaf output {
             type string;
           }
         }
         case actual-tag {
           anyxml bsg-statistics-denied-messages-details;
         }
         case multichassis-tag {
           anyxml multi-routing-engine-results;
         }
       }
     }
   }
   rpc get-service-border-signaling-gateway-statistics-admission-control {
     description "Show border signaling gateway admission control profile statistics statistics";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       choice output_c {
         case output-tag {
           leaf output {
             type string;
           }
         }
         case actual-tag {
           anyxml bsg-statistics-admission-control;
         }
         case multichassis-tag {
           anyxml multi-routing-engine-results;
         }
       }
     }
   }
   rpc get-service-border-signaling-gateway-information-by-request-uri {
     description "Show border signaling gateway information by request uri";
     input {
       leaf gateway {
         description "Name of border signaling gateway";
         type string;
         mandatory true;
       }
       leaf uri {
         description "URI";
         type string;
       }
       leaf display {
         default "brief";
         type enumeration {
           enum "brief" {
             description "Display brief output (default)";
           }
           enum "summary" {
             description "Display summary output";
           }
           enum "detail" {
             description "Display detailed output";
           }
         }
       }
       leaf redundancy-option {
         default "master";
         type enumeration {
           enum "master" {
             description "Query the master border signaling gateway (default)";
           }
           enum "backup" {
             description "Query the backup border signaling gateway";
           }
         }
       }
     }
     output {
       choice output_c {
         case output-tag {
           leaf output {
             type string;
           }
         }
         case actual-tag {
           anyxml bsg-information-details;
         }
         case multichassis-tag {
           anyxml multi-routing-engine-results;
         }
       }
     }
   }
   rpc get-service-border-signaling-gateway-information-by-contact {
     description "Show border signaling gateway information by contact";
     input {
       leaf gateway {
         description "Name of border signaling gateway";
         type string;
         mandatory true;
       }
       leaf contact {
         description "Contact";
         type string;
       }
       leaf display {
         default "brief";
         type enumeration {
           enum "brief" {
             description "Display brief output (default)";
           }
           enum "summary" {
             description "Display summary output";
           }
           enum "detail" {
             description "Display detailed output";
           }
         }
       }
       leaf redundancy-option {
         default "master";
         type enumeration {
           enum "master" {
             description "Query the master border signaling gateway (default)";
           }
           enum "backup" {
             description "Query the backup border signaling gateway";
           }
         }
       }
     }
     output {
       choice output_c {
         case output-tag {
           leaf output {
             type string;
           }
         }
         case actual-tag {
           anyxml bsg-information-details;
         }
         case multichassis-tag {
           anyxml multi-routing-engine-results;
         }
       }
     }
   }
   rpc get-service-bsg-information-by-call-context-id {
     description "Show border signaling gateway information by call context ID";
     input {
       leaf gateway {
         description "Name of border signaling gateway";
         type string;
         mandatory true;
       }
       leaf context-id {
         description "Call context ID";
         type union {
           type uint32;
           type string {
             pattern "<.*>|$.*";
           }
         }
       }
       leaf display {
         default "brief";
         type enumeration {
           enum "brief" {
             description "Display brief output (default)";
           }
           enum "detail" {
             description "Display detailed output";
           }
         }
       }
       leaf redundancy-option {
         default "master";
         type enumeration {
           enum "master" {
             description "Query the master border signaling gateway (default)";
           }
           enum "backup" {
             description "Query the backup border signaling gateway";
           }
         }
       }
     }
     output {
       choice output_c {
         case output-tag {
           leaf output {
             type string;
           }
         }
         case actual-tag {
           anyxml bsg-information-details;
         }
         case multichassis-tag {
           anyxml multi-routing-engine-results;
         }
       }
     }
   }
   rpc get-service-bsg-status-information {
     description "Show border signaling gateway status information";
     input {
       leaf gateway {
         description "Name of border signaling gateway";
         type string;
         mandatory true;
       }
       leaf display {
         default "brief";
         type enumeration {
           enum "brief" {
             description "Display brief output (default)";
           }
           enum "detail" {
             description "Display detailed output";
           }
         }
       }
       leaf redundancy-option {
         default "master";
         type enumeration {
           enum "master" {
             description "Query the master border signaling gateway (default)";
           }
           enum "backup" {
             description "Query the backup border signaling gateway";
           }
         }
       }
     }
     output {
       choice output_c {
         case output-tag {
           leaf output {
             type string;
           }
         }
         case actual-tag {
           anyxml bsg-status-information;
         }
         case multichassis-tag {
           anyxml multi-routing-engine-results;
         }
       }
     }
   }
   rpc get-border-signaling-gateway-name-resolution-cache-by-fqdn {
     description "Show records for the Fully Qualified Domain Name";
     input {
       leaf fqdn {
         description "Fully Qualified Domain Name";
         type string;
         mandatory true;
       }
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       choice output_c {
         case output-tag {
           leaf output {
             type string;
           }
         }
         case actual-tag {
           anyxml bsg-name-resolution-cache-information;
         }
         case multichassis-tag {
           anyxml multi-routing-engine-results;
         }
       }
     }
   }
   rpc get-service-border-signaling-gateway-name-resolution-cache-all {
     description "Show contents of the cache";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       choice output_c {
         case output-tag {
           leaf output {
             type string;
           }
         }
         case actual-tag {
           anyxml bsg-name-resolution-cache-information;
         }
         case multichassis-tag {
           anyxml multi-routing-engine-results;
         }
       }
     }
   }
   rpc get-service-border-signaling-gateway-routing-blacklist {
     description "Show border signaling gateway servers blacklist content";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       choice output_c {
         case output-tag {
           leaf output {
             type string;
           }
         }
         case actual-tag {
           anyxml bsg-routing-blacklist;
         }
         case multichassis-tag {
           anyxml multi-routing-engine-results;
         }
       }
     }
   }
   rpc get-service-bsg-registrations {
     description "Show border signaling gateway registrations statistics";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       choice output_c {
         case output-tag {
           leaf output {
             type string;
           }
         }
         case actual-tag {
           anyxml bsg-registrations;
         }
         case multichassis-tag {
           anyxml multi-routing-engine-results;
         }
       }
     }
   }
   rpc get-service-bsg-registrations-statistics {
     description "Show registration statistics";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       choice output_c {
         case output-tag {
           leaf output {
             type string;
           }
         }
         case actual-tag {
           anyxml bsg-registrations;
         }
         case multichassis-tag {
           anyxml multi-routing-engine-results;
         }
       }
     }
   }
   rpc get-service-bsg-registrations-realm-statistics {
     description "Realm statistics";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
       leaf realm-name {
         type string;
       }
     }
     output {
       choice output_c {
         case output-tag {
           leaf output {
             type string;
           }
         }
         case actual-tag {
           anyxml bsg-registrations-realm;
         }
         case multichassis-tag {
           anyxml multi-routing-engine-results;
         }
       }
     }
   }
   rpc get-service-border-signaling-gateway-address-of-record {
     description "Show border signaling gateway address of record";
     output {
       choice output_c {
         case output-tag {
           leaf output {
             type string;
           }
         }
         case actual-tag {
           anyxml bsg-address-of-records;
         }
         case multichassis-tag {
           anyxml multi-routing-engine-results;
         }
       }
     }
   }
   rpc get-service-border-signaling-gateway-address-of-record-bindings {
     description "Show address of record bindings";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
       leaf address-of-record {
         description "Address of record name";
         type string;
       }
       leaf detail {
         description "Detail mode";
         type empty;
       }
     }
     output {
       choice output_c {
         case output-tag {
           leaf output {
             type string;
           }
         }
         case actual-tag {
           anyxml bsg-address-of-record-bindings;
         }
         case multichassis-tag {
           anyxml multi-routing-engine-results;
         }
       }
     }
   }
   rpc get-service-border-signaling-gateway-charging-status {
     description "Show border signaling gateway accounting status";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       choice output_c {
         case output-tag {
           leaf output {
             type string;
           }
         }
         case actual-tag {
           anyxml bsg-charging-status;
         }
         case multichassis-tag {
           anyxml multi-routing-engine-results;
         }
       }
     }
   }
   rpc get-service-border-signaling-gateway-charging-statistics {
     description "Show border signaling gateway accounting statistics";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       choice output_c {
         case output-tag {
           leaf output {
             type string;
           }
         }
         case actual-tag {
           anyxml bsg-charging-statistics;
         }
         case multichassis-tag {
           anyxml multi-routing-engine-results;
         }
       }
     }
   }
   rpc get-service-msp-flow-table-information {
     description "Show flow table entries";
     input {
       leaf all {
         description "Display all the entries";
         type empty;
       }
       leaf limit {
         description "Maximum number of entries to display";
         type union {
           type string {
             pattern "<.*>|$.*";
           }
           type uint32 {
             range "1 .. 4294967295";
           }
         }
       }
       leaf display {
         default "brief";
         type enumeration {
           enum "extensive" {
             description "Display extensive output";
           }
           enum "brief" {
             description "Display brief output (default)";
           }
           enum "terse" {
             description "Display terse output";
           }
         }
       }
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf protocol {
         description "IP protocol type to use as filter";
         type string;
       }
       leaf service-set {
         description "Name of service set";
         type string;
       }
       leaf interface {
         description "Name of extension provider interface";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
         }
       }
       leaf get-service-sfw-flow-count-information {
         description "Show count of matching entries";
         type empty;
       }
     }
     output {
       choice output_c {
         case output-tag {
           leaf output {
             type string;
           }
         }
         case actual-tag {
           anyxml service-sfw-flow-table-information;
         }
         case multichassis-tag {
           anyxml multi-routing-engine-results;
         }
       }
     }
   }
   rpc get-msp-session-table {
     description "Show session table entries";
     input {
       leaf limit {
         description "Maximum number of entries to display";
         type union {
           type string {
             pattern "<.*>|$.*";
           }
           type uint32 {
             range "1 .. 4294967295";
           }
         }
       }
       leaf display {
         default "brief";
         type enumeration {
           enum "extensive" {
             description "Display extensive output";
           }
           enum "brief" {
             description "Display brief output (default)";
           }
         }
       }
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf protocol {
         description "IP protocol type to use as filter";
         type string;
       }
       leaf service-set {
         description "Name of service set";
         type string;
       }
       leaf interface {
         description "Name of extension provider interface";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
         }
       }
     }
     output {
       choice output_c {
         case output-tag {
           leaf output {
             type string;
           }
         }
         case actual-tag {
           anyxml msp-session-table;
         }
         case multichassis-tag {
           anyxml multi-routing-engine-results;
         }
       }
     }
   }
   rpc get-service-msp-sess-count-information {
     description "Show count of matching entries";
     input {
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf protocol {
         description "IP protocol type to use as filter";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
         }
       }
       leaf service-set {
         description "Name of service set";
         type string;
       }
       leaf interface {
         description "Name of extension provider interface";
         type string;
       }
     }
     output {
       choice output_c {
         case output-tag {
           leaf output {
             type string;
           }
         }
         case actual-tag {
           anyxml service-msp-sess-count-information;
         }
         case multichassis-tag {
           anyxml multi-routing-engine-results;
         }
       }
     }
   }
   rpc show-service-msp-session-analysis-information {
     description "Show service sessions statistics";
     input {
       leaf interface {
         description "Name of extension provider interface";
         type string;
       }
     }
     output {
       choice output_c {
         case output-tag {
           leaf output {
             type string;
           }
         }
         case actual-tag {
           anyxml show-service-msp-session-analysis-information;
         }
         case multichassis-tag {
           anyxml multi-routing-engine-results;
         }
       }
     }
   }
   rpc get-services-sessions-utilization {
     description "Show session utilization statistics";
     input {
       leaf interface {
         description "Name of extension provider interface";
         type string;
       }
     }
     output {
       choice output_c {
         case output-tag {
           leaf output {
             type string;
           }
         }
         case actual-tag {
           anyxml services-sessions-utilization-information;
         }
         case multichassis-tag {
           anyxml multi-routing-engine-results;
         }
       }
     }
   }
   rpc get-services-sessions-tcp-log {
     description "Show services sessions tcp-log";
     input {
       leaf interface {
         description "Name of extension provider interface";
         type string;
       }
     }
     output {
       choice output_c {
         case output-tag {
           leaf output {
             type string;
           }
         }
         case actual-tag {
           anyxml services-sessions-tcp-log-information;
         }
         case multichassis-tag {
           anyxml multi-routing-engine-results;
         }
       }
     }
   }
   rpc get-service-msp-alg-conversation-information {
     description "Show alg conversations";
     input {
       leaf interface {
         description "Name of extension provider interface";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
         }
       }
       leaf display {
         default "brief";
         type enumeration {
           enum "extensive" {
             description "Display extensive output";
           }
           enum "brief" {
             description "Display brief output (default)";
           }
         }
       }
     }
     output {
       choice output_c {
         case output-tag {
           leaf output {
             type string;
           }
         }
         case actual-tag {
           anyxml service-msp-alg-conversation-information;
         }
         case multichassis-tag {
           anyxml multi-routing-engine-results;
         }
       }
     }
   }
   rpc get-service-msp-alg-stats-information {
     description "Show ALG Statistics";
     input {
       leaf interface {
         description "Name of extension provider interface";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
         }
       }
     }
     output {
       choice output_c {
         case output-tag {
           leaf output {
             type string;
           }
         }
         case actual-tag {
           anyxml service-msp-alg-stats-information;
         }
         case multichassis-tag {
           anyxml multi-routing-engine-results;
         }
       }
     }
   }
   rpc get-service-msp-alg-sip-globals-information {
     description "Show SIP ALG global configurations";
     input {
       leaf interface {
         description "Name of extension provider interface";
         type string;
       }
     }
     output {
       choice output_c {
         case output-tag {
           leaf output {
             type string;
           }
         }
         case actual-tag {
           anyxml service-msp-alg-sip-globals-information;
         }
         case multichassis-tag {
           anyxml multi-routing-engine-results;
         }
       }
     }
   }
   rpc get-service-ha-info {
     description "Show HA info and current status";
     input {
       leaf interface {
         description "Name of adaptive services interface";
         type string;
       }
       leaf level {
         default "brief";
         type enumeration {
           enum "brief" {
             description "Display brief output";
           }
           enum "detail" {
             description "Display detailed output";
           }
           enum "statistics" {
             description "Display statistics output";
           }
         }
       }
     }
     output {
       choice output_c {
         case output-tag {
           leaf output {
             type string;
           }
         }
         case actual-tag {
           anyxml service-ha-info;
         }
         case multichassis-tag {
           anyxml multi-routing-engine-results;
         }
       }
     }
   }
   rpc get-service-flow-analysis-information {
     description "Show flow table entries";
     input {
       leaf interface {
         description "Name of adaptive services interface";
         type string;
       }
     }
     output {
       choice output_c {
         case output-tag {
           leaf output {
             type string;
           }
         }
         case actual-tag {
           anyxml service-flow-analysis-information;
         }
         case multichassis-tag {
           anyxml multi-routing-engine-results;
         }
       }
     }
   }
   rpc get-service-subs-analysis-information {
     description "Show subscriber table entries";
     input {
       leaf interface {
         description "Name of adaptive services interface";
         type string;
       }
     }
     output {
       choice output_c {
         case output-tag {
           leaf output {
             type string;
           }
         }
         case actual-tag {
           anyxml service-subs-analysis-information;
         }
         case multichassis-tag {
           anyxml multi-routing-engine-results;
         }
       }
     }
   }
   rpc get-service-sfw-flow-table-information {
     description "Show flow table entries";
     input {
       leaf all {
         description "Display all the entries";
         type empty;
       }
       leaf limit {
         description "Maximum number of entries to display";
         type union {
           type string {
             pattern "<.*>|$.*";
           }
           type uint32 {
             range "1 .. 4294967295";
           }
         }
       }
       leaf display {
         default "brief";
         type enumeration {
           enum "extensive" {
             description "Display extensive output";
           }
           enum "brief" {
             description "Display brief output (default)";
           }
           enum "terse" {
             description "Display terse output";
           }
         }
       }
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf protocol {
         description "IP protocol type to use as filter";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
         }
       }
       leaf service-set {
         description "Name of service set";
         type string;
       }
       leaf interface {
         description "Name of adaptive services interface";
         type string;
       }
       leaf pgcp {
         description "Use pgcp flow type as filter";
         type empty;
       }
       leaf get-service-sfw-flow-count-information {
         description "Show count of matching entries";
         type empty;
       }
     }
     output {
       choice output_c {
         case output-tag {
           leaf output {
             type string;
           }
         }
         case actual-tag {
           anyxml service-sfw-flow-table-information;
         }
         case multichassis-tag {
           anyxml multi-routing-engine-results;
         }
       }
     }
   }
   rpc get-service-sfw-conversation-information {
     description "Show conversations";
     input {
       leaf all {
         description "Display all the entries";
         type empty;
       }
       leaf limit {
         description "Maximum number of entries to display";
         type union {
           type string {
             pattern "<.*>|$.*";
           }
           type uint32 {
             range "1 .. 4294967295";
           }
         }
       }
       leaf display {
         default "brief";
         type enumeration {
           enum "extensive" {
             description "Display extensive output";
           }
           enum "brief" {
             description "Display brief output (default)";
           }
           enum "terse" {
             description "Display terse output";
           }
         }
       }
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf protocol {
         description "IP protocol type to use as filter";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
         }
       }
       leaf service-set {
         description "Name of service set";
         type string;
       }
       leaf interface {
         description "Name of adaptive services interface";
         type string;
       }
       leaf pgcp {
         description "Use pgcp flow type as filter";
         type empty;
       }
     }
     output {
       choice output_c {
         case output-tag {
           leaf output {
             type string;
           }
         }
         case actual-tag {
           anyxml service-sfw-conversation-information;
         }
         case multichassis-tag {
           anyxml multi-routing-engine-results;
         }
       }
     }
   }
   rpc get-service-sfw-sip-call-information {
     description "Show SIP call information";
     input {
       leaf all {
         description "Display all the entries";
         type empty;
       }
       leaf limit {
         description "Maximum number of entries to display";
         type union {
           type string {
             pattern "<.*>|$.*";
           }
           type uint32 {
             range "1 .. 4294967295";
           }
         }
       }
       leaf display {
         default "brief";
         type enumeration {
           enum "extensive" {
             description "Display extensive output";
           }
           enum "brief" {
             description "Display brief output (default)";
           }
           enum "terse" {
             description "Display terse output";
           }
         }
       }
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf protocol {
         description "IP protocol type to use as filter";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
         }
       }
       leaf service-set {
         description "Name of service set";
         type string;
       }
       leaf interface {
         description "Name of adaptive services interface";
         type string;
       }
       leaf get-service-sfw-sip-call-count-information {
         description "Show count of matching entries";
         type empty;
       }
     }
     output {
       choice output_c {
         case output-tag {
           leaf output {
             type string;
           }
         }
         case actual-tag {
           anyxml service-sfw-sip-call-information;
         }
         case multichassis-tag {
           anyxml multi-routing-engine-results;
         }
       }
     }
   }
   rpc get-service-sfw-sip-register-information {
     description "Show SIP register information";
     input {
       leaf all {
         description "Display all the entries";
         type empty;
       }
       leaf limit {
         description "Maximum number of entries to display";
         type union {
           type string {
             pattern "<.*>|$.*";
           }
           type uint32 {
             range "1 .. 4294967295";
           }
         }
       }
       leaf display {
         default "brief";
         type enumeration {
           enum "extensive" {
             description "Display extensive output";
           }
           enum "brief" {
             description "Display brief output (default)";
           }
           enum "terse" {
             description "Display terse output";
           }
         }
       }
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf protocol {
         description "IP protocol type to use as filter";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
         }
       }
       leaf service-set {
         description "Name of service set";
         type string;
       }
       leaf interface {
         description "Name of adaptive services interface";
         type string;
       }
       leaf get-service-sfw-sip-register-count-information {
         description "Show count of matching entries";
         type empty;
       }
     }
     output {
       choice output_c {
         case output-tag {
           leaf output {
             type string;
           }
         }
         case actual-tag {
           anyxml service-sfw-sip-register-information;
         }
         case multichassis-tag {
           anyxml multi-routing-engine-results;
         }
       }
     }
   }
   rpc get-service-sfw-statistics-information {
     description "Show statistics";
     input {
       leaf display {
         default "brief";
         type enumeration {
           enum "brief" {
             description "Display brief output (default)";
           }
           enum "detail" {
             description "Display detailed output";
           }
           enum "extensive" {
             description "Display extensive output";
           }
           enum "summary" {
             description "Display summary output";
           }
         }
       }
       leaf service-set {
         description "Name of service set";
         type string;
       }
       leaf interface {
         description "Name of adaptive services interface";
         type string;
       }
     }
     output {
       choice output_c {
         case output-tag {
           leaf output {
             type string;
           }
         }
         case actual-tag {
           anyxml service-sfw-statistics-information;
         }
         case multichassis-tag {
           anyxml multi-routing-engine-results;
         }
       }
     }
   }
   rpc get-sfw-application-protocol-statistics {
     description "Application protocol type to use as filter";
     input {
       leaf protocol {
         description "Application protocol type to use as filter";
         type enumeration {
           enum "sip" {
             description "Session Initiation Protocol";
           }
         }
       }
     }
     output {
       choice output_c {
         case output-tag {
           leaf output {
             type string;
           }
         }
         case actual-tag {
           anyxml service-sfw-statistics-information;
         }
         case multichassis-tag {
           anyxml multi-routing-engine-results;
         }
       }
     }
   }
   rpc get-service-sfw-redundancy-statistics {
     description "Show redundancy statistics";
     input {
       leaf backup-data-pic {
         description "Query the backup data PIC";
         type empty;
       }
       leaf display {
         default "brief";
         type enumeration {
           enum "extensive" {
             description "Display extensive output";
           }
           enum "brief" {
             description "Display brief output (default)";
           }
         }
       }
     }
     output {
       choice output_c {
         case output-tag {
           leaf output {
             type string;
           }
         }
         case actual-tag {
           anyxml service-sfw-redundancy-statistics;
         }
         case multichassis-tag {
           anyxml multi-routing-engine-results;
         }
       }
     }
   }
   rpc get-service-capture {
     description "Show Services PIC packet capture";
     input {
       leaf file {
         type string;
         mandatory true;
       }
       leaf level {
         default "brief";
         type enumeration {
           enum "brief" {
             description "Display brief output";
           }
           enum "detail" {
             description "Display detailed output";
           }
           enum "extensive" {
             description "Display extensive output";
           }
         }
       }
       leaf packet-id {
         description "Packet-id to be used as filter";
         type string;
       }
     }
     output {
       choice output_c {
         case output-tag {
           leaf output {
             type string;
           }
         }
         case actual-tag {
           anyxml service-capture;
         }
         case multichassis-tag {
           anyxml multi-routing-engine-results;
         }
       }
     }
   }
   rpc get-service-softwire-table-information {
     description "Show softwire information";
     input {
       leaf get-service-current-softwire-count-information {
         description "Show count of softwires created";
         type empty;
       }
     }
     output {
       choice output_c {
         case output-tag {
           leaf output {
             type string;
           }
         }
         case actual-tag {
           anyxml service-softwire-table-information;
         }
         case multichassis-tag {
           anyxml multi-routing-engine-results;
         }
       }
     }
   }
   rpc get-service-softwire-flow-table-information {
     description "Show flow table entries";
     input {
       leaf service-set {
         description "Name of service set";
         type string;
       }
       leaf interface {
         description "Name of adaptive services interface";
         type string;
       }
       leaf get-service-softwire-count-information {
         description "Show count of matching entries";
         type empty;
       }
     }
     output {
       choice output_c {
         case output-tag {
           leaf output {
             type string;
           }
         }
         case actual-tag {
           anyxml service-softwire-flow-table-information;
         }
         case multichassis-tag {
           anyxml multi-routing-engine-results;
         }
       }
     }
   }
   rpc get-service-softwire-ds-lite-flow-table-information {
     description "Show ds-lite related softwire flows";
     input {
       leaf AFTR {
         description "AFTR IPV6 Address";
         type jt:ipv6addr;
       }
       leaf B4 {
         description "B4 IPV6 Address";
         type jt:ipv6addr;
       }
     }
     output {
       choice output_c {
         case output-tag {
           leaf output {
             type string;
           }
         }
         case actual-tag {
           anyxml service-softwire-flow-table-information;
         }
         case multichassis-tag {
           anyxml multi-routing-engine-results;
         }
       }
     }
   }
   rpc get-service-softwire-v6rd-flow-table-information {
     description "Show v6rd related softwire flows";
     input {
       leaf concentrator {
         description "Softwire concentrator IPV4 Address";
         type jt:ipv4addr;
       }
       leaf initiator {
         description "Softwire initiator IPV4 Address";
         type jt:ipv4addr;
       }
     }
     output {
       choice output_c {
         case output-tag {
           leaf output {
             type string;
           }
         }
         case actual-tag {
           anyxml service-softwire-flow-table-information;
         }
         case multichassis-tag {
           anyxml multi-routing-engine-results;
         }
       }
     }
   }
   rpc get-service-softwire-session-table-information {
     description "Show session table entries";
     input {
       leaf service-set {
         description "Name of service set";
         type string;
       }
       leaf interface {
         description "Name of adaptive services interface";
         type string;
       }
       leaf get-service-softwire-session-count-info {
         description "Show count of matching entries";
         type empty;
       }
     }
     output {
       choice output_c {
         case output-tag {
           leaf output {
             type string;
           }
         }
         case actual-tag {
           anyxml msp-session-table;
         }
         case multichassis-tag {
           anyxml multi-routing-engine-results;
         }
       }
     }
   }
   rpc get-service-softwire-session-dslite-table-info {
     description "Show ds-lite related softwire sessions";
     input {
       leaf service-set {
         description "Name of service set";
         type string;
       }
       leaf interface {
         description "Name of adaptive services interface";
         type string;
       }
       leaf get-service-softwire-session-count-info {
         description "Show count of matching entries";
         type empty;
       }
       leaf aftr {
         description "AFTR IPV6 Address";
         type jt:ipv6addr;
       }
       leaf b4 {
         description "B4 IPV6 Address";
         type jt:ipv6addr;
       }
     }
     output {
       choice output_c {
         case output-tag {
           leaf output {
             type string;
           }
         }
         case actual-tag {
           anyxml msp-session-table;
         }
         case multichassis-tag {
           anyxml multi-routing-engine-results;
         }
       }
     }
   }
   rpc get-service-softwire-statistics-information {
     description "Show global softwire statistics";
     input {
       leaf interface {
         description "Name of adaptive services interface";
         type string;
       }
       leaf display {
         type enumeration {
           enum "ds-lite" {
             description "Show softwire statistics for dslite";
           }
           enum "v6rd" {
             description "Show softwire statistics for v6rd";
           }
         }
       }
     }
     output {
       choice output_c {
         case output-tag {
           leaf output {
             type string;
           }
         }
         case actual-tag {
           anyxml service-softwire-statistics-information;
         }
         case multichassis-tag {
           anyxml multi-routing-engine-results;
         }
       }
     }
   }
   rpc get-inline-service-sw-statistics-information {
     description "Show global inline softwire statistics";
     input {
       leaf interface {
         description "Name of adaptive services interface";
         type string;
       }
       leaf display {
         type enumeration {
           enum "v6rd" {
             description "Show softwire statistics for 6rd";
           }
           enum "mape" {
             description "Show softwire statistics for MAPE";
           }
         }
       }
     }
     output {
       choice output_c {
         case output-tag {
           leaf output {
             type string;
           }
         }
         case actual-tag {
           anyxml inline-service-sw-statistics-information;
         }
         case multichassis-tag {
           anyxml multi-routing-engine-results;
         }
       }
     }
   }
   rpc get-inline-nat-statistics-information {
     description "Show global inline nat statistics";
     input {
       leaf interface {
         description "Name of adaptive services interface";
         type string;
       }
     }
     output {
       choice output_c {
         case output-tag {
           leaf output {
             type string;
           }
         }
         case actual-tag {
           anyxml inline-nat-statistics-information;
         }
         case multichassis-tag {
           anyxml multi-routing-engine-results;
         }
       }
     }
   }
   rpc get-inline-nat-pool-information {
     description "Show NAT pools information";
     input {
       leaf pool-name {
         description "Name of pool";
         type string;
       }
     }
     output {
       choice output_c {
         case output-tag {
           leaf output {
             type string;
           }
         }
         case actual-tag {
           anyxml inline-nat-pool-information;
         }
         case multichassis-tag {
           anyxml multi-routing-engine-results;
         }
       }
     }
   }
   rpc get-inline-nat-mapping-nptv6-information {
     description "Show nptv6 translated address";
     input {
       leaf address {
         description "IPV6 Address";
         type jt:ipv6addr;
         mandatory true;
       }
       leaf direction {
         type enumeration {
           enum "internal" {
             description "Internal-address";
           }
           enum "external" {
             description "External-address";
           }
         }
         mandatory true;
       }
     }
     output {
       choice output_c {
         case output-tag {
           leaf output {
             type string;
           }
         }
         case actual-tag {
           anyxml inline-nat-mapping-nptv6-information;
         }
         case multichassis-tag {
           anyxml multi-routing-engine-results;
         }
       }
     }
   }
   rpc get-inline-ip-reass-statistics {
     description "Show IP Reassembly statistics";
     output {
       choice output_c {
         case output-tag {
           leaf output {
             type string;
           }
         }
         case actual-tag {
           anyxml inline-ip-reass-statistics-information;
         }
         case multichassis-tag {
           anyxml multi-routing-engine-results;
         }
       }
     }
   }
   rpc get-inline-ip-reass-si-statistics-information {
     description "Show inline ip-reassembly statistics on si-ifl";
     input {
       leaf interface-name {
         description "Name of adaptive services interface";
         type string;
         mandatory true;
       }
     }
     output {
       choice output_c {
         case output-tag {
           leaf output {
             type string;
           }
         }
         case actual-tag {
           anyxml inline-ip-reass-statistics-information;
         }
         case multichassis-tag {
           anyxml multi-routing-engine-results;
         }
       }
     }
   }
   rpc get-inline-ip-reass-fpc-slot-information {
     description "FPC slot number";
     input {
       uses command-forwarding;
       leaf fpc-slot {
         description "FPC slot number";
         type union {
           type string {
             pattern "<.*>|$.*";
           }
           type uint32;
         }
         mandatory true;
       }
       leaf pfe-slot {
         description "PFE slot number";
         type union {
           type string {
             pattern "<.*>|$.*";
           }
           type uint32;
         }
       }
     }
     output {
       choice output_c {
         case output-tag {
           leaf output {
             type string;
           }
         }
         case actual-tag {
           anyxml inline-ip-reass-statistics-information;
         }
         case multichassis-tag {
           anyxml multi-routing-engine-results;
         }
       }
     }
   }
   rpc get-inline-sfw-flow-table-information {
     description "Show flow table entries";
     input {
       leaf all {
         description "Display all the entries";
         type empty;
       }
       leaf limit {
         description "Maximum number of entries to display";
         type union {
           type string {
             pattern "<.*>|$.*";
           }
           type uint32 {
             range "1 .. 4294967295";
           }
         }
       }
       leaf display {
         default "brief";
         type enumeration {
           enum "extensive" {
             description "Display extensive output";
           }
           enum "brief" {
             description "Display brief output (default)";
           }
           enum "terse" {
             description "Display terse output";
           }
         }
       }
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf protocol {
         description "IP protocol type to use as filter";
         type string;
       }
       leaf service-set {
         description "Name of service set";
         type string;
       }
       leaf interface {
         description "Name of adaptive services interface";
         type string;
       }
       leaf get-inline-sfw-flow-count-information {
         description "Show count of matching entries";
         type empty;
       }
     }
     output {
       choice output_c {
         case output-tag {
           leaf output {
             type string;
           }
         }
         case actual-tag {
           anyxml service-sfw-flow-table-information;
         }
         case multichassis-tag {
           anyxml multi-routing-engine-results;
         }
       }
     }
   }
   rpc get-inline-sfw-statistics-information {
     description "Show statistics";
     input {
       leaf display {
         default "brief";
         type enumeration {
           enum "brief" {
             description "Display brief output (default)";
           }
           enum "summary" {
             description "Display summary output";
           }
         }
       }
       leaf service-set {
         description "Name of service set";
         type string;
       }
       leaf interface {
         description "Name of adaptive services interface";
         type string;
       }
     }
     output {
       choice output_c {
         case output-tag {
           leaf output {
             type string;
           }
         }
         case actual-tag {
           anyxml service-sfw-statistics-information;
         }
         case multichassis-tag {
           anyxml multi-routing-engine-results;
         }
       }
     }
   }
   rpc get-service-ids-source-table-information {
     description "Show attack source address table";
     input {
       leaf source-prefix {
         description "Source prefix to use as filter";
         type string;
       }
       leaf service-set {
         description "Name of service set";
         type string;
       }
       leaf interface {
         description "Name of adaptive services interface";
         type string;
       }
       leaf order {
         description "Specify table ordering criteria";
         default "anomalies";
         type enumeration {
           enum "anomalies" {
             description "Order by number of anomalies (default)";
           }
           enum "bytes" {
             description "Order by bytes received";
           }
           enum "flows" {
             description "Order by number of flows";
           }
           enum "packets" {
             description "Order by packets received";
           }
         }
       }
       leaf threshold {
         description "Minimum threshold for table entries";
         type union {
           type int32;
           type string {
             pattern "<.*>|$.*";
           }
         }
       }
       leaf limit {
         description "Maximum number of entries to display";
         type union {
           type int32;
           type string {
             pattern "<.*>|$.*";
           }
         }
       }
       leaf display {
         default "brief";
         type enumeration {
           enum "extensive" {
             description "Display extensive output";
           }
           enum "brief" {
             description "Display brief output (default)";
           }
           enum "terse" {
             description "Display terse output";
           }
         }
       }
     }
     output {
       choice output_c {
         case output-tag {
           leaf output {
             type string;
           }
         }
         case actual-tag {
           anyxml service-ids-flow-table-information;
         }
         case multichassis-tag {
           anyxml multi-routing-engine-results;
         }
       }
     }
   }
   rpc get-service-ids-destination-table-information {
     description "Show attack destination address table";
     input {
       leaf destination-prefix {
         description "Destination prefix to use as filter";
         type string;
       }
       leaf service-set {
         description "Name of service set";
         type string;
       }
       leaf interface {
         description "Name of adaptive services interface";
         type string;
       }
       leaf order {
         description "Specify table ordering criteria";
         default "anomalies";
         type enumeration {
           enum "anomalies" {
             description "Order by number of anomalies (default)";
           }
           enum "bytes" {
             description "Order by bytes received";
           }
           enum "flows" {
             description "Order by number of flows";
           }
           enum "packets" {
             description "Order by packets received";
           }
         }
       }
       leaf threshold {
         description "Minimum threshold for table entries";
         type union {
           type int32;
           type string {
             pattern "<.*>|$.*";
           }
         }
       }
       leaf limit {
         description "Maximum number of entries to display";
         type union {
           type int32;
           type string {
             pattern "<.*>|$.*";
           }
         }
       }
       leaf display {
         default "brief";
         type enumeration {
           enum "extensive" {
             description "Display extensive output";
           }
           enum "brief" {
             description "Display brief output (default)";
           }
           enum "terse" {
             description "Display terse output";
           }
         }
       }
     }
     output {
       choice output_c {
         case output-tag {
           leaf output {
             type string;
           }
         }
         case actual-tag {
           anyxml service-ids-flow-table-information;
         }
         case multichassis-tag {
           anyxml multi-routing-engine-results;
         }
       }
     }
   }
   rpc get-service-ids-pair-table-information {
     description "Show attack source and destination address pair table";
     input {
       leaf source-prefix {
         description "Source prefix to use as filter";
         type string;
       }
       leaf destination-prefix {
         description "Destination prefix to use as filter";
         type string;
       }
       leaf service-set {
         description "Name of service set";
         type string;
       }
       leaf interface {
         description "Name of adaptive services interface";
         type string;
       }
       leaf order {
         description "Specify table ordering criteria";
         default "anomalies";
         type enumeration {
           enum "anomalies" {
             description "Order by number of anomalies (default)";
           }
           enum "bytes" {
             description "Order by bytes received";
           }
           enum "flows" {
             description "Order by number of flows";
           }
           enum "packets" {
             description "Order by packets received";
           }
         }
       }
       leaf threshold {
         description "Minimum threshold for table entries";
         type union {
           type int32;
           type string {
             pattern "<.*>|$.*";
           }
         }
       }
       leaf limit {
         description "Maximum number of entries to display";
         type union {
           type int32;
           type string {
             pattern "<.*>|$.*";
           }
         }
       }
       leaf display {
         default "brief";
         type enumeration {
           enum "extensive" {
             description "Display extensive output";
           }
           enum "brief" {
             description "Display brief output (default)";
           }
           enum "terse" {
             description "Display terse output";
           }
         }
       }
     }
     output {
       choice output_c {
         case output-tag {
           leaf output {
             type string;
           }
         }
         case actual-tag {
           anyxml service-ids-flow-table-information;
         }
         case multichassis-tag {
           anyxml multi-routing-engine-results;
         }
       }
     }
   }
   rpc get-service-identification-statistics-information {
     description "Show service identification statistics";
     input {
       leaf detail {
         description "Display detailed statistics";
         type empty;
       }
     }
     output {
       choice output_c {
         case output-tag {
           leaf output {
             type string;
           }
         }
         case actual-tag {
           anyxml service-identification-statistics-information;
         }
         case multichassis-tag {
           anyxml multi-routing-engine-results;
         }
       }
     }
   }
   rpc get-header-redirect-set-statistics-information {
     description "Show header redirect set statistics";
     input {
       leaf detail {
         description "Display detailed statistics";
         type empty;
       }
     }
     output {
       choice output_c {
         case output-tag {
           leaf output {
             type string;
           }
         }
         case actual-tag {
           anyxml header-redirect-set-statistics-information;
         }
         case multichassis-tag {
           anyxml multi-routing-engine-results;
         }
       }
     }
   }
   rpc get-uri-redirect-set-statistics-information {
     description "Show URI redirect set statistics";
     input {
       leaf detail {
         description "Display detailed statistics";
         type empty;
       }
     }
     output {
       choice output_c {
         case output-tag {
           leaf output {
             type string;
           }
         }
         case actual-tag {
           anyxml uri-redirect-set-statistics-information;
         }
         case multichassis-tag {
           anyxml multi-routing-engine-results;
         }
       }
     }
   }
   rpc get-flow-table-statistics-information {
     description "Show flow table statistics";
     input {
       leaf detail {
         description "Show detailed statistics information";
         type empty;
       }
     }
     output {
       choice output_c {
         case output-tag {
           leaf output {
             type string;
           }
         }
         case actual-tag {
           anyxml flow-table-statistics-information;
         }
         case multichassis-tag {
           anyxml multi-routing-engine-results;
         }
       }
     }
   }
   rpc get-soft-gre-tunnel-database {
     description "Show active soft gre active tunnels";
     input {
       leaf display {
         default "brief";
         type enumeration {
           enum "extensive" {
             description "Display extensive output";
           }
           enum "brief" {
             description "Display brief output (default)";
           }
           enum "detail" {
             description "Display detailed output";
           }
           enum "statistics" {
             description "Display statistics";
           }
         }
       }
       choice filter {
         case interface {
           leaf interface {
             description "Interface name to use as filter";
             type string;
           }
         }
         case tunnel-group {
           leaf tunnel-group {
             description "Tunnel group to use as filter";
             type string;
           }
         }
         case local-ip {
           leaf local-ip {
             description "Local ip address to use as filter";
             type jt:ipv4addr;
           }
         }
         case remote-ip {
           leaf remote-ip {
             description "Remote ip address to use as filter";
             type jt:ipv4addr;
           }
         }
       }
     }
     output {
       choice output_c {
         case output-tag {
           leaf output {
             type string;
           }
         }
         case actual-tag {
           anyxml soft-gre-tunnel-database;
         }
         case multichassis-tag {
           anyxml multi-routing-engine-results;
         }
       }
     }
   }
   rpc get-l2tp-destination-information {
     description "Show L2TP destination information";
     input {
       leaf display {
         default "brief";
         type enumeration {
           enum "extensive" {
             description "Display extensive output";
           }
           enum "brief" {
             description "Display brief output (default)";
           }
           enum "detail" {
             description "Display detailed output";
           }
           enum "statistics" {
             description "Display statistics";
           }
         }
       }
       choice filter {
         case local-gateway {
           leaf local-gateway {
             description "Local gateway address to use as filter";
             type jt:ipv4addr;
           }
         }
         case peer-gateway {
           leaf peer-gateway {
             description "Peer gateway address to use as filter";
             type jt:ipv4addr;
           }
         }
       }
     }
     output {
       choice output_c {
         case output-tag {
           leaf output {
             type string;
           }
         }
         case actual-tag {
           anyxml service-l2tp-destination-information;
         }
         case multichassis-tag {
           anyxml multi-routing-engine-results;
         }
       }
     }
   }
   rpc get-services-l2tp-destination-lockout {
     description "Display locked out destinations";
     output {
       choice output_c {
         case output-tag {
           leaf output {
             type string;
           }
         }
         case actual-tag {
           anyxml service-l2tp-destination-lockout-information;
         }
         case multichassis-tag {
           anyxml multi-routing-engine-results;
         }
       }
     }
   }
   rpc get-l2tp-tunnel-information {
     description "Show active L2TP tunnel list";
     input {
       leaf display {
         default "brief";
         type enumeration {
           enum "extensive" {
             description "Display extensive output";
           }
           enum "brief" {
             description "Display brief output (default)";
           }
           enum "detail" {
             description "Display detailed output";
           }
           enum "statistics" {
             description "Display statistics";
           }
         }
       }
       choice filter {
         case tunnel-group {
           leaf tunnel-group {
             description "Tunnel group to use as filter";
             type string;
           }
         }
         case local-tunnel-id {
           leaf local-tunnel-id {
             description "Local tunnel ID to use as filter";
             type string;
           }
         }
         case local-gateway {
           leaf local-gateway {
             description "Local gateway address to use as filter";
             type jt:ipv4addr;
           }
         }
         case local-gateway-name {
           leaf local-gateway-name {
             description "Local gateway name to use as filter";
             type string;
           }
         }
         case peer-gateway {
           leaf peer-gateway {
             description "Peer gateway address to use as filter";
             type jt:ipv4addr;
           }
         }
         case peer-gateway-name {
           leaf peer-gateway-name {
             description "Peer gateway name to use as filter";
             type string;
           }
         }
         case interface {
           leaf interface {
             description "Interface name to use as filter";
             type string;
           }
         }
       }
     }
     output {
       choice output_c {
         case output-tag {
           leaf output {
             type string;
           }
         }
         case actual-tag {
           anyxml service-l2tp-tunnel-information;
         }
         case multichassis-tag {
           anyxml multi-routing-engine-results;
         }
       }
     }
   }
   rpc get-l2tp-session-information {
     description "Show active L2TP session list";
     input {
       leaf display {
         default "brief";
         type enumeration {
           enum "extensive" {
             description "Display extensive output";
           }
           enum "brief" {
             description "Display brief output (default)";
           }
           enum "detail" {
             description "Display detailed output";
           }
           enum "statistics" {
             description "Display statistics";
           }
         }
       }
       choice filter {
         case tunnel-group {
           leaf tunnel-group {
             description "Tunnel group to use as filter";
             type string;
           }
         }
         case local-tunnel-id {
           leaf local-tunnel-id {
             description "Local tunnel ID to use as filter";
             type string;
           }
         }
         case local-gateway {
           leaf local-gateway {
             description "Local gateway address to use as filter";
             type jt:ipv4addr;
           }
         }
         case local-gateway-name {
           leaf local-gateway-name {
             description "Local gateway name to use as filter";
             type string;
           }
         }
         case peer-gateway {
           leaf peer-gateway {
             description "Peer gateway address to use as filter";
             type jt:ipv4addr;
           }
         }
         case peer-gateway-name {
           leaf peer-gateway-name {
             description "Peer gateway name to use as filter";
             type string;
           }
         }
         case local-session-id {
           leaf local-session-id {
             description "Local session ID to use as filter";
             type string;
           }
         }
         case user {
           leaf user {
             description "Username to use as filter";
             type string;
           }
         }
         case interface {
           leaf interface {
             description "Interface name to use as filter";
             type string;
           }
         }
       }
     }
     output {
       choice output_c {
         case output-tag {
           leaf output {
             type string;
           }
         }
         case actual-tag {
           anyxml service-l2tp-session-information;
         }
         case multichassis-tag {
           anyxml multi-routing-engine-results;
         }
       }
     }
   }
   rpc get-l2tp-client-information {
     description "Show active L2TP clients list";
     input {
       leaf client-name {
         description "Client name";
         type string;
       }
     }
     output {
       choice output_c {
         case output-tag {
           leaf output {
             type string;
           }
         }
         case actual-tag {
           anyxml service-l2tp-client-information;
         }
         case multichassis-tag {
           anyxml multi-routing-engine-results;
         }
       }
     }
   }
   rpc get-l2tp-tunnel-group-information {
     description "Show tunnel-group list";
     input {
       leaf tunnel-group-name {
         description "Tunnel group name";
         type string;
       }
     }
     output {
       choice output_c {
         case output-tag {
           leaf output {
             type string;
           }
         }
         case actual-tag {
           anyxml service-l2tp-tunnel-group-information;
         }
         case multichassis-tag {
           anyxml multi-routing-engine-results;
         }
       }
     }
   }
   rpc get-l2tp-session-limit-group-information {
     description "Show session-limit-group list";
     input {
       leaf session-limit-group-name {
         description "Session limit group name";
         type string;
       }
     }
     output {
       choice output_c {
         case output-tag {
           leaf output {
             type string;
           }
         }
         case actual-tag {
           anyxml service-l2tp-session-limit-group-information;
         }
         case multichassis-tag {
           anyxml multi-routing-engine-results;
         }
       }
     }
   }
   rpc get-l2tp-tunnel-switch-information {
     description "Show table of tunnel switched sessions";
     output {
       choice output_c {
         case output-tag {
           leaf output {
             type string;
           }
         }
         case actual-tag {
           anyxml service-l2tp-tunnel-switch-information;
         }
         case multichassis-tag {
           anyxml multi-routing-engine-results;
         }
       }
     }
   }
   rpc get-l2tp-tunnel-switch-session-information {
     description "Show tunnel switched sessions";
     input {
       leaf display {
         default "brief";
         type enumeration {
           enum "extensive" {
             description "Display extensive output";
           }
           enum "brief" {
             description "Display brief output (default)";
           }
           enum "detail" {
             description "Display detailed output";
           }
           enum "statistics" {
             description "Display statistics";
           }
         }
       }
       choice filter {
         case tunnel-group {
           leaf tunnel-group {
             description "Tunnel group to use as filter";
             type string;
           }
         }
         case local-tunnel-id {
           leaf local-tunnel-id {
             description "Local tunnel ID to use as filter";
             type string;
           }
         }
         case local-gateway {
           leaf local-gateway {
             description "Local gateway address to use as filter";
             type jt:ipv4addr;
           }
         }
         case local-gateway-name {
           leaf local-gateway-name {
             description "Local gateway name to use as filter";
             type string;
           }
         }
         case peer-gateway {
           leaf peer-gateway {
             description "Peer gateway address to use as filter";
             type jt:ipv4addr;
           }
         }
         case peer-gateway-name {
           leaf peer-gateway-name {
             description "Peer gateway name to use as filter";
             type string;
           }
         }
         case local-session-id {
           leaf local-session-id {
             description "Local session ID to use as filter";
             type string;
           }
         }
         case user {
           leaf user {
             description "Username to use as filter";
             type string;
           }
         }
         case interface {
           leaf interface {
             description "Interface name to use as filter";
             type string;
           }
         }
       }
     }
     output {
       choice output_c {
         case output-tag {
           leaf output {
             type string;
           }
         }
         case actual-tag {
           anyxml service-l2tp-session-information;
         }
         case multichassis-tag {
           anyxml multi-routing-engine-results;
         }
       }
     }
   }
   rpc get-l2tp-tunnel-switch-tunnel-information {
     description "Show switched tunnels";
     input {
       leaf display {
         default "brief";
         type enumeration {
           enum "extensive" {
             description "Display extensive output";
           }
           enum "brief" {
             description "Display brief output (default)";
           }
           enum "detail" {
             description "Display detailed output";
           }
           enum "statistics" {
             description "Display statistics";
           }
         }
       }
       choice filter {
         case tunnel-group {
           leaf tunnel-group {
             description "Tunnel group to use as filter";
             type string;
           }
         }
         case local-tunnel-id {
           leaf local-tunnel-id {
             description "Local tunnel ID to use as filter";
             type string;
           }
         }
         case local-gateway {
           leaf local-gateway {
             description "Local gateway address to use as filter";
             type jt:ipv4addr;
           }
         }
         case local-gateway-name {
           leaf local-gateway-name {
             description "Local gateway name to use as filter";
             type string;
           }
         }
         case peer-gateway {
           leaf peer-gateway {
             description "Peer gateway address to use as filter";
             type jt:ipv4addr;
           }
         }
         case peer-gateway-name {
           leaf peer-gateway-name {
             description "Peer gateway name to use as filter";
             type string;
           }
         }
         case interface {
           leaf interface {
             description "Interface name to use as filter";
             type string;
           }
         }
       }
     }
     output {
       choice output_c {
         case output-tag {
           leaf output {
             type string;
           }
         }
         case actual-tag {
           anyxml service-l2tp-tunnel-information;
         }
         case multichassis-tag {
           anyxml multi-routing-engine-results;
         }
       }
     }
   }
   rpc get-l2tp-tunnel-switch-destination-information {
     description "Show tunnel switched destinations";
     input {
       leaf display {
         default "brief";
         type enumeration {
           enum "extensive" {
             description "Display extensive output";
           }
           enum "brief" {
             description "Display brief output (default)";
           }
           enum "detail" {
             description "Display detailed output";
           }
           enum "statistics" {
             description "Display statistics";
           }
         }
       }
       choice filter {
         case local-gateway {
           leaf local-gateway {
             description "Local gateway address to use as filter";
             type jt:ipv4addr;
           }
         }
         case peer-gateway {
           leaf peer-gateway {
             description "Peer gateway address to use as filter";
             type jt:ipv4addr;
           }
         }
       }
     }
     output {
       choice output_c {
         case output-tag {
           leaf output {
             type string;
           }
         }
         case actual-tag {
           anyxml service-l2tp-destination-information;
         }
         case multichassis-tag {
           anyxml multi-routing-engine-results;
         }
       }
     }
   }
   rpc get-l2tp-disconnect-cause-summary {
     description "Show L2TP disconnect cause summary";
     output {
       choice output_c {
         case output-tag {
           leaf output {
             type string;
           }
         }
         case actual-tag {
           anyxml service-l2tp-disconnect-cause-summary;
         }
         case multichassis-tag {
           anyxml multi-routing-engine-results;
         }
       }
     }
   }
   rpc get-l2tp-user-information {
     description "Show active L2TP user list";
     input {
       leaf display {
         default "brief";
         type enumeration {
           enum "extensive" {
             description "Display extensive output";
           }
           enum "brief" {
             description "Display brief output (default)";
           }
           enum "detail" {
             description "Display detailed output";
           }
           enum "statistics" {
             description "Display statistics";
           }
         }
       }
       choice filter {
         case user {
           leaf user {
             description "Filter by username";
             type string;
           }
         }
       }
     }
     output {
       choice output_c {
         case output-tag {
           leaf output {
             type string;
           }
         }
         case actual-tag {
           anyxml service-l2tp-session-information;
         }
         case multichassis-tag {
           anyxml multi-routing-engine-results;
         }
       }
     }
   }
   rpc get-l2tp-multilink-information {
     description "Show active L2TP multilink list";
     input {
       leaf display {
         default "brief";
         type enumeration {
           enum "extensive" {
             description "Display extensive output";
           }
           enum "brief" {
             description "Display brief output (default)";
           }
           enum "detail" {
             description "Display detailed output";
           }
           enum "statistics" {
             description "Display statistics";
           }
         }
       }
       choice filter {
         case bundle-id {
           leaf bundle-id {
             description "Filter by multilink bundle ID";
             type string;
           }
         }
       }
     }
     output {
       choice output_c {
         case output-tag {
           leaf output {
             type string;
           }
         }
         case actual-tag {
           anyxml services-l2tp-multilink-information;
         }
         case multichassis-tag {
           anyxml multi-routing-engine-results;
         }
       }
     }
   }
   rpc get-l2tp-summary-information {
     description "Show L2TP summary information";
     input {
       leaf display {
         default "brief";
         type enumeration {
           enum "extensive" {
             description "Display extensive output";
           }
           enum "brief" {
             description "Display brief output (default)";
           }
           enum "detail" {
             description "Display detailed output";
           }
           enum "statistics" {
             description "Display statistics";
           }
         }
       }
       leaf interface {
         description "Name of adaptive services interface";
         type string;
       }
     }
     output {
       choice output_c {
         case output-tag {
           leaf output {
             type string;
           }
         }
         case actual-tag {
           anyxml service-l2tp-summary-information;
         }
         case multichassis-tag {
           anyxml multi-routing-engine-results;
         }
       }
     }
   }
   rpc get-services-l2tp-radius-authentication-accounting-servers-information {
     description "Show RADIUS authentication and accounting servers information";
     output {
       choice output_c {
         case output-tag {
           leaf output {
             type string;
           }
         }
         case actual-tag {
           anyxml services-l2tp-radius-authentication-accounting-servers-information;
         }
         case multichassis-tag {
           anyxml multi-routing-engine-results;
         }
       }
     }
   }
   rpc get-services-l2tp-radius-authentication-accounting-statistics-information {
     description "Show RADIUS authentication and accounting statistics information";
     output {
       choice output_c {
         case output-tag {
           leaf output {
             type string;
           }
         }
         case actual-tag {
           anyxml services-l2tp-radius-authentication-accounting-statistics-information;
         }
         case multichassis-tag {
           anyxml multi-routing-engine-results;
         }
       }
     }
   }
   rpc get-services-l2tp-radius-authentication-servers-information {
     description "Show RADIUS authentication servers information";
     output {
       choice output_c {
         case output-tag {
           leaf output {
             type string;
           }
         }
         case actual-tag {
           anyxml services-l2tp-radius-authentication-servers-information;
         }
         case multichassis-tag {
           anyxml multi-routing-engine-results;
         }
       }
     }
   }
   rpc get-services-l2tp-radius-authentication-statistics-information {
     description "Show RADIUS authentication statistics information";
     output {
       choice output_c {
         case output-tag {
           leaf output {
             type string;
           }
         }
         case actual-tag {
           anyxml services-l2tp-radius-authentication-statistics-information;
         }
         case multichassis-tag {
           anyxml multi-routing-engine-results;
         }
       }
     }
   }
   rpc get-services-l2tp-radius-accounting-servers-information {
     description "Show RADIUS accounting servers information";
     output {
       choice output_c {
         case output-tag {
           leaf output {
             type string;
           }
         }
         case actual-tag {
           anyxml services-l2tp-radius-accounting-servers-information;
         }
         case multichassis-tag {
           anyxml multi-routing-engine-results;
         }
       }
     }
   }
   rpc get-services-l2tp-radius-accounting-statistics-information {
     description "Show RADIUS accounting statistics information";
     output {
       choice output_c {
         case output-tag {
           leaf output {
             type string;
           }
         }
         case actual-tag {
           anyxml services-l2tp-radius-accounting-statistics-information;
         }
         case multichassis-tag {
           anyxml multi-routing-engine-results;
         }
       }
     }
   }
   rpc get-service-crtp-params-information {
     description "Show Compressed Real-Time Protocol information";
     input {
       leaf interface {
         description "Name of link services interface";
         type string;
       }
     }
     output {
       choice output_c {
         case output-tag {
           leaf output {
             type string;
           }
         }
         case actual-tag {
           anyxml service-crtp-params-information;
         }
         case multichassis-tag {
           anyxml multi-routing-engine-results;
         }
       }
     }
   }
   rpc get-service-crtp-extensive-information {
     description "Show CRTP extensive output";
     input {
       leaf interface {
         description "Name of link services interface";
         type string;
       }
     }
     output {
       choice output_c {
         case output-tag {
           leaf output {
             type string;
           }
         }
         case actual-tag {
           anyxml service-crtp-extensive-information;
         }
         case multichassis-tag {
           anyxml multi-routing-engine-results;
         }
       }
     }
   }
   rpc get-service-crtp-flow-table-information {
     description "Show CRTP flow table entries";
     input {
       leaf interface {
         description "Name of link services interface";
         type string;
       }
     }
     output {
       choice output_c {
         case output-tag {
           leaf output {
             type string;
           }
         }
         case actual-tag {
           anyxml service-crtp-flow-table-information;
         }
         case multichassis-tag {
           anyxml multi-routing-engine-results;
         }
       }
     }
   }
   rpc get-link-services-cpu-usage {
     description "Show cpu usage as a percentage for the specified PIC";
     input {
       leaf interface {
         description "Name of link services interface";
         type string;
         mandatory true;
       }
       leaf level {
         default "brief";
         type enumeration {
           enum "brief" {
             description "Display brief output (1 and 5 second average)";
           }
           enum "detail" {
             description "Display detailed output (per cpu average)";
           }
         }
       }
     }
     output {
       choice output_c {
         case output-tag {
           leaf output {
             type string;
           }
         }
         case actual-tag {
           anyxml lsqinfo-cpu-usage-information;
         }
         case multichassis-tag {
           anyxml multi-routing-engine-results;
         }
       }
     }
   }
   rpc get-global-pcp-statistics-information {
     description "Show global PCP statistics";
     input {
       leaf interface {
         description "Name of adaptive services interface";
         type string;
       }
       leaf level {
         type enumeration {
           enum "protocol" {
             description "Display PCP protocol statistics";
           }
         }
       }
     }
     output {
       choice output_c {
         case output-tag {
           leaf output {
             type string;
           }
         }
         case actual-tag {
           anyxml global-pcp-statistics-information;
         }
         case multichassis-tag {
           anyxml multi-routing-engine-results;
         }
       }
     }
   }
   rpc get-msp-ssubscriber-table {
     description "Show subscriber table entries";
     output {
       choice output_c {
         case output-tag {
           leaf output {
             type string;
           }
         }
         case actual-tag {
           anyxml msp-subscriber-table;
         }
         case multichassis-tag {
           anyxml multi-routing-engine-results;
         }
       }
     }
   }
   rpc get-service-subscriber-analysis-information {
     description "Show service subscribers statistics";
     input {
       leaf interface {
         description "Name of extension provider interface";
         type string;
       }
     }
     output {
       choice output_c {
         case output-tag {
           leaf output {
             type string;
           }
         }
         case actual-tag {
           anyxml service-subscriber-analysis-information;
         }
         case multichassis-tag {
           anyxml multi-routing-engine-results;
         }
       }
     }
   }
   rpc get-tcp-log-connection-information {
     description "Show connections related to TCP logging";
     input {
       leaf interface {
         description "Name of extension provider interface";
         type string;
       }
     }
     output {
       choice output_c {
         case output-tag {
           leaf output {
             type string;
           }
         }
         case actual-tag {
           anyxml tcp-log-connection-information;
         }
         case multichassis-tag {
           anyxml multi-routing-engine-results;
         }
       }
     }
   }
   rpc get-services-redundancy-group-information {
     description "Show services redundancy-group information";
     input {
       leaf verbose {
         default "terse";
         type enumeration {
           enum "terse" {
             description "Display terse output(default)";
           }
           enum "brief" {
             description "Display brief output";
           }
           enum "extensive" {
             description "Display detailed output";
           }
         }
       }
     }
     output {
       choice output_c {
         case output-tag {
           leaf output {
             type string;
           }
         }
         case actual-tag {
           anyxml services-redundancy-group-information;
         }
         case multichassis-tag {
           anyxml multi-routing-engine-results;
         }
       }
     }
   }
   rpc get-services-redundancy-group-id-information {
     description "Show redundancy group-id information";
     input {
       leaf verbose {
         default "terse";
         type enumeration {
           enum "terse" {
             description "Display terse output(default)";
           }
           enum "brief" {
             description "Display brief output";
           }
           enum "extensive" {
             description "Display detailed output";
           }
         }
       }
       leaf id {
         description "Show redundancy group-id information";
         type union {
           type uint32;
           type string {
             pattern "<.*>|$.*";
           }
         }
         mandatory true;
       }
     }
     output {
       choice output_c {
         case output-tag {
           leaf output {
             type string;
           }
         }
         case actual-tag {
           anyxml services-redundancy-group-id-information;
         }
         case multichassis-tag {
           anyxml multi-routing-engine-results;
         }
       }
     }
   }
   rpc get-traffic-load-balance-statistics {
     description "Traffic load balance statistics";
     input {
       leaf verbose {
         type enumeration {
           enum "summary" {
             description "Display summary output";
           }
           enum "extensive" {
             description "Display extensive output";
           }
         }
       }
       leaf group {
         description "Group name";
         default "all";
         type string;
       }
       leaf instance {
         description "Instance name";
         default "all";
         type string;
       }
       leaf real-service {
         description "Real service name";
         default "all";
         type string;
       }
       leaf virtual-service {
         description "Virtual service name";
         default "all";
         type string;
       }
       leaf num-instances {
         description "Number of instances to be displayed";
         default "200";
         type union {
           type uint32;
           type string {
             pattern "<.*>|$.*";
           }
         }
       }
     }
     output {
       choice output_c {
         case output-tag {
           leaf output {
             type string;
           }
         }
         case actual-tag {
           anyxml service-traffic-load-balance-statistics;
         }
         case multichassis-tag {
           anyxml multi-routing-engine-results;
         }
       }
     }
   }
   rpc traffic-load-balance-commit-status {
     description "Display commit status";
     output {
       choice output_c {
         case output-tag {
           leaf output {
             type string;
           }
         }
         case actual-tag {
           anyxml tdir-commit-status;
         }
         case multichassis-tag {
           anyxml multi-routing-engine-results;
         }
       }
     }
   }
   rpc get-url-filter-statistics {
     description "Show web filter statistics";
     input {
       leaf profile {
         description "Web filter profile specific statistics";
         type string;
         mandatory true;
       }
       leaf url-filter-template {
         description "Url filter template specific statistics";
         type string;
       }
       leaf dns-filter-template {
         description "DNS filter template specific statistics";
         type string;
       }
       leaf dns-filter-term {
         description "DNS filter term specific statistics";
         type string;
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf level {
         default "brief";
         type enumeration {
           enum "brief" {
             description "Brief Information";
           }
           enum "detail" {
             description "Detailed Information";
           }
           enum "extensive" {
             description "Extensive Information";
           }
         }
       }
     }
     output {
       choice output_c {
         case output-tag {
           leaf output {
             type string;
           }
         }
         case actual-tag {
           anyxml url-filter-statistics;
         }
         case multichassis-tag {
           anyxml multi-routing-engine-results;
         }
       }
     }
   }
   rpc get-url-filter-dns-resolution {
     description "Show url-filter dns-resolution";
     input {
       leaf profile {
         description "Url-filter profile specific DNS resolution information";
         type string;
         mandatory true;
       }
       leaf url-filter-template {
         description "Url-filter template specific DNS resolution information";
         type string;
       }
     }
     output {
       choice output_c {
         case output-tag {
           leaf output {
             type string;
           }
         }
         case actual-tag {
           anyxml url-filter-dns-resolution;
         }
         case multichassis-tag {
           anyxml multi-routing-engine-results;
         }
       }
     }
   }
   rpc get-url-filter-dns-resolution-statistics {
     description "Show url-filter dns-resolution statistics";
     input {
       leaf profile {
         description "Url-filter profile specific DNS resolution information";
         type string;
         mandatory true;
       }
       leaf url-filter-template {
         description "Url-filter template specific DNS resolution information";
         type string;
         mandatory true;
       }
       leaf verbosity_level {
         type enumeration {
           enum "summary" {
             description "Display summary output";
           }
           enum "extensive" {
             description "Display extensive output";
           }
         }
         mandatory true;
       }
     }
     output {
       choice output_c {
         case output-tag {
           leaf output {
             type string;
           }
         }
         case actual-tag {
           anyxml url-filter-dns-resolution-statistics;
         }
         case multichassis-tag {
           anyxml multi-routing-engine-results;
         }
       }
     }
   }
   rpc get-url-filter-secintel-policy-status {
     description "Show secintel policy status";
     input {
       leaf profile {
         description "Url-filter profile specific secintel policy status";
         type string;
         mandatory true;
       }
       leaf verbosity_level {
         type enumeration {
           enum "summary" {
             description "Display summary output";
           }
           enum "extensive" {
             description "Display extensive output";
           }
         }
       }
     }
     output {
       choice output_c {
         case output-tag {
           leaf output {
             type string;
           }
         }
         case actual-tag {
           anyxml url-filter-secintel-policy-status;
         }
         case multichassis-tag {
           anyxml multi-routing-engine-results;
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member";
           type union {
             type string {
               pattern "<.*>|$.*";
             }
             type uint32;
           }
         }
       }
     }
   }
 }
