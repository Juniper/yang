/*
 * Copyright (c) 2019 Juniper Networks, Inc.
 * All rights reserved.
 */
 module junos-nfx-conf-services {
   namespace "http://yang.juniper.net/junos-nfx/conf/services";

   prefix jc-services;

   import junos-common-ddl-extensions {
     prefix junos;
   }

   import junos-common-types {
     prefix jt;
   }

   import junos-nfx-conf-root {
     prefix jc;
   }

   organization "Juniper Networks, Inc.";

   contact "yang-support@juniper.net";

   description "Junos services configuration module";

   revision 2019-01-01 {
     description "Junos: 18.4R2.7";
   }

   augment /jc:configuration {
     uses services-group;
   }
   augment /jc:configuration/jc:groups {
     uses services-group;
   }
   grouping services-group {
     container services {
       description "Set services parameters";
       uses apply-advanced;
       container analytics {
         presence "enable analytics";
         description "Traffic analytics configuration options";
         uses apply-advanced;
         container traceoptions {
           description "Traffic analytics trace options";
           uses apply-advanced;
           leaf no-remote-trace {
             description "Disable remote tracing";
             junos:must "(\"system tracing\")";
             junos:must-message "'no-remote-trace' is valid only when [system tracing] is configured";
             type empty;
           }
           container file {
             description "Trace file information";
             leaf filename {
               description "Name of file in which to write trace information";
               type string {
                 length "1 .. 1024";
                 junos:posix-pattern "![/ %]";
                 junos:pattern-message "Must not contain '/', % or a space";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             description "Tracing parameters";
             leaf name {
               type enumeration {
                 enum "all" {
                   description "Trace configuration events";
                 }
                 enum "configuration" {
                   description "Log configuration events";
                 }
                 enum "rtsock" {
                   description "Trace rtsock message events";
                 }
                 enum "client-server" {
                   description "Trace client-server events";
                 }
                 enum "interface" {
                   description "Trace interface update events";
                 }
                 enum "xmlproxy" {
                   description "Trace xmlproxy events";
                 }
               }
             }
             leaf disable {
               description "Disable this trace flag";
               type empty;
             }
           }
         }
         list export-profiles {
           key name;
           ordered-by user;
           description "Mapping of export-profiles to collectors";
           leaf name {
             description "Export profile name";
             type string {
               length "1 .. 64";
             }
           }
           uses apply-advanced;
           leaf stream-format {
             description "Streaming data format";
             default "gpb";
             type enumeration {
               enum "gpb" {
                 description "Google protocol buffer format";
               }
               enum "json" {
                 description "Java script object notation format";
               }
               enum "csv" {
                 description "Comma separated value";
               }
               enum "tsv" {
                 description "Tab separated value";
               }
             }
           }
           container interface {
             presence "enable interface";
             description "Interface specific information";
             uses apply-advanced;
             leaf information {
               description "Enable streaming of interface information";
               type empty;
             }
             container statistics {
               description "Type of statistics to stream";
               uses apply-advanced;
               leaf traffic {
                 description "Enable streaming of interface traffic statistics";
                 type empty;
               }
               leaf queue {
                 description "Enable streaming of interface queue statistics";
                 type empty;
               }
             }
             container status {
               description "Type of statistics to stream";
               uses apply-advanced;
               leaf link {
                 description "Enable streaming of interface link status";
                 type empty;
               }
               leaf traffic {
                 description "Enable streaming of interface traffic status";
                 type empty;
               }
               leaf queue {
                 description "Enable streaming of interface queue status";
                 type empty;
               }
             }
           }
           container system {
             presence "enable system";
             description "Interface specific information";
             uses apply-advanced;
             leaf information {
               description "Enable streaming of system information";
               type empty;
             }
             container status {
               description "Type of statistics to stream";
               uses apply-advanced;
               leaf traffic {
                 description "Enable streaming of system traffic status";
                 type empty;
               }
               leaf queue {
                 description "Enable streaming of system queue status";
                 type empty;
               }
             }
           }
         }
         list resource-profiles {
           key name;
           ordered-by user;
           description "Mapping of resource profiles to interfaces/queues/system";
           leaf name {
             description "Export profile name";
             type string {
               length "1 .. 64";
             }
           }
           uses apply-advanced;
           choice queue-monitoring-choice {
             leaf queue-monitoring {
               description "Enable queue statistics monitoring";
               type empty;
             }
             leaf no-queue-monitoring {
               description "Don't enable queue statistics monitoring";
               type empty;
             }
           }
           choice traffic-monitoring-choice {
             leaf traffic-monitoring {
               description "Enable traffic statistics monitoring";
               type empty;
             }
             leaf no-traffic-monitoring {
               description "Don't enable traffic statistics monitoring";
               type empty;
             }
           }
           container depth-threshold {
             junos:must "(!(\".. latency-threshold\"))";
             junos:must-message "latency and queue-depth thresholds can not be set together";
             description "Depth threshold configuration";
             leaf high {
               description "High queue depth threshold";
               units "bytes";
               type union {
                 type string {
                   pattern "<.*>|$.*";
                 }
                 type uint32 {
                   range "1 .. 1250000000";
                 }
               }
             }
             leaf low {
               description "Low queue depth threshold";
               units "bytes";
               type union {
                 type string {
                   pattern "<.*>|$.*";
                 }
                 type uint32 {
                   range "1 .. 1250000000";
                 }
               }
             }
           }
           container latency-threshold {
             junos:must "(!(\".. depth-threshold\"))";
             junos:must-message "latency and queue-depth thresholds can not be set together";
             description "Latency threshold configuration";
             leaf high {
               description "High latency threshold";
               units "nanoseconds";
               type union {
                 type string {
                   pattern "<.*>|$.*";
                 }
                 type uint32 {
                   range "1 .. 100000000";
                 }
               }
             }
             leaf low {
               description "Low latency threshold";
               units "nanoseconds";
               type union {
                 type string {
                   pattern "<.*>|$.*";
                 }
                 type uint32 {
                   range "1 .. 100000000";
                 }
               }
             }
           }
         }
         container resource {
           presence "enable resource";
           uses apply-advanced;
           container system {
             description "System configuration options";
             uses apply-advanced;
             leaf resource-profile {
               description "Resouce profile name";
               junos:must "(\"services analytics resource-profiles $$\")";
               junos:must-message "binded resource-profile in not configured";
               type string {
                 length "1 .. 64";
               }
             }
             container polling-interval {
               description "Polling interval";
               uses apply-advanced;
               leaf traffic-monitoring {
                 description "Traffic statistics polling interval";
                 units "seconds";
                 type union {
                   type string {
                     pattern "<.*>|$.*";
                   }
                   type uint32 {
                     range "1 .. 300";
                   }
                 }
               }
               leaf queue-monitoring {
                 description "Queue statistics polling interval";
                 units "milliseconds";
                 type union {
                   type string {
                     pattern "<.*>|$.*";
                   }
                   type uint32 {
                     range "1 .. 1000";
                   }
                 }
               }
             }
           }
           container interfaces {
             description "Interface configuration options";
             uses apply-advanced;
             list interface {
               key name;
               uses interface_type;
             }
           }
         }
         container collector {
           description "Remote streaming servers configuration options";
           uses apply-advanced;
           container local {
             description "Remote streaming servers configuration options";
             uses apply-advanced;
             container file {
               description "Log file information";
               leaf filename {
                 description "Name of file in which to write log information";
                 type jt:filename;
               }
               leaf size {
                 description "Maximum log file size";
                 type string;
               }
               leaf files {
                 description "Maximum number of trace files";
                 default "10";
                 type union {
                   type string {
                     pattern "<.*>|$.*";
                   }
                   type uint32 {
                     range "2 .. 1000";
                   }
                 }
               }
             }
           }
           list address {
             key name;
             description "IP address of remote server";
             leaf name {
               description "IP address";
               type jt:ipaddr;
             }
             uses apply-advanced;
             list port {
               key name;
               description "Remote streaming server port number";
               leaf name {
                 description "Port number";
                 type union {
                   type string {
                     pattern "<.*>|$.*";
                   }
                   type uint32 {
                     range "1 .. 65535";
                   }
                 }
               }
               uses apply-advanced;
               list transport {
                 key name;
                 description "Transport protocol";
                 leaf name {
                   type enumeration {
                     enum "tcp" {
                       description "Transmission control protocol";
                     }
                     enum "udp" {
                       description "User datagram protocol";
                     }
                   }
                 }
                 uses apply-advanced;
                 leaf export-profile {
                   description "Export profile name";
                   junos:must "(\"services analytics export-profiles $$\")";
                   junos:must-message "binded export-profiles in not configured";
                   type string {
                     length "1 .. 64";
                   }
                 }
               }
             }
           }
         }
         container traffic-statistics {
           description "Traffic statistics configuration options";
           status deprecated;
           uses apply-advanced;
           container file {
             description "Log file information";
             leaf filename {
               description "Name of file in which to write log information";
               type jt:filename;
             }
             leaf size {
               description "Maximum log file size";
               type string;
             }
             leaf files {
               description "Maximum number of trace files";
               default "10";
               type union {
                 type string {
                   pattern "<.*>|$.*";
                 }
                 type uint32 {
                   range "2 .. 1000";
                 }
               }
             }
           }
           leaf interval {
             description "Traffic statistics polling interval";
             units "seconds";
             type union {
               type string {
                 pattern "<.*>|$.*";
               }
               type uint32 {
                 range "1 .. 300";
               }
             }
           }
         }
         container queue-statistics {
           description "Microburst statistics configuration options";
           status deprecated;
           uses apply-advanced;
           container file {
             description "Log file information";
             leaf filename {
               description "Name of file in which to write log information";
               type jt:filename;
             }
             leaf size {
               description "Maximum log file size";
               type string;
             }
             leaf files {
               description "Maximum number of trace files";
               default "10";
               type union {
                 type string {
                   pattern "<.*>|$.*";
                 }
                 type uint32 {
                   range "2 .. 1000";
                 }
               }
             }
           }
           leaf interval {
             description "Queue statistics polling interval";
             units "milliseconds";
             type union {
               type string {
                 pattern "<.*>|$.*";
               }
               type uint32 {
                 range "1 .. 1000";
               }
             }
           }
         }
         container interfaces {
           description "Interface configuration options";
           status deprecated;
           uses apply-advanced;
           list interface {
             key name;
             uses interface_type;
           }
         }
         container streaming-servers {
           description "Remote streaming servers configuration options";
           status deprecated;
           uses apply-advanced;
           list address {
             key name;
             ordered-by user;
             description "IP address of remote server";
             leaf name {
               description "IP address";
               type jt:ipaddr;
             }
             uses apply-advanced;
             list port {
               key name;
               description "Remote streaming server port number";
               leaf name {
                 description "Port number";
                 type union {
                   type string {
                     pattern "<.*>|$.*";
                   }
                   type uint32 {
                     range "1 .. 65535";
                   }
                 }
               }
               uses apply-advanced;
               leaf stream-format {
                 description "Streaming data format";
                 type enumeration {
                   enum "json" {
                     description "Javascript object notation";
                   }
                   enum "csv" {
                     description "Comma separated value";
                   }
                   enum "tsv" {
                     description "Tab separated value";
                   }
                 }
               }
               list stream-type {
                 key name;
                 description "Type of statistics to stream";
                 leaf name {
                   type enumeration {
                     enum "traffic-statistics" {
                       description "Enable streaming of traffic statistics";
                     }
                     enum "queue-statistics" {
                       description "Enable streaming of queue statistics";
                     }
                   }
                 }
                 uses apply-advanced;
               }
             }
           }
         }
         list streaming-server {
           key name;
           ordered-by user;
           description "Define Telemetry data servers";
           leaf name {
             description "Telemetry App server Name";
             type string {
               length "1 .. 128";
             }
           }
           uses apply-advanced;
           leaf remote-address {
             description "Telemetry server IP address";
             type jt:ipv4addr;
           }
           leaf remote-port {
             description "Telemetry server Port";
             type union {
               type uint16;
               type string {
                 pattern "<.*>|$.*";
               }
             }
           }
           leaf transport {
             description "Telemetry export transport protocol";
             type enumeration {
               enum "udp" {
                 description "Use UDP transport protocol";
               }
               enum "grpc" {
                 description "Use grpc transport";
               }
             }
           }
         }
         list export-profile {
           key name;
           ordered-by user;
           description "Telemetry export profile name";
           leaf name {
             description "Telemetry export profile name";
             type string {
               length "1 .. 128";
             }
           }
           uses apply-advanced;
           leaf local-address {
             description "Source address for exported packets";
             type jt:ipv4addr;
           }
           leaf local-port {
             description "Source port for exported packets";
             type union {
               type uint16;
               type string {
                 pattern "<.*>|$.*";
               }
             }
           }
           leaf dscp {
             description "DSCP value for exported packets";
             type union {
               type string {
                 pattern "<.*>|$.*";
               }
               type uint8 {
                 range "0 .. 63";
               }
             }
           }
           leaf forwarding-class {
             description "Forwarding-class for exported packets, applicable only for PFE sensors";
             type string {
               length "1 .. 64";
             }
           }
           leaf loss-priority {
             description "Packet Loss Priority for exported packets, applicable only for PFE sensors";
             type enumeration {
               enum "low" {
                 description "Marking when loss priority is low";
               }
               enum "high" {
                 description "Marking when loss priority is high";
               }
               enum "medium-low" {
                 description "Marking when loss priority is medium-low";
               }
               enum "medium-high" {
                 description "Marking when loss priority is medium-high";
               }
             }
           }
           leaf reporting-rate {
             description "Telemetry interval in seconds, max 24 hours";
             units "seconds";
             type union {
               type string {
                 pattern "<.*>|$.*";
               }
               type uint32 {
                 range "0 .. 86400";
               }
             }
           }
           leaf payload-size {
             description "Telemetry payload size";
             default "5000";
             units "bytes";
             type union {
               type string {
                 pattern "<.*>|$.*";
               }
               type uint32 {
                 range "1400 .. 9192";
               }
             }
           }
           leaf format {
             description "Telemetry export record format";
             type enumeration {
               enum "gpb" {
                 description "Use gpb format";
               }
               enum "gpb-sdm" {
                 description "Use gpb self-describing-message format";
               }
               enum "gpb-gnmi" {
                 description "Use gnmi format for gpb messages";
               }
             }
           }
           leaf transport {
             description "Telemetry export transport protocol";
             type enumeration {
               enum "udp" {
                 description "Use UDP transport protocol";
               }
             }
           }
         }
         list sensor {
           key name;
           ordered-by user;
           description "Define Telemetry sensors";
           junos:must "(!(\"system services cloud-analytics instance\"))";
           junos:must-message "Cloud analytics shoud not be defined";
           leaf name {
             description "Name of the sensor";
             type string {
               length "1 .. 128";
             }
           }
           uses apply-advanced;
           leaf-list server-name {
             ordered-by user;
             description "Define Telemetry server ";
             type string {
               length "1 .. 128";
             }
           }
           leaf export-name {
             description "Define Telemetry export profiles";
             type string {
               length "1 .. 128";
             }
           }
           leaf polling-interval {
             description "Define sensor polling interval in nano secs (1 .. 4294967295)";
             status deprecated;
             units "nanoseconds";
             type union {
               type string {
                 pattern "<.*>|$.*";
               }
               type uint32 {
                 range "1 .. 4294967295";
               }
             }
           }
           leaf resource {
             description "System resource identifier string";
             type string {
               length "1 .. 255";
             }
           }
           leaf resource-filter {
             description "Regexp for filtering resource instances (1 .. 1024)";
             type string {
               length "1 .. 1024";
             }
           }
           leaf subscription-id {
             description "Subscription ID (Used internally to group sensors)";
             type union {
               type uint64;
               type string {
                 pattern "<.*>|$.*";
               }
             }
           }
           leaf suppress-zeros {
             description "Supress zeros while data export";
             type empty;
           }
           leaf reporting-rate {
             description "Telemetry interval in seconds, max 24 hours";
             units "seconds";
             type union {
               type string {
                 pattern "<.*>|$.*";
               }
               type uint32 {
                 range "0 .. 86400";
               }
             }
           }
           leaf-list end-of-sync-identifiers {
             ordered-by user;
             description "Set of end-of-syncs for this sensor";
             type union {
               type string {
                 pattern "<.*>|$.*";
               }
               type uint32 {
                 range "1 .. 64";
               }
             }
           }
           leaf target-defined {
             description "Allow target to decide periodic, on-change or mix";
             type empty;
           }
           leaf life-time {
             description "Denotes sensor life-time";
             type enumeration {
               enum "long-lived" {
                 description "A long-lived susbcription";
               }
               enum "one-off" {
                 description "An one-off subscription";
               }
             }
           }
         }
         container agent {
           description "Configure analytics agent";
           uses apply-advanced;
           list service-agents {
             key name;
             ordered-by user;
             description "Analytics service agent configuration";
             leaf name {
               description "Analytics service agent name";
               type string;
             }
             uses apply-advanced;
             container inputs {
               description "List of input plugins";
               uses apply-advanced;
               container input-jti-ipfix {
                 presence "enable input-jti-ipfix";
                 description "Junos grpc IPFIX group plugin";
                 uses apply-advanced;
                 container parameters {
                   presence "enable parameters";
                   uses apply-advanced;
                   list record-group {
                     key name;
                     ordered-by user;
                     description "Group sensors";
                     max-elements 10;
                     leaf name {
                       description "Group sensors";
                       type string;
                     }
                     uses apply-advanced;
                     leaf reporting-interval {
                       description "Reporting-interval";
                       default "900";
                       type union {
                         type string {
                           pattern "<.*>|$.*";
                         }
                         type uint32 {
                           range "60 .. 86400";
                         }
                       }
                     }
                     leaf-list record {
                       ordered-by user;
                       description "Ipfix record name";
                       type enumeration {
                         enum "port-statistics" {
                           description "Port statistics";
                         }
                         enum "address-pool-utilization" {
                           description "Address pool utilization";
                         }
                         enum "dhcpv4-server-stats" {
                           description "Dhcpv4 server statistics";
                         }
                         enum "thermal" {
                           description "Thermal statistics";
                         }
                         enum "chassis-inventory" {
                           description "Chassis inventory details";
                         }
                         enum "chassis-power" {
                           description "Chassis power details";
                         }
                         enum "resource-utilization" {
                           description "Resource utilization details";
                         }
                         enum "uptime" {
                           description "Uptime value";
                         }
                         enum "subscriber-statistics" {
                           description "Subscriber statistics";
                         }
                         enum "interface-metadata" {
                           description "Interface metadata details";
                         }
                       }
                     }
                   }
                 }
               }
               container input-ipfix {
                 presence "enable input-ipfix";
                 description "Junos IPFIX Mediator input plugin";
                 uses apply-advanced;
                 container parameters {
                   presence "enable parameters";
                   description "List of IPFIX parameters";
                   uses apply-advanced;
                   leaf tcp-port {
                     description "Listening TCP Port for IPFIX Mediator";
                     type union {
                       type uint16;
                       type string {
                         pattern "<.*>|$.*";
                       }
                     }
                   }
                   leaf maximum-connections {
                     description "Maximum TCP Connections 1..500";
                     type union {
                       type string {
                         pattern "<.*>|$.*";
                       }
                       type uint32 {
                         range "1 .. 500";
                       }
                     }
                   }
                   leaf vrf-name {
                     description "VRF name on which IPFIX packets are accepted";
                     type string;
                   }
                 }
               }
               container analytics {
                 presence "enable analytics";
                 description "Junos Telemetry plugin";
                 uses apply-advanced;
                 container parameters {
                   presence "enable parameters";
                   description "List of key:value parameters";
                   uses apply-advanced;
                   leaf sample-frequency {
                     description "Interval for sensor data in seconds, max 24 hours";
                     default "5";
                     units "seconds";
                     type union {
                       type string {
                         pattern "<.*>|$.*";
                       }
                       type uint32 {
                         range "1 .. 86400";
                       }
                     }
                   }
                   leaf sensors {
                     description "Space separated list of sensor paths";
                     type string {
                       length "1 .. 2048";
                     }
                   }
                   leaf generate-tags {
                     description "Enable generation of tags";
                     type empty;
                   }
                 }
               }
             }
             list outputs {
               key name;
               ordered-by user;
               description "List of output plugins";
               max-elements 1;
               uses output-plugin;
             }
           }
           container traceoptions {
             presence "enable traceoptions";
             uses apply-advanced;
             leaf flag {
               description "Set log level for tracing";
               type enumeration {
                 enum "trace" {
                   description "Log level TRACE, will trace everything";
                 }
                 enum "debug" {
                   description "Log level DEBUG, will trace debug messages";
                 }
                 enum "info" {
                   description "Log level INFO";
                 }
                 enum "error" {
                   description "Log level ERROR, will trace all error messages";
                 }
               }
             }
             leaf filename {
               description "Configure filename for trace messages";
               default "ntf-agent.log";
               type string;
             }
           }
         }
       }
       container jinsightd {
         presence "enable jinsightd";
         description "Health Monitoring services";
         uses apply-advanced;
         container traceoptions {
           description "Jinsight trace options";
           uses apply-advanced;
           leaf no-remote-trace {
             description "Disable remote tracing";
             junos:must "(\"system tracing\")";
             junos:must-message "'no-remote-trace' is valid only when [system tracing] is configured";
             type empty;
           }
           container file {
             description "Trace file information";
             leaf filename {
               description "Name of file in which to write trace information";
               type string {
                 length "1 .. 1024";
                 junos:posix-pattern "![/ %]";
                 junos:pattern-message "Must not contain '/', % or a space";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             description "Tracing parameters";
             leaf name {
               type enumeration {
                 enum "all" {
                   description "Trace all events";
                 }
                 enum "rule-engine" {
                   description "Log configuration rule engine";
                 }
                 enum "core" {
                   description "Trace core message events";
                 }
                 enum "database" {
                   description "Trace database events";
                 }
                 enum "timer" {
                   description "Trace timer events";
                 }
               }
             }
           }
         }
         container subscribe {
           presence "enable subscribe";
           description "Subscription";
           uses apply-advanced;
           leaf health-monitor {
             description "Health-monitor parameters";
             type empty;
           }
         }
       }
       container captive-portal-content-delivery {
         description "Configuration for captive portal and content delivery service";
         uses apply-advanced;
         leaf auto-deactivate {
           description "Deactivate content delivery service";
           type string;
         }
         list rule {
           key name;
           ordered-by user;
           description "Define a captive portal content delivery rule";
           uses cpcd-rule-object-type;
         }
         list rule-set {
           key name;
           ordered-by user;
           description "Define a set of captive portal content delivery rules";
           max-elements 16960;
           leaf name {
             description "Name of the rule set";
             type string {
               length "1 .. 63";
               junos:posix-pattern "^[[:alnum:]][[:alnum:]_-]*$";
               junos:pattern-message "Must be a string beginning with a number or letter and consisting of letters, numbers, dashes and underscores.";
             }
           }
           uses apply-advanced;
           list rule {
             key name;
             ordered-by user;
             description "Rule to be included in this rule set";
             max-elements 16960;
             leaf name {
               description "Rule name";
               junos:must "(\"services  captive-portal-content-delivery rule $$\")";
               junos:must-message "rule must be configured";
               type string {
                 junos:posix-pattern "^[A-Za-z0-9][_0-9A-Za-z-]{0,62}$";
                 junos:pattern-message "Must be a string beginning with a number or letter and consisting of no more than 63 total letters, numbers, dashes and underscores.";
               }
             }
             uses apply-advanced;
           }
         }
         list profile {
           key name;
           ordered-by user;
           description "One or more rule/rule set in the profile";
           leaf name {
             description "Profile name";
             type string {
               length "1 .. 63";
             }
           }
           uses apply-advanced;
           choice cpcd_rules_choice {
             case case_1 {
               leaf dynamic {
                 description "Dynamic profile flag";
                 type empty;
               }
             }
             case case_2 {
               list cpcd-rules {
                 key name;
                 ordered-by user;
                 description "List of captive portal content delivery rules";
                 leaf name {
                   junos:must "(\"services captive-portal-content-delivery rule $$\")";
                   junos:must-message "referenced cpcd rules must be defined";
                   type string {
                     length "1 .. 63";
                     junos:posix-pattern "^[[:alnum:]][[:alnum:]_-]*$";
                     junos:pattern-message "Must be a string beginning with a number or letter and consisting of letters, numbers, dashes and underscores.";
                   }
                 }
                 uses apply-advanced;
               }
             }
             case case_3 {
               list cpcd-rule-sets {
                 key name;
                 ordered-by user;
                 description "List of captive portal content delivery rule sets";
                 leaf name {
                   junos:must "(\"services captive-portal-content-delivery rule-set $$\")";
                   junos:must-message "referenced cpcd rule sets must be defined";
                   type string {
                     length "1 .. 63";
                     junos:posix-pattern "^[[:alnum:]][[:alnum:]_-]*$";
                     junos:pattern-message "Must be a string beginning with a number or letter and consisting of letters, numbers, dashes and underscores.";
                   }
                 }
                 uses apply-advanced;
               }
             }
           }
           container ipda-rewrite-options {
             description "Ipda rewrite options";
             uses apply-advanced;
             leaf destination-address {
               description "Default ipda rewrite IP address";
               type jt:ipaddr;
             }
             leaf destination-port {
               description "Default ipda rewrite port";
               type union {
                 type string {
                   pattern "<.*>|$.*";
                 }
                 type uint16 {
                   range "1 .. 65535";
                 }
               }
             }
           }
           container http-redirect-options {
             description "Http redirect options";
             uses apply-advanced;
             leaf url {
               description "URL of the captive portal file";
               type string {
                 junos:posix-pattern "^((http)|(https)):";
                 junos:pattern-message "URL must start with http or https";
               }
             }
           }
           leaf auto-deactivate {
             description "Deactivate content delivery service";
             junos:must "(!(\".. dynamic\"))";
             junos:must-message "auto-deactivate is not applicable for dynamic profile";
             type enumeration {
               enum "never" {
                 description "Deactivate never";
               }
               enum "initial-get" {
                 description "Deactivate on initial http-get";
               }
             }
           }
         }
         container traceoptions {
           description "Captive portal and content delivery trace options";
           uses cpcd-trace-options-type;
         }
       }
       container dynamic-flow-capture {
         description "Configure Dynamic Flow Capture parameters";
         uses apply-advanced;
         leaf g-max-duplicates {
           description "Maximum content destinations for the capture group";
           default "3";
           type union {
             type string {
               pattern "<.*>|$.*";
             }
             type uint32 {
               range "1 .. 64";
             }
           }
         }
         leaf g-duplicates-dropped-periodicity {
           description "Periodicity of DuplicatesDropped notification in secs";
           default "30";
           type union {
             type string {
               pattern "<.*>|$.*";
             }
             type uint32 {
               range "1 .. 255";
             }
           }
         }
         list capture-group {
           key name;
           ordered-by user;
           description "Configure DFC group parameters";
           max-elements 16;
           uses dfc_group_type;
         }
         container traceoptions {
           presence "enable traceoptions";
           description "Trace options for dynamic-flow-capture service";
           uses apply-advanced;
           leaf no-remote-trace {
             description "Disable remote tracing";
             junos:must "(\"system tracing\")";
             junos:must-message "'no-remote-trace' is valid only when [system tracing] is configured";
             type empty;
           }
           container file {
             description "Trace file information";
             leaf filename {
               description "Name of file in which to write trace information";
               type string {
                 length "1 .. 1024";
                 junos:posix-pattern "![/ %]";
                 junos:pattern-message "Must not contain '/', % or a space";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
         }
       }
       container flow-tap {
         description "Configure flow-tap parameters";
         uses apply-advanced;
         container family {
           description "Address family of packets to tap";
           uses apply-advanced;
           leaf inet {
             description "IPv4 family";
             type empty;
           }
           leaf inet6 {
             description "IPv4 family";
             type empty;
           }
           leaf ccc {
             description "CCC family";
             type empty;
           }
         }
         leaf interface {
           description "Service interface on which to configure flow-tap service";
           junos:must "(!(\"services flow-tap tunnel-interface\"))";
           junos:must-message "tunnel-interface and service interface cannot be confgured together for flowtap application";
           junos:must "(!(\"services dynamic-flow-capture\"))";
           junos:must-message "Dynamic flow capture cannot be configured when flow tap is configured";
           junos:must "(\"interfaces $$-IFL family inet\")";
           junos:must-message "Interface with family inet must be defined in the [edit interfaces] hierarchy";
           type union {
             type jt:interface-name;
             type string {
               pattern "<.*>|$.*";
             }
           }
         }
         leaf tunnel-interface {
           description "Tunnel interface through which flow-tap would communicate with MD";
           junos:must "(!(\"services flow-tap interface\"))";
           junos:must-message "tunnel-interface and service interface cannot be confgured together for flowtap application";
           junos:must "(!(\"services dynamic-flow-capture\"))";
           junos:must-message "Dynamic flow capture cannot be configured when flow tap is configured";
           junos:must "(\"interfaces $$-IFL family inet6\")";
           junos:must-message "Interface with family inet6 must be defined in the [edit interfaces] hierarchy";
           junos:must "(\"interfaces $$-IFL family inet\")";
           junos:must-message "Interface with family inet must be defined in the [edit interfaces] hierarchy";
           type union {
             type jt:interface-name;
             type string {
               pattern "<.*>|$.*";
             }
           }
         }
       }
       container radius-flow-tap {
         description "Configure radius triggered flow-tap parameters";
         uses apply-advanced;
         leaf forwarding-class {
           description "Forwarding class assigned to intercepted packets";
           type string {
             junos:posix-pattern "^.{1,64}$";
             junos:pattern-message "Must be string of 64 characters or less";
           }
         }
         leaf source-ipv4-address {
           description "IP Address to use as source address in IPv4 header appended to intercepted packets";
           type jt:ipv4addr;
         }
         leaf multicast-interception {
           description "Enable Multicast Tapping";
           type empty;
         }
         container interfaces {
           description "Tunnel Interfaces";
           uses apply-advanced;
           list tunnel-interface {
             key name;
             uses tunnel_interface_type;
           }
         }
         choice ri_or_ls {
           case case_1 {
             leaf routing-instance {
               description "Routing instance to be used for radius flow tap";
               junos:must "(\"routing-instances $$\")";
               junos:must-message "Referenced routing instance must be defined";
               type string;
             }
           }
           case case_2 {
             list logical-system {
               key name;
               ordered-by user;
               description "Logical system to be used for radius flow tap";
               max-elements 1;
               leaf name {
                 description "Logical system name";
                 junos:must "(\"logical-systems $$\")";
                 junos:must-message "Referenced logical system must be defined";
                 type string;
               }
               uses apply-advanced;
               leaf routing-instance {
                 description "Routing instance to be used for radius flow tap";
                 junos:must "(\"logical-systems ${logical-system} routing-instances $$\")";
                 junos:must-message "Referenced routing instance must be defined";
                 type string;
               }
             }
           }
         }
         list policy {
           key name;
           ordered-by user;
           description "Policy";
           leaf name {
             description "Policy Name";
             type string {
               junos:posix-pattern "^.{1,64}$";
               junos:pattern-message "Must be string of 64 characters or less";
             }
           }
           uses apply-advanced;
           container inet {
             description "Protocol family IPv4 drop policy terms";
             uses apply-advanced;
             list drop-policy {
               key name;
               ordered-by user;
               description "Define an IPv4 drop policy";
               uses drop-policy-term;
             }
           }
           container inet6 {
             description "Protocol family IPv6 drop policy terms";
             uses apply-advanced;
             list drop-policy {
               key name;
               ordered-by user;
               description "Define an IPv6 drop policy";
               uses drop-policy6-term;
             }
           }
         }
         container snmp {
           description "SNMP options for radius flow tap";
           uses apply-advanced;
           list notify-targets {
             key name;
             ordered-by user;
             description "Target list for packet mirror SNMP notifications";
             leaf name {
               description "Target IP address";
               type jt:ipaddr;
             }
             uses apply-advanced;
           }
         }
       }
       container mobile-flow-tap {
         description "Configure mobile triggered flow-tap parameters";
         uses apply-advanced;
         container source-interface {
           presence "enable source-interface";
           junos:must "(!(\"services dynamic-flow-capture\"))";
           junos:must-message "mobile flow service and dynamic flow capture service cannot be configured together";
           junos:must "(!(\"services radius-flow-tap\"))";
           junos:must-message "mobile flow service and radius flow capture service cannot be configured together";
           junos:must "(!(\"services flow-tap\"))";
           junos:must-message "mobile flow service and flow capture service cannot be configured together";
           description "Source interface from which IRI packets will be sent";
           leaf interface-name {
             description "Interface name";
             junos:must "(\"interfaces $$\")";
             junos:must-message "Interface must be defined";
             type union {
               type jt:interface-name;
               type string {
                 pattern "<.*>|$.*";
               }
             }
           }
           leaf ipv4-address {
             description "Source IPv4 address to be used";
             type jt:ipv4addr;
           }
         }
       }
       container flow-monitoring {
         presence "enable flow-monitoring";
         description "Configure flow monitoring";
         uses apply-advanced;
         container version9 {
           description "Version 9 configuration";
           uses apply-advanced;
           list template {
             key name;
             ordered-by user;
             description "One or more version 9 templates";
             max-elements 10;
             uses version9-template;
           }
         }
         container version-ipfix {
           description "Version IP-Fix configuration";
           uses apply-advanced;
           list template {
             key name;
             ordered-by user;
             description "One or more version ip-fix templates";
             max-elements 10;
             uses version-ipfix-template;
           }
         }
       }
       container jdaf {
         description "Juniper distributed application framework (JDAF)";
         uses apply-advanced;
         leaf-list routing-instances {
           ordered-by user;
           description "List of routing-instance name for JDAF clients";
           type string {
             length "1 .. 128";
           }
         }
       }
       container rpm {
         presence "enable rpm";
         description "Real-time performance monitoring";
         uses apply-advanced;
         container traceoptions {
           description "RMOPD trace options";
           uses rmopd-traceoptions;
         }
         container bgp {
           description "BGP options for real-time performance monitoring";
           uses apply-advanced;
           leaf probe-type {
             description "RPM-BGP probe request type";
             default "icmp-ping";
             type enumeration {
               enum "icmp-ping" {
                 description "Send ICMP echo request to target address";
               }
               enum "icmp-ping-timestamp" {
                 description "Send ICMP timestamp request to target address";
               }
               enum "icmp6-ping" {
                 description "Send ICMP6 echo request to target address";
               }
               enum "tcp-ping" {
                 description "Send TCP packets to target";
               }
               enum "udp-ping" {
                 description "Send UDP packets to target";
               }
               enum "udp-ping-timestamp" {
                 description "Send UDP packets with timestamp to target";
               }
             }
           }
           leaf probe-count {
             description "Total number of probes per test";
             default "1";
             type union {
               type string {
                 pattern "<.*>|$.*";
               }
               type uint32 {
                 range "1 .. 15";
               }
             }
           }
           leaf probe-interval {
             description "Delay between probes";
             default "3";
             units "seconds";
             type union {
               type string {
                 pattern "<.*>|$.*";
               }
               type uint32 {
                 range "1 .. 255";
               }
             }
           }
           leaf test-interval {
             description "Delay between tests";
             default "1";
             units "seconds";
             type union {
               type string {
                 pattern "<.*>|$.*";
               }
               type uint32 {
                 range "0 .. 86400";
               }
             }
           }
           leaf destination-port {
             description "TCP/UDP port number";
             type union {
               type string {
                 pattern "<.*>|$.*";
               }
               type uint16 {
                 range "7 .. 65535";
               }
             }
           }
           leaf history-size {
             description "Number of stored history entries";
             default "50";
             type union {
               type string {
                 pattern "<.*>|$.*";
               }
               type uint32 {
                 range "0 .. 512";
               }
             }
           }
           leaf moving-average-size {
             description "Number of samples used for moving average";
             default "0";
             type union {
               type string {
                 pattern "<.*>|$.*";
               }
               type uint32 {
                 range "0 .. 1024";
               }
             }
           }
           leaf data-size {
             description "Size of the data portion of the probes";
             default "0";
             type union {
               type string {
                 pattern "<.*>|$.*";
               }
               type uint32 {
                 range "0 .. 65400";
               }
             }
           }
           leaf data-fill {
             description "Define contents of the data portion of the probes";
             type string {
               length "1 .. 2048";
               junos:posix-pattern "^[[:xdigit:]]+$";
               junos:pattern-message "Must be hexadecimal digits (0-9, a-f, A-F)";
             }
           }
           leaf ttl {
             description "Time to Live (hop-limit) value for an RPM IPv4(IPv6) packet";
             default "64";
             type union {
               type string {
                 pattern "<.*>|$.*";
               }
               type uint32 {
                 range "1 .. 254";
               }
             }
           }
           list logical-system {
             key name;
             description "Logical systems";
             uses bgp-logical-system;
           }
           list routing-instances {
             key name;
             description "Routing instances";
             uses bgp-routing-instances;
           }
         }
         list probe {
           key name;
           ordered-by user;
           description "TCP/UDP/ICMP ping";
           leaf name {
             description "Name of owner";
             type string {
               length "1 .. 32";
             }
           }
           uses apply-advanced;
           leaf delegate-probes {
             description "Offload real-time performance monitoring probes to MS-MIC/MS-MPC card";
             type empty;
           }
           list test {
             key name;
             ordered-by user;
             description "TCP/UDP/ICMP/ICMP6 ping test";
             leaf name {
               description "Name of test";
               type string {
                 length "1 .. 32";
               }
             }
             uses apply-advanced;
             container rpm-scale {
               presence "enable rpm-scale";
               description "Configuring real-time performance monitoring scale tests";
               uses apply-advanced;
               leaf tests-count {
                 description "Number of probe-tests generated using scale config";
                 type union {
                   type string {
                     pattern "<.*>|$.*";
                   }
                   type uint32 {
                     range "1 .. 500000";
                   }
                 }
               }
               choice target-type {
                 case case_1 {
                   container target {
                     presence "enable target";
                     junos:must "(!(\".. source-inet6\"))";
                     junos:must-message "source-inet6 knob not valid for IPV4 probes";
                     description "Target address generation for scale test config";
                     uses apply-advanced;
                     leaf address-base {
                       description "Base address of target host in a.b.c.d format";
                       type jt:ipv4addr;
                     }
                     leaf step {
                       description "Steps to increment target address in a.b.c.d format";
                       type jt:ipv4addr;
                     }
                     leaf count {
                       description "Target address count";
                       type union {
                         type string {
                           pattern "<.*>|$.*";
                         }
                         type uint32 {
                           range "1 .. 500000";
                         }
                       }
                     }
                   }
                 }
                 case case_2 {
                   container target-inet6 {
                     presence "enable target-inet6";
                     junos:must "(!(\".. source\"))";
                     junos:must-message "source knob not valid for IPV6 probes";
                     description "IPv6 target address generation for scale test config";
                     uses apply-advanced;
                     leaf address-base {
                       description "Base address of target host in a:b:c:d:e:f:g:h format";
                       type jt:ipv6addr;
                     }
                     leaf step {
                       description "Steps to increment target address in a:b:c:d:e:f:g:h format";
                       type jt:ipv6addr;
                     }
                     leaf count {
                       description "Target address count";
                       type union {
                         type string {
                           pattern "<.*>|$.*";
                         }
                         type uint32 {
                           range "1 .. 500000";
                         }
                       }
                     }
                   }
                 }
               }
               choice source-type {
                 case case_1 {
                   container source {
                     presence "enable source";
                     junos:must "(!(\".. target-inet6\"))";
                     junos:must-message "target-inet6 knob not valid for IPV4 probes";
                     description "Source address generation in scale tests";
                     uses apply-advanced;
                     leaf address-base {
                       description "Base address of host in a.b.c.d format";
                       type jt:ipv4addr;
                     }
                     leaf step {
                       description "Steps to increment src address in a.b.c.d format";
                       type jt:ipv4addr;
                     }
                     leaf count {
                       description "Source-address count";
                       type union {
                         type string {
                           pattern "<.*>|$.*";
                         }
                         type uint32 {
                           range "1 .. 500000";
                         }
                       }
                     }
                   }
                 }
                 case case_2 {
                   container source-inet6 {
                     presence "enable source-inet6";
                     junos:must "(!(\".. target\"))";
                     junos:must-message "target knob not valid for IPV6 probes";
                     description "IPv6 source address generation in scale tests";
                     uses apply-advanced;
                     leaf address-base {
                       description "Base address of host in a:b:c:d:e:f:g:h format";
                       type jt:ipv6addr;
                     }
                     leaf step {
                       description "Steps to increment src address in a:b:c:d:e:f:g:h format";
                       type jt:ipv6addr;
                     }
                     leaf count {
                       description "Source-address count";
                       type union {
                         type string {
                           pattern "<.*>|$.*";
                         }
                         type uint32 {
                           range "1 .. 500000";
                         }
                       }
                     }
                   }
                 }
               }
               container destination {
                 presence "enable destination";
                 description "Name of output interface for probes";
                 uses apply-advanced;
                 leaf interface {
                   description "Base destination interface for scale test";
                   type union {
                     type jt:interface-name;
                     type string {
                       pattern "<.*>|$.*";
                     }
                   }
                 }
                 leaf subunit-cnt {
                   description "Subunit count for destination interface for scale test";
                   type union {
                     type string {
                       pattern "<.*>|$.*";
                     }
                     type uint32 {
                       range "1 .. 500000";
                     }
                   }
                 }
               }
             }
             leaf probe-type {
               description "Probe request type";
               default "icmp-ping";
               type enumeration {
                 enum "http-get" {
                   description "Perform HTTP Get request at target URL";
                 }
                 enum "http-metadata-get" {
                   description "Perform HTTP Get request of metadata at target URL";
                 }
                 enum "icmp-ping" {
                   description "Send ICMP echo request to target address";
                 }
                 enum "icmp-ping-timestamp" {
                   description "Send ICMP timestamp request to target address";
                 }
                 enum "icmp6-ping" {
                   description "Send ICMP6 echo request to target address";
                 }
                 enum "tcp-ping" {
                   description "Send TCP packets to target";
                 }
                 enum "udp-ping" {
                   description "Send UDP packets to target";
                 }
                 enum "udp-ping-timestamp" {
                   description "Send UDP packets with timestamp to target";
                 }
               }
             }
             container target {
               presence "enable target";
               description "Target destination for probe";
               choice target-type {
                 case case_1 {
                   leaf address {
                     description "Address of target host";
                     junos:must "(!(\".. .. inet6-options\"))";
                     junos:must-message "inet6-options knob not valid for IPV4 probes";
                     type jt:ipv4addr;
                   }
                 }
                 case case_2 {
                   leaf inet6-address {
                     description "Inet6 Address of target host";
                     junos:must "(!(\".. .. source-address\"))";
                     junos:must-message "source-address knob not valid for IPV6 probes";
                     type jt:ipv6addr;
                   }
                 }
                 case case_3 {
                   leaf url {
                     description "Fully formed target URL";
                     junos:must "(!(\".. .. inet6-options\"))";
                     junos:must-message "inet6-options knob not valid for IPV4 probes";
                     type string;
                   }
                 }
                 case case_4 {
                   leaf inet6-url {
                     description "Fully formed target IPV6 URL";
                     junos:must "(!(\".. .. source-address\"))";
                     junos:must-message "source-address knob not valid for IPV6 probes";
                     type string;
                   }
                 }
               }
             }
             container inet6-options {
               presence "enable inet6-options";
               description "IPV6 related options";
               uses apply-advanced;
               leaf source-address {
                 description "Inet6 Source Address of the probe";
                 type jt:ipv6addr;
               }
             }
             leaf probe-count {
               description "Total number of probes per test";
               default "1";
               type union {
                 type string {
                   pattern "<.*>|$.*";
                 }
                 type uint32 {
                   range "1 .. 15";
                 }
               }
             }
             leaf probe-interval {
               description "Delay between probes";
               default "3";
               units "seconds";
               type union {
                 type string {
                   pattern "<.*>|$.*";
                 }
                 type uint32 {
                   range "1 .. 255";
                 }
               }
             }
             leaf test-interval {
               description "Delay between tests";
               default "1";
               units "seconds";
               type union {
                 type string {
                   pattern "<.*>|$.*";
                 }
                 type uint32 {
                   range "0 .. 86400";
                 }
               }
             }
             leaf destination-port {
               description "TCP/UDP port number";
               type union {
                 type string {
                   pattern "<.*>|$.*";
                 }
                 type uint16 {
                   range "7 .. 65535";
                 }
               }
             }
             leaf source-address {
               description "Source address for probe";
               junos:must "(!(\".. target inet6-address\"))";
               junos:must-message "source-address knob for IPV6 based probes is under inet6-options";
               type jt:ipv4addr;
             }
             leaf routing-instance {
               description "Routing instance used by probes";
               junos:must "(\"routing-instances $$\")";
               junos:must-message "referenced routing-instance must be defined";
               type string {
                 junos:posix-pattern "!^((__.*__)|(all)|(.*[ ].*)|(\"\")|(.{129,}))$";
                 junos:pattern-message "Must be a non-reserved string of 128 characters or less with no spaces.";
               }
             }
             leaf history-size {
               description "Number of stored history entries";
               default "50";
               type union {
                 type string {
                   pattern "<.*>|$.*";
                 }
                 type uint32 {
                   range "0 .. 512";
                 }
               }
             }
             leaf moving-average-size {
               description "Number of samples used for moving average";
               default "0";
               type union {
                 type string {
                   pattern "<.*>|$.*";
                 }
                 type uint32 {
                   range "0 .. 1024";
                 }
               }
             }
             leaf dscp-code-points {
               description "Differentiated Services code point bits or alias";
               default "000000";
               type string {
                 junos:posix-pattern "^(([01]{6})|([a-zA-Z].{0,63}))$";
                 junos:pattern-message "Not 6-bit pattern or code point alias";
               }
             }
             leaf data-size {
               description "Size of the data portion of the probes";
               default "0";
               type union {
                 type string {
                   pattern "<.*>|$.*";
                 }
                 type uint32 {
                   range "0 .. 65400";
                 }
               }
             }
             leaf data-fill {
               description "Define contents of the data portion of the probes";
               type string {
                 length "1 .. 2048";
                 junos:posix-pattern "^[[:xdigit:]]+$";
                 junos:pattern-message "Must be hexadecimal digits (0-9, a-f, A-F)";
               }
             }
             leaf ttl {
               description "Time to Live (hop-limit) value for an RPM IPv4(IPv6) packet";
               default "64";
               type union {
                 type string {
                   pattern "<.*>|$.*";
                 }
                 type uint32 {
                   range "1 .. 254";
                 }
               }
             }
             container thresholds {
               presence "enable thresholds";
               description "Probe and test threshold values. Set 0 to disable respective threshold";
               uses apply-advanced;
               leaf successive-loss {
                 description "Successive probe loss count indicating probe failure";
                 default "1";
                 type union {
                   type string {
                     pattern "<.*>|$.*";
                   }
                   type uint32 {
                     range "0 .. 15";
                   }
                 }
               }
               leaf total-loss {
                 description "Total probe loss count indicating test failure";
                 default "1";
                 type union {
                   type string {
                     pattern "<.*>|$.*";
                   }
                   type uint32 {
                     range "0 .. 15";
                   }
                 }
               }
               leaf rtt {
                 description "Maximum round trip time per probe";
                 default "0";
                 units "microseconds";
                 type union {
                   type string {
                     pattern "<.*>|$.*";
                   }
                   type uint32 {
                     range "0 .. 60000000";
                   }
                 }
               }
               leaf jitter-rtt {
                 description "Maximum jitter per test";
                 default "0";
                 units "microseconds";
                 type union {
                   type string {
                     pattern "<.*>|$.*";
                   }
                   type uint32 {
                     range "0 .. 60000000";
                   }
                 }
               }
               leaf std-dev-rtt {
                 description "Maximum standard deviation per test";
                 default "0";
                 units "microseconds";
                 type union {
                   type string {
                     pattern "<.*>|$.*";
                   }
                   type uint32 {
                     range "0 .. 60000000";
                   }
                 }
               }
               leaf egress-time {
                 description "Maximum source to destination time per probe";
                 default "0";
                 units "microseconds";
                 type union {
                   type string {
                     pattern "<.*>|$.*";
                   }
                   type uint32 {
                     range "0 .. 60000000";
                   }
                 }
               }
               leaf ingress-time {
                 description "Maximum destination to source time per probe";
                 default "0";
                 units "microseconds";
                 type union {
                   type string {
                     pattern "<.*>|$.*";
                   }
                   type uint32 {
                     range "0 .. 60000000";
                   }
                 }
               }
               leaf jitter-ingress {
                 description "Maximum destination to source jitter per test";
                 default "0";
                 units "microseconds";
                 type union {
                   type string {
                     pattern "<.*>|$.*";
                   }
                   type uint32 {
                     range "0 .. 60000000";
                   }
                 }
               }
               leaf jitter-egress {
                 description "Maximum source to destination jitter per test";
                 default "0";
                 units "microseconds";
                 type union {
                   type string {
                     pattern "<.*>|$.*";
                   }
                   type uint32 {
                     range "0 .. 60000000";
                   }
                 }
               }
               leaf std-dev-ingress {
                 description "Maximum destination to source standard deviation per test";
                 default "0";
                 units "microseconds";
                 type union {
                   type string {
                     pattern "<.*>|$.*";
                   }
                   type uint32 {
                     range "0 .. 60000000";
                   }
                 }
               }
               leaf std-dev-egress {
                 description "Maximum source to destination standard deviation per test";
                 default "0";
                 units "microseconds";
                 type union {
                   type string {
                     pattern "<.*>|$.*";
                   }
                   type uint32 {
                     range "0 .. 60000000";
                   }
                 }
               }
             }
             leaf-list traps {
               ordered-by user;
               description "Trap to send if threshold is met or exceeded";
               type enumeration {
                 enum "probe-failure" {
                   description "Successive probe loss threshold reached";
                 }
                 enum "test-failure" {
                   description "Total probe loss threshold reached";
                 }
                 enum "test-completion" {
                   description "Test completed";
                 }
                 enum "rtt-exceeded" {
                   description "Exceeded maximum round trip time threshold";
                 }
                 enum "std-dev-exceeded" {
                   description "Exceeded round trip time standard deviation threshold";
                 }
                 enum "jitter-exceeded" {
                   description "Exceeded jitter in round trip time threshold";
                 }
                 enum "ingress-time-exceeded" {
                   description "Exceeded maximum ingress time threshold";
                 }
                 enum "ingress-std-dev-exceeded" {
                   description "Exceeded ingress time standard deviation threshold";
                 }
                 enum "ingress-jitter-exceeded" {
                   description "Exceeded jitter in ingress time threshold";
                 }
                 enum "egress-time-exceeded" {
                   description "Exceeded maximum egress time threshold";
                 }
                 enum "egress-std-dev-exceeded" {
                   description "Exceeded egress time standard deviation threshold";
                 }
                 enum "egress-jitter-exceeded" {
                   description "Exceeded jitter in egress time threshold";
                 }
               }
             }
             leaf destination-interface {
               description "Name of output interface for probes";
               type union {
                 type jt:interface-name;
                 type string {
                   pattern "<.*>|$.*";
                 }
               }
             }
             leaf hardware-timestamp {
               description "Packet Forwarding Engine updates timestamps";
               junos:must "(!(\".. target inet6-address\"))";
               junos:must-message "Hardware timestamping not supported for IPV6 based probes.";
               junos:must "((!(\".. destination-port\") || \".. destination-port $$={7}\"))";
               junos:must-message "For UDP pings, only port 7 can be configured for hardware timestamping.";
               type empty;
             }
             leaf one-way-hardware-timestamp {
               description "Enable hardware timestamps for one-way measurements";
               junos:must "(!(\".. target inet6-address\"))";
               junos:must-message "One-way hardware timestamping not supported for IPV6 based probes.";
               type empty;
             }
             leaf next-hop {
               description "Next-hop to which probe should be sent";
               type jt:ipv4addr;
             }
           }
         }
         container probe-server {
           description "ICMP/TCP/UDP probe server";
           uses apply-advanced;
           container icmp {
             description "ICMP probe server";
             uses apply-advanced;
             leaf destination-interface {
               description "Name of output interface for probes";
               type union {
                 type jt:interface-name;
                 type string {
                   pattern "<.*>|$.*";
                 }
               }
             }
           }
           container tcp {
             description "TCP probe server";
             uses apply-advanced;
             leaf port {
               description "Port number 7 through 65535";
               type union {
                 type uint16;
                 type string {
                   pattern "<.*>|$.*";
                 }
               }
             }
             leaf destination-interface {
               description "Name of output interface for probes";
               type union {
                 type jt:interface-name;
                 type string {
                   pattern "<.*>|$.*";
                 }
               }
             }
           }
           container udp {
             description "UDP probe server";
             uses apply-advanced;
             leaf port {
               description "Port number 7 through 65535";
               type union {
                 type uint16;
                 type string {
                   pattern "<.*>|$.*";
                 }
               }
             }
             leaf destination-interface {
               description "Name of output interface for probes";
               type union {
                 type jt:interface-name;
                 type string {
                   pattern "<.*>|$.*";
                 }
               }
             }
           }
         }
         leaf probe-limit {
           description "Maximum number of concurrent probes allowed";
           default "100";
           type union {
             type string {
               pattern "<.*>|$.*";
             }
             type uint32 {
               range "1 .. 500";
             }
           }
         }
         container rfc2544-benchmarking {
           presence "enable rfc2544-benchmarking";
           description "Rfc2544 benchmarking tests";
           uses apply-advanced;
           container profiles {
             description "Rfc2544 test profiles";
             uses apply-advanced;
             list test-profile {
               key name;
               ordered-by user;
               description "Test-profile definition";
               leaf name {
                 description "Test name";
                 junos:must "(\".. bandwidth-kbps\")";
                 junos:must-message "bandwidth-kbps has to be configured in a profile";
                 junos:must "(\".. test-type\")";
                 junos:must-message "test-type has to be configured in a profile";
                 junos:must "(\".. packet-size\")";
                 junos:must-message "packet-size has to be configured in a profile";
                 type string {
                   length "1 .. 32";
                 }
               }
               uses apply-advanced;
               leaf test-type {
                 description "Rfc2544 test type";
                 default "throughput";
                 type enumeration {
                   enum "throughput" {
                     description "Rfc2544 throughput test";
                   }
                   enum "latency" {
                     description "Rfc2544 latency test";
                   }
                   enum "frame-loss" {
                     description "Rfc2544 frame-loss test";
                   }
                   enum "back-back-frames" {
                     description "Rfc2544 back to back frames test";
                   }
                 }
               }
               leaf-list packet-size {
                 ordered-by user;
                 description "Size of the test packet";
                 type union {
                   type string {
                     pattern "<.*>|$.*";
                   }
                   type uint32 {
                     range "64 .. 9216";
                   }
                 }
               }
               leaf bandwidth-kbps {
                 description "Theoretical max service bandwidth in kbps (1000..1000000)";
                 default "10000";
                 type union {
                   type uint32;
                   type string {
                     pattern "<.*>|$.*";
                   }
                 }
               }
               leaf step-percent {
                 description "Step percent for test";
                 default "10";
                 junos:must "(\".. test-type frame-loss\")";
                 junos:must-message "step-percent is valid only for frame-loss test";
                 type union {
                   type string {
                     pattern "<.*>|$.*";
                   }
                   type uint32 {
                     range "1 .. 100";
                   }
                 }
               }
             }
           }
           container tests {
             presence "enable tests";
             description "Rfc2544 test configuration";
             uses apply-advanced;
             list test-name {
               key name;
               ordered-by user;
               description "Test definition";
               leaf name {
                 description "Test name";
                 junos:must "(\".. mode\")";
                 junos:must-message "mode has to be configured in a test";
                 type string {
                   length "1 .. 32";
                 }
               }
               uses apply-advanced;
               leaf test-profile {
                 description "Name of the test profile";
                 junos:must "(\".. family\")";
                 junos:must-message "family has to be configured in a test";
                 junos:must "(\"services rpm rfc2544-benchmarking profiles test-profile $$\")";
                 junos:must-message "test-profile not configured";
                 type string;
               }
               leaf source-mac-address {
                 description "MAC address of source host in xx:xx:xx:xx:xx:xx format -Generator MAC";
                 junos:must "((\".. family ccc\" || (\".. family bridge\" || \".. family vpls\")))";
                 junos:must-message "source-mac-address valid only for ccc/bridge/vpls family";
                 type jt:mac-unicast;
               }
               leaf destination-mac-address {
                 description "MAC address of destination host in xx:xx:xx:xx:xx:xx format -Reflector MAC";
                 junos:must "((\".. family ccc\" || (\".. family bridge\" || \".. family vpls\")))";
                 junos:must-message "destination-mac-address valid only for ccc/bridge/vpls family";
                 type jt:mac-unicast;
               }
               leaf ovlan-id {
                 description "Outer vlan id";
                 junos:must "(!(\".. mode ethernet-loopback\"))";
                 junos:must-message "ovlan-id is not valid for mode ethernet-loopback";
                 junos:must "((\".. family ccc\" || (\".. family bridge\" || \".. family vpls\")))";
                 junos:must-message "ovlan-id valid only for ccc/bridge/vpls family";
                 type union {
                   type string {
                     pattern "<.*>|$.*";
                   }
                   type int32 {
                     range "0 .. 4094";
                   }
                 }
               }
               leaf ovlan-priority {
                 description "Outer vlan priority";
                 junos:must "(\".. ovlan-id\")";
                 junos:must-message "ovlan-priority is valid only when ovlan-id is configured";
                 junos:must "(\".. family bridge\")";
                 junos:must-message "ovlan-priority is valid only for bridge family";
                 type union {
                   type string {
                     pattern "<.*>|$.*";
                   }
                   type int32 {
                     range "0 .. 7";
                   }
                 }
               }
               leaf ovlan-cfi {
                 description "Outer vlan CFI bit";
                 junos:must "(\".. ovlan-id\")";
                 junos:must-message "ovlan-cfi is valid only when ovlan-id is configured";
                 junos:must "(\".. family bridge\")";
                 junos:must-message "ovlan-cfi is valid only for bridge family";
                 type union {
                   type string {
                     pattern "<.*>|$.*";
                   }
                   type int32 {
                     range "0 .. 1";
                   }
                 }
               }
               leaf outer-tag-protocol-id {
                 description "Outer tag protocol id";
                 default "0x8100";
                 junos:must "(!(\".. mode ethernet-loopback\"))";
                 junos:must-message "outer-tag-protocol-id is not valid for mode ethernet-loopback";
                 junos:must "(\".. ovlan-id\")";
                 junos:must-message "outer-tag-protocol-id is valid only when ovlan-id is configured";
                 junos:must "(\".. family bridge\")";
                 junos:must-message "outer-tag-protocol-id is valid only for Bridge family";
                 type string {
                   junos:posix-pattern "^0x[abcdefABCDEF0123456789]{4}$";
                   junos:pattern-message "Must be hexadecimal bit pattern of form 0xNNNN";
                 }
               }
               leaf ivlan-id {
                 description "Inner vlan id";
                 junos:must "(!(\".. mode ethernet-loopback\"))";
                 junos:must-message "ivlan-id is not valid for mode ethernet-loopback";
                 junos:must "(\".. ovlan-id\")";
                 junos:must-message "ivlan-id is valid only when ovlan-id is configured";
                 junos:must "((\".. family ccc\" || \".. family bridge\"))";
                 junos:must-message "ivlan-id valid only for ccc/bridge family";
                 type union {
                   type string {
                     pattern "<.*>|$.*";
                   }
                   type int32 {
                     range "0 .. 4094";
                   }
                 }
               }
               leaf ivlan-priority {
                 description "Inner vlan priority";
                 junos:must "(\".. ivlan-id\")";
                 junos:must-message "ivlan-priority is valid only when ivlan-id is configured";
                 junos:must "(\".. family bridge\")";
                 junos:must-message "ivlan-priority is valid only for bridge family";
                 type union {
                   type string {
                     pattern "<.*>|$.*";
                   }
                   type int32 {
                     range "0 .. 7";
                   }
                 }
               }
               leaf ivlan-cfi {
                 description "Inner vlan CFI bit";
                 junos:must "(\".. ivlan-id\")";
                 junos:must-message "ivlan-cfi is valid only when ivlan-id is configured";
                 junos:must "(\".. family bridge\")";
                 junos:must-message "ivlan-cfi is valid only for bridge family";
                 type union {
                   type string {
                     pattern "<.*>|$.*";
                   }
                   type int32 {
                     range "0 .. 1";
                   }
                 }
               }
               leaf vlan-id {
                 description "VLAN identifier";
                 junos:must "(\".. mode ethernet-loopback\")";
                 junos:must-message "vlan-id is valid only for ethernet-loopback mode";
                 type union {
                   type string {
                     pattern "<.*>|$.*";
                   }
                   type int32 {
                     range "0 .. 4094";
                   }
                 }
               }
               leaf vlan-priority {
                 description "VLAN priority";
                 junos:must "(\".. vlan-id\")";
                 junos:must-message "vlan-priority is valid only when vlan-id is configured";
                 junos:must "(\".. mode ethernet-loopback\")";
                 junos:must-message "vlan-priority is valid only for ethernet-loopback mode";
                 type union {
                   type string {
                     pattern "<.*>|$.*";
                   }
                   type int32 {
                     range "0 .. 7";
                   }
                 }
               }
               leaf vlan-cfi {
                 description "VLAN CFI bit";
                 junos:must "(\".. vlan-id\")";
                 junos:must-message "vlan-cfi is valid only when vlan-id is configured";
                 junos:must "(\".. mode ethernet-loopback\")";
                 junos:must-message "vlan-cfi is valid only for ethernet-loopback mode";
                 type union {
                   type string {
                     pattern "<.*>|$.*";
                   }
                   type int32 {
                     range "0 .. 1";
                   }
                 }
               }
               leaf service-type {
                 description "Service type";
                 junos:must "(!(\".. mode ethernet-loopback\"))";
                 junos:must-message "service-type is not valid for mode ethernet-loopback";
                 junos:must "((\".. family bridge\" || \".. family vpls\"))";
                 junos:must-message "service-type is valid only for bridge family";
                 type enumeration {
                   enum "eline" {
                     description "Eline service";
                   }
                   enum "elan" {
                     description "Elan service";
                   }
                 }
               }
               leaf in-service {
                 description "Test executed in-service mode";
                 junos:must "(!(\".. mode ethernet-loopback\"))";
                 junos:must-message "in-service is not valid for mode ethernet-loopback";
                 junos:must "((\".. family bridge\" || \".. family vpls\"))";
                 junos:must-message "in-service mode is supported only for bridge/vpls family";
                 type empty;
               }
               leaf ip-swap {
                 description "Swap IP in the test payload";
                 junos:must "((\".. mode reflect\" || \".. mode ethernet-loopback\"))";
                 junos:must-message "ip-swap is valid only in reflector or ethernet-loopback mode";
                 junos:must "((\".. family bridge\" || \".. family vpls\"))";
                 junos:must-message "ip-swap is supported only for bridge/vpls family";
                 type empty;
               }
               leaf udp-tcp-port-swap {
                 description "Swap UDP/TCP port in the test payload";
                 junos:must "((\".. mode reflect\" || \".. mode ethernet-loopback\"))";
                 junos:must-message "udp-tcp-port-swap is valid only in reflector or ethernet-loopback mode";
                 junos:must "((\".. family bridge\" || \".. family vpls\"))";
                 junos:must-message "udp-tcp-port-swap is supported only for bridge/vpls family";
                 type empty;
               }
               leaf ignore-test-interface-state {
                 description "Ignore interface state to run the test";
                 junos:must "(\".. family bridge\")";
                 junos:must-message "ignore-test-interface-state is supported only for bridge family";
                 type empty;
               }
               leaf check-test-interface-mtu {
                 description "Check interface MTU to run the test";
                 junos:must "(\".. family bridge\")";
                 junos:must-message "check-test-interface-mtu is supported only for bridge family";
                 type empty;
               }
               leaf disable-signature-check {
                 description "Signature check disable";
                 junos:must "(\".. mode reflect\")";
                 junos:must-message "disable-signature-check is valid only in reflector mode";
                 type empty;
               }
               leaf forwarding-class {
                 description "Forwarding class assigned to the frames";
                 type string {
                   junos:posix-pattern "^.{1,64}$";
                   junos:pattern-message "Must be string of 64 characters or less";
                 }
               }
               leaf packet-loss-priority {
                 description "Packet loss priority assigned to the frames";
                 junos:must "(\".. family bridge\")";
                 junos:must-message "packet-loss-priority is valid only for bridge family";
                 type enumeration {
                   enum "low" {
                     description "Packet loss priority is low";
                   }
                   enum "high" {
                     description "Packet loss priority is high";
                   }
                   enum "medium-high" {
                     description "Packet loss priority is medium-high";
                   }
                 }
               }
               leaf dscp-code-points {
                 description "Differentiated Services code point bits or alias";
                 default "000000";
                 junos:must "(!(\".. mode terminate\"))";
                 junos:must-message "'dscp-code-points' cannot be configured in terminate mode";
                 junos:must "(!(\".. mode ethernet-loopback\"))";
                 junos:must-message "'dscp-code-points' cannot be configured in ethernet-loopback mode";
                 junos:must "(!(\".. mode reflect\"))";
                 junos:must-message "'dscp-code-points' cannot be configured in reflector mode";
                 type string {
                   junos:posix-pattern "^(([01]{6})|([a-zA-Z].{0,63}))$";
                   junos:pattern-message "Not 6-bit pattern or code point alias";
                 }
               }
               leaf mode {
                 description "Test mode";
                 type enumeration {
                   enum "reflect" {
                     description "Reflector end";
                     junos:must "(\".. family\")";
                     junos:must-message "family has to be configured in a test";
                   }
                   enum "initiate-and-terminate" {
                     description "Initiate and terminator";
                     junos:must "(\".. test-profile\")";
                     junos:must-message "test-profile <profilename> has to be configured in a test when in initiate:and-terminate mode";
                   }
                   enum "ethernet-loopback" {
                     description "Ethernet loopback";
                     junos:must "(\".. test-interface\")";
                     junos:must-message "test-interface has to be configured in a test when in ethernet-loopback mode";
                     junos:must "(\".. family bridge\")";
                     junos:must-message "family bridge has to be configured in a test";
                   }
                 }
               }
               leaf reflect-mode {
                 description "Reflect mode";
                 junos:must "((\".. mode reflect\" || \".. mode ethernet-loopback\"))";
                 junos:must-message "reflect-mode is valid only when test mode is reflect or ethernet-loopback";
                 type enumeration {
                   enum "mac-swap" {
                     description "Mac swap ";
                   }
                   enum "no-mac-swap" {
                     description "No mac-swap";
                     junos:must "(!(\".. service-type elan\"))";
                     junos:must-message "'no-mac-swap' cannot be configured for elan service-type";
                   }
                   enum "mac-rewrite" {
                     description "Mac-rewrite";
                     junos:must "(\".. destination-mac-address\")";
                     junos:must-message "destination-mac-address needs to be configured with mac-rewrite mode";
                     junos:must "(\".. source-mac-address\")";
                     junos:must-message "source-mac-address needs to be configured with mac-rewrite mode";
                     junos:must "(!(\".. mode ethernet-loopback\"))";
                     junos:must-message "'mac-rewrite' cannot be configured for mode ethernet-loopback";
                   }
                 }
               }
               leaf family {
                 description "Family type";
                 type enumeration {
                   enum "inet" {
                     description "Inet family";
                     junos:must "(\".. destination-ipv4-address\")";
                     junos:must-message "destination-ipv4-address has to be configured with inet family";
                     junos:must "(\".. destination-udp-port\")";
                     junos:must-message "destination-udp-port has to be configured with inet family";
                   }
                   enum "ccc" {
                     description "CCC family ";
                     junos:must "(\".. direction\")";
                     junos:must-message "direction needs to be configured with CCC family";
                   }
                   enum "bridge" {
                     description "Bridge family ";
                     junos:must "(\".. test-interface\")";
                     junos:must-message "test-interface has to be configured with bridge family";
                     junos:must "(\".. direction\")";
                     junos:must-message "Direction needs to be configured with bridge family";
                   }
                   enum "vpls" {
                     description "VPLS family ";
                     junos:must "(\".. test-interface\")";
                     junos:must-message "test-interface has to be configured with vpls family";
                     junos:must "(\".. source-mac-address\")";
                     junos:must-message "source-mac-address has to be configured with vpls family";
                     junos:must "(\".. destination-mac-address\")";
                     junos:must-message "destination-mac-address has to be configured with vpls family";
                     junos:must "(\".. direction\")";
                     junos:must-message "Direction needs to be configured with vpls family";
                   }
                 }
               }
               leaf reflect-etype {
                 description "Etype to match for reflect mode";
                 junos:must "((\".. mode reflect\" || \".. mode ethernet-loopback\"))";
                 junos:must-message "reflect-etype valid only with mode reflect or ethernet-loopback";
                 junos:must "((\".. family ccc\" || (\".. family bridge\" || \".. family vpls\")))";
                 junos:must-message "reflect-etype valid only for CCC/Bridge/VPLS family";
                 type union {
                   type string {
                     pattern "<.*>|$.*";
                   }
                   type uint32 {
                     range "1 .. 65535";
                   }
                 }
               }
               leaf direction {
                 description "Direction of test";
                 junos:must "(\".. test-interface\")";
                 junos:must-message "direction must be configured along with test-interface";
                 junos:must "((\".. family ccc\" || (\".. family bridge\" || \".. family vpls\")))";
                 junos:must-message "direction can be configured only with ccc/bridge/vpls family";
                 type enumeration {
                   enum "ingress" {
                     description "Pseudo-wire/Bridge/Vpls Ingress direction";
                   }
                   enum "egress" {
                     description "Pseudo-wire/Bridge/Vpls Egress direction";
                   }
                 }
               }
               leaf timestamp-format {
                 description "Format of timestamp values";
                 type enumeration {
                   enum "microseconds" {
                     description "Timestamps in microseconds";
                   }
                   enum "nanoseconds" {
                     description "Timestamps in nanoseconds";
                   }
                 }
               }
               leaf source-udp-port {
                 description "Source udp port";
                 type union {
                   type string {
                     pattern "<.*>|$.*";
                   }
                   type uint32 {
                     range "1 .. 65535";
                   }
                 }
               }
               leaf destination-udp-port {
                 description "Destination udp port";
                 type union {
                   type string {
                     pattern "<.*>|$.*";
                   }
                   type uint32 {
                     range "1 .. 65535";
                   }
                 }
               }
               leaf test-duration {
                 description "Test duration in minutes";
                 status deprecated;
                 default "10";
                 type union {
                   type string {
                     pattern "<.*>|$.*";
                   }
                   type uint32 {
                     range "1 .. 5000";
                   }
                 }
               }
               leaf test-iterator-duration {
                 description "Duration of each iteration in seconds";
                 type union {
                   type string {
                     pattern "<.*>|$.*";
                   }
                   type uint32 {
                     range "10 .. 1728000";
                   }
                 }
               }
               leaf test-finish-wait-duration {
                 description "Number of seconds to wait after test completes before stopping the test";
                 default "1";
                 junos:must "(\".. mode initiate-and-terminate\")";
                 junos:must-message "test-finish-wait-duration is valid only when test mode is initiate-and-terminate";
                 type union {
                   type string {
                     pattern "<.*>|$.*";
                   }
                   type uint32 {
                     range "1 .. 60";
                   }
                 }
               }
               leaf transmit-failure-threshold {
                 description "Transmit failure-threshold (default 0.5%)";
                 default "0.5";
                 type decimal64 {
                   fraction-digits 2;
                   range "0 .. 100";
                 }
               }
               leaf receive-failure-threshold {
                 description "Receive failure-threshold (default 0%)";
                 default "0";
                 type decimal64 {
                   fraction-digits 2;
                   range "0 .. 100";
                 }
               }
               leaf test-iterator-pass-threshold {
                 description "Test pass-threshold (default 0.5%)";
                 default "0.5";
                 type decimal64 {
                   fraction-digits 2;
                   range "0 .. 100";
                 }
               }
               leaf halt-on-prefix-down {
                 description "Halt test on prefix down";
                 junos:must "(\".. family inet\")";
                 junos:must-message "halt-on-prefix-down is valid only for inet family";
                 type empty;
               }
               leaf skip-arp-iteration {
                 description "Skip arp iteration in tests";
                 type empty;
               }
               leaf test-interface {
                 description "Name of interface(ifl) for test";
                 type union {
                   type jt:interface-name;
                   type string {
                     pattern "<.*>|$.*";
                   }
                 }
               }
               leaf reflector-port {
                 description "Front panel port number - ACX5048: [16-53], ACX5096: [64-95, 100-103]";
                 junos:must "((\".. family ccc\" || \".. family bridge\"))";
                 junos:must-message "'Reflector-port' needs family bridge/ccc";
                 junos:must "(\".. mode reflect\")";
                 junos:must-message "'Reflector-port' can be used only in reflect mode";
                 type union {
                   type uint32;
                   type string {
                     pattern "<.*>|$.*";
                   }
                 }
               }
               leaf destination-ipv4-address {
                 description "Destination address for test";
                 type jt:ipv4addr;
               }
               leaf source-ipv4-address {
                 description "Source address for test";
                 type jt:ipv4addr;
               }
             }
           }
         }
         container twamp {
           description "Two-way Active Measurement Protocol configuration";
           uses apply-advanced;
           leaf post-cli-implicit-firewall {
             description "Enable post cli implicit firewall";
             type empty;
           }
           container client {
             description "TWAMP client configuration";
             uses apply-advanced;
             list control-connection {
               key name;
               ordered-by user;
               description "TWAMP control session configuration";
               leaf name {
                 description "Client name";
                 type string {
                   length "1 .. 32";
                 }
               }
               uses apply-advanced;
               container authentication-mode {
                 description "Authentication modes";
                 uses apply-advanced;
                 leaf none {
                   description "No authentication or encryption";
                   type empty;
                 }
               }
               leaf destination-interface {
                 description "Name of output interface for all test sessions";
                 type union {
                   type jt:interface-name;
                   type string {
                     pattern "<.*>|$.*";
                   }
                 }
               }
               leaf persistent-results {
                 description "Displays the old results along with present. Default disable";
                 type empty;
               }
               leaf tcp-keepidle {
                 description "Time to start TCP KEEPALIVEs on control connection (default 120)";
                 default "120";
                 units "seconds";
                 type union {
                   type string {
                     pattern "<.*>|$.*";
                   }
                   type uint32 {
                     range "1 .. 600";
                   }
                 }
               }
               leaf tcp-keepintvl {
                 description "Delay between succesive TCP KEEPALIVEs (default 5)";
                 default "5";
                 units "seconds";
                 type union {
                   type string {
                     pattern "<.*>|$.*";
                   }
                   type uint32 {
                     range "1 .. 600";
                   }
                 }
               }
               leaf tcp-keepcnt {
                 description "Number of TCP KEEPALIVEs sent (default 6)";
                 default "6";
                 type union {
                   type string {
                     pattern "<.*>|$.*";
                   }
                   type uint32 {
                     range "1 .. 50";
                   }
                 }
               }
               leaf destination-port {
                 description "TCP TWAMP client listening port for the test sessions. Default 862";
                 default "862";
                 type union {
                   type string {
                     pattern "<.*>|$.*";
                   }
                   type uint16 {
                     range "1 .. 65535";
                   }
                 }
               }
               leaf history-size {
                 description "Number of stored history entries";
                 default "50";
                 type union {
                   type string {
                     pattern "<.*>|$.*";
                   }
                   type uint16 {
                     range "0 .. 500";
                   }
                 }
               }
               leaf moving-average-size {
                 description "Number of samples used for moving average";
                 default "0";
                 type union {
                   type string {
                     pattern "<.*>|$.*";
                   }
                   type uint32 {
                     range "0 .. 1024";
                   }
                 }
               }
               leaf routing-instance {
                 description "Routing instance used by the test sessions";
                 junos:must "(\"routing-instances $$\")";
                 junos:must-message "referenced routing-instance must be defined";
                 type string {
                   junos:posix-pattern "!^((__.*__)|(all)|(.*[ ].*)|(\"\")|(.{129,}))$";
                   junos:pattern-message "Must be a non-reserved string of 128 characters or less with no spaces.";
                 }
               }
               leaf target-address {
                 description "Destination address of TWAMP responder";
                 type jt:ipv4addr;
               }
               leaf test-count {
                 description "Total number of test session iterations";
                 default "0";
                 type union {
                   type string {
                     pattern "<.*>|$.*";
                   }
                   type uint32 {
                     range "0 .. 4294967290";
                   }
                 }
               }
               leaf test-interval {
                 description "Delay between test session iterations";
                 default "1";
                 units "seconds";
                 type union {
                   type string {
                     pattern "<.*>|$.*";
                   }
                   type uint16 {
                     range "1 .. 255";
                   }
                 }
               }
               container traps {
                 description "Trap to send if threshold is met or exceeded";
                 uses apply-advanced;
                 leaf test-iteration-done {
                   description "All test sessions configured under the control connection have completed an iteration";
                   type empty;
                 }
                 leaf control-connection-closed {
                   description "Control connection closed";
                   type empty;
                 }
               }
               list test-session {
                 key name;
                 ordered-by user;
                 description "Test session details";
                 leaf name {
                   description "Test session name";
                   type string {
                     length "1 .. 32";
                   }
                 }
                 uses apply-advanced;
                 leaf target-address {
                   description "Destination address of TWAMP responder";
                   type jt:ipv4addr;
                 }
                 leaf data-fill-with-zeros {
                   description "Fill contents of test packet with zeros";
                   type empty;
                 }
                 leaf data-size {
                   description "Size of the data portion of the probes";
                   default "60";
                   type union {
                     type string {
                       pattern "<.*>|$.*";
                     }
                     type uint16 {
                       range "60 .. 1400";
                     }
                   }
                 }
                 leaf dscp-code-points {
                   description "Differentiated Services code point bits or alias used for TCP control and UDP TWAMP test packets";
                   default "000000";
                   type string {
                     junos:posix-pattern "^(([01]{6})|([a-zA-Z].{0,63}))$";
                     junos:pattern-message "Not 6-bit pattern or code point alias";
                   }
                 }
                 leaf ttl {
                   description "Time to Live (hop-limit) value for an RPM IPv4(IPv6) packet";
                   default "64";
                   type union {
                     type string {
                       pattern "<.*>|$.*";
                     }
                     type uint32 {
                       range "1 .. 254";
                     }
                   }
                 }
                 leaf probe-count {
                   description "Total number of probes per test";
                   default "1";
                   type union {
                     type string {
                       pattern "<.*>|$.*";
                     }
                     type uint32 {
                       range "1 .. 4294967290";
                     }
                   }
                 }
                 leaf probe-interval {
                   description "Delay between two consecutive probes";
                   default "1";
                   units "seconds";
                   type union {
                     type string {
                       pattern "<.*>|$.*";
                     }
                     type uint32 {
                       range "1 .. 255";
                     }
                   }
                 }
                 container thresholds {
                   presence "enable thresholds";
                   description "TWAMP test threshold values. Set 0 to disable respective threshold";
                   uses apply-advanced;
                   leaf successive-loss {
                     description "Successive probe loss count indicating probe failure";
                     default "1";
                     type union {
                       type string {
                         pattern "<.*>|$.*";
                       }
                       type uint32 {
                         range "0 .. 15";
                       }
                     }
                   }
                   leaf total-loss {
                     description "Total probe loss count indicating test failure";
                     default "1";
                     type union {
                       type string {
                         pattern "<.*>|$.*";
                       }
                       type uint32 {
                         range "0 .. 4294967290";
                       }
                     }
                   }
                   leaf rtt {
                     description "Maximum round trip time per probe";
                     default "0";
                     units "microseconds";
                     type union {
                       type string {
                         pattern "<.*>|$.*";
                       }
                       type uint32 {
                         range "0 .. 60000000";
                       }
                     }
                   }
                   leaf max-rtt {
                     description "Maximum round trip time per test";
                     default "0";
                     units "microseconds";
                     type union {
                       type string {
                         pattern "<.*>|$.*";
                       }
                       type uint32 {
                         range "0 .. 60000000";
                       }
                     }
                   }
                   leaf jitter-rtt {
                     description "Maximum jitter per test";
                     default "0";
                     units "microseconds";
                     type union {
                       type string {
                         pattern "<.*>|$.*";
                       }
                       type uint32 {
                         range "0 .. 60000000";
                       }
                     }
                   }
                   leaf std-dev-rtt {
                     description "Maximum standard deviation per test";
                     default "0";
                     units "microseconds";
                     type union {
                       type string {
                         pattern "<.*>|$.*";
                       }
                       type uint32 {
                         range "0 .. 60000000";
                       }
                     }
                   }
                   leaf egress-time {
                     description "Maximum source to destination time per probe";
                     default "0";
                     units "microseconds";
                     type union {
                       type string {
                         pattern "<.*>|$.*";
                       }
                       type uint32 {
                         range "0 .. 60000000";
                       }
                     }
                   }
                   leaf ingress-time {
                     description "Maximum destination to source time per probe";
                     default "0";
                     units "microseconds";
                     type union {
                       type string {
                         pattern "<.*>|$.*";
                       }
                       type uint32 {
                         range "0 .. 60000000";
                       }
                     }
                   }
                   leaf jitter-ingress {
                     description "Maximum destination to source jitter per test";
                     default "0";
                     units "microseconds";
                     type union {
                       type string {
                         pattern "<.*>|$.*";
                       }
                       type uint32 {
                         range "0 .. 60000000";
                       }
                     }
                   }
                   leaf jitter-egress {
                     description "Maximum source to destination jitter per test";
                     default "0";
                     units "microseconds";
                     type union {
                       type string {
                         pattern "<.*>|$.*";
                       }
                       type uint32 {
                         range "0 .. 60000000";
                       }
                     }
                   }
                   leaf std-dev-ingress {
                     description "Maximum destination to source standard deviation per test";
                     default "0";
                     units "microseconds";
                     type union {
                       type string {
                         pattern "<.*>|$.*";
                       }
                       type uint32 {
                         range "0 .. 60000000";
                       }
                     }
                   }
                   leaf std-dev-egress {
                     description "Maximum source to destination standard deviation per test";
                     default "0";
                     units "microseconds";
                     type union {
                       type string {
                         pattern "<.*>|$.*";
                       }
                       type uint32 {
                         range "0 .. 60000000";
                       }
                     }
                   }
                 }
                 container traps {
                   description "Trap to send if threshold is met or exceeded";
                   uses apply-advanced;
                   leaf probe-failure {
                     description "Successive probe loss threshold reached";
                     type empty;
                   }
                   leaf test-failure {
                     description "Total probe loss threshold reached";
                     type empty;
                   }
                   leaf test-completion {
                     description "Test completed";
                     type empty;
                   }
                   leaf rtt-exceeded {
                     description "Exceeded maximum round trip time threshold";
                     type empty;
                   }
                   leaf max-rtt-exceeded {
                     description "Exceeded maximum round trip time threshold at the end of per test";
                     type empty;
                   }
                   leaf std-dev-exceeded {
                     description "Exceeded round trip time standard deviation threshold";
                     type empty;
                   }
                   leaf jitter-exceeded {
                     description "Exceeded jitter in round trip time threshold";
                     type empty;
                   }
                   leaf ingress-time-exceeded {
                     description "Exceeded maximum ingress time threshold";
                     type empty;
                   }
                   leaf ingress-std-dev-exceeded {
                     description "Exceeded ingress time standard deviation threshold";
                     type empty;
                   }
                   leaf ingress-jitter-exceeded {
                     description "Exceeded jitter in ingress time threshold";
                     type empty;
                   }
                   leaf egress-time-exceeded {
                     description "Exceeded maximum egress time threshold";
                     type empty;
                   }
                   leaf egress-std-dev-exceeded {
                     description "Exceeded egress time standard deviation threshold";
                     type empty;
                   }
                   leaf egress-jitter-exceeded {
                     description "Exceeded jitter in egress time threshold";
                     type empty;
                   }
                 }
               }
             }
           }
           container server {
             description "TWAMP server configuration";
             uses apply-advanced;
             leaf tcp-keepidle {
               description "Time to start TCP KEEPALIVEs on control connection (default 120)";
               default "120";
               units "seconds";
               type union {
                 type string {
                   pattern "<.*>|$.*";
                 }
                 type uint32 {
                   range "1 .. 600";
                 }
               }
             }
             leaf tcp-keepintvl {
               description "Delay between succesive TCP KEEPALIVEs (default 5)";
               default "5";
               units "seconds";
               type union {
                 type string {
                   pattern "<.*>|$.*";
                 }
                 type uint32 {
                   range "1 .. 600";
                 }
               }
             }
             leaf tcp-keepcnt {
               description "Number of TCP KEEPALIVEs sent (default 6)";
               default "6";
               type union {
                 type string {
                   pattern "<.*>|$.*";
                 }
                 type uint32 {
                   range "1 .. 50";
                 }
               }
             }
             list routing-instance-list {
               key name;
               ordered-by user;
               description "List of allowed routing instances,not more than 100, along with ports";
               leaf name {
                 description "Name of the routing instance";
                 junos:must "(\"routing-instances $$\")";
                 junos:must-message "referenced routing-instance must be defined";
                 type string {
                   junos:posix-pattern "!^((__.*__)|(all)|(.*[ ].*)|(\"\")|(.{129,}))$";
                   junos:pattern-message "Must be a non-reserved string of 128 characters or less with no spaces.";
                 }
               }
               uses apply-advanced;
               leaf port {
                 description "Port to be used by the routing instance";
                 type union {
                   type string {
                     pattern "<.*>|$.*";
                   }
                   type uint32 {
                     range "1 .. 65535";
                   }
                 }
               }
             }
             container authentication-mode {
               description "Authentication modes";
               uses apply-advanced;
               leaf none {
                 description "No authentication or encryption";
                 type empty;
               }
               container authenticated {
                 presence "enable authenticated";
                 description "Authenticated mode";
                 leaf control-only {
                   description "Authentication mode only for TWAMP control protocol";
                   status deprecated;
                   type empty;
                 }
               }
               container encrypted {
                 presence "enable encrypted";
                 description "Encrypted mode";
                 leaf control-only {
                   description "Encryption mode only for TWAMP control protocol";
                   status deprecated;
                   junos:must "(!(\".. .. encrypted-control-only\"))";
                   junos:must-message "'encrypted control-only' and 'control-only-encrypted' cannot be configured simultaneously";
                   type empty;
                 }
               }
               leaf control-only-encrypted {
                 description "Encrypted control and unauthenticated data mode";
                 type empty;
               }
             }
             list authentication-key-chain {
               key name;
               ordered-by user;
               description "Authentication key chain configuration";
               uses twamp-authentication-key-chain;
             }
             leaf server-inactivity-timeout {
               description "Control packet idle timeout value in minutes, 0 to disable";
               default "15";
               units "minutes";
               type union {
                 type string {
                   pattern "<.*>|$.*";
                 }
                 type uint32 {
                   range "0 .. 30";
                 }
               }
             }
             leaf max-connection-duration {
               description "Maximum Connection duration in hours, 0 to disable";
               default "0";
               units "hours";
               type union {
                 type string {
                   pattern "<.*>|$.*";
                 }
                 type uint32 {
                   range "0 .. 120";
                 }
               }
             }
             leaf maximum-sessions {
               description "Maximum number of test sessions for the server";
               default "64";
               type union {
                 type string {
                   pattern "<.*>|$.*";
                 }
                 type uint32 {
                   range "1 .. 2048";
                 }
               }
             }
             leaf maximum-sessions-per-connection {
               description "Maximum number of test sessions per client connection";
               type union {
                 type string {
                   pattern "<.*>|$.*";
                 }
                 type uint32 {
                   range "1 .. 1024";
                 }
               }
             }
             leaf maximum-connections {
               description "Maximum number of connections for the server";
               default "64";
               type union {
                 type string {
                   pattern "<.*>|$.*";
                 }
                 type uint32 {
                   range "1 .. 1000";
                 }
               }
             }
             leaf maximum-connections-per-client {
               description "Maximum number of server connections per client";
               type union {
                 type string {
                   pattern "<.*>|$.*";
                 }
                 type uint32 {
                   range "1 .. 500";
                 }
               }
             }
             leaf port {
               description "TWAMP server listening port";
               default "862";
               type union {
                 type string {
                   pattern "<.*>|$.*";
                 }
                 type uint32 {
                   range "1 .. 65535";
                 }
               }
             }
             list client-list {
               key name;
               ordered-by user;
               description "List of allowed clients";
               leaf name {
                 description "Name of client list";
                 type string {
                   length "1 .. 127";
                 }
               }
               uses apply-advanced;
               list address {
                 key name;
                 ordered-by user;
                 description "IP prefix of client";
                 leaf name {
                   description "IP prefix of client";
                   junos:must "(unique \"services rpm twamp server client-list <*> address $$\")";
                   junos:must-message "Same ip address can not be configured under multiple client lists";
                   type jt:ipv4prefix;
                 }
                 uses apply-advanced;
               }
             }
           }
         }
       }
       container video-monitoring {
         presence "enable video-monitoring";
         description "Video monitoring service";
         uses apply-advanced;
         list templates {
           key name;
           ordered-by user;
           description "Template for MDI flows";
           leaf name {
             description "Name of template";
             type string {
               length "1 .. 32";
             }
           }
           uses apply-advanced;
           leaf interval-duration {
             description "Monitoring interval in sec";
             type union {
               type string {
                 pattern "<.*>|$.*";
               }
               type uint32 {
                 range "1 .. 50";
               }
             }
           }
           leaf inactive-timeout {
             description "Inactive timeout for idle flow in sec";
             type union {
               type string {
                 pattern "<.*>|$.*";
               }
               type uint32 {
                 range "30 .. 300";
               }
             }
           }
           container rate {
             description "Media rate or layer3 pps";
             uses apply-advanced;
             choice rate-choice {
               case case_1 {
                 leaf media {
                   description "Constant bit rate in bps";
                   type string;
                 }
               }
               case case_2 {
                 leaf layer3 {
                   description "Layer3 packet rate in pps";
                   type string;
                 }
               }
             }
           }
           container delay-factor {
             description "Delay factor related parameters";
             uses apply-advanced;
             container threshold {
               description "Threshold for delay factor alarm";
               uses apply-advanced;
               leaf info {
                 description "Threshold for information alarm";
                 units "milli-sec";
                 type decimal64 {
                   fraction-digits 2;
                   range "0 .. 65535";
                 }
               }
               leaf warning {
                 description "Threshold for warning alarm";
                 units "milli-sec";
                 type decimal64 {
                   fraction-digits 2;
                   range "0 .. 65535";
                 }
               }
               leaf critical {
                 description "Threshold for critical alarm";
                 units "milli-sec";
                 type decimal64 {
                   fraction-digits 2;
                   range "0 .. 65535";
                 }
               }
             }
             choice enable-disable {
               case case_1 {
                 leaf disable {
                   description "Disable DF Calculation";
                   type empty;
                 }
               }
             }
           }
           container media-loss-rate {
             description "MLR related parameters";
             uses apply-advanced;
             container threshold {
               description "Threshold for MLR alarm";
               uses apply-advanced;
               container info {
                 description "Threshold for information alarm";
                 uses apply-advanced;
                 choice mlr-threshold-choice {
                   case case_1 {
                     leaf packet-count {
                       description "MLR threshold value in packets count";
                       type jt:unsigned-float;
                     }
                   }
                   case case_2 {
                     leaf percentage {
                       description "MLR threshold value in percentage";
                       type decimal64 {
                         fraction-digits 2;
                         range "0 .. 100";
                       }
                     }
                   }
                 }
               }
               container warning {
                 description "Threshold for warning alarm";
                 uses apply-advanced;
                 choice mlr-threshold-choice {
                   case case_1 {
                     leaf packet-count {
                       description "MLR threshold value in packets count";
                       type jt:unsigned-float;
                     }
                   }
                   case case_2 {
                     leaf percentage {
                       description "MLR threshold value in percentage";
                       type decimal64 {
                         fraction-digits 2;
                         range "0 .. 100";
                       }
                     }
                   }
                 }
               }
               container critical {
                 description "Threshold for critical alarm";
                 uses apply-advanced;
                 choice mlr-threshold-choice {
                   case case_1 {
                     leaf packet-count {
                       description "MLR threshold value in packets count";
                       type jt:unsigned-float;
                     }
                   }
                   case case_2 {
                     leaf percentage {
                       description "MLR threshold value in percentage";
                       type decimal64 {
                         fraction-digits 2;
                         range "0 .. 100";
                       }
                     }
                   }
                 }
               }
             }
             choice enable-disable {
               case case_1 {
                 leaf disable {
                   description "Disable MLR Caltulation";
                   type empty;
                 }
               }
             }
           }
           container media-rate-variation {
             description "MRV related parameters";
             uses apply-advanced;
             container threshold {
               description "Threshold for MRV alarm";
               uses apply-advanced;
               leaf info {
                 description "Threshold for information alarm";
                 type decimal64 {
                   fraction-digits 2;
                   range "0 .. 100";
                 }
               }
               leaf warning {
                 description "Threshold for warning alarm";
                 type decimal64 {
                   fraction-digits 2;
                   range "0 .. 100";
                 }
               }
               leaf critical {
                 description "Threshold for critical alarm";
                 type decimal64 {
                   fraction-digits 2;
                   range "0 .. 100";
                 }
               }
             }
             choice enable-disable {
               case case_1 {
                 leaf disable {
                   description "Disable MRV Caltulation";
                   type empty;
                 }
               }
             }
           }
           leaf media-packets-count-in-layer3 {
             description "Number of media packets in a IP packet";
             type union {
               type string {
                 pattern "<.*>|$.*";
               }
               type uint32 {
                 range "1 .. 32";
               }
             }
           }
           leaf media-packet-size {
             description "Size of media packet";
             type union {
               type string {
                 pattern "<.*>|$.*";
               }
               type uint32 {
                 range "1 .. 2048";
               }
             }
           }
         }
         list interfaces {
           key name;
           ordered-by user;
           description "Interfaces to enable video monitoring";
           leaf name {
             description "Name of IFL";
             junos:must "(\"interfaces $$-IFL\")";
             junos:must-message "specified interface is not configured in interfaces hierarchy";
             type union {
               type jt:interface-unit;
               type string {
                 pattern "<.*>|$.*";
               }
             }
           }
           uses apply-advanced;
           container family {
             description "Protocol family";
             uses apply-advanced;
             container inet {
               description "IPv4 flows";
               uses apply-advanced;
               list input-flows {
                 key name;
                 ordered-by user;
                 description "Input flows informations";
                 leaf name {
                   description "Name of flow";
                   type string {
                     length "1 .. 32";
                   }
                 }
                 uses apply-advanced;
                 leaf-list source-address {
                   ordered-by user;
                   description "Prefix to match";
                   type jt:ipv4prefix;
                   max-elements 32;
                 }
                 leaf-list destination-address {
                   ordered-by user;
                   description "Prefix to match";
                   type jt:ipv4prefix;
                   max-elements 32;
                 }
                 leaf-list source-port {
                   ordered-by user;
                   description "Source port number to match";
                   type string;
                   max-elements 32;
                 }
                 leaf-list destination-port {
                   ordered-by user;
                   description "Destination port number to match";
                   type string;
                   max-elements 32;
                 }
                 leaf template {
                   description "Name of template";
                   junos:must "(\"services video-monitoring templates $$\")";
                   junos:must-message "Referenced template must be defined under 'services video-monitoring templates'";
                   type string {
                     length "1 .. 32";
                   }
                 }
               }
               list output-flows {
                 key name;
                 ordered-by user;
                 description "Output flows informations";
                 leaf name {
                   description "Name of flow";
                   type string {
                     length "1 .. 32";
                   }
                 }
                 uses apply-advanced;
                 leaf-list source-address {
                   ordered-by user;
                   description "Prefix to match";
                   type jt:ipv4prefix;
                   max-elements 32;
                 }
                 leaf-list destination-address {
                   ordered-by user;
                   description "Prefix to match";
                   type jt:ipv4prefix;
                   max-elements 32;
                 }
                 leaf-list source-port {
                   ordered-by user;
                   description "Source port number to match";
                   type string;
                   max-elements 32;
                 }
                 leaf-list destination-port {
                   ordered-by user;
                   description "Destination port number to match";
                   type string;
                   max-elements 32;
                 }
                 leaf template {
                   description "Name of template";
                   junos:must "(\"services video-monitoring templates $$\")";
                   junos:must-message "Referenced template must be defined under 'services video-monitoring templates'";
                   type string {
                     length "1 .. 32";
                   }
                 }
               }
             }
             container inet6 {
               description "IPv6 flows";
               uses apply-advanced;
               list input-flows {
                 key name;
                 ordered-by user;
                 description "Input flows informations";
                 leaf name {
                   description "Name of flow";
                   type string {
                     length "1 .. 32";
                   }
                 }
                 uses apply-advanced;
                 leaf-list source-address {
                   ordered-by user;
                   description "Prefix to match";
                   type jt:ipv6prefix;
                   max-elements 32;
                 }
                 leaf-list destination-address {
                   ordered-by user;
                   description "Prefix to match";
                   type jt:ipv6prefix;
                   max-elements 32;
                 }
                 leaf-list source-port {
                   ordered-by user;
                   description "Source port number to match";
                   type string;
                   max-elements 32;
                 }
                 leaf-list destination-port {
                   ordered-by user;
                   description "Destination port number to match";
                   type string;
                   max-elements 32;
                 }
                 leaf template {
                   description "Name of template";
                   junos:must "(\"services video-monitoring templates $$\")";
                   junos:must-message "Referenced template must be defined under 'services video-monitoring templates'";
                   type string {
                     length "1 .. 32";
                   }
                 }
               }
               list output-flows {
                 key name;
                 ordered-by user;
                 description "Output flows informations";
                 leaf name {
                   description "Name of flow";
                   type string {
                     length "1 .. 32";
                   }
                 }
                 uses apply-advanced;
                 leaf-list source-address {
                   ordered-by user;
                   description "Prefix to match";
                   type jt:ipv6prefix;
                   max-elements 32;
                 }
                 leaf-list destination-address {
                   ordered-by user;
                   description "Prefix to match";
                   type jt:ipv6prefix;
                   max-elements 32;
                 }
                 leaf-list source-port {
                   ordered-by user;
                   description "Source port number to match";
                   type string;
                   max-elements 32;
                 }
                 leaf-list destination-port {
                   ordered-by user;
                   description "Destination port number to match";
                   type string;
                   max-elements 32;
                 }
                 leaf template {
                   description "Name of template";
                   junos:must "(\"services video-monitoring templates $$\")";
                   junos:must-message "Referenced template must be defined under 'services video-monitoring templates'";
                   type string {
                     length "1 .. 32";
                   }
                 }
               }
             }
             container mpls {
               description "MPLS flows";
               uses apply-advanced;
               list input-flows {
                 key name;
                 ordered-by user;
                 description "Input flows informations";
                 leaf name {
                   description "Name of flow";
                   type string {
                     length "1 .. 32";
                   }
                 }
                 uses apply-advanced;
                 leaf payload-type {
                   description "Specify MPLS payload-type";
                   type enumeration {
                     enum "ipv4" {
                       description "IPv4 over MPLS";
                     }
                     enum "ipv6" {
                       description "IPv6 over MPLS";
                     }
                   }
                 }
                 leaf-list source-address {
                   ordered-by user;
                   description "Prefix to match";
                   type jt:ipprefix;
                   max-elements 32;
                 }
                 leaf-list destination-address {
                   ordered-by user;
                   description "Prefix to match";
                   type jt:ipprefix;
                   max-elements 32;
                 }
                 leaf-list source-port {
                   ordered-by user;
                   description "Source port number to match";
                   type string;
                   max-elements 32;
                 }
                 leaf-list destination-port {
                   ordered-by user;
                   description "Destination port number to match";
                   type string;
                   max-elements 32;
                 }
                 leaf template {
                   description "Name of template";
                   junos:must "(\"services video-monitoring templates $$\")";
                   junos:must-message "Referenced template must be defined under 'services video-monitoring templates'";
                   type string {
                     length "1 .. 32";
                   }
                 }
               }
               list output-flows {
                 key name;
                 ordered-by user;
                 description "Output flows informations";
                 leaf name {
                   description "Name of flow";
                   type string {
                     length "1 .. 32";
                   }
                 }
                 uses apply-advanced;
                 leaf payload-type {
                   description "Specify MPLS payload-type";
                   type enumeration {
                     enum "ipv4" {
                       description "IPv4 over MPLS";
                     }
                     enum "ipv6" {
                       description "IPv6 over MPLS";
                     }
                   }
                 }
                 leaf-list source-address {
                   ordered-by user;
                   description "Prefix to match";
                   type jt:ipprefix;
                   max-elements 32;
                 }
                 leaf-list destination-address {
                   ordered-by user;
                   description "Prefix to match";
                   type jt:ipprefix;
                   max-elements 32;
                 }
                 leaf-list source-port {
                   ordered-by user;
                   description "Source port number to match";
                   type string;
                   max-elements 32;
                 }
                 leaf-list destination-port {
                   ordered-by user;
                   description "Destination port number to match";
                   type string;
                   max-elements 32;
                 }
                 leaf template {
                   description "Name of template";
                   junos:must "(\"services video-monitoring templates $$\")";
                   junos:must-message "Referenced template must be defined under 'services video-monitoring templates'";
                   type string {
                     length "1 .. 32";
                   }
                 }
               }
             }
           }
         }
         leaf stats-cache-life-time {
           description "Lifetime of cached stats in seconds";
           default "10";
           type union {
             type string {
               pattern "<.*>|$.*";
             }
             type uint32 {
               range "1 .. 600";
             }
           }
         }
         leaf errors-cache-life-time {
           description "Lifetime of cached errors in seconds";
           default "10";
           type union {
             type string {
               pattern "<.*>|$.*";
             }
             type uint32 {
               range "1 .. 600";
             }
           }
         }
         leaf flow-cache-life-time {
           description "Lifetime of cached flows in seconds";
           default "10";
           type union {
             type string {
               pattern "<.*>|$.*";
             }
             type uint32 {
               range "1 .. 600";
             }
           }
         }
         container alarms {
           description "Alarms for Flows";
           uses apply-advanced;
           container delay-factor {
             description "DF Alarms";
             uses apply-advanced;
             leaf no-syslog-generation {
               description "Don't generate syslog when threshold exceed";
               type empty;
             }
             leaf generate-snmp-traps {
               description "Generate SNMP traps when threshold exceed";
               junos:must "(\".. storm-control\")";
               junos:must-message "Storm control must be configured";
               type empty;
             }
             container storm-control {
               presence "enable storm-control";
               description "Control frequency of alarm generation";
               uses apply-advanced;
               leaf count {
                 description "Max number of alarms in specified interval";
                 type union {
                   type string {
                     pattern "<.*>|$.*";
                   }
                   type uint32 {
                     range "1 .. 300";
                   }
                 }
               }
               leaf interval {
                 description "Interval in Seconds";
                 type union {
                   type string {
                     pattern "<.*>|$.*";
                   }
                   type uint32 {
                     range "1 .. 300";
                   }
                 }
               }
             }
             container alarm-mode {
               presence "enable alarm-mode";
               description "Mode of alarm generation";
               uses apply-advanced;
               leaf mdi-records-count {
                 description "Number of MDI records to average";
                 junos:must "(\".. average\")";
                 junos:must-message "Applicable only if alarm-mode is average";
                 type union {
                   type string {
                     pattern "<.*>|$.*";
                   }
                   type uint32 {
                     range "2 .. 10";
                   }
                 }
               }
               choice alarm_mode {
                 case case_1 {
                   leaf immediate {
                     description "Alarm will be triggered immediately";
                     type empty;
                   }
                 }
                 case case_2 {
                   leaf average {
                     description "Alarm will be triggered based on average";
                     type empty;
                   }
                 }
               }
             }
           }
           container media-rate-variation {
             description "MLR Alarms";
             uses apply-advanced;
             leaf no-syslog-generation {
               description "Don't generate syslog when threshold exceed";
               type empty;
             }
             leaf generate-snmp-traps {
               description "Generate SNMP traps when threshold exceed";
               junos:must "(\".. storm-control\")";
               junos:must-message "Storm control must be configured";
               type empty;
             }
             container storm-control {
               presence "enable storm-control";
               description "Control frequency of alarm generation";
               uses apply-advanced;
               leaf count {
                 description "Max number of alarms in specified interval";
                 type union {
                   type string {
                     pattern "<.*>|$.*";
                   }
                   type uint32 {
                     range "1 .. 300";
                   }
                 }
               }
               leaf interval {
                 description "Interval in Seconds";
                 type union {
                   type string {
                     pattern "<.*>|$.*";
                   }
                   type uint32 {
                     range "1 .. 300";
                   }
                 }
               }
             }
             container alarm-mode {
               presence "enable alarm-mode";
               description "Mode of alarm generation";
               uses apply-advanced;
               leaf mdi-records-count {
                 description "Number of MDI records to average";
                 junos:must "(\".. average\")";
                 junos:must-message "Applicable only if alarm-mode is average";
                 type union {
                   type string {
                     pattern "<.*>|$.*";
                   }
                   type uint32 {
                     range "2 .. 10";
                   }
                 }
               }
               choice alarm_mode {
                 case case_1 {
                   leaf immediate {
                     description "Alarm will be triggered immediately";
                     type empty;
                   }
                 }
                 case case_2 {
                   leaf average {
                     description "Alarm will be triggered based on average";
                     type empty;
                   }
                 }
               }
             }
           }
           container media-loss-rate {
             description "MRV Alarms";
             uses apply-advanced;
             leaf no-syslog-generation {
               description "Don't generate syslog when threshold exceed";
               type empty;
             }
             leaf generate-snmp-traps {
               description "Generate SNMP traps when threshold exceed";
               junos:must "(\".. storm-control\")";
               junos:must-message "Storm control must be configured";
               type empty;
             }
             container storm-control {
               presence "enable storm-control";
               description "Control frequency of alarm generation";
               uses apply-advanced;
               leaf count {
                 description "Max number of alarms in specified interval";
                 type union {
                   type string {
                     pattern "<.*>|$.*";
                   }
                   type uint32 {
                     range "1 .. 300";
                   }
                 }
               }
               leaf interval {
                 description "Interval in Seconds";
                 type union {
                   type string {
                     pattern "<.*>|$.*";
                   }
                   type uint32 {
                     range "1 .. 300";
                   }
                 }
               }
             }
             container alarm-mode {
               presence "enable alarm-mode";
               description "Mode of alarm generation";
               uses apply-advanced;
               leaf mdi-records-count {
                 description "Number of MDI records to average";
                 junos:must "(\".. average\")";
                 junos:must-message "Applicable only if alarm-mode is average";
                 type union {
                   type string {
                     pattern "<.*>|$.*";
                   }
                   type uint32 {
                     range "2 .. 10";
                   }
                 }
               }
               choice alarm_mode {
                 case case_1 {
                   leaf immediate {
                     description "Alarm will be triggered immediately";
                     type empty;
                   }
                 }
                 case case_2 {
                   leaf average {
                     description "Alarm will be triggered based on average";
                     type empty;
                   }
                 }
               }
             }
           }
           container flow-insert {
             description "Flow Insert Alarms";
             uses apply-advanced;
             leaf no-syslog-generation {
               description "Don't generate syslog when threshold exceed";
               type empty;
             }
             leaf generate-snmp-traps {
               description "Generate SNMP traps when threshold exceed";
               junos:must "(\".. storm-control\")";
               junos:must-message "Storm control must be configured";
               type empty;
             }
             container storm-control {
               presence "enable storm-control";
               description "Control frequency of alarm generation";
               uses apply-advanced;
               leaf count {
                 description "Max number of alarms in specified interval";
                 type union {
                   type string {
                     pattern "<.*>|$.*";
                   }
                   type uint32 {
                     range "1 .. 300";
                   }
                 }
               }
               leaf interval {
                 description "Interval in Seconds";
                 type union {
                   type string {
                     pattern "<.*>|$.*";
                   }
                   type uint32 {
                     range "1 .. 300";
                   }
                 }
               }
             }
           }
           container flow-delete {
             description "Flow Delete Alarms";
             uses apply-advanced;
             leaf no-syslog-generation {
               description "Don't generate syslog when threshold exceed";
               type empty;
             }
             leaf generate-snmp-traps {
               description "Generate SNMP traps when threshold exceed";
               junos:must "(\".. storm-control\")";
               junos:must-message "Storm control must be configured";
               type empty;
             }
             container storm-control {
               presence "enable storm-control";
               description "Control frequency of alarm generation";
               uses apply-advanced;
               leaf count {
                 description "Max number of alarms in specified interval";
                 type union {
                   type string {
                     pattern "<.*>|$.*";
                   }
                   type uint32 {
                     range "1 .. 300";
                   }
                 }
               }
               leaf interval {
                 description "Interval in Seconds";
                 type union {
                   type string {
                     pattern "<.*>|$.*";
                   }
                   type uint32 {
                     range "1 .. 300";
                   }
                 }
               }
             }
           }
         }
       }
       container app-engine {
         description "App-engine";
         uses apply-advanced;
         container security {
           presence "enable security";
           description "Enable app-engine security";
         }
         container monitor-cpu {
           description "Monitor node CPU usage";
           uses monitor-threshold;
         }
         container monitor-memory {
           description "Monitor node memory usage";
           uses monitor-threshold;
         }
         container monitor-storage {
           description "Monitor storage usage";
           uses monitor-threshold;
         }
         leaf default-compute-node-package {
           description "Default JunosV App Engine package for appliance";
           type string;
         }
         list compute-cluster {
           key name;
           ordered-by user;
           description "Configure compute cluster";
           leaf name {
             description "Compute cluster name";
             type string {
               length "1 .. 15";
             }
           }
           uses apply-advanced;
           container local-management {
             junos:must "(all \".. compute-node <*> interfaces\")";
             junos:must-message "Must specify compute-node management interface";
             description "Management address connected to compute cluster";
             uses apply-advanced;
             list routing-instance {
               key routing-instance-name;
               ordered-by user;
               description "Packets are restriction to specified routing instance";
               junos:must "(!(any \".. logical-system <*>\"))";
               junos:must-message "Must specify 'family' only under one hierarchy";
               max-elements 1;
               leaf routing-instance-name {
                 description "Name of routing instance";
                 type string {
                   junos:posix-pattern "!^((__.*__)|(all)|(.*[ ].*)|(\"\")|(.{129,}))$";
                   junos:pattern-message "Must be a non-reserved string of 128 characters or less with no spaces.";
                 }
               }
               uses apply-advanced;
               container family {
                 description "Protocol family";
                 container inet {
                   description "IPv4 parameters";
                   uses apply-advanced;
                   leaf address {
                     description "Interface address";
                     type jt:ipv4addr;
                   }
                 }
               }
             }
             container family {
               junos:must "(!(any \".. routing-instance <*>\"))";
               junos:must-message "Must specify 'family' only under one hierarchy";
               description "Protocol family";
               container inet {
                 description "IPv4 parameters";
                 uses apply-advanced;
                 leaf address {
                   description "Interface address";
                   type jt:ipv4addr;
                 }
               }
             }
           }
           container monitor-cpu {
             description "Monitor node CPU usage";
             uses monitor-threshold;
           }
           container monitor-memory {
             description "Monitor node memory usage";
             uses monitor-threshold;
           }
           container monitor-storage {
             description "Monitor storage usage";
             uses monitor-threshold;
           }
           list compute-node {
             key name;
             ordered-by user;
             description "Compute node name";
             max-elements 1;
             leaf name {
               description "Compute node name";
               type string {
                 length "1 .. 15";
               }
             }
             uses apply-advanced;
             container monitor-cpu {
               description "Monitor node CPU usage";
               uses monitor-threshold;
             }
             container monitor-memory {
               description "Monitor node memory usage";
               uses monitor-threshold;
             }
             container monitor-storage {
               description "Monitor storage usage";
               uses monitor-threshold;
             }
             choice compute-node-identifier {
               case case_1 {
                 leaf mac-address {
                   description "MAC address of the network boot interface";
                   junos:must "(\".. interfaces\")";
                   junos:must-message "Must specify management interface";
                   junos:must "(\".. .. local-management\")";
                   junos:must-message "Must specify compute cluster local-management";
                   junos:must "(unique \"services app-engine compute-cluster <*> compute-node <*> mac-address $$\")";
                   junos:must-message "MAC address must be unique across compute clusters";
                   type jt:mac-addr;
                 }
               }
               case case_2 {
                 leaf fpc {
                   description "FPC slot number";
                   junos:must "(!(\".. .. local-management\"))";
                   junos:must-message "Must not specify compute cluster local-management";
                   junos:must "(unique \"services app-engine compute-cluster <*> compute-node <*> fpc $$\")";
                   junos:must-message "FPC slot must be unique across compute clusters";
                   junos:must "(!(\".. package\"))";
                   junos:must-message "Must not specify package for FPC slot here. It is necessary and sufficient to specify it under 'chassis fpc <> application-services'";
                   type union {
                     type string {
                       pattern "<.*>|$.*";
                     }
                     type uint32;
                   }
                 }
               }
               case case_3 {
                 leaf hypervisor {
                   description "Compute node is hypervisor";
                   junos:must "(!(\".. interfaces\"))";
                   junos:must-message "";
                   type empty;
                 }
               }
             }
             leaf package {
               description "JunosV App Engine package";
               type string;
             }
             container routing-options {
               description "Route configuration for compute node";
               uses apply-advanced;
               container static {
                 description "Static routes";
                 uses apply-advanced;
                 list route {
                   key name;
                   ordered-by user;
                   description "Static route";
                   leaf name {
                     description "Destination IP address or prefix";
                     junos:must "(!(any \".. .. .. rib <*> static route $$\"))";
                     junos:must-message "Duplicate route entry";
                     type jt:ipv4prefix;
                   }
                   uses apply-advanced;
                   leaf next-hop {
                     description "Next hop to destination";
                     type jt:ipv4addr;
                   }
                 }
               }
               list rib {
                 key name;
                 ordered-by user;
                 description "Routing table options";
                 leaf name {
                   description "Routing table name";
                   type string {
                     length "1 .. 10";
                     junos:posix-pattern "inet.0";
                     junos:pattern-message "Only inet.0 is supported";
                   }
                 }
                 uses apply-advanced;
                 container static {
                   description "Static routes";
                   uses apply-advanced;
                   list route {
                     key name;
                     ordered-by user;
                     description "Static route";
                     leaf name {
                       description "Destination IP address or prefix";
                       junos:must "(!(\".. .. .. .. static route $$\"))";
                       junos:must-message "Duplicate route entry";
                       type jt:ipv4prefix;
                     }
                     uses apply-advanced;
                     leaf next-hop {
                       description "Next hop to destination";
                       type jt:ipv4addr;
                     }
                   }
                 }
               }
             }
             container interfaces {
               description "Network interfaces configuration";
               uses apply-advanced;
               list ethernet {
                 key name;
                 ordered-by user;
                 description "Interface configuration";
                 leaf name {
                   description "Interface name";
                   junos:must "(!(any \".. .. bridge <*> interface $$\"))";
                   junos:must-message "This interface is already associated with a bridge";
                   junos:must "(!(\".. .. bridge $$\"))";
                   junos:must-message "A bridge is configured with this name";
                   type string {
                     length "1 .. 15";
                     junos:posix-pattern "^eth[0-9]{1,2}$";
                     junos:pattern-message "Must be of the form eth<0-99>";
                   }
                 }
                 uses apply-advanced;
                 leaf management {
                   description "Use this as management interface";
                   junos:must "(!(\".. ether-options\"))";
                   junos:must-message "This interface belongs to an aggregated interface";
                   junos:must "(!(\".. .. .. fpc\"))";
                   junos:must-message "Must not specify any interface as management with fpc";
                   junos:must "((\".. family inet address\" || \".. family inet dhcp\"))";
                   junos:must-message "Management interface must have an address or dhcp configured";
                   junos:must "(!(\".. enable-passthrough\"))";
                   junos:must-message "Management interface cannot be passthrough interface";
                   type empty;
                 }
                 container family {
                   description "Protocol family";
                   junos:must "(!(\".. ether-options\"))";
                   junos:must-message "This interface belongs to an aggregated interface";
                   uses family;
                   junos:must "(!(\".. ether-options\"))";
                   junos:must-message "This interface belongs to an aggregated interface";
                 }
                 leaf enable-passthrough {
                   description "Enable passthrough on this interface";
                   junos:must "(!(\".. ether-options\"))";
                   junos:must-message "This interface belongs to an aggregated interface";
                   junos:must "(!(\".. mtu\"))";
                   junos:must-message "Passthrough interface cannot have MTU";
                   junos:must "(!(\".. family inet address\"))";
                   junos:must-message "Passthrough interface cannot have an address";
                   type empty;
                 }
                 leaf mtu {
                   description "Maximum transmit packet size";
                   type union {
                     type string {
                       pattern "<.*>|$.*";
                     }
                     type uint16 {
                       range "256 .. 9192";
                     }
                   }
                 }
                 container ether-options {
                   junos:must "((!(\".. management\") && (!(\".. family\") && !(\".. enable-passthrough\"))))";
                   junos:must-message "Ethernet interface can not exist separately if it is under a aggregated interface and vice versa";
                   uses apply-advanced;
                   choice agg-intf {
                     case case_1 {
                       leaf ieee-802-3ad {
                         description "Aggregated interface name";
                         junos:must "(!(\".. .. mtu\"))";
                         junos:must-message "Aggregate slave interface cannot have MTU";
                         junos:must "(!(\".. .. .. bridge $$\"))";
                         junos:must-message "A bridge is configured with this name";
                         type string {
                           length "1 .. 15";
                           junos:posix-pattern "^ae[0-9]{1,2}$";
                           junos:pattern-message "Must be of the form ae<0-99>";
                         }
                       }
                     }
                   }
                 }
               }
               list bridge {
                 key name;
                 ordered-by user;
                 description "Bridge configuration";
                 leaf name {
                   description "Bridge name";
                   junos:must "(!(any \".. .. bridge <*> interface $$\"))";
                   junos:must-message "Bridge name is already used in one of the bridge interface list";
                   junos:must "(!(\".. .. aggregate $$\"))";
                   junos:must-message "An aggregate interface is configured with this name";
                   junos:must "(!(\".. .. ethernet $$\"))";
                   junos:must-message "An interface is configured with this name";
                   type string {
                     length "1 .. 15";
                     junos:posix-pattern "^[A-za-z][.0-9A-Za-z_]{1,15}$";
                     junos:pattern-message "Must be a string of 15 or fewer characters. The string should start with a letter and can contain letters, digits, underscores and periods";
                   }
                 }
                 uses apply-advanced;
                 leaf management {
                   description "Use this as management bridge";
                   junos:must "(!(\".. .. .. fpc\"))";
                   junos:must-message "Must not specify any interface as management with FPC compute node";
                   junos:must "((\".. family inet address\" || \".. family inet dhcp\"))";
                   junos:must-message "Management bridge must have an address or dhcp configured";
                   type empty;
                 }
                 container family {
                   description "Protocol family";
                   uses family;
                 }
                 leaf-list interface {
                   ordered-by user;
                   description "Bridge interface list";
                   junos:must "((!(\".. .. aggregate family inet address\") && !(\".. .. aggregate family inet dhcp\")))";
                   junos:must-message "Interface associated to bridge can not have address";
                   type string {
                     length "1 .. 15";
                   }
                   max-elements 4;
                 }
                 leaf mtu {
                   description "Maximum transmit packet size";
                   type union {
                     type string {
                       pattern "<.*>|$.*";
                     }
                     type uint16 {
                       range "256 .. 9192";
                     }
                   }
                 }
               }
               list aggregate {
                 key name;
                 ordered-by user;
                 description "Aggregate interface configuration";
                 leaf name {
                   description "Aggregated interface name";
                   junos:must "(!(\".. .. bridge $$\"))";
                   junos:must-message "A bridge is configured with this name";
                   junos:must "(!(\".. .. ethernet $$\"))";
                   junos:must-message "An interface is configured with this name";
                   junos:must "(any \".. .. ethernet <*> ether-options ieee-802-3ad $$\")";
                   junos:must-message "Aggregated interface must have some slave interface";
                   type string {
                     length "1 .. 15";
                     junos:posix-pattern "^ae[0-9]{1,2}$";
                     junos:pattern-message "Must be of the form ae<0-99>";
                   }
                 }
                 uses apply-advanced;
                 leaf management {
                   description "Use this as management aggregate";
                   junos:must "((\".. family inet address\" || \".. family inet dhcp\"))";
                   junos:must-message "Management aggregate must have an address or dhcp configured";
                   type empty;
                 }
                 container family {
                   description "Protocol family";
                   uses family;
                 }
                 leaf mtu {
                   description "Maximum transmit packet size";
                   type union {
                     type string {
                       pattern "<.*>|$.*";
                     }
                     type uint16 {
                       range "256 .. 9192";
                     }
                   }
                 }
                 container aggregated-ether-options {
                   presence "enable aggregated-ether-options";
                   description "Link aggregation parameters";
                   uses apply-advanced;
                   leaf hash-policy {
                     default "layer-3-and-4";
                     type enumeration {
                       enum "layer-2" {
                         description "Uses mac address of both source and destination for hashing";
                       }
                       enum "layer-3-and-4" {
                         description "Uses port number and IP address of both source and destination for hashing";
                       }
                       enum "layer-2-and-3" {
                         description "Uses mac and IP address of both source and destination for hashing";
                       }
                     }
                   }
                   leaf miimon {
                     description "Link monitoring interval in milli-second";
                     type union {
                       type uint32;
                       type string {
                         pattern "<.*>|$.*";
                       }
                     }
                   }
                 }
               }
             }
             list syslog {
               key name;
               ordered-by user;
               description "System logging facility";
               leaf name {
                 description "Facility type";
                 type enumeration {
                   enum "any" {
                     description "All facilities";
                   }
                   enum "authorization" {
                     description "Authorization system";
                   }
                   enum "privileged" {
                     description "Privileged authorization events";
                   }
                   enum "cron" {
                     description "Cron daemon";
                   }
                   enum "daemon" {
                     description "Various system processes";
                   }
                   enum "kernel" {
                     description "Kernel";
                   }
                   enum "syslog" {
                     description "Syslog messages";
                   }
                   enum "user" {
                     description "User processes";
                   }
                   enum "uucp" {
                     description "UUCP system";
                   }
                   enum "local0" {
                     description "Local 0 messages";
                   }
                   enum "local1" {
                     description "Local 1 messages";
                   }
                   enum "local2" {
                     description "Local 2 messages";
                   }
                   enum "local3" {
                     description "Local 3 messages";
                   }
                   enum "local4" {
                     description "Local 4 messages";
                   }
                   enum "local5" {
                     description "Local 5 messages";
                   }
                   enum "local6" {
                     description "Local 6 messages";
                   }
                   enum "local7" {
                     description "Local 7 messages";
                   }
                 }
               }
               choice level {
                 case case_1 {
                   leaf any {
                     description "All levels";
                     type empty;
                   }
                 }
                 case case_2 {
                   leaf emergency {
                     description "Panic conditions";
                     type empty;
                   }
                 }
                 case case_3 {
                   leaf alert {
                     description "Conditions that should be corrected immediately";
                     type empty;
                   }
                 }
                 case case_4 {
                   leaf critical {
                     description "Critical conditions";
                     type empty;
                   }
                 }
                 case case_5 {
                   leaf error {
                     description "Error conditions";
                     type empty;
                   }
                 }
                 case case_6 {
                   leaf warning {
                     description "Warning messages";
                     type empty;
                   }
                 }
                 case case_7 {
                   leaf notice {
                     description "Conditions that should be handled specially";
                     type empty;
                   }
                 }
                 case case_8 {
                   leaf info {
                     description "Informational messages";
                     type empty;
                   }
                 }
                 case case_9 {
                   leaf debug {
                     description "Debug messages";
                     type empty;
                   }
                 }
               }
             }
           }
         }
         container virtual-machines {
           description "Virtual-machine management";
           uses apply-advanced;
           list instance {
             key name;
             ordered-by user;
             description "Virtual-machine instance";
             leaf name {
               description "Virtual-machine instance identifier";
               type string {
                 length "1 .. 39";
               }
             }
             uses apply-advanced;
             leaf cpu {
               description "Units of CPUs (default 1 cpu)";
               default "1";
               type union {
                 type string {
                   pattern "<.*>|$.*";
                 }
                 type uint32 {
                   range "1 .. 16";
                 }
               }
             }
             leaf memory {
               description "Memory for the virtual-machine (default 1 gigabytes)";
               default "1";
               units "gigabytes";
               type union {
                 type string {
                   pattern "<.*>|$.*";
                 }
                 type uint32 {
                   range "1 .. 32";
                 }
               }
             }
             leaf management-interface {
               description "Virtual-machine management interface name";
               type string {
                 length "1 .. 31";
                 junos:posix-pattern "em0|em1";
                 junos:pattern-message "valid interface is em0 or em1";
               }
             }
             leaf package {
               description "Virtual-machine package";
               type string {
                 length "1 .. 120";
               }
             }
             container local-management {
               description "Management address connected to virtual machine";
               uses apply-advanced;
               list routing-instance {
                 key routing-instance-name;
                 ordered-by user;
                 description "Packets are restriction to specified routing instance";
                 junos:must "(!(any \".. logical-system <*>\"))";
                 junos:must-message "Must specify 'family' only under one hierarchy";
                 max-elements 1;
                 leaf routing-instance-name {
                   description "Name of routing instance";
                   type string {
                     junos:posix-pattern "!^((__.*__)|(all)|(.*[ ].*)|(\"\")|(.{129,}))$";
                     junos:pattern-message "Must be a non-reserved string of 128 characters or less with no spaces.";
                   }
                 }
                 uses apply-advanced;
                 container family {
                   description "Protocol family";
                   container inet {
                     description "IPv4 parameters";
                     uses apply-advanced;
                     leaf address {
                       description "Interface address";
                       type jt:ipv4addr;
                     }
                   }
                 }
               }
               container family {
                 junos:must "(!(any \".. routing-instance <*>\"))";
                 junos:must-message "Must specify 'family' only under one hierarchy";
                 description "Protocol family";
                 container inet {
                   description "IPv4 parameters";
                   uses apply-advanced;
                   leaf address {
                     description "Interface address";
                     type jt:ipv4addr;
                   }
                 }
               }
             }
             list compute-cluster {
               key name;
               ordered-by user;
               description "Compute cluster on which the virtual-machine runs";
               max-elements 1;
               leaf name {
                 description "Compute cluster name";
                 junos:must "(\"services app-engine compute-cluster $$\")";
                 junos:must-message "Referenced compute cluster must be defined";
                 type string {
                   length "1 .. 15";
                 }
               }
               uses apply-advanced;
               leaf compute-node {
                 description "Compute node on which the virtual-machine runs";
                 junos:must "(((\"services app-engine compute-cluster ${compute-cluster} compute-node $$ fpc\" && \".. .. local-management\") || !(\"services app-engine compute-cluster ${compute-cluster} compute-node $$ fpc\")))";
                 junos:must-message "Must specify local-management for virtual machine on FPC compute node";
                 junos:must "(\"services app-engine compute-cluster ${compute-cluster} compute-node $$\")";
                 junos:must-message "Referenced compute node must be defined";
                 type string {
                   length "1 .. 15";
                 }
               }
             }
             list interface {
               key name;
               ordered-by user;
               description "Virtual-machine interface configuration";
               leaf name {
                 description "Virtual-machine interface name";
                 type string {
                   length "1 .. 31";
                 }
               }
               uses apply-advanced;
               leaf hw-model {
                 description "Interface hardware model";
                 default "e1000g";
                 type enumeration {
                   enum "e1000g" {
                     description "Gigabit Ethernet e1000g driver";
                   }
                   enum "virtio" {
                     description "Para-virtualizing the interface";
                   }
                 }
               }
               leaf host-interface {
                 description "Passthrough host interface for virtual-machine";
                 type string {
                   length "1 .. 15";
                 }
               }
               leaf bridge {
                 description "Bridge that the interface connected to";
                 junos:must "(!(\".. mtu\"))";
                 junos:must-message "Bridged VM interface inherits MTU from the bridge";
                 junos:must "(!(\".. host-interface\"))";
                 junos:must-message "bridge can not defined with passthrough/host-interface";
                 type string {
                   length "1 .. 15";
                 }
               }
               leaf mtu {
                 description "Maximum transmit packet size";
                 type union {
                   type string {
                     pattern "<.*>|$.*";
                   }
                   type uint16 {
                     range "256 .. 9192";
                   }
                 }
               }
               container family {
                 description "Interface address family";
                 container inet {
                   presence "enable inet";
                   description "IPv4 parameters";
                   uses apply-advanced;
                   list address {
                     key name;
                     ordered-by user;
                     description "Interface address/destination prefix";
                     leaf name {
                       description "Interface address/destination prefix";
                       type jt:ipv4prefix;
                     }
                     uses apply-advanced;
                     leaf primary {
                       description "Primary address on the interface";
                       type empty;
                     }
                   }
                 }
               }
             }
             container routing-options {
               description "Route configuration for virutal machine";
               uses apply-advanced;
               container static {
                 description "Static routes";
                 uses apply-advanced;
                 list route {
                   key name;
                   ordered-by user;
                   description "Static route";
                   leaf name {
                     description "Destination IP address or prefix";
                     junos:must "(!(any \".. .. .. rib <*> static route $$\"))";
                     junos:must-message "Duplicate route entry";
                     type jt:ipv4prefix;
                   }
                   uses apply-advanced;
                   leaf next-hop {
                     description "Next hop to destination";
                     type jt:ipv4addr;
                   }
                 }
               }
               list rib {
                 key name;
                 ordered-by user;
                 description "Routing table options";
                 leaf name {
                   description "Routing table name";
                   type string {
                     length "1 .. 10";
                     junos:posix-pattern "inet.0";
                     junos:pattern-message "Only inet.0 is supported";
                   }
                 }
                 uses apply-advanced;
                 container static {
                   description "Static routes";
                   uses apply-advanced;
                   list route {
                     key name;
                     ordered-by user;
                     description "Static route";
                     leaf name {
                       description "Destination IP address or prefix";
                       junos:must "(!(\".. .. .. .. static route $$\"))";
                       junos:must-message "Duplicate route entry";
                       type jt:ipv4prefix;
                     }
                     uses apply-advanced;
                     leaf next-hop {
                       description "Next hop to destination";
                       type jt:ipv4addr;
                     }
                   }
                 }
               }
             }
             list secondary-disk {
               key name;
               ordered-by user;
               description "Virtual-machine disk";
               leaf name {
                 description "Virtual-machine disk name";
                 type enumeration {
                   enum "hdb" {
                     description "Disk name is hdb";
                   }
                   enum "hdc" {
                     description "Disk name is hdc";
                   }
                   enum "hdd" {
                     description "Disk name is hdd";
                   }
                 }
               }
               leaf size {
                 description "Virtual-machine secondary disk size";
                 units "gigabytes";
                 type union {
                   type string {
                     pattern "<.*>|$.*";
                   }
                   type uint32 {
                     range "1 .. 160";
                   }
                 }
               }
             }
           }
         }
       }
       container unified-access-control {
         description "Configure Unified Access Control";
         uses apply-advanced;
         list infranet-controller {
           key name;
           ordered-by user;
           description "Configure infranet controller";
           leaf name {
             description "Infranet controller name";
             type string {
               length "1 .. 31";
             }
           }
           uses apply-advanced;
           leaf address {
             description "Infranet controller IP address";
             type jt:ipv4addr;
           }
           leaf port {
             description "Infranet controller port";
             default "11123";
             type union {
               type string {
                 pattern "<.*>|$.*";
               }
               type uint32 {
                 range "1 .. 65535";
               }
             }
           }
           leaf interface {
             description "Outgoing interface";
             type union {
               type jt:interface-name;
               type string {
                 pattern "<.*>|$.*";
               }
             }
           }
           leaf password {
             description "Infranet controller server password";
             type string {
               length "1 .. 255";
             }
           }
           leaf-list ca-profile {
             ordered-by user;
             description "Define a list of certificate authority";
             type string;
           }
           leaf server-certificate-subject {
             description "Subject name of infranet controller certificate to match";
             type string {
               length "1 .. 255";
             }
           }
         }
         leaf certificate-verification {
           description "Specify certificate verification requirement";
           default "warning";
           type enumeration {
             enum "warning" {
               description "Warn if certificate is not being verified";
             }
             enum "required" {
               description "Require certificate verification. Most secure";
             }
             enum "optional" {
               description "Make verification optional, no warnings. Least secure";
             }
           }
         }
         leaf timeout {
           description "Timeout for idle infranet controller link in seconds";
           default "300";
           type union {
             type string {
               pattern "<.*>|$.*";
             }
             type uint32 {
               range "2 .. 10000";
             }
           }
         }
         leaf interval {
           description "Heartbeat interval from infranet controller in seconds";
           default "30";
           type union {
             type string {
               pattern "<.*>|$.*";
             }
             type uint32 {
               range "1 .. 9999";
             }
           }
         }
         leaf timeout-action {
           description "Specify action when infranet controller timeout occurs";
           default "close";
           type enumeration {
             enum "close" {
               description "Remove existing sessions and block further traffic";
             }
             enum "no-change" {
               description "Preserve existing connections; block new sessions";
             }
             enum "open" {
               description "Allow traffic for new and existing sessions to go through";
             }
           }
         }
         leaf test-only-mode {
           description "Allow all traffic and only log enforcement result";
           type empty;
         }
         container traceoptions {
           description "UAC trace options";
           uses apply-advanced;
           leaf no-remote-trace {
             description "Disable remote tracing";
             junos:must "(\"system tracing\")";
             junos:must-message "'no-remote-trace' is valid only when [system tracing] is configured";
             type empty;
           }
           container file {
             description "Trace file information";
             leaf filename {
               description "Name of file in which to write trace information";
               type string {
                 length "1 .. 1024";
                 junos:posix-pattern "![/ %]";
                 junos:pattern-message "Must not contain '/', % or a space";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "all" {
                   description "Trace with all flags enabled";
                 }
                 enum "ipc" {
                   description "IPC tracing";
                 }
                 enum "config" {
                   description "Configuration tracing";
                 }
                 enum "connect" {
                   description "Communication with infranet controller tracing";
                 }
               }
             }
           }
         }
         list captive-portal {
           key name;
           ordered-by user;
           description "Unauthenticated HTTP redirect";
           leaf name {
             description "Redirect policy name";
             type string {
               length "1 .. 128";
             }
           }
           uses apply-advanced;
           leaf redirect-traffic {
             description "Traffic to redirect";
             type enumeration {
               enum "unauthenticated" {
                 description "Redirect unauthenticated traffic";
               }
               enum "all" {
                 description "Redirect all traffic";
               }
             }
           }
           leaf redirect-url {
             description "Redirect URL for unauthenticated users";
             type string {
               length "1 .. 512";
               junos:posix-pattern "^https?://([[:alnum:]%]?[[:alnum:]%._-]*[[:alnum:]%]?)(/[[:alnum:]_-]*)*/?([?][[:alnum:]_%+-]*=[[:alnum:]_%+-:/.]*(&[[:alnum:]_%+-]*=[[:alnum:]_%+-:/.]*)*)?$";
               junos:pattern-message "Redirect URL be a valid HTTP URL";
             }
           }
         }
       }
       container flow-collector {
         description "Configure options to control flow collector";
         uses apply-advanced;
         leaf analyzer-address {
           description "Analyzer IP address field override value";
           type jt:ipv4addr;
         }
         leaf analyzer-id {
           description "Analyzer ID field override value";
           type string {
             length "1 .. 64";
           }
         }
         leaf retry {
           description "Transfer retry attempt count";
           default "0";
           type union {
             type string {
               pattern "<.*>|$.*";
             }
             type uint32 {
               range "0 .. 10";
             }
           }
         }
         leaf retry-delay {
           description "Delay between transfer retry attempts";
           default "0";
           units "seconds";
           type union {
             type string {
               pattern "<.*>|$.*";
             }
             type uint32 {
               range "0 .. 60";
             }
           }
         }
         list destinations {
           key name;
           ordered-by user;
           description "Configure destination for files";
           uses collector_destinations_type;
         }
         list file-specification {
           key name;
           description "File format specification";
           uses file_specification_type;
         }
         container interface-map {
           description "Input interface to Collector PIC mapping";
           uses interface_map_type;
         }
         container transfer-log-archive {
           description "Transfer log archive specification";
           uses collector_transfer_log_archive_type;
         }
       }
       container captive-portal {
         description "Captive Portal options";
         uses juniper-services-captive-portal;
       }
       container logging {
         description "Bulk logging configuration";
         uses juniper-pic-services-logging-options;
       }
       container application-identification {
         presence "enable application-identification";
         description "Application identification configuration";
         uses apply-advanced;
         leaf enable-heuristics {
           description "Enable heuristic application identification";
           status deprecated;
           type empty;
         }
         container enable-performance-mode {
           presence "enable enable-performance-mode";
           description "Enable performance mode knobs for best DPI performance";
           uses apply-advanced;
           leaf max-packet-threshold {
             description "Max packet inspection threshold including both c2s ans s2c direction packets. Default value is 2 if not configured";
             default "2";
             type union {
               type string {
                 pattern "<.*>|$.*";
               }
               type uint32 {
                 range "1 .. 100";
               }
             }
           }
         }
         leaf imap-cache-timeout {
           description "IMAP cache entry timeout in seconds";
           type union {
             type string {
               pattern "<.*>|$.*";
             }
             type uint32 {
               range "1 .. 86400";
             }
           }
         }
         leaf imap-cache-size {
           description "IMAP cache size, it will be effective only after next appid sigpack install";
           type union {
             type string {
               pattern "<.*>|$.*";
             }
             type uint32 {
               range "60 .. 512000";
             }
           }
         }
         container download {
           uses apply-advanced;
           leaf url {
             description "URL for application package download";
             type string {
               junos:posix-pattern "^((file)|(http)|(https)):";
               junos:pattern-message "URL starts with http, https or file";
             }
           }
           leaf ignore-server-validation {
             description "Disable server authentication for Applicaton Signature download";
             type empty;
           }
           container automatic {
             description "Scheduled download and update";
             uses apply-advanced;
             leaf start-time {
               description "Start time(MM-DD.hh:mm)";
               type string {
                 junos:posix-pattern "^((0[1-9]|1[012])[-](0[1-9]|[12][0-9]|3[01])[.]([0-1][0-9]|[2][0-3])[:]([0-5][0-9]))$";
                 junos:pattern-message "Invalid date; format is MM-DD.hh:mm";
               }
             }
             leaf interval {
               description "Attempt to download new application package";
               default "24";
               units "hours";
               type union {
                 type string {
                   pattern "<.*>|$.*";
                 }
                 type uint32 {
                   range "6 .. 720";
                 }
               }
             }
           }
           leaf proxy-profile {
             description "Configure web proxy for Application signature download";
             junos:must "(\"services proxy profile $$\")";
             junos:must-message "proxy profile must be defined";
             type string {
               length "1 .. 128";
             }
           }
         }
         container statistics {
           description "Configure application statistics information";
           leaf interval {
             description "Application statistics collection interval";
             default "1";
             units "minutes";
             type union {
               type string {
                 pattern "<.*>|$.*";
               }
               type uint32 {
                 range "1 .. 1440";
               }
             }
           }
         }
         container nested-application-settings {
           presence "enable nested-application-settings";
           description "Nested application settings";
           status deprecated;
           uses apply-advanced;
           leaf no-nested-application {
             description "Disable nested application identification";
             type empty;
           }
           leaf no-application-system-cache {
             description "Not to save nested AI match in application system cache";
             type empty;
           }
         }
         leaf no-application-identification {
           description "Disable all application identification methods";
           status deprecated;
           type empty;
         }
         leaf no-signature-based {
           description "Disable signature based method";
           status deprecated;
           type empty;
         }
         leaf no-protocol-based {
           description "Disable protocol based method";
           status deprecated;
           type empty;
         }
         leaf signature-method-all-ports {
           description "Use signature-method on all(including well-known) ports";
           status deprecated;
           type empty;
         }
         leaf no-clear-application-system-cache {
           description "Disable clearing application system cache";
           status deprecated;
           type empty;
         }
         leaf no-application-system-cache {
           description "Disable storing AI result in application system cache";
           type empty;
         }
         leaf max-sessions {
           description "Max sessions that can run AI at the same time";
           status deprecated;
           type union {
             type string {
               pattern "<.*>|$.*";
             }
             type uint32 {
               range "0 .. 500000";
             }
           }
         }
         leaf application-system-cache-timeout {
           description "Application system cache entry lifetime";
           type union {
             type string {
               pattern "<.*>|$.*";
             }
             type uint32 {
               range "0 .. 1000000";
             }
           }
         }
         container application-system-cache {
           presence "enable application-system-cache";
           description "Enable or Disable application system cache";
           uses apply-advanced;
           leaf security-services {
             description "Enable ASC for security services (appfw, appqos, idp, skyatp..)";
             type empty;
           }
           leaf no-miscellaneous-services {
             description "Disable ASC for miscellaneous services APBR,...";
             type empty;
           }
         }
         leaf max-transactions {
           description "Number of transaction finals to terminate application classification";
           type union {
             type string {
               pattern "<.*>|$.*";
             }
             type uint16 {
               range "0 .. 25";
             }
           }
         }
         leaf max-checked-bytes {
           description "Inspect the maximal number of bytes";
           status deprecated;
           type union {
             type string {
               pattern "<.*>|$.*";
             }
             type uint32 {
               range "0 .. 100000";
             }
           }
         }
         list application {
           key name;
           description "Configure application definition";
           junos:must "((any \". <*> icmp-mapping\" || (any \". <*> ip-protocol-mapping\" || (any \". <*> address-mapping\" || (any \". <*> over\" || any \". <*> signature\")))))";
           junos:must-message "All applications must have either icmp-mapping or ip-protocol-mapping or address-mapping or over or signature object ";
           leaf name {
             description "A unique application identifier";
             type string {
               length "1 .. 63";
             }
           }
           uses apply-advanced;
           leaf type {
             description "Well-known application such as HTTP and FTP";
             junos:must "(unique \"services application-identification application <*> type $$\")";
             junos:must-message "Application type has to be unique among all applications";
             type string {
               length "1 .. 63";
             }
           }
           leaf index {
             description "Custom index (32768..65534). Application index";
             status deprecated;
             junos:must "(unique \"services application-identification application <*> index $$\")";
             junos:must-message "Application index has to be unique among all applications";
             type union {
               type string {
                 pattern "<.*>|$.*";
               }
               type uint16 {
                 range "1 .. 65534";
               }
             }
           }
           list tags {
             key name;
             ordered-by user;
             description "Application tags eg. risk factors, technology, traffic type";
             max-elements 3;
             leaf name {
               description "General information about the application type";
               type string;
             }
             uses apply-advanced;
             leaf value {
               description "Value";
               type string;
             }
           }
           leaf session-timeout {
             description "Lifetime of a session";
             status deprecated;
             default "86400";
             type enumeration {
               enum "0" {
                 description "No session timeout";
                 status deprecated;
               }
               enum "30" {
                 description "30 seconds";
                 status deprecated;
               }
               enum "60" {
                 description "60 seconds";
                 status deprecated;
               }
               enum "1800" {
                 description "1800 seconds";
                 status deprecated;
               }
               enum "3600" {
                 description "3600 seconds";
                 status deprecated;
               }
               enum "43200" {
                 description "43200 seconds (12 hours)";
                 status deprecated;
               }
               enum "86400" {
                 description "86400 seconds (1 day)";
                 status deprecated;
               }
               enum "2592000" {
                 description "2592000 seconds (30 days)";
                 status deprecated;
               }
             }
           }
           leaf idle-timeout {
             description "Remove the session if no packets";
             status deprecated;
             default "30";
             type enumeration {
               enum "0" {
                 description "No idle timeout";
                 status deprecated;
               }
               enum "5" {
                 description "5 seconds";
                 status deprecated;
               }
               enum "15" {
                 description "15 seconds";
                 status deprecated;
               }
               enum "30" {
                 description "30 seconds";
                 status deprecated;
               }
               enum "60" {
                 description "60 seconds";
                 status deprecated;
               }
               enum "1800" {
                 description "1800 seconds";
                 status deprecated;
               }
               enum "3600" {
                 description "3600 seconds";
                 status deprecated;
               }
             }
           }
           container type-of-service {
             description "Type of service";
             status deprecated;
             uses apply-advanced;
             leaf minimize-delay {
               description "Requires minimal delay in packet transmission";
               type empty;
             }
             leaf maximize-throughput {
               description "Requires maximal throughput in packet transmission";
               type empty;
             }
             leaf maximize-reliability {
               description "Requires maximal reliability in packet transmission";
               type empty;
             }
             leaf minimize-monetary-cost {
               description "Requires minimal monetary cost in packet transmission";
               type empty;
             }
           }
           leaf disable {
             description "Disable this application definition in AI";
             status deprecated;
             type empty;
           }
           leaf cacheable {
             description "Cacheable";
             type empty;
           }
           leaf description {
             description "Text description of application";
             type string {
               junos:posix-pattern "^.{1,255}$";
               junos:pattern-message "Must be a string of 255 characters or less";
             }
           }
           leaf priority {
             description "Application matching priority";
             default "high";
             type enumeration {
               enum "high" {
                 description "Highest priority over all other signatures";
               }
               enum "low" {
                 description "Lowest priority over all other signatures";
               }
             }
           }
           leaf order {
             description "The order value, lower the value higher the priority";
             junos:must "(unique \"services application-identification application <*> order $$\")";
             junos:must-message "Application order has to be unique among all applications";
             type union {
               type string {
                 pattern "<.*>|$.*";
               }
               type uint16 {
                 range "1 .. 50000";
               }
             }
           }
           leaf maximum-transactions {
             description "Maximum number of transactions matched by AI";
             status deprecated;
             type union {
               type uint16;
               type string {
                 pattern "<.*>|$.*";
               }
             }
           }
           leaf alt-name {
             description "Alt name for the application";
             type string {
               junos:posix-pattern "^.{1,255}$";
               junos:pattern-message "Must be a string of 255 characters or less";
             }
           }
           leaf compatibility {
             description "Juniper compatibility version";
             type string {
               junos:posix-pattern "^.{1,255}$";
               junos:pattern-message "Must be a string of 255 characters or less";
             }
           }
           container port-mapping {
             status deprecated;
             uses apply-advanced;
             container icmp {
               description "Match ICMP message";
               uses apply-advanced;
               leaf type {
                 description "Numeric type value (0 .. 254)";
                 junos:must "(unique \"services application-identification application <*> port-mapping icmp type $$\")";
                 junos:must-message "Icmp type has to be unique among all applications";
                 type union {
                   type string {
                     pattern "<.*>|$.*";
                   }
                   type uint16 {
                     range "0 .. 254";
                   }
                 }
               }
               leaf code {
                 description "Numeric code value (0 .. 254)";
                 junos:must "(\".. type\")";
                 junos:must-message "Icmp type must be configured";
                 type union {
                   type string {
                     pattern "<.*>|$.*";
                   }
                   type uint16 {
                     range "0 .. 254";
                   }
                 }
               }
             }
             leaf protocol {
               description "Numeric protocol value (0 .. 254)";
               junos:must "(unique \"services application-identification application <*> port-mapping protocol $$\")";
               junos:must-message "Protocol has to be unique among all applications";
               type union {
                 type string {
                   pattern "<.*>|$.*";
                 }
                 type uint16 {
                   range "0 .. 254";
                 }
               }
             }
             container port-range {
               description "Used by port-based AI method";
               uses apply-advanced;
               leaf-list tcp {
                 ordered-by user;
                 description "TCP port range";
                 type string;
                 max-elements 64;
               }
               leaf-list udp {
                 ordered-by user;
                 description "UDP port range";
                 type string;
                 max-elements 64;
               }
             }
             leaf disable {
               description "Disable port-based method for this application";
               type empty;
             }
           }
           container icmp-mapping {
             description "Match ICMP message";
             uses apply-advanced;
             leaf type {
               description "Numeric type value";
               type union {
                 type string {
                   pattern "<.*>|$.*";
                 }
                 type uint16 {
                   range "0 .. 254";
                 }
               }
             }
             leaf code {
               description "Numeric code value";
               junos:must "(\".. type\")";
               junos:must-message "ICMP type must be configured";
               type union {
                 type string {
                   pattern "<.*>|$.*";
                 }
                 type uint16 {
                   range "0 .. 254";
                 }
               }
             }
             leaf order {
               description "The Order value";
               status deprecated;
               type union {
                 type string {
                   pattern "<.*>|$.*";
                 }
                 type uint16 {
                   range "0 .. 65535";
                 }
               }
             }
             leaf order-priority {
               description "Application matching priority";
               status deprecated;
               default "high";
               type enumeration {
                 enum "high" {
                   description "Highest priority over all other signatures";
                   status deprecated;
                 }
                 enum "low" {
                   description "Lowest priority over all other signatures";
                   status deprecated;
                 }
               }
             }
           }
           container ip-protocol-mapping {
             description "Match IP protocol";
             uses apply-advanced;
             leaf protocol {
               description "Numeric protocol value";
               junos:must "(unique \"services application-identification application <*> ip-protocol-mapping protocol $$\")";
               junos:must-message "Protocol has to be unique among all applications";
               type union {
                 type string {
                   pattern "<.*>|$.*";
                 }
                 type uint16 {
                   range "0 .. 254";
                 }
               }
             }
             leaf order {
               description "The Order value";
               status deprecated;
               type union {
                 type string {
                   pattern "<.*>|$.*";
                 }
                 type uint16 {
                   range "0 .. 65535";
                 }
               }
             }
             leaf order-priority {
               description "Application matching priority";
               status deprecated;
               default "high";
               type enumeration {
                 enum "high" {
                   description "Highest priority over all other signatures";
                   status deprecated;
                 }
                 enum "low" {
                   description "Lowest priority over all other signatures";
                   status deprecated;
                 }
               }
             }
           }
           list address-mapping {
             key name;
             ordered-by user;
             description "Match IP address";
             leaf name {
               description "Address name";
               type string {
                 length "1 .. 63";
               }
             }
             uses apply-advanced;
             container filter {
               description "Match IP/port";
               uses apply-advanced;
               leaf ip {
                 description "IP address and prefix-length";
                 type jt:ipprefix;
               }
               container port-range {
                 description "Port ranges";
                 uses apply-advanced;
                 leaf-list tcp {
                   ordered-by user;
                   description "TCP port range";
                   type string;
                   max-elements 20;
                 }
                 leaf-list udp {
                   ordered-by user;
                   description "UDP port range";
                   type string;
                   max-elements 20;
                 }
               }
             }
             container source {
               junos:must "((any \". ip <*>\" || any \". wildcard-address <*>\"))";
               junos:must-message "Source must have either ip/prefix or wildcard address";
               description "Match IP source address";
               uses apply-advanced;
               leaf ip {
                 description "IP address and prefix-length";
                 type jt:ipprefix;
               }
               container wildcard-address {
                 description "IP wildcard address and mask";
                 leaf address {
                   description "IP wildcard address";
                   type jt:ipaddr;
                 }
                 leaf wildcard-mask {
                   description "IP wildcard address mask";
                   type jt:ipaddr;
                 }
               }
               container port-range {
                 description "IP port ranges";
                 uses apply-advanced;
                 leaf-list tcp {
                   ordered-by user;
                   description "TCP port range";
                   type string;
                   max-elements 64;
                 }
                 leaf-list udp {
                   ordered-by user;
                   description "UDP port range";
                   type string;
                   max-elements 64;
                 }
               }
             }
             container destination {
               junos:must "((any \". ip <*>\" || any \". wildcard-address <*>\"))";
               junos:must-message "Destination must have either ip/prefix or wildcard address";
               description "Match IP destination address";
               uses apply-advanced;
               leaf ip {
                 description "IP address and prefix-length";
                 type jt:ipprefix;
               }
               container wildcard-address {
                 description "IP wildcard address and mask";
                 leaf address {
                   description "IP wildcard address";
                   type jt:ipaddr;
                 }
                 leaf wildcard-mask {
                   description "IP wildcard address mask";
                   type jt:ipaddr;
                 }
               }
               container port-range {
                 description "IP port ranges";
                 uses apply-advanced;
                 leaf-list tcp {
                   ordered-by user;
                   description "TCP port range";
                   type string;
                   max-elements 64;
                 }
                 leaf-list udp {
                   ordered-by user;
                   description "UDP port range";
                   type string;
                   max-elements 64;
                 }
               }
             }
             leaf order {
               description "Application matching priority";
               status deprecated;
               junos:must "(unique \"services application-identification application <*> address-mapping <*> order $$\")";
               junos:must-message "Address mapping order must be unique among all applications";
               type union {
                 type string {
                   pattern "<.*>|$.*";
                 }
                 type uint16 {
                   range "1 .. 65535";
                 }
               }
             }
             leaf order-priority {
               description "Application matching priority";
               status deprecated;
               default "high";
               type enumeration {
                 enum "high" {
                   description "Highest priority over all other signatures";
                   status deprecated;
                 }
                 enum "low" {
                   description "Lowest priority over all other signatures";
                   status deprecated;
                 }
               }
             }
           }
           list over {
             key name;
             description "Set of L4/L7 application that carries given application";
             max-elements 8;
             leaf name {
               description "A unique application and protocol identifier";
               type string {
                 length "1 .. 63";
               }
             }
             uses apply-advanced;
             leaf protocol {
               description "Application protocol";
               status deprecated;
               type enumeration {
                 enum "http" {
                   description "Application over http protocol";
                   status deprecated;
                 }
                 enum "ssl" {
                   description "Application over ssl protocol";
                   status deprecated;
                 }
                 enum "udp" {
                   description "Application over over udp protocol";
                   status deprecated;
                 }
                 enum "tcp" {
                   description "Application over tcp protocol";
                   status deprecated;
                 }
               }
             }
             leaf chain-order {
               description "The order of members is used to match the pattern";
               type empty;
             }
             leaf order-priority {
               description "Application matching priority";
               status deprecated;
               default "high";
               type enumeration {
                 enum "high" {
                   description "Highest priority over all other signatures";
                   status deprecated;
                 }
                 enum "low" {
                   description "Lowest priority over all other signatures";
                   status deprecated;
                 }
               }
             }
             leaf order {
               description "The order value";
               status deprecated;
               type union {
                 type string {
                   pattern "<.*>|$.*";
                 }
                 type uint16 {
                   range "0 .. 65535";
                 }
               }
             }
             container port-range {
               description "Apply signature to packets sent to this port range";
               uses apply-advanced;
               leaf-list tcp {
                 ordered-by user;
                 description "TCP port range";
                 junos:must "(!(\".. udp\"))";
                 junos:must-message "udp cannot be specified with tcp";
                 type string;
                 max-elements 64;
               }
               leaf-list udp {
                 ordered-by user;
                 description "UDP port range";
                 junos:must "(!(\".. tcp\"))";
                 junos:must-message "tcp cannot be specified with udp";
                 type string;
                 max-elements 64;
               }
             }
             list member {
               key name;
               description "Pattern matched on client-to-server packets";
               status deprecated;
               max-elements 4;
               leaf name {
                 description "A unique application signature member identifier. Must be m01 ..m16";
                 type string {
                   length "1 .. 63";
                   junos:posix-pattern "^m(0[1-9]|1[0-6])";
                   junos:pattern-message "Must be m01 - m16";
                 }
               }
               uses apply-advanced;
               leaf context {
                 description "Context to be matched on";
                 type string;
               }
               leaf pattern {
                 description "Pattern matched on context";
                 type string;
               }
               leaf direction {
                 description "Connection direction of the packets to apply pattern matching";
                 type enumeration {
                   enum "client-to-server" {
                     description "Client to server";
                   }
                   enum "server-to-client" {
                     description "Server to client";
                   }
                   enum "any" {
                     description "Any direction";
                   }
                 }
               }
               leaf check-bytes {
                 description "Maximum number of bytes to check for stream context ";
                 default "1000";
                 type union {
                   type string {
                     pattern "<.*>|$.*";
                   }
                   type uint32 {
                     range "1 .. 5000";
                   }
                 }
               }
             }
             list signature {
               key name;
               description "Application signature for pattern matching";
               leaf name {
                 description "A unique application signature identifier";
                 type string {
                   length "1 .. 63";
                 }
               }
               uses apply-advanced;
               leaf-list port-range {
                 ordered-by user;
                 description "Port range";
                 type string;
                 max-elements 64;
               }
               list member {
                 key name;
                 description "Application signature member";
                 leaf name {
                   description "Application signature member identifier in range m01 - m15";
                   type string {
                     length "1 .. 63";
                     junos:posix-pattern "^m(0[1-9]|1[0-5])";
                     junos:pattern-message "Must be m01 - m15";
                   }
                 }
                 uses apply-advanced;
                 leaf context {
                   description "Context to be matched on";
                   type string;
                 }
                 leaf pattern {
                   description "DFA pattern matched on context";
                   type string {
                     junos:posix-pattern "^.{1,127}$";
                     junos:pattern-message "Must be a string of 127 characters or less";
                   }
                 }
                 leaf direction {
                   description "Connection direction of the packets to apply pattern matching";
                   type enumeration {
                     enum "client-to-server" {
                       description "Client to server";
                     }
                     enum "server-to-client" {
                       description "Server to client";
                     }
                     enum "any" {
                       description "Any direction";
                     }
                   }
                 }
               }
             }
           }
         }
         list nested-application {
           key name;
           description "Configure nested application definition";
           status deprecated;
           leaf name {
             description "A unique application identifier";
             type string {
               length "1 .. 63";
             }
           }
           uses apply-advanced;
           leaf type {
             description "Well-known application such as FACEBOOK and KAZZA";
             junos:must "(unique \"services application-identification nested-application <*> type $$\")";
             junos:must-message "Nested application type has to be unique among all nested applications";
             type string {
               length "1 .. 63";
             }
           }
           leaf index {
             description "Custom index (32768..65534). Application index";
             status deprecated;
             junos:must "(!(any \"services application-identification application <*> index $$\"))";
             junos:must-message "Nested application index has to be unique among all applications and nested applications";
             junos:must "(unique \"services application-identification nested-application <*> index $$\")";
             junos:must-message "Nested application index has to be unique among all nested applications";
             type union {
               type string {
                 pattern "<.*>|$.*";
               }
               type uint16 {
                 range "1 .. 65534";
               }
             }
           }
           leaf protocol {
             description "Name of layer 7 application that carries nested application";
             type string {
               length "1 .. 63";
             }
           }
           list signature {
             key name;
             description "Nested application signature for pattern matching";
             leaf name {
               description "A unique nested application signature identifier";
               junos:must "(unique \"services application-identification nested-application <*> signature $$\")";
               junos:must-message "Nested application signature name has to be unique among all nested applications";
               type string {
                 length "1 .. 63";
               }
             }
             uses apply-advanced;
             list member {
               key name;
               description "Pattern matched on client-to-server packets";
               leaf name {
                 description "A unique nested application signature member identifier";
                 type string {
                   length "1 .. 63";
                   junos:posix-pattern "^m(0[1-9]|1[0-6])";
                   junos:pattern-message "Must be m01 - m16";
                 }
               }
               uses apply-advanced;
               leaf context {
                 description "Context to be matched on";
                 type string;
               }
               leaf pattern {
                 description "Pattern matched on context";
                 type string;
               }
               leaf direction {
                 description "Connection direction of the packets to apply pattern matching";
                 type enumeration {
                   enum "client-to-server" {
                     description "Client to server";
                   }
                   enum "server-to-client" {
                     description "Server to client";
                   }
                   enum "any" {
                     description "Any direction";
                   }
                 }
               }
               leaf check-bytes {
                 description "Maximum number of bytes to check for stream context ";
                 default "1000";
                 type union {
                   type string {
                     pattern "<.*>|$.*";
                   }
                   type uint32 {
                     range "1 .. 5000";
                   }
                 }
               }
             }
             leaf chain-order {
               description "The order of members is used to match the pattern";
               type empty;
             }
             leaf maximum-transactions {
               description "Maximum number of transactions matched by AI";
               type union {
                 type uint16;
                 type string {
                   pattern "<.*>|$.*";
                 }
               }
             }
             leaf order {
               description "Application matching priority";
               status deprecated;
               junos:must "(!(any \"services application-identification application <*> signature order $$\"))";
               junos:must-message "Nested application order has to be unique among all applications and nested applications";
               junos:must "(unique \"services application-identification nested-application <*> signature <*> order $$\")";
               junos:must-message "Nested application order has to be unique among all nested applications";
               type union {
                 type string {
                   pattern "<.*>|$.*";
                 }
                 type uint16 {
                   range "1 .. 65535";
                 }
               }
             }
             container insert-before {
               description "Insert before another signature";
               uses apply-advanced;
               leaf insert-before-name {
                 description "An application name";
                 type string;
               }
             }
           }
         }
         list application-group {
           key name;
           description "Define application group";
           leaf name {
             description "A unique application group identifier";
             type string {
               length "1 .. 63";
             }
           }
           uses apply-advanced;
           list application-groups {
             key name;
             description "Configure child application group(s)";
             leaf name {
               description "Name of the child application group";
               type string {
                 length "1 .. 63";
               }
             }
             uses apply-advanced;
           }
           list applications {
             key name;
             description "Configure applications that belong to this application group";
             leaf name {
               description "Configure application name";
               type string {
                 length "1 .. 63";
               }
             }
             uses apply-advanced;
           }
           leaf disable {
             description "Disable this application group definition in AI";
             status deprecated;
             type empty;
           }
         }
         list rule {
           key name;
           ordered-by user;
           description "One or more application rules for address-based method AI";
           status deprecated;
           leaf name {
             description "Rule name";
             type string {
               length "1 .. 63";
             }
           }
           uses apply-advanced;
           leaf application-name {
             description "Name of application that is target of this rule";
             type string {
               length "1 .. 63";
             }
           }
           list address {
             key name;
             ordered-by user;
             description "Configure one of more addresses";
             junos:must "((any \". <*> source\" || any \". <*> destination\"))";
             junos:must-message "All addresses must have either source or destination or both";
             leaf name {
               description "Address name";
               type string;
             }
             uses apply-advanced;
             container source {
               description "Match IP source address";
               uses apply-advanced;
               leaf ip {
                 description "IP address and prefix-length";
                 type jt:ipv4prefix;
               }
               container port-range {
                 description "IP port ranges";
                 uses apply-advanced;
                 leaf-list tcp {
                   ordered-by user;
                   description "TCP port range";
                   type string;
                   max-elements 64;
                 }
                 leaf-list udp {
                   ordered-by user;
                   description "UDP port range";
                   type string;
                   max-elements 64;
                 }
               }
             }
             container destination {
               description "Match IP destination address";
               uses apply-advanced;
               leaf ip {
                 description "IP address and prefix-length";
                 type jt:ipv4prefix;
               }
               container port-range {
                 description "IP port ranges";
                 uses apply-advanced;
                 leaf-list tcp {
                   ordered-by user;
                   description "TCP port range";
                   type string;
                   max-elements 64;
                 }
                 leaf-list udp {
                   ordered-by user;
                   description "UDP port range";
                   type string;
                   max-elements 64;
                 }
               }
             }
             leaf order {
               description "Application matching priority";
               junos:must "(unique \"services application-identification rule <*> address <*> order $$\")";
               junos:must-message "Address order has to be unique among all rules";
               type union {
                 type string {
                   pattern "<.*>|$.*";
                 }
                 type uint16 {
                   range "1 .. 65535";
                 }
               }
             }
           }
         }
         list rule-set {
           key name;
           ordered-by user;
           description "One or more application rules";
           status deprecated;
           leaf name {
             description "Name of the rule set";
             type string {
               length "1 .. 63";
               junos:posix-pattern "^[[:alnum:]][[:alnum:]_-]*$";
               junos:pattern-message "Must be a string beginning with a number or letter and consisting of letters, numbers, dashes and underscores.";
             }
           }
           uses apply-advanced;
           list rule {
             key name;
             ordered-by user;
             description "Rule to be included in this rule set";
             leaf name {
               description "Rule name";
               junos:must "(\"services application-identification rule $$\")";
               junos:must-message "rule must be configured";
               type string {
                 junos:posix-pattern "^[A-Za-z0-9][_0-9A-Za-z-]{0,62}$";
                 junos:pattern-message "Must be a string beginning with a number or letter and consisting of no more than 63 total letters, numbers, dashes and underscores.";
               }
             }
             uses apply-advanced;
           }
         }
         list profile {
           key name;
           ordered-by user;
           description "One or more application rule-sets";
           leaf name {
             description "Profile name";
             type string {
               length "1 .. 63";
             }
           }
           uses apply-advanced;
           list rule-set {
             key name;
             ordered-by user;
             description "One or more rule-sets in the profile";
             leaf name {
               description "Rule-set name";
               junos:must "(\"services application-identification rule-set $$\")";
               junos:must-message "rule set must be configured";
               type string {
                 length "1 .. 63";
               }
             }
             uses apply-advanced;
           }
         }
         container traceoptions {
           description "Trace options for application identification";
           uses apply-advanced;
           leaf no-remote-trace {
             description "Disable remote tracing";
             junos:must "(\"system tracing\")";
             junos:must-message "'no-remote-trace' is valid only when [system tracing] is configured";
             type empty;
           }
           container file {
             description "Trace file information";
             leaf filename {
               description "Name of file in which to write trace information";
               type string {
                 length "1 .. 1024";
                 junos:posix-pattern "![/ %]";
                 junos:pattern-message "Must not contain '/', % or a space";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Events and other information to include in trace output";
             leaf name {
               description "Flag name to include in trace output";
               type enumeration {
                 enum "all" {
                   description "All events";
                 }
               }
             }
           }
           leaf level {
             description "Level of debugging output";
             default "error";
             type enumeration {
               enum "error" {
                 description "Match error conditions";
               }
               enum "warning" {
                 description "Match warning messages";
               }
               enum "notice" {
                 description "Match conditions that should be handled specially";
               }
               enum "info" {
                 description "Match informational messages";
               }
               enum "verbose" {
                 description "Match verbose messages";
               }
               enum "all" {
                 description "Match all levels";
               }
             }
           }
         }
       }
       list service-set {
         key name;
         ordered-by user;
         description "Define a service set";
         leaf name {
           description "Service set name";
           type string {
             length "1 .. 52";
             junos:posix-pattern "^[[:alnum:]][[:alnum:]/.:_-]*$";
             junos:pattern-message "Must be a string beginning with a number or letter and consisting of letters, numbers, dashes, underscores, forward slashes, colons and dots.";
           }
         }
         uses apply-advanced;
         container syslog {
           description "Define system logging parameters";
           uses log-object;
         }
         leaf max-flows {
           description "Maximum number of flows allowed for a service set";
           type string;
         }
         leaf hosted-service-identifier {
           description "Service Set to Hosted service Map";
           type union {
             type string {
               pattern "<.*>|$.*";
             }
             type int32 {
               range "1 .. 63";
             }
           }
         }
         leaf max-session-setup-rate {
           description "Maximum number of session creations allowed per second";
           type string;
         }
         container max-drop-flows {
           description "Maximum number of drop flows allowed for a service-set";
           uses apply-advanced;
           leaf ingress {
             description "Maximum number of ingress drop flows allowed";
             type union {
               type string {
                 pattern "<.*>|$.*";
               }
               type int32 {
                 range "0 .. 8500000";
               }
             }
           }
           leaf egress {
             description "Maximum number of egress drop flows allowed";
             type union {
               type string {
                 pattern "<.*>|$.*";
               }
               type int32 {
                 range "0 .. 8500000";
               }
             }
           }
         }
         container snmp-trap-thresholds {
           presence "enable snmp-trap-thresholds";
           description "Define snmp traps for service sets";
           uses apply-advanced;
           container flow {
             presence "enable flow";
             junos:must "(\".. .. max-flows\")";
             junos:must-message "Max flow must be set for configuring flow threshold";
             description "Flow Threshold range for a service set";
             leaf low {
               description "Lower limit of flow threshold";
               units "percent";
               type union {
                 type string {
                   pattern "<.*>|$.*";
                 }
                 type uint16 {
                   range "0 .. 100";
                 }
               }
             }
             leaf high {
               description "Upper limit of flow threshold";
               units "percent";
               type union {
                 type string {
                   pattern "<.*>|$.*";
                 }
                 type uint16 {
                   range "0 .. 100";
                 }
               }
             }
           }
           container nat-address-port {
             presence "enable nat-address-port";
             description "Nat Address and port usage trap threshold range";
             leaf low {
               description "Lower limit of trap threshold";
               units "percent";
               type union {
                 type string {
                   pattern "<.*>|$.*";
                 }
                 type uint16 {
                   range "0 .. 100";
                 }
               }
             }
             leaf high {
               description "Upper limit of trap threshold";
               units "percent";
               type union {
                 type string {
                   pattern "<.*>|$.*";
                 }
                 type uint16 {
                   range "0 .. 100";
                 }
               }
             }
           }
           container session {
             presence "enable session";
             junos:must "(\".. .. service-set-options session-limit\")";
             junos:must-message "Maximum session limit must be set for configuring session threshold";
             description "Session threshold range for a service set";
             leaf low {
               description "Lower limit of flow threshold";
               units "percent";
               type union {
                 type string {
                   pattern "<.*>|$.*";
                 }
                 type uint16 {
                   range "0 .. 100";
                 }
               }
             }
             leaf high {
               description "Upper limit of flow threshold";
               units "percent";
               type union {
                 type string {
                   pattern "<.*>|$.*";
                 }
                 type uint16 {
                   range "0 .. 100";
                 }
               }
             }
           }
         }
         leaf tcp-mss {
           description "Enable the limit on TCP Max. Seg. Size in SYN packets";
           type union {
             type string {
               pattern "<.*>|$.*";
             }
             type uint16 {
               range "536 .. 65535";
             }
           }
         }
         container cos-options {
           presence "enable cos-options";
           description "Options for COS service";
           uses apply-advanced;
           leaf match-rules-on-reverse-flow {
             description "If forward rules match fails, do it on reverse flow";
             type empty;
           }
         }
         container softwire-options {
           presence "enable softwire-options";
           description "Options for softwire";
           uses apply-advanced;
           leaf dslite-ipv6-prefix-length {
             description "The ipv6 prefix length for subscriber addresses";
             default "128";
             type enumeration {
               enum "56" {
                 description "The ipv6 prefix length of 56";
               }
               enum "64" {
                 description "The ipv6 prefix length of 64";
               }
               enum "96" {
                 description "The ipv6 prefix length of 96";
               }
               enum "128" {
                 description "The ipv6 prefix length of 128";
               }
             }
           }
         }
         container nat-options {
           description "Options for NAT";
           uses apply-advanced;
           container stateful-nat64 {
             description "Options for stateful NAT64";
             uses apply-advanced;
             leaf clear-dont-fragment-bit {
               description "Clear DF bit in IPv4 header if IPv6 packet size is less than 1280 bytes";
               type empty;
             }
             leaf ipv6-mtu {
               description "Path MTU of IPv6 network";
               type union {
                 type string {
                   pattern "<.*>|$.*";
                 }
                 type uint16 {
                   range "1280 .. 9192";
                 }
               }
             }
             leaf disable-h323-ras {
               description "Disable H323 and RAS ALG for NAT64";
               type empty;
             }
           }
           container nptv6 {
             description "Options for NPTv6";
             uses apply-advanced;
             leaf icmpv6-error-messages {
               description "Send ICMP Error messages if NPTv6 address translation fails";
               type empty;
             }
           }
           leaf land-attack-check {
             description "Enable land attack checks";
             type enumeration {
               enum "ip-only" {
                 description "Land attack check is on IP address only";
               }
               enum "ip-port" {
                 description "Land attack check is on both IP and port";
               }
             }
           }
           leaf max-sessions-per-subscriber {
             description "Limit the number of sessions per subscriber";
             type union {
               type string {
                 pattern "<.*>|$.*";
               }
               type uint16 {
                 range "1 .. 32000";
               }
             }
           }
           leaf snmp-value-match-msmic {
             description "Match the MSMIC specific snmp values for the msdpc";
             type empty;
           }
         }
         container service-set-options {
           presence "enable service-set-options";
           description "Options for service set";
           uses apply-advanced;
           leaf tcp-non-syn {
             description "Deny session creation on receiving first non SYN pkt";
             type enumeration {
               enum "drop-flow" {
                 description "Drop tcp non SYN first packe";
               }
               enum "drop-flow-send-rst" {
                 description "Enable sending TCP RST on receiving first non SYN pkt";
               }
             }
           }
           leaf tcp-fast-open {
             description "Tcp-fast-Open enabled packets will be handled accordingly";
             type enumeration {
               enum "disabled" {
                 description "TFO option will be stripped and packet will be forwarded";
               }
               enum "drop" {
                 description "TFO enabled packets will be dropeed";
               }
             }
           }
           leaf bypass-traffic-on-pic-failure {
             description "Bypass traffic on service PIC failure";
             type empty;
           }
           leaf bypass-traffic-on-exceeding-flow-limits {
             description "Bypass traffic when exceeding the max flow limit";
             type empty;
           }
           leaf enable-asymmetric-traffic-processing {
             description "Enable service-processing for asymmetric traffic";
             type empty;
           }
           leaf subscriber-awareness {
             description "Enable subscriber awareness on the service chain";
             type empty;
           }
           container header-integrity-check {
             description "Enable/Disable header integrity checks";
             uses apply-advanced;
             leaf enable-all {
               description "Enable all header integrity checks";
               type empty;
             }
           }
           leaf enable-change-on-ams-redistribution {
             description "Allow NAT pool change on AMS redistribution";
             status deprecated;
             type empty;
           }
           leaf routing-engine-services {
             description "Enable service-processing at RE";
             type empty;
           }
           leaf inactivity-non-tcp-timeout {
             description "Inactivity timeout period for non-TCP established sessions";
             units "seconds";
             type union {
               type string {
                 pattern "<.*>|$.*";
               }
               type uint32 {
                 range "4 .. 86400";
               }
             }
           }
           leaf session-timeout {
             description "Session timeout period for established sessions";
             units "seconds";
             type union {
               type string {
                 pattern "<.*>|$.*";
               }
               type uint32 {
                 range "4 .. 86400";
               }
             }
           }
           container session-limit {
             presence "enable session-limit";
             description "Session limit";
             uses apply-advanced;
             leaf maximum {
               description "Maximum number of sessions allowed simultaneously";
               type string;
             }
           }
           container tcp-session {
             presence "enable tcp-session";
             description "Transmission Control Protocol session configuration";
             uses apply-advanced;
             leaf tcp-mss {
               description "Enable the limit on TCP Max. Seg. Size in SYN packets";
               type union {
                 type string {
                   pattern "<.*>|$.*";
                 }
                 type uint16 {
                   range "536 .. 65535";
                 }
               }
             }
             leaf tcp-tickles {
               description "Number of TCP keep-alive packets to be sent for bi-directional TCP flows";
               default "4";
               type union {
                 type string {
                   pattern "<.*>|$.*";
                 }
                 type uint8 {
                   range "0 .. 30";
                 }
               }
             }
             leaf open-timeout {
               description "Timeout period for TCP session establishment";
               units "seconds";
               type union {
                 type string {
                   pattern "<.*>|$.*";
                 }
                 type uint32 {
                   range "4 .. 300";
                 }
               }
             }
             leaf inactivity-tcp-timeout {
               description "Inactivity timeout period for TCP established sessions";
               units "seconds";
               type union {
                 type string {
                   pattern "<.*>|$.*";
                 }
                 type uint32 {
                   range "4 .. 86400";
                 }
               }
             }
             leaf inactivity-asymm-tcp-timeout {
               description "Inactivity timeout period for asymmetric TCP established sessions";
               units "seconds";
               type union {
                 type string {
                   pattern "<.*>|$.*";
                 }
                 type uint32 {
                   range "4 .. 86400";
                 }
               }
             }
             container ignore-errors {
               presence "enable ignore-errors";
               description "Ignore anomalies or errors";
               leaf tcp {
                 description "TCP protocol errors";
                 type empty;
               }
             }
             leaf close-timeout {
               description "Timeout period for TCP session tear-down";
               units "seconds";
               type union {
                 type string {
                   pattern "<.*>|$.*";
                 }
                 type uint32 {
                   range "2 .. 300";
                 }
               }
             }
             leaf tcp-non-syn {
               description "Deny session creation on receiving first non SYN pkt";
               type enumeration {
                 enum "drop-flow" {
                   description "Drop tcp non SYN first packe";
                 }
                 enum "drop-flow-send-rst" {
                   description "Enable sending TCP RST on receiving first non SYN pkt";
                 }
               }
             }
             leaf tcp-fast-open {
               description "Tcp-fast-Open enabled paclets will be handled accordingly";
               type enumeration {
                 enum "disabled" {
                   description "TFO option will be stripped and packet will be forwarded";
                 }
                 enum "drop" {
                   description "TFO enabled packets will be dropeed";
                 }
               }
             }
           }
         }
         container replicate-services {
           description "Define services that will be replicated to peer.";
           uses apply-advanced;
           leaf replication-threshold {
             description "Duration in seconds for which flow should remain active for replication. (Min 180s)";
             default "180";
             type union {
               type string {
                 pattern "<.*>|$.*";
               }
               type uint32 {
                 range "180 .. 86400";
               }
             }
           }
           leaf disable-replication-capability {
             description "Disable replication capability for this service-set";
             type empty;
           }
         }
         container allow-multicast {
           presence "enable allow-multicast";
           junos:must "(\".. next-hop-service\")";
           junos:must-message "Service-set must be nexthop style to use allow-multicast";
           description "Allow multicast packets";
           uses apply-advanced;
         }
         choice softwire_choice {
           case case_1 {
             list softwire-rules {
               key name;
               ordered-by user;
               description "List of softwire rules";
               leaf name {
                 type string {
                   length "1 .. 63";
                   junos:posix-pattern "^[[:alnum:]][[:alnum:]_-]*$";
                   junos:pattern-message "Must be a string beginning with a number or letter and consisting of letters, numbers, dashes and underscores.";
                 }
               }
               uses apply-advanced;
             }
           }
           case case_2 {
             list softwire-rule-sets {
               key name;
               ordered-by user;
               description "List of softwire rule sets";
               leaf name {
                 type string {
                   length "1 .. 63";
                   junos:posix-pattern "^[[:alnum:]][[:alnum:]_-]*$";
                   junos:pattern-message "Must be a string beginning with a number or letter and consisting of letters, numbers, dashes and underscores.";
                 }
               }
               uses apply-advanced;
             }
           }
         }
         list softwires-rule-set {
           key name;
           ordered-by user;
           description "List of softwire rule sets";
           leaf name {
             type string {
               length "1 .. 63";
               junos:posix-pattern "^[[:alnum:]][[:alnum:]_-]*$";
               junos:pattern-message "Must be a string beginning with a number or letter and consisting of letters, numbers, dashes and underscores.";
             }
           }
           uses apply-advanced;
         }
         choice stateful_firewall_rules_choice {
           case case_1 {
             list stateful-firewall-rules {
               key name;
               ordered-by user;
               description "List of stateful firewall rules";
               leaf name {
                 type string {
                   length "1 .. 63";
                   junos:posix-pattern "^[[:alnum:]][[:alnum:]/.:_-]*$";
                   junos:pattern-message "Must be a string beginning with a number or letter and consisting of letters, numbers, dashes, underscores, forward slashes, colons and dots.";
                 }
               }
               uses apply-advanced;
             }
           }
           case case_2 {
             list stateful-firewall-rule-sets {
               key name;
               ordered-by user;
               description "List of stateful firewall rule sets";
               leaf name {
                 type string {
                   length "1 .. 63";
                   junos:posix-pattern "^[[:alnum:]][[:alnum:]/.:_-]*$";
                   junos:pattern-message "Must be a string beginning with a number or letter and consisting of letters, numbers, dashes, underscores, forward slashes, colons and dots.";
                 }
               }
               uses apply-advanced;
             }
           }
         }
         choice ids-option-choice {
           case case_1 {
             list ids-option {
               key name;
               ordered-by user;
               description "List of ids-options";
               leaf name {
                 junos:must "(\".. .. .. screen ids-option $$\")";
                 junos:must-message "ids-option must be configured under screens";
                 type string {
                   length "1 .. 31";
                   junos:posix-pattern "^[[:alnum:]][[:alnum:]/.:_-]*$";
                   junos:pattern-message "Must be a string beginning with a number or letter and consisting of letters, numbers, dashes, underscores, forward slashes, colons and dots.";
                 }
               }
               uses apply-advanced;
             }
           }
         }
         choice pcp_rules_choice {
           case case_1 {
             list pcp-rules {
               key name;
               ordered-by user;
               description "List of PCP rules";
               junos:must "(!(\".. extension-service\"))";
               junos:must-message "incompatible with extension service";
               leaf name {
                 type string {
                   length "1 .. 63";
                   junos:posix-pattern "^[[:alnum:]][[:alnum:]_-]*$";
                   junos:pattern-message "Must be a string beginning with a number or letter and consisting of letters, numbers, dashes and underscores.";
                 }
               }
               uses apply-advanced;
             }
           }
           case case_2 {
             list pcp-rule-sets {
               key name;
               ordered-by user;
               description "List of PCP rule sets";
               junos:must "(!(\".. extension-service\"))";
               junos:must-message "incompatible with extension service";
               leaf name {
                 type string {
                   length "1 .. 63";
                   junos:posix-pattern "^[[:alnum:]][[:alnum:]_-]*$";
                   junos:pattern-message "Must be a string beginning with a number or letter and consisting of letters, numbers, dashes and underscores.";
                 }
               }
               uses apply-advanced;
             }
           }
         }
         leaf appid-profile {
           description "Define AppID profile";
           junos:must "(\"services application-identification profile  $$\")";
           junos:must-message "referenced appid profile must be defined";
           type string {
             length "1 .. 63";
           }
         }
         choice nat_rules_choice {
           case case_1 {
             list nat-rules {
               key name;
               ordered-by user;
               description "List of NAT rules";
               junos:must "(!(\".. extension-service\"))";
               junos:must-message "incompatible with extension service";
               leaf name {
                 type string {
                   length "1 .. 63";
                   junos:posix-pattern "^[[:alnum:]][[:alnum:]/.:_-]*$";
                   junos:pattern-message "Must be a string beginning with a number or letter and consisting of letters, numbers, dashes, underscores, forward slashes, colons and dots.";
                 }
               }
               uses apply-advanced;
             }
           }
           case case_2 {
             list nat-rule-sets {
               key name;
               ordered-by user;
               description "List of NAT rule sets";
               junos:must "(!(\".. extension-service\"))";
               junos:must-message "incompatible with extension service";
               leaf name {
                 junos:must "((\"services nat source rule-set $$\" || (\"services nat rule-set $$\" || \"services nat destination rule-set $$\")))";
                 junos:must-message "rule-set must be defined under 'services nat'";
                 type string {
                   length "1 .. 63";
                   junos:posix-pattern "^[[:alnum:]][[:alnum:]/.:_-]*$";
                   junos:pattern-message "Must be a string beginning with a number or letter and consisting of letters, numbers, dashes, underscores, forward slashes, colons and dots.";
                 }
               }
               uses apply-advanced;
             }
           }
         }
         choice ip_reassembly_rules_choice {
           case case_1 {
             list ip-reassembly-rules {
               key name;
               ordered-by user;
               description "List of ip-reassembly rules";
               leaf name {
                 junos:must "(\"services ip-reassembly rule $$\")";
                 junos:must-message "referenced ip-reassembly rule must be defined";
                 type string {
                   length "1 .. 63";
                   junos:posix-pattern "^[[:alnum:]][[:alnum:]_-]*$";
                   junos:pattern-message "Must be a string beginning with a number or letter and consisting of letters, numbers, dashes and underscores.";
                 }
               }
               uses apply-advanced;
             }
           }
         }
         choice ids_rules_choice {
           case case_1 {
             list ids-rules {
               key name;
               ordered-by user;
               description "List of IDS rules";
               junos:must "(!(\".. extension-service\"))";
               junos:must-message "incompatible with extension service";
               leaf name {
                 type string {
                   length "1 .. 63";
                   junos:posix-pattern "^[[:alnum:]][[:alnum:]_-]*$";
                   junos:pattern-message "Must be a string beginning with a number or letter and consisting of letters, numbers, dashes and underscores.";
                 }
               }
               uses apply-advanced;
             }
           }
           case case_2 {
             list ids-rule-sets {
               key name;
               ordered-by user;
               description "List of IDS rule sets";
               junos:must "(!(\".. extension-service\"))";
               junos:must-message "incompatible with extension service";
               leaf name {
                 type string {
                   length "1 .. 63";
                   junos:posix-pattern "^[[:alnum:]][[:alnum:]_-]*$";
                   junos:pattern-message "Must be a string beginning with a number or letter and consisting of letters, numbers, dashes and underscores.";
                 }
               }
               uses apply-advanced;
             }
           }
         }
         choice cos_rules_choice {
           case case_1 {
             list cos-rules {
               key name;
               ordered-by user;
               description "One or more CoS rules";
               junos:must "(!(\".. extension-service\"))";
               junos:must-message "incompatible with extension service";
               leaf name {
                 description "Rule name";
                 type string {
                   length "1 .. 63";
                   junos:posix-pattern "^[[:alnum:]][[:alnum:]_-]*$";
                   junos:pattern-message "Must be a string beginning with a number or letter and consisting of letters, numbers, dashes and underscores.";
                 }
               }
               uses apply-advanced;
             }
           }
           case case_2 {
             list cos-rule-sets {
               key name;
               ordered-by user;
               description "One or more CoS rule sets";
               junos:must "(!(\".. extension-service\"))";
               junos:must-message "incompatible with extension service";
               leaf name {
                 description "Name of rule set";
                 type string {
                   length "1 .. 63";
                   junos:posix-pattern "^[[:alnum:]][[:alnum:]_-]*$";
                   junos:pattern-message "Must be a string beginning with a number or letter and consisting of letters, numbers, dashes and underscores.";
                 }
               }
               uses apply-advanced;
             }
           }
         }
         choice aacl_rules_choice {
           case case_1 {
             list aacl-rules {
               key name;
               ordered-by user;
               description "One or more AACL rules";
               leaf name {
                 description "Rule name";
                 type string {
                   length "1 .. 63";
                   junos:posix-pattern "^[[:alnum:]][[:alnum:]_-]*$";
                   junos:pattern-message "Must be a string beginning with a number or letter and consisting of letters, numbers, dashes and underscores.";
                 }
               }
               uses apply-advanced;
             }
           }
           case case_2 {
             list aacl-rule-sets {
               key name;
               ordered-by user;
               description "One or more AACL rule sets";
               leaf name {
                 description "Name of rule set";
                 type string {
                   length "1 .. 63";
                   junos:posix-pattern "^[[:alnum:]][[:alnum:]_-]*$";
                   junos:pattern-message "Must be a string beginning with a number or letter and consisting of letters, numbers, dashes and underscores.";
                 }
               }
               uses apply-advanced;
             }
           }
         }
         list aacl-dyn-rules {
           key name;
           ordered-by user;
           description "One or more AACL rule ";
           junos:must "(!(\".. extension-service\"))";
           junos:must-message "incompatible with extension service";
           leaf name {
             description "Name of dynamic rule set";
             type string {
               length "1 .. 63";
               junos:posix-pattern "^[[:alnum:]][[:alnum:]_-]*$";
               junos:pattern-message "Must be a string beginning with a number or letter and consisting of letters, numbers, dashes and underscores.";
             }
           }
           uses apply-advanced;
         }
         choice pgcp_rules_choice {
           case case_1 {
             list pgcp-rules {
               key name;
               ordered-by user;
               description "One or more PGCP rules";
               junos:must "(!(\".. extension-service\"))";
               junos:must-message "incompatible with extension service";
               leaf name {
                 description "Rule name";
                 junos:must "(\"services pgcp rule $$\")";
                 junos:must-message "referenced pgcp rule must be defined";
                 type string {
                   length "1 .. 63";
                   junos:posix-pattern "^[[:alnum:]][[:alnum:]_-]*$";
                   junos:pattern-message "Must be a string beginning with a number or letter and consisting of letters, numbers, dashes and underscores.";
                 }
               }
               uses apply-advanced;
             }
           }
           case case_2 {
             list pgcp-rule-sets {
               key name;
               ordered-by user;
               description "One or more PGCP rule sets";
               junos:must "(!(\".. extension-service\"))";
               junos:must-message "incompatible with extension service";
               leaf name {
                 description "Name of rule set";
                 junos:must "(\"services pgcp rule-set $$\")";
                 junos:must-message "referenced pgcp rule-set must be defined";
                 type string {
                   length "1 .. 63";
                   junos:posix-pattern "^[[:alnum:]][[:alnum:]_-]*$";
                   junos:pattern-message "Must be a string beginning with a number or letter and consisting of letters, numbers, dashes and underscores.";
                 }
               }
               uses apply-advanced;
             }
           }
         }
         container jflow-rules {
           presence "enable jflow-rules";
           junos:must "(\".. sampling-service\")";
           junos:must-message "sampling-service must be configured";
           junos:must "(!(\".. extension-service\"))";
           junos:must-message "incompatible with extension service";
           description "One or more jflow rules";
           uses apply-advanced;
           container sampling {
             presence "enable sampling";
             junos:must "((any \"forwarding-options sampling instance <*>\" || \"forwarding-options sampling family\"))";
             junos:must-message "forwarding-options sampling must be configured";
             uses apply-advanced;
             leaf instance {
               description "Name of the instance";
               junos:must "(\"forwarding-options sampling instance $$\")";
               junos:must-message "Referenced sampling instance does not exist";
               type string {
                 length "1 .. 64";
               }
             }
           }
         }
         choice appid-choice {
           case case_1 {
             leaf application-identification-profile {
               description "Define Application Identification profile";
               junos:must "(\"services application-identification profile $$\")";
               junos:must-message "referenced appid profile must be defined";
               type string {
                 length "1 .. 63";
               }
             }
           }
         }
         leaf pcef-profile {
           description "Define PCEF profile";
           junos:must "(\"services pcef profile $$\")";
           junos:must-message "referenced pcef profile must be defined";
           type string {
             length "1 .. 63";
           }
         }
         leaf lrf-profile {
           description "Define logging and reporting profile";
           junos:must "(\"services lrf profile $$\")";
           junos:must-message "Specified LRF profile must be configured under services lrf profile";
           type string {
             length "1 .. 63";
           }
         }
         leaf hcm-profile {
           description "Define HCM profile";
           junos:must "(\"services hcm profile $$\")";
           junos:must-message "referenced hcm profile must be defined";
           type string {
             length "1 .. 63";
           }
         }
         leaf web-filter-profile {
           description "Define WEB filtering profile";
           junos:must "(\"services web-filter profile $$\")";
           junos:must-message "Specified web filter profile must be configured under services web-filter";
           type string {
             length "1 .. 63";
           }
         }
         choice hcm_url_rules_choice {
           case case_1 {
             list hcm-url-rules {
               key name;
               ordered-by user;
               description "One or more HCM uri rules";
               junos:must "(!(\".. extension-service\"))";
               junos:must-message "incompatible with extension service";
               leaf name {
                 description "Rule name";
                 type string {
                   length "1 .. 63";
                   junos:posix-pattern "^[[:alnum:]][[:alnum:]_-]*$";
                   junos:pattern-message "Must be a string beginning with a number or letter and consisting of letters, numbers, dashes and underscores.";
                 }
               }
               uses apply-advanced;
             }
           }
           case case_2 {
             list hcm-url-rule-sets {
               key name;
               ordered-by user;
               description "One or more HCM url rule sets";
               junos:must "(!(\".. extension-service\"))";
               junos:must-message "incompatible with extension service";
               leaf name {
                 description "Name of rule set";
                 type string {
                   length "1 .. 63";
                   junos:posix-pattern "^[[:alnum:]][[:alnum:]_-]*$";
                   junos:pattern-message "Must be a string beginning with a number or letter and consisting of letters, numbers, dashes and underscores.";
                 }
               }
               uses apply-advanced;
             }
           }
         }
         choice hcm-tag-rules-choice {
           case case_1 {
             list tag-rules {
               key name;
               ordered-by user;
               description "One or more HCM tag rules";
               junos:must "(!(\".. extension-service\"))";
               junos:must-message "incompatible with extension service";
               leaf name {
                 description "Rule name";
                 type string {
                   length "1 .. 63";
                   junos:posix-pattern "^[[:alnum:]][[:alnum:]_-]*$";
                   junos:pattern-message "Must be a string beginning with a number or letter and consisting of letters, numbers, dashes and underscores.";
                 }
               }
               uses apply-advanced;
             }
           }
           case case_2 {
             list tag-rule-sets {
               key name;
               ordered-by user;
               description "One or more HCM tag rule sets";
               junos:must "(!(\".. extension-service\"))";
               junos:must-message "incompatible with extension service";
               leaf name {
                 description "Name of rule set";
                 type string {
                   length "1 .. 63";
                   junos:posix-pattern "^[[:alnum:]][[:alnum:]_-]*$";
                   junos:pattern-message "Must be a string beginning with a number or letter and consisting of letters, numbers, dashes and underscores.";
                 }
               }
               uses apply-advanced;
             }
           }
         }
         choice idppolicy-choice {
           case case_1 {
             leaf idp-profile {
               description "IDP policy to use";
               junos:must "(\"security idp idp-policy $$\")";
               junos:must-message "referenced IDP policy must be defined";
               type string {
                 length "1 .. 63";
               }
             }
           }
         }
         choice cpcdd-choice {
           case case_1 {
             leaf captive-portal-content-delivery-profile {
               description "Define captive portal and content delivery profile";
               junos:must "(\"services captive-portal-content-delivery profile $$\")";
               junos:must-message "referenced cpcdd profile must be defined";
               type string {
                 length "1 .. 63";
               }
             }
           }
         }
         choice lpdf-stats-choice {
           case case_1 {
             container policy-decision-statistics-profile {
               description "Define policy decision statistics profile";
               uses apply-advanced;
               leaf profile-name {
                 description "Policy decision statistics profile name";
                 junos:must "((\"system services local-policy-decision-function statistics aacl-statistics-profile $$\" || \"accounting-options policy-decision-statistics-profile $$\"))";
                 junos:must-message "referenced statistics profile must be defined";
                 type string {
                   length "1 .. 63";
                 }
               }
             }
           }
         }
         choice service_type_choice {
           case case_1 {
             container interface-service {
               description "Define parameters for interface-specific service sets";
               uses apply-advanced;
               leaf service-interface {
                 description "Services interface to use";
                 junos:must "(\"interfaces $$-IFL\")";
                 junos:must-message "Service interface must be configured";
                 type union {
                   type jt:interface-unit;
                   type string {
                     pattern "<.*>|$.*";
                   }
                 }
               }
               container load-balancing-options {
                 uses apply-advanced;
                 container hash-keys {
                   presence "enable hash-keys";
                   uses apply-advanced;
                   leaf resource-triggered {
                     description "Resource Triggered load balancing";
                     type empty;
                   }
                   leaf-list ingress-key {
                     ordered-by user;
                     description "Hash Key for the ingress direction";
                     type enumeration {
                       enum "source-ip" {
                         description "Source Ip Address";
                       }
                       enum "destination-ip" {
                         description "Destination Ip Address";
                       }
                       enum "protocol" {
                         description "Protocol";
                       }
                       enum "iif" {
                         description "Incoming Interface";
                       }
                     }
                   }
                   leaf-list egress-key {
                     ordered-by user;
                     description "Hash Key for the egress direction";
                     type enumeration {
                       enum "source-ip" {
                         description "Source Ip Address";
                       }
                       enum "destination-ip" {
                         description "Destination Ip Address";
                       }
                       enum "protocol" {
                         description "Protocol";
                       }
                       enum "oif" {
                         description "Outgoing Interface";
                       }
                     }
                   }
                 }
               }
             }
           }
           case case_2 {
             container sampling-service {
               description "Define parameters for sampling service sets";
               uses apply-advanced;
               leaf service-interface {
                 description "Services interface to use";
                 type union {
                   type jt:interface-unit;
                   type string {
                     pattern "<.*>|$.*";
                   }
                 }
               }
             }
           }
           case case_3 {
             container next-hop-service {
               description "Define parameters for next-hop service sets";
               uses apply-advanced;
               leaf inside-service-interface {
                 description "Service interface to inside network";
                 junos:must "((\"interfaces $$-IFL family inet\" || \"interfaces $$-IFL family inet6\"))";
                 junos:must-message "Family inet/inet6 must be configured";
                 junos:must "(\"interfaces $$-IFL service-domain inside\")";
                 junos:must-message "Interface requires service-domain inside";
                 type union {
                   type jt:interface-unit;
                   type string {
                     pattern "<.*>|$.*";
                   }
                 }
               }
               leaf outside-service-interface {
                 description "Service interface name";
                 junos:must "((\"interfaces $$-IFL family inet\" || \"interfaces $$-IFL family inet6\"))";
                 junos:must-message "Family inet/inet6 must be configured";
                 junos:must "(\".. inside-service-interface\")";
                 junos:must-message "Both inside-service-interface and ouside-service-interface must be configured";
                 junos:must "(\"interfaces $$-IFL service-domain outside\")";
                 junos:must-message "Interface requires service-domain outside";
                 type union {
                   type jt:interface-unit;
                   type string {
                     pattern "<.*>|$.*";
                   }
                 }
               }
               leaf outside-service-interface-type {
                 description "Service interface type local for reassembly service";
                 type enumeration {
                   enum "local" {
                     description "Must be local for reassembly service";
                   }
                 }
               }
               leaf service-interface-pool {
                 description "Service interface pool name";
                 junos:must "(!((\".. .. cos-rule-sets\" || (\".. .. cos-rules\" || (\".. .. ids-rule-sets\" || (\".. .. ids-rules\" || (\".. .. ipsec-vpn-rule-sets\" || (\".. .. ipsec-vpn-rules\" || (\".. .. nat-rule-sets\" || (\".. .. nat-rules\" || (\".. .. stateful-firewall-rule-sets\" || (\".. .. stateful-firewall-rules\" || (\".. .. softwire-rule-sets\" || \".. .. softwire-rules\")))))))))))))";
                 junos:must-message "Can not define any other rules than pgcp when service-interface-pool is defined";
                 junos:must "(\"services service-interface-pools pool $$\")";
                 junos:must-message "referenced service interface pool must be defined";
                 type string {
                   length "1 .. 63";
                   junos:posix-pattern "^[[:alnum:]][[:alnum:]_-]*$";
                   junos:pattern-message "Must be a string beginning with a number or letter and consisting of letters, numbers, dashes and underscores.";
                 }
               }
             }
           }
         }
         list extension-service {
           key name;
           ordered-by user;
           description "Define the customer specific extensions";
           max-elements 2;
           leaf name {
             description "Customer-prefixed service name";
             type string {
               length "1 .. 63";
             }
           }
           uses apply-advanced;
         }
         container service-order {
           presence "enable service-order";
           description "Define of order of services to be applied";
           uses apply-advanced;
           leaf-list forward-flow {
             ordered-by user;
             description "Service Order for forward flow";
             type string;
           }
           leaf-list reverse-flow {
             ordered-by user;
             description "Service Order for reverse flow";
             type string;
           }
         }
         container jflow-log {
           description "Define Jflow-logging parameters.";
           uses apply-advanced;
           leaf template-profile {
             description "Allow jflow messages for applications";
             junos:must "((!(\".. .. softwire-rules\") && !(\".. .. softwire-rule-sets\")))";
             junos:must-message "Template-profile cannot be configured with softwire-rules or softwire-rule-sets configured";
             junos:must "(\"services jflow-log template-profile $$\")";
             junos:must-message "The referenced template-profile is not defined";
             type string {
               length "1 .. 63";
             }
           }
         }
         list ipsec-vpn {
           key name;
           ordered-by user;
           description "List of IPsec VPN policies";
           leaf name {
             junos:must "(\"security ipsec vpn $$\")";
             junos:must-message "Referenced IPsec vpn  must be defined under  [edit security ipsec vpn ]";
             type string {
               length "1 .. 32";
             }
           }
           uses apply-advanced;
         }
         leaf redundancy-set-id {
           description "Redundancy set identifier";
           junos:must "(\"services redundancy-set $$\")";
           junos:must-message "Referenced redundancy set must be defined";
           type union {
             type string {
               pattern "<.*>|$.*";
             }
             type uint32 {
               range "1 .. 100";
             }
           }
         }
       }
       container ssl {
         description "Configuration for Secure Socket Layer support service";
         uses apply-advanced;
         container traceoptions {
           description "Trace options for Secure Socket Layer support service";
           uses ssl-traceoptions;
         }
         container termination {
           description "Configuration for Secure Socket Layer termination support service";
           uses ssl-termination-config;
         }
         container initiation {
           description "Configuration for Secure Socket Layer initiation support service";
           uses ssl-initiation-config;
         }
         container proxy {
           description "Configuration for Secure Socket Layer proxy support service";
           uses ssl-proxy-config;
         }
       }
       container softwires {
         description "Configure softwire feature";
         uses softwires-object;
       }
       container screen {
         description "Configure screen feature";
         uses apply-advanced;
         container trap {
           presence "enable trap";
           description "Configure trap interval";
           leaf interval {
             description "Trap interval";
             default "2";
             units "seconds";
             type union {
               type string {
                 pattern "<.*>|$.*";
               }
               type uint32 {
                 range "1 .. 3600";
               }
             }
           }
         }
         container cpu-throttle {
           presence "enable cpu-throttle";
           description "Configure cpu-throttle percentage";
           uses apply-advanced;
           leaf percentage {
             description "Percentage of cpu throttle";
             units "percentage";
             type union {
               type string {
                 pattern "<.*>|$.*";
               }
               type uint32 {
                 range "1 .. 100";
               }
             }
           }
         }
         list ids-option {
           key name;
           description "Configure ids-option";
           uses ids-option-type;
         }
         container traceoptions {
           description "Trace options for Network Security Screen";
           uses apply-advanced;
           leaf no-remote-trace {
             description "Disable remote tracing";
             junos:must "(\"system tracing\")";
             junos:must-message "'no-remote-trace' is valid only when [system tracing] is configured";
             type empty;
           }
           container file {
             description "Trace file information";
             leaf filename {
               description "Name of file in which to write trace information";
               type string {
                 length "1 .. 1024";
                 junos:posix-pattern "![/ %]";
                 junos:pattern-message "Must not contain '/', % or a space";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "configuration" {
                   description "Trace configuration events";
                 }
                 enum "flow" {
                   description "Trace flow events";
                 }
                 enum "all" {
                   description "Trace everything";
                 }
               }
             }
           }
         }
       }
       container security-intelligence {
         uses apply-advanced;
         container category {
           description "Category to be disabled";
           uses apply-advanced;
           container all {
             presence "enable all";
             description "All categories";
             uses apply-advanced;
             container disable {
               presence "enable disable";
               description "To disable all categories";
             }
           }
           list category-name {
             key name;
             ordered-by user;
             uses secintel-category-disable;
           }
         }
         leaf url {
           description "Configure the url of feed server [https://<ip or hostname>:<port>/<uri>]";
           type string;
         }
         leaf proxy-profile {
           description "The proxy profile name";
           junos:must "(\"services proxy profile\")";
           junos:must-message "Proxy profile must be defined";
           type string {
             length "1 .. 64";
           }
         }
         container authentication {
           description "Authenticate to use feed update services";
           uses apply-advanced;
           leaf auth-token {
             description "Token string for authentication";
             type string {
               junos:posix-pattern "^[A-Za-z0-9]{32}$";
               junos:pattern-message "Auth token must be consisted of 32 alphanumeric characters";
             }
           }
           leaf tls-profile {
             description "TLS profile";
             junos:must "(\"services ssl initiation profile $$\")";
             junos:must-message "Referenced SSL initiation profile is not defined";
             type string;
           }
         }
         container traceoptions {
           description "Security intelligence trace options";
           uses secintel-traceoptions;
         }
         list profile {
           key name;
           ordered-by user;
           description "Configure security intelligence profile";
           uses secintel-profile-setting;
         }
         container default-policy {
           description "Configure security intelligence default policy";
           uses apply-advanced;
           list category-profiles {
             key name;
             ordered-by user;
             description "Security intelligence category profiles";
             leaf name {
               description "Name of security intelligence category";
               type string;
             }
             uses apply-advanced;
             leaf profile-name {
               description "Name of profile";
               junos:must "(\"services security-intelligence profile $$\")";
               junos:must-message "security intelligence profile must be defined";
               type string;
             }
           }
         }
         list policy {
           key name;
           ordered-by user;
           description "Configure security intelligence policy";
           uses secintel-policy-setting;
         }
       }
       container icap-redirect {
         description "Configure ICAP redirection service";
         uses apply-advanced;
         list profile {
           key name;
           ordered-by user;
           description "Congifure ICAP service profile";
           uses icap-profile-object;
         }
         container traceoptions {
           description "ICAP redirect trace options";
           uses icap-redirect-traceoptions;
         }
       }
       container advanced-anti-malware {
         uses apply-advanced;
         container connection {
           presence "enable connection";
           description "Cloud service RE connection, only for master logical domain";
           uses apply-advanced;
           leaf url {
             description "The url of the cloud server [https://<ip or hostname>:<port>]";
             junos:must "(\"services advanced-anti-malware connection authentication tls-profile\")";
             junos:must-message "Authentication profile must be defined";
             type string;
           }
           container authentication {
             description "The authentication profile for using cloud services";
             uses apply-advanced;
             leaf tls-profile {
               description "TLS profile";
               junos:must "((\"services ssl initiation profile $$\" && \"services advanced-anti-malware connection url\"))";
               junos:must-message "Referenced SSL initiation profile and URL must be defined";
               type string;
             }
           }
           leaf proxy-profile {
             description "Proxy profile";
             junos:must "(\"services proxy profile $$\")";
             junos:must-message "Referenced Proxy profile must be defined";
             type string {
               length "1 .. 63";
             }
           }
           leaf source-address {
             description "The source ip for connecting to the cloud server.";
             type jt:ipaddr;
           }
           leaf source-interface {
             description "The source interface for connecting to the cloud server";
             type union {
               type jt:interface-name;
               type string {
                 pattern "<.*>|$.*";
               }
             }
           }
         }
         container default-policy {
           presence "enable default-policy";
           description "Advanced Anti-malware default policy";
           uses apply-advanced;
           container http {
             description "Configure HTTP options";
             uses apply-advanced;
             leaf inspection-profile {
               description "Advanced Anti-malware inspection-profile name (default:default_profile)";
               type string {
                 length "1 .. 63";
               }
             }
             leaf action {
               description "Action taken for contents with verdict meet threshold";
               type enumeration {
                 enum "permit" {
                   description "Allow contents";
                 }
                 enum "block" {
                   description "Disallow contents";
                 }
               }
             }
             container notification {
               description "Notification action taken for contents with verdict meet threshold";
               uses apply-advanced;
               leaf log {
                 description "Logging option for Advanced Anti-malware actions";
                 type empty;
               }
             }
           }
           container smtp {
             description "Configure SMTP options";
             uses apply-advanced;
             leaf inspection-profile {
               description "Advanced Anti-malware inspection-profile name (default:default_profile)";
               type string {
                 length "1 .. 63";
               }
             }
             container notification {
               description "Notification action taken for contents with verdict meet threshold";
               uses apply-advanced;
               leaf log {
                 description "Logging option for Advanced Anti-malware actions";
                 type empty;
               }
             }
           }
           container imap {
             description "Configure IMAP options";
             uses apply-advanced;
             leaf inspection-profile {
               description "Advanced Anti-malware inspection-profile name (default:default_profile)";
               type string {
                 length "1 .. 63";
               }
             }
             container notification {
               description "Notification action taken for contents with verdict meet threshold";
               uses apply-advanced;
               leaf log {
                 description "Logging option for Advanced Anti-malware actions";
                 type empty;
               }
             }
           }
           leaf verdict-threshold {
             description "Verdict threshold";
             type enumeration {
               enum "1" {
                 description "Verdict-threshold level 1";
               }
               enum "2" {
                 description "Verdict-threshold level 2";
               }
               enum "3" {
                 description "Verdict-threshold level 3";
               }
               enum "4" {
                 description "Verdict-threshold level 4";
               }
               enum "5" {
                 description "Verdict-threshold level 5";
               }
               enum "6" {
                 description "Verdict-threshold level 6";
               }
               enum "7" {
                 description "Verdict-threshold level 7";
               }
               enum "8" {
                 description "Verdict-threshold level 8";
               }
               enum "9" {
                 description "Verdict-threshold level 9";
               }
               enum "10" {
                 description "Verdict-threshold level 10";
               }
               enum "recommended" {
                 description "Recommended verdict-threshold";
               }
             }
           }
           leaf inspection-profile {
             description "Advanced Anti-malware inspection-profile name";
             status deprecated;
             type string {
               length "1 .. 63";
             }
           }
           container fallback-options {
             description "Fallback options for abnormal conditions";
             uses apply-advanced;
             leaf action {
               description "Action taken for fallback conditions";
               type enumeration {
                 enum "permit" {
                   description "Allow contents";
                 }
                 enum "block" {
                   description "Disallow contents";
                 }
               }
             }
             container notification {
               description "Notification action taken for fallback action";
               uses apply-advanced;
               leaf log {
                 description "Logging option for Advanced Anti-malware fallback action";
                 type empty;
               }
             }
           }
           container default-notification {
             description "Notification action taken for action";
             uses apply-advanced;
             leaf log {
               description "Logging option for Advanced Anti-malware action";
               type empty;
             }
           }
           container whitelist-notification {
             description "Whitelist notification logging option";
             uses apply-advanced;
             leaf log {
               description "Logging option for Advanced Anti-malware whitelist hit";
               type empty;
             }
           }
           container blacklist-notification {
             description "Blacklist notification logging option";
             uses apply-advanced;
             leaf log {
               description "Logging option for Advanced Anti-malware blacklist hit";
               type empty;
             }
           }
         }
         list policy {
           key name;
           description "Advanced Anti-malware policy";
           leaf name {
             description "Policy name, default policy must name (default-policy)";
             type string {
               length "1 .. 63";
             }
           }
           uses apply-advanced;
           container match {
             description "Policy match conditions";
             status deprecated;
             uses apply-advanced;
             leaf application {
               description "Application";
               type enumeration {
                 enum "HTTP" {
                   description "HTTP Traffic";
                 }
               }
             }
             leaf verdict-threshold {
               description "Verdict threshold";
               type enumeration {
                 enum "1" {
                   description "Verdict-threshold level 1";
                 }
                 enum "2" {
                   description "Verdict-threshold level 2";
                 }
                 enum "3" {
                   description "Verdict-threshold level 3";
                 }
                 enum "4" {
                   description "Verdict-threshold level 4";
                 }
                 enum "5" {
                   description "Verdict-threshold level 5";
                 }
                 enum "6" {
                   description "Verdict-threshold level 6";
                 }
                 enum "7" {
                   description "Verdict-threshold level 7";
                 }
                 enum "8" {
                   description "Verdict-threshold level 8";
                 }
                 enum "9" {
                   description "Verdict-threshold level 9";
                 }
                 enum "10" {
                   description "Verdict-threshold level 10";
                 }
                 enum "recommended" {
                   description "Recommended verdict-threshold";
                 }
               }
             }
           }
           container then {
             junos:must "(\".. match\")";
             junos:must-message "match must be defined";
             status deprecated;
             uses apply-advanced;
             leaf action {
               description "Action taken for contents with verdict meet threshold";
               type enumeration {
                 enum "permit" {
                   description "Allow contents";
                 }
                 enum "block" {
                   description "Disallow contents";
                 }
               }
             }
             container notification {
               description "Notification action taken for contents with verdict meet threshold";
               uses apply-advanced;
               leaf log {
                 description "Logging option for Advanced Anti-malware actions";
                 type empty;
               }
             }
           }
           container http {
             description "Configure HTTP options";
             uses apply-advanced;
             leaf inspection-profile {
               description "Advanced Anti-malware inspection-profile name (default:default_profile)";
               type string {
                 length "1 .. 63";
               }
             }
             leaf action {
               description "Action taken for contents with verdict meet threshold";
               type enumeration {
                 enum "permit" {
                   description "Allow contents";
                 }
                 enum "block" {
                   description "Disallow contents";
                 }
               }
             }
             container notification {
               description "Notification action taken for contents with verdict meet threshold";
               uses apply-advanced;
               leaf log {
                 description "Logging option for Advanced Anti-malware actions";
                 type empty;
               }
             }
           }
           container smtp {
             description "Configure SMTP options";
             uses apply-advanced;
             leaf inspection-profile {
               description "Advanced Anti-malware inspection-profile name (default:default_profile)";
               type string {
                 length "1 .. 63";
               }
             }
             container notification {
               description "Notification action taken for contents with verdict meet threshold";
               uses apply-advanced;
               leaf log {
                 description "Logging option for Advanced Anti-malware actions";
                 type empty;
               }
             }
           }
           container imap {
             description "Configure IMAP options";
             uses apply-advanced;
             leaf inspection-profile {
               description "Advanced Anti-malware inspection-profile name (default:default_profile)";
               type string {
                 length "1 .. 63";
               }
             }
             container notification {
               description "Notification action taken for contents with verdict meet threshold";
               uses apply-advanced;
               leaf log {
                 description "Logging option for Advanced Anti-malware actions";
                 type empty;
               }
             }
           }
           leaf verdict-threshold {
             description "Verdict threshold";
             type enumeration {
               enum "1" {
                 description "Verdict-threshold level 1";
               }
               enum "2" {
                 description "Verdict-threshold level 2";
               }
               enum "3" {
                 description "Verdict-threshold level 3";
               }
               enum "4" {
                 description "Verdict-threshold level 4";
               }
               enum "5" {
                 description "Verdict-threshold level 5";
               }
               enum "6" {
                 description "Verdict-threshold level 6";
               }
               enum "7" {
                 description "Verdict-threshold level 7";
               }
               enum "8" {
                 description "Verdict-threshold level 8";
               }
               enum "9" {
                 description "Verdict-threshold level 9";
               }
               enum "10" {
                 description "Verdict-threshold level 10";
               }
               enum "recommended" {
                 description "Recommended verdict-threshold";
               }
             }
           }
           leaf inspection-profile {
             description "Advanced Anti-malware inspection-profile name";
             status deprecated;
             type string {
               length "1 .. 63";
             }
           }
           container fallback-options {
             description "Fallback options for abnormal conditions";
             uses apply-advanced;
             leaf action {
               description "Action taken for fallback conditions";
               type enumeration {
                 enum "permit" {
                   description "Allow contents";
                 }
                 enum "block" {
                   description "Disallow contents";
                 }
               }
             }
             container notification {
               description "Notification action taken for fallback action";
               uses apply-advanced;
               leaf log {
                 description "Logging option for Advanced Anti-malware fallback action";
                 type empty;
               }
             }
           }
           container default-notification {
             description "Notification action taken for action";
             uses apply-advanced;
             leaf log {
               description "Logging option for Advanced Anti-malware action";
               type empty;
             }
           }
           container whitelist-notification {
             description "Whitelist notification logging option";
             uses apply-advanced;
             leaf log {
               description "Logging option for Advanced Anti-malware whitelist hit";
               type empty;
             }
           }
           container blacklist-notification {
             description "Blacklist notification logging option";
             uses apply-advanced;
             leaf log {
               description "Logging option for Advanced Anti-malware blacklist hit";
               type empty;
             }
           }
         }
         container traceoptions {
           description "Advanced Anti-malware trace options";
           uses aamwd-traceoptions;
         }
       }
       container user-identification {
         description "Configure user-identification";
         uses apply-advanced;
         container active-directory-access {
           presence "enable active-directory-access";
           description "Configure active directory access";
           uses apply-advanced;
           container traceoptions {
             description "Active-directory-access Tracing Options";
             uses apply-advanced;
             leaf no-remote-trace {
               description "Disable remote tracing";
               junos:must "(\"system tracing\")";
               junos:must-message "'no-remote-trace' is valid only when [system tracing] is configured";
               type empty;
             }
             container file {
               description "Trace file information";
               leaf filename {
                 description "Name of file in which to write trace information";
                 type string {
                   length "1 .. 1024";
                   junos:posix-pattern "![/ %]";
                   junos:pattern-message "Must not contain '/', % or a space";
                 }
               }
               leaf size {
                 description "Maximum trace file size";
                 type string;
               }
               leaf files {
                 description "Maximum number of trace files";
                 default "3";
                 type union {
                   type string {
                     pattern "<.*>|$.*";
                   }
                   type uint32 {
                     range "2 .. 1000";
                   }
                 }
               }
               choice world-readable-choice {
                 leaf world-readable {
                   description "Allow any user to read the log file";
                   type empty;
                 }
                 leaf no-world-readable {
                   description "Don't allow any user to read the log file";
                   type empty;
                 }
               }
               leaf match {
                 description "Regular expression for lines to be logged";
                 type jt:regular-expression;
               }
             }
             leaf level {
               description "Level of debugging output";
               type enumeration {
                 enum "error" {
                   description "Match error conditions";
                 }
                 enum "warning" {
                   description "Match warning messages";
                 }
                 enum "notice" {
                   description "Match conditions that should be handled specially";
                 }
                 enum "info" {
                   description "Match informational messages";
                 }
                 enum "verbose" {
                   description "Match verbose messages";
                 }
                 enum "all" {
                   description "Match all levels";
                 }
               }
             }
             list flag {
               key name;
               ordered-by user;
               description "Tracing parameters";
               leaf name {
                 type enumeration {
                   enum "active-directory-authentication" {
                     description "Trace active directory auth";
                   }
                   enum "configuration" {
                     description "Trace configuration";
                   }
                   enum "db" {
                     description "Trace db";
                   }
                   enum "ip-user-mapping" {
                     description "Trace ip-user-mapping module";
                   }
                   enum "ip-user-probe" {
                     description "Trace ip-user-probe";
                   }
                   enum "ipc" {
                     description "Trace ipc";
                   }
                   enum "user-group-mapping" {
                     description "Trace user-group-mapping module";
                   }
                   enum "wmic" {
                     description "Trace wmic";
                   }
                   enum "all" {
                     description "Trace everything";
                   }
                 }
               }
             }
           }
           list domain {
             key name;
             ordered-by user;
             description "Configure active-directory-access domain";
             max-elements 2;
             leaf name {
               description "Domain name";
               type string {
                 length "1 .. 64";
                 junos:posix-pattern "^[[:alnum:]._-]+$|^\\\\*$";
                 junos:pattern-message "Must be a string consisting of letters, numbers, dashes, underscores and dots";
               }
             }
             uses apply-advanced;
             container user {
               description "User name";
               uses apply-advanced;
               leaf user-name {
                 description "User name";
                 type string {
                   length "1 .. 64";
                   junos:posix-pattern "^[[:alnum:]._-]+$|^\\\\*$";
                   junos:pattern-message "Must be a string consisting of letters, numbers, dashes, underscores and dots";
                 }
               }
               leaf password {
                 description "Password string";
                 type string {
                   length "1 .. 128";
                 }
               }
             }
             list domain-controller {
               key name;
               ordered-by user;
               description "Domain controller";
               max-elements 10;
               leaf name {
                 description "Domain controller name";
                 type string {
                   length "1 .. 64";
                   junos:posix-pattern "^[[:alnum:]._-]+$|^\\\\*$";
                   junos:pattern-message "Must be a string consisting of letters, numbers, dashes, underscores and dots";
                 }
               }
               uses apply-advanced;
               leaf address {
                 description "Address of domain controller";
                 type jt:ipaddr;
               }
             }
             container ip-user-mapping {
               description "Ip-user-mapping";
               uses apply-advanced;
               container discovery-method {
                 description "Discovery method";
                 uses apply-advanced;
                 container wmi {
                   presence "enable wmi";
                   description "WMI";
                   uses apply-advanced;
                   leaf event-log-scanning-interval {
                     description "Interval of event log scanning";
                     units "seconds";
                     type union {
                       type string {
                         pattern "<.*>|$.*";
                       }
                       type uint16 {
                         range "5 .. 60";
                       }
                     }
                   }
                   leaf initial-event-log-timespan {
                     description "Event log scanning timespan";
                     units "hours";
                     type union {
                       type string {
                         pattern "<.*>|$.*";
                       }
                       type uint16 {
                         range "1 .. 168";
                       }
                     }
                   }
                 }
               }
             }
             container user-group-mapping {
               description "User-group-mapping";
               uses user-group-mapping-type;
             }
           }
           leaf no-on-demand-probe {
             description "Disable on-demand probe";
             type empty;
           }
           leaf authentication-entry-timeout {
             description "Authentication entry timeout number (0, 10-1440)";
             units "minutes";
             type union {
               type uint16;
               type string {
                 pattern "<.*>|$.*";
               }
             }
           }
           leaf invalid-authentication-entry-timeout {
             description "Invalid authentication entry timeout number (0, 10-1440)";
             units "minutes";
             type union {
               type uint16;
               type string {
                 pattern "<.*>|$.*";
               }
             }
           }
           leaf firewall-authentication-forced-timeout {
             description "Firewallauth fallback authentication entry forced timeout number (10-1440)";
             units "minutes";
             type union {
               type uint16;
               type string {
                 pattern "<.*>|$.*";
               }
             }
           }
           leaf wmi-timeout {
             description "Wmi timeout number";
             units "seconds";
             type union {
               type string {
                 pattern "<.*>|$.*";
               }
               type uint32 {
                 range "3 .. 120";
               }
             }
           }
           leaf thread {
             description "Thread to do PC probe";
             type union {
               type string {
                 pattern "<.*>|$.*";
               }
               type uint16 {
                 range "1 .. 100";
               }
             }
           }
           leaf probe-rate {
             description "PC probe rate per minute";
             type union {
               type string {
                 pattern "<.*>|$.*";
               }
               type uint32 {
                 range "100 .. 1500";
               }
             }
           }
           leaf-list event-log-identifier {
             ordered-by user;
             description "Event log identifier";
             type union {
               type uint16;
               type string {
                 pattern "<.*>|$.*";
               }
             }
           }
           leaf-list logon-type {
             ordered-by user;
             description "Logon type";
             type union {
               type uint16;
               type string {
                 pattern "<.*>|$.*";
               }
             }
           }
           container filter {
             description "Configure filter address or prefix";
             uses apply-advanced;
             list include {
               key name;
               ordered-by user;
               description "Include address";
               max-elements 20;
               leaf name {
                 description "Address or prefix";
                 type jt:ipprefix;
               }
             }
             list exclude {
               key name;
               ordered-by user;
               description "Exclude address";
               max-elements 20;
               leaf name {
                 description "Address or prefix";
                 type jt:ipprefix;
               }
             }
           }
         }
         list authentication-source {
           key name;
           ordered-by user;
           description "Configure authentication-source";
           max-elements 2;
           leaf name {
             description "Authenticaton source name";
             type enumeration {
               enum "aruba-clearpass" {
                 description "Authentication source from Aruba ClearPass";
               }
             }
           }
           uses apply-advanced;
           leaf authentication-entry-timeout {
             description "Aruba ClearPass authentication entry timeout number (0, 10-1440)";
             units "minutes";
             type union {
               type uint16;
               type string {
                 pattern "<.*>|$.*";
               }
             }
           }
           leaf invalid-authentication-entry-timeout {
             description "Invalid authentication entry timeout number (0, 10-1440)";
             units "minutes";
             type union {
               type uint16;
               type string {
                 pattern "<.*>|$.*";
               }
             }
           }
           container traceoptions {
             description "Aruba ClearPass authentication table Tracing Options";
             uses apply-advanced;
             leaf no-remote-trace {
               description "Disable remote tracing";
               junos:must "(\"system tracing\")";
               junos:must-message "'no-remote-trace' is valid only when [system tracing] is configured";
               type empty;
             }
             container file {
               description "Trace file information";
               leaf filename {
                 description "Name of file in which to write trace information";
                 type string {
                   length "1 .. 1024";
                   junos:posix-pattern "![/ %]";
                   junos:pattern-message "Must not contain '/', % or a space";
                 }
               }
               leaf size {
                 description "Maximum trace file size";
                 type string;
               }
               leaf files {
                 description "Maximum number of trace files";
                 default "3";
                 type union {
                   type string {
                     pattern "<.*>|$.*";
                   }
                   type uint32 {
                     range "2 .. 1000";
                   }
                 }
               }
               choice world-readable-choice {
                 leaf world-readable {
                   description "Allow any user to read the log file";
                   type empty;
                 }
                 leaf no-world-readable {
                   description "Don't allow any user to read the log file";
                   type empty;
                 }
               }
               leaf match {
                 description "Regular expression for lines to be logged";
                 type jt:regular-expression;
               }
             }
             leaf level {
               description "Level of debugging output";
               type enumeration {
                 enum "error" {
                   description "Match error conditions";
                 }
                 enum "warning" {
                   description "Match warning messages";
                 }
                 enum "notice" {
                   description "Match conditions that should be handled specially";
                 }
                 enum "info" {
                   description "Match informational messages";
                 }
                 enum "verbose" {
                   description "Match verbose messages";
                 }
                 enum "all" {
                   description "Match all levels";
                 }
               }
             }
             list flag {
               key name;
               ordered-by user;
               description "Tracing parameters";
               leaf name {
                 type enumeration {
                   enum "all" {
                     description "Trace Aruba ClearPass all modules";
                   }
                   enum "clearpass-authentication" {
                     description "Trace Aruba ClearPass auth table management module";
                   }
                   enum "configuration" {
                     description "Trace Aruba ClearPass configuration";
                   }
                   enum "dispatcher" {
                     description "Trace dispatcher module";
                   }
                   enum "ipc" {
                     description "Trace ipc";
                   }
                   enum "user-query" {
                     description "Trace user-query module";
                   }
                 }
               }
             }
           }
           container user-query {
             description "ClearPass individual user query";
             uses apply-advanced;
             container web-server {
               description "Web server for user query";
               uses apply-advanced;
               leaf server-name {
                 description "Web server name";
                 type string {
                   length "1 .. 64";
                 }
               }
               leaf connect-method {
                 description "Method of connecting to web server";
                 type enumeration {
                   enum "https" {
                     description "HTTPS connection to web server";
                   }
                   enum "http" {
                     description "HTTP connection to web server";
                   }
                 }
               }
               leaf address {
                 description "IP address or hostname of web server";
                 type string {
                   length "1 .. 128";
                 }
               }
               leaf port {
                 description "Web server port";
                 default "443";
                 type union {
                   type string {
                     pattern "<.*>|$.*";
                   }
                   type uint32 {
                     range "1 .. 65535";
                   }
                 }
               }
             }
             leaf ca-certificate {
               description "Ca-certificate file name";
               type string {
                 length "1 .. 256";
               }
             }
             leaf client-id {
               description "Client ID for OAuth2 grant";
               type string {
                 length "1 .. 64";
               }
             }
             leaf client-secret {
               description "Client secret for OAuth2 grant";
               type string {
                 length "1 .. 128";
               }
             }
             leaf token-api {
               description "API of acquiring token for OAuth2 authentication";
               type string {
                 length "1 .. 128";
               }
             }
             leaf query-api {
               description "User query API";
               type string {
                 length "4 .. 128";
               }
             }
             leaf delay-query-time {
               description "Delay time to send user query (0~60sec)";
               default "15";
               units "seconds";
               type union {
                 type string {
                   pattern "<.*>|$.*";
                 }
                 type uint8 {
                   range "0 .. 60";
                 }
               }
             }
           }
           container no-user-query {
             presence "enable no-user-query";
             description "Disable user query from ClearPass";
           }
         }
         container device-information {
           description "Device information configuration";
           uses apply-advanced;
           container authentication-source {
             description "Configure authentication-source";
             uses apply-advanced;
             leaf authentication-source-name {
               default "no-configured";
               type enumeration {
                 enum "active-directory" {
                   description "From windows active directory";
                 }
                 enum "network-access-controller" {
                   description "From network access controller such as Aruba ClearPass or JIMS";
                 }
                 enum "no-configured" {
                   description "No configuring authentication source for device entry";
                 }
               }
             }
           }
           container end-user-profile {
             description "End-user-profile configuration";
             uses apply-advanced;
             list profile-name {
               key name;
               ordered-by user;
               description "End-user-profile profile-name configuration";
               leaf name {
                 description "End-user-profile profile-name";
                 type string {
                   length "1 .. 64";
                   junos:posix-pattern "^[[:alnum:]._-]+$|^\\\\*$";
                   junos:pattern-message "Must be a string consisting of letters, numbers, dashes, underscores and dots";
                 }
               }
               uses apply-advanced;
               leaf domain-name {
                 description "Domain name";
                 type string {
                   length "1 .. 64";
                   junos:posix-pattern "^[[:alnum:]._-]+$|^\\\\*$";
                   junos:pattern-message "Must be a string consisting of letters, numbers, dashes, underscores and dots";
                 }
               }
               list attribute {
                 key name;
                 ordered-by user;
                 description "Attribute";
                 leaf name {
                   description "Attribute name";
                   type string;
                 }
                 uses apply-advanced;
                 choice attribute-value {
                   case case_1 {
                     leaf-list string {
                       ordered-by user;
                       description "Value type is strings";
                       type string;
                       max-elements 20;
                     }
                   }
                   case case_2 {
                     container digital {
                       presence "enable digital";
                       description "Value type is digital";
                       uses apply-advanced;
                       leaf-list value {
                         ordered-by user;
                         description "Digital value";
                         type union {
                           type uint32;
                           type string {
                             pattern "<.*>|$.*";
                           }
                         }
                       }
                       list from {
                         key name;
                         ordered-by user;
                         description "Range of digital value";
                         leaf name {
                           description "Digit range's start value";
                           type union {
                             type uint32;
                             type string {
                               pattern "<.*>|$.*";
                             }
                           }
                         }
                         uses apply-advanced;
                         leaf to {
                           description "Digit range's end value";
                           type union {
                             type uint32;
                             type string {
                               pattern "<.*>|$.*";
                             }
                           }
                         }
                       }
                     }
                   }
                 }
               }
             }
           }
           container traceoptions {
             description "Device info related Tracing Options";
             uses apply-advanced;
             leaf no-remote-trace {
               description "Disable remote tracing";
               junos:must "(\"system tracing\")";
               junos:must-message "'no-remote-trace' is valid only when [system tracing] is configured";
               type empty;
             }
             container file {
               description "Trace file information";
               leaf filename {
                 description "Name of file in which to write trace information";
                 type string {
                   length "1 .. 1024";
                   junos:posix-pattern "![/ %]";
                   junos:pattern-message "Must not contain '/', % or a space";
                 }
               }
               leaf size {
                 description "Maximum trace file size";
                 type string;
               }
               leaf files {
                 description "Maximum number of trace files";
                 default "3";
                 type union {
                   type string {
                     pattern "<.*>|$.*";
                   }
                   type uint32 {
                     range "2 .. 1000";
                   }
                 }
               }
               choice world-readable-choice {
                 leaf world-readable {
                   description "Allow any user to read the log file";
                   type empty;
                 }
                 leaf no-world-readable {
                   description "Don't allow any user to read the log file";
                   type empty;
                 }
               }
               leaf match {
                 description "Regular expression for lines to be logged";
                 type jt:regular-expression;
               }
             }
             leaf level {
               description "Level of debugging output";
               type enumeration {
                 enum "error" {
                   description "Match error conditions";
                 }
                 enum "warning" {
                   description "Match warning messages";
                 }
                 enum "notice" {
                   description "Match conditions that should be handled specially";
                 }
                 enum "info" {
                   description "Match informational messages";
                 }
                 enum "verbose" {
                   description "Match verbose messages";
                 }
                 enum "all" {
                   description "Match all levels";
                 }
               }
             }
             list flag {
               key name;
               ordered-by user;
               description "Tracing parameters";
               leaf name {
                 type enumeration {
                   enum "all" {
                     description "Trace device info all modules";
                   }
                   enum "auth-source" {
                     description "Trace Auth source module";
                   }
                   enum "configuration" {
                     description "Trace Device info configuration";
                   }
                   enum "device-table" {
                     description "Trace device table management module";
                   }
                   enum "ipid-all" {
                     description "Trace IPID all functions";
                   }
                   enum "ipid-db" {
                     description "Trace IPID Database function";
                   }
                   enum "ipid-entry" {
                     description "Trace IPID entry management function";
                   }
                   enum "ipid-ipc" {
                     description "Trace IPID communication processing function";
                   }
                   enum "ipid-message" {
                     description "Trace IPID message processing function";
                   }
                   enum "ipid-others" {
                     description "Trace IPID other function";
                   }
                   enum "ipid-server" {
                     description "Trace IPID server handling function";
                   }
                   enum "ipid-statistics" {
                     description "Trace IPID statistics handling function";
                   }
                   enum "ipid-task" {
                     description "Trace IPID task handling function";
                   }
                   enum "profile-lookup" {
                     description "Trace End-user-profile lookup function";
                   }
                 }
               }
             }
           }
         }
         container identity-management {
           description "Identity management configuration";
           uses apply-advanced;
           leaf authentication-entry-timeout {
             description "Authentication entry timeout number (0, 10-1440)";
             default "60";
             units "minutes";
             type union {
               type uint16;
               type string {
                 pattern "<.*>|$.*";
               }
             }
           }
           leaf invalid-authentication-entry-timeout {
             description "Invalid authentication entry timeout number (0, 10-1440)";
             default "30";
             units "minutes";
             type union {
               type uint16;
               type string {
                 pattern "<.*>|$.*";
               }
             }
           }
           leaf preserve-valid-user {
             description "Null user will not overwrite valid user for the same ip";
             type empty;
           }
           container connection {
             description "Connection to identity management";
             uses apply-advanced;
             leaf connect-method {
               description "Method of connection";
               type enumeration {
                 enum "https" {
                   description "HTTPS connection";
                 }
                 enum "http" {
                   description "HTTP connection";
                 }
               }
             }
             leaf port {
               description "Server port";
               default "443";
               type union {
                 type string {
                   pattern "<.*>|$.*";
                 }
                 type uint32 {
                   range "1 .. 65535";
                 }
               }
             }
             container primary {
               description "Primary server";
               uses server-connection-type;
             }
             container secondary {
               description "Secondary server";
               uses server-connection-type;
             }
             leaf token-api {
               description "API of acquiring token for OAuth2 authentication";
               type string {
                 length "1 .. 128";
               }
             }
             leaf query-api {
               description "Query API";
               type string {
                 length "4 .. 128";
               }
             }
           }
           container batch-query {
             description "Batch query parameters";
             uses apply-advanced;
             leaf items-per-batch {
               description "Items number per batch query";
               default "200";
               type union {
                 type string {
                   pattern "<.*>|$.*";
                 }
                 type uint32 {
                   range "100 .. 1000";
                 }
               }
             }
             leaf query-interval {
               description "Query interval";
               default "5";
               units "seconds";
               type union {
                 type string {
                   pattern "<.*>|$.*";
                 }
                 type uint32 {
                   range "1 .. 60";
                 }
               }
             }
           }
           container ip-query {
             description "IP query parameters";
             uses apply-advanced;
             leaf query-delay-time {
               description "Delay time to send IP query (0~60sec)";
               default "15";
               units "seconds";
               type union {
                 type string {
                   pattern "<.*>|$.*";
                 }
                 type uint8 {
                   range "0 .. 60";
                 }
               }
             }
             container no-ip-query {
               presence "enable no-ip-query";
               description "Disable IP query";
             }
             leaf max-connections {
               description "Max connection number";
               type union {
                 type string {
                   pattern "<.*>|$.*";
                 }
                 type uint32 {
                   range "1 .. 20";
                 }
               }
             }
           }
           container filter {
             description "Filter for query";
             uses apply-advanced;
             list domain {
               key name;
               ordered-by user;
               description "Domain filter";
               max-elements 20;
               leaf name {
                 description "Domain name";
                 type string {
                   length "1 .. 64";
                   junos:posix-pattern "^[[:alnum:]._-]+$|^\\\\*$";
                   junos:pattern-message "Must be a string consisting of letters, numbers, dashes, underscores and dots";
                 }
               }
             }
             container include-ip {
               description "Include IP filter";
               uses address-filter-type;
             }
             container exclude-ip {
               description "Exclude IP filter";
               uses address-filter-type;
             }
           }
           container traceoptions {
             description "Tracing Options";
             uses apply-advanced;
             leaf no-remote-trace {
               description "Disable remote tracing";
               junos:must "(\"system tracing\")";
               junos:must-message "'no-remote-trace' is valid only when [system tracing] is configured";
               type empty;
             }
             container file {
               description "Trace file information";
               leaf filename {
                 description "Name of file in which to write trace information";
                 type string {
                   length "1 .. 1024";
                   junos:posix-pattern "![/ %]";
                   junos:pattern-message "Must not contain '/', % or a space";
                 }
               }
               leaf size {
                 description "Maximum trace file size";
                 type string;
               }
               leaf files {
                 description "Maximum number of trace files";
                 default "3";
                 type union {
                   type string {
                     pattern "<.*>|$.*";
                   }
                   type uint32 {
                     range "2 .. 1000";
                   }
                 }
               }
               choice world-readable-choice {
                 leaf world-readable {
                   description "Allow any user to read the log file";
                   type empty;
                 }
                 leaf no-world-readable {
                   description "Don't allow any user to read the log file";
                   type empty;
                 }
               }
               leaf match {
                 description "Regular expression for lines to be logged";
                 type jt:regular-expression;
               }
             }
             leaf level {
               description "Level of debugging output";
               type enumeration {
                 enum "error" {
                   description "Match error conditions";
                 }
                 enum "warning" {
                   description "Match warning messages";
                 }
                 enum "notice" {
                   description "Match conditions that should be handled specially";
                 }
                 enum "info" {
                   description "Match informational messages";
                 }
                 enum "verbose" {
                   description "Match verbose messages";
                 }
                 enum "all" {
                   description "Match all levels";
                 }
               }
             }
             list flag {
               key name;
               ordered-by user;
               description "Tracing parameters";
               leaf name {
                 type enumeration {
                   enum "all" {
                     description "Trace identity management all modules";
                   }
                   enum "authentication-management" {
                     description "Trace advanced-query auth table management module";
                   }
                   enum "configuration" {
                     description "Trace identity management configuration";
                   }
                   enum "dispatcher" {
                     description "Trace dispatcher module";
                   }
                   enum "query" {
                     description "Trace query process";
                   }
                 }
               }
             }
           }
         }
       }
       container ip-monitoring {
         description "IP monitoring for route action";
         uses apply-advanced;
         list policy {
           key name;
           ordered-by user;
           description "Policy for route action";
           leaf name {
             description "Policy name";
             type string {
               length "1 .. 64";
             }
           }
           uses apply-advanced;
           leaf no-preempt {
             description "No automatic failback preemption once policy failover";
             type empty;
           }
           container match {
             description "Matching probing condition";
             uses apply-advanced;
             leaf-list rpm-probe {
               ordered-by user;
               description "RPM probe name";
               type string;
             }
           }
           container then {
             description "Action to be taken";
             uses action-object-type;
           }
         }
         container traceoptions {
           description "IP-Monitoring trace options";
           uses apply-advanced;
           leaf no-remote-trace {
             description "Disable remote tracing";
             junos:must "(\"system tracing\")";
             junos:must-message "'no-remote-trace' is valid only when [system tracing] is configured";
             type empty;
           }
           container file {
             description "Trace file information";
             leaf filename {
               description "Name of file in which to write trace information";
               type string {
                 length "1 .. 1024";
                 junos:posix-pattern "![/ %]";
                 junos:pattern-message "Must not contain '/', % or a space";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "debug" {
                   description "Trace debug";
                 }
                 enum "configuration" {
                   description "Trace configuration events";
                 }
                 enum "errors" {
                   description "Trace errors";
                 }
                 enum "memory" {
                   description "Trace memory allocation or deallocation messages";
                 }
                 enum "event" {
                   description "Trace events";
                 }
                 enum "all" {
                   description "Trace events";
                 }
               }
             }
           }
         }
       }
       container wireless-wan {
         description "Wireless WAN configuration";
         uses apply-advanced;
         list adapter {
           key name;
           ordered-by user;
           description "Wireless adapter name configuration";
           leaf name {
             description "Wireless adapter name";
             type string {
               length "1 .. 16";
               junos:posix-pattern "^[A-Za-z]+[_0-9A-Za-z-]*$";
               junos:pattern-message "Must be a string beginning with a letter and consisting of no more than 16 total letters, numbers, dashes and underscores.";
             }
           }
           uses apply-advanced;
           leaf ip-address {
             description "Adapter management IP address";
             type jt:ipaddr;
           }
           leaf adapter-type {
             description "Select adapter type";
             type enumeration {
               enum "cx-bridge" {
                 description "Adapter type - CX-bridge";
               }
             }
           }
           container modem {
             description "Adapter modem settings";
             uses apply-advanced;
             container usb1 {
               presence "enable usb1";
               description "Adapter USB1 modem name";
               uses apply-advanced;
               leaf description {
                 description "Text description for modem";
                 type string;
               }
             }
             container usb2 {
               presence "enable usb2";
               description "Adapter USB2 modem name";
               uses apply-advanced;
               leaf description {
                 description "Text description for modem";
                 type string;
               }
             }
             container usb3 {
               presence "enable usb3";
               description "Adapter USB3 modem name";
               uses apply-advanced;
               leaf description {
                 description "Text description for modem";
                 type string;
               }
             }
             container expresscard {
               presence "enable expresscard";
               description "Adapter Expresscard modem name";
               uses apply-advanced;
               leaf description {
                 description "Text description for modem";
                 type string;
               }
             }
           }
         }
       }
       container proxy {
         description "Proxy setting for services";
         uses apply-advanced;
         list profile {
           key name;
           ordered-by user;
           description "Proxy profile";
           uses proxy-profile-setting;
         }
       }
       container lrf {
         description "Logging and reporting service configuration";
         uses apply-advanced;
         list profile {
           key name;
           ordered-by user;
           description "One or more LRF profiles";
           max-elements 8;
           uses lrf_profile_object;
         }
       }
       container pcef {
         description "Policy and Charging Enforcement Function(PCEF) configuration";
         uses services-pcef;
       }
       container stateful-firewall {
         description "Configure stateful firewall services";
         uses apply-advanced;
         list rule {
           key name;
           ordered-by user;
           description "Define a stateful firewall rule";
           uses sfw_rule_object;
         }
         list rule-set {
           key name;
           ordered-by user;
           description "Define a set of stateful firewall rules";
           max-elements 16960;
           leaf name {
             description "Name of the rule set";
             type string {
               length "1 .. 63";
               junos:posix-pattern "^[[:alnum:]][[:alnum:]/.:_-]*$";
               junos:pattern-message "Must be a string beginning with a number or letter and consisting of letters, numbers, dashes, underscores, forward slashes, colons and dots.";
             }
           }
           uses apply-advanced;
           list rule {
             key name;
             ordered-by user;
             description "Rule to be included in this rule set";
             max-elements 16960;
             leaf name {
               description "Rule name";
               junos:must "(\"services stateful-firewall rule $$\")";
               junos:must-message "rule must be configured";
               type string {
                 junos:posix-pattern "^[[:alnum:]][[:alnum:]/.:_-]{0,62}$";
                 junos:pattern-message "Must be a string beginning with a number or letter and consisting of no more than 63 total letters, numbers, dashes, underscores, forward slashes, colons and dots.";
               }
             }
             uses apply-advanced;
           }
         }
       }
       container ip-reassembly {
         description "Configure ip-reassembly services";
         uses apply-advanced;
         list profile {
           key name;
           description "Define a ip reassembly profile";
           uses ipr_profile_object;
         }
         list rule {
           key name;
           ordered-by user;
           description "Define a ip reassembly rule";
           uses ipr_rule_object;
         }
         list rule-set {
           key name;
           ordered-by user;
           description "Define a set of ip reassembly rules";
           max-elements 16960;
           leaf name {
             description "Name of the rule set";
             type string {
               length "1 .. 63";
               junos:posix-pattern "^[[:alnum:]][[:alnum:]_-]*$";
               junos:pattern-message "Must be a string beginning with a number or letter and consisting of letters, numbers, dashes and underscores.";
             }
           }
           uses apply-advanced;
           list rule {
             key name;
             ordered-by user;
             description "Rule to be included in this rule set";
             max-elements 16960;
             leaf name {
               description "Rule name";
               junos:must "(\"services ip-reassembly rule $$\")";
               junos:must-message "rule must be configured";
               type string {
                 junos:posix-pattern "^[A-Za-z0-9][_0-9A-Za-z-]{0,62}$";
                 junos:pattern-message "Must be a string beginning with a number or letter and consisting of no more than 63 total letters, numbers, dashes and underscores.";
               }
             }
             uses apply-advanced;
           }
         }
       }
       container softwire {
         description "Configure softwire services";
         uses apply-advanced;
         list ipv6-multicast-interfaces {
           key name;
           ordered-by user;
           description "Enable IPv6 multicast filter";
           leaf name {
             description "Interface name";
             type string;
           }
           uses apply-advanced;
         }
         container softwire-concentrator {
           description "Configure softwire concentrators";
           uses apply-advanced;
           list ds-lite {
             key name;
             ordered-by user;
             description "Configure DS-Lite concentrator";
             uses dslite_object;
           }
           list v6rd {
             key name;
             ordered-by user;
             description "Configure 6rd concentrator";
             uses v6rd_object;
           }
           list map-e {
             key name;
             ordered-by user;
             description "Configure MAP-E concentrator";
             uses mape_object;
           }
         }
         list rule {
           key name;
           ordered-by user;
           description "Define a softwire rule";
           uses sw_rule_object;
         }
         list rule-set {
           key name;
           ordered-by user;
           description "Define a set of softwire rules";
           max-elements 16960;
           leaf name {
             description "Name of the rule set";
             type string {
               length "1 .. 63";
               junos:posix-pattern "^[[:alnum:]][[:alnum:]_-]*$";
               junos:pattern-message "Must be a string beginning with a number or letter and consisting of letters, numbers, dashes and underscores.";
             }
           }
           uses apply-advanced;
           list rule {
             key name;
             ordered-by user;
             description "Rule to be included in this rule set";
             max-elements 16960;
             leaf name {
               description "Rule name";
               junos:must "(\"services softwire rule $$\")";
               junos:must-message "rule must be configured";
               type string {
                 junos:posix-pattern "^[A-Za-z0-9][_0-9A-Za-z-]{0,62}$";
                 junos:pattern-message "Must be a string beginning with a number or letter and consisting of no more than 63 total letters, numbers, dashes and underscores.";
               }
             }
             uses apply-advanced;
           }
         }
       }
       container aacl {
         description "Application Aware Access List services configuration";
         uses apply-advanced;
         list rule {
           key name;
           ordered-by user;
           description "One or more AACL rules";
           uses aacl_rule_object;
         }
         list rule-set {
           key name;
           ordered-by user;
           description "Define a Set of AACL rules";
           max-elements 16960;
           leaf name {
             description "Name of the rule set";
             type string {
               length "1 .. 63";
               junos:posix-pattern "^[[:alnum:]][[:alnum:]_-]*$";
               junos:pattern-message "Must be a string beginning with a number or letter and consisting of letters, numbers, dashes and underscores.";
             }
           }
           uses apply-advanced;
           list rule {
             key name;
             ordered-by user;
             description "Rule to be included in this rule set";
             max-elements 16960;
             leaf name {
               description "Rule name";
               junos:must "(\"services aacl rule $$\")";
               junos:must-message "rule must be configured";
               type string {
                 junos:posix-pattern "^[A-Za-z0-9][_0-9A-Za-z-]{0,62}$";
                 junos:pattern-message "Must be a string beginning with a number or letter and consisting of no more than 63 total letters, numbers, dashes and underscores.";
               }
             }
             uses apply-advanced;
           }
         }
         list aacl-dyn-rule-set {
           key name;
           ordered-by user;
           description "Define a set of AACL dynamic rules";
           max-elements 16960;
           leaf name {
             description "Name of the rule set";
             type string {
               length "1 .. 63";
               junos:posix-pattern "^[[:alnum:]][[:alnum:]_-]*$";
               junos:pattern-message "Must be a string beginning with a number or letter and consisting of letters, numbers, dashes and underscores.";
             }
           }
           uses apply-advanced;
           list rule {
             key name;
             ordered-by user;
             description "Rule to be included in this rule set";
             max-elements 16960;
             leaf name {
               description "Rule name";
               junos:must "(\"services aacl rule $$\")";
               junos:must-message "rule must be configured";
               type string {
                 junos:posix-pattern "^[A-Za-z0-9][_0-9A-Za-z-]{0,62}$";
                 junos:pattern-message "Must be a string beginning with a number or letter and consisting of no more than 63 total letters, numbers, dashes and underscores.";
               }
             }
             uses apply-advanced;
           }
         }
       }
       container hcm {
         description "Http Content Management services configuration";
         uses apply-advanced;
         list url-rule {
           key name;
           ordered-by user;
           description "One or more url HCM rules";
           uses hcm_url_rule_object;
         }
         list tag-rule {
           key name;
           ordered-by user;
           description "One or more  HCM tag rules";
           uses hcm_tag_rule_object;
         }
         list url-list {
           key name;
           ordered-by user;
           description "List of URL's";
           uses hcm_url_list_object;
         }
         leaf-list tag-attribute {
           ordered-by user;
           description "Tag Attributes (Subscriber Aware Attrs: imsi,msisdn,ipv4addr,imei,ipv6addr,apn,ggsnipv4,ggsnipv6)";
           type enumeration {
             enum "msisdn" {
             }
             enum "imsi" {
             }
             enum "apn" {
             }
             enum "imei" {
             }
             enum "ipv4addr" {
             }
             enum "ipv6addr" {
             }
             enum "ggsnipv4" {
             }
             enum "ggsnipv6" {
             }
             enum "radiusclass" {
             }
           }
         }
         list url-rule-set {
           key name;
           ordered-by user;
           description "Define a Set of HCM url rules";
           max-elements 16960;
           leaf name {
             description "Name of the rule set";
             type string {
               length "1 .. 63";
               junos:posix-pattern "^[[:alnum:]][[:alnum:]_-]*$";
               junos:pattern-message "Must be a string beginning with a number or letter and consisting of letters, numbers, dashes and underscores.";
             }
           }
           uses apply-advanced;
           list rule {
             key name;
             ordered-by user;
             description "Rule to be included in this rule set";
             max-elements 16960;
             leaf name {
               description "Rule name";
               junos:must "(\"services hcm url-rule $$\")";
               junos:must-message "rule must be configured";
               type string {
                 junos:posix-pattern "^[A-Za-z0-9][_0-9A-Za-z-]{0,62}$";
                 junos:pattern-message "Must be a string beginning with a number or letter and consisting of no more than 63 total letters, numbers, dashes and underscores.";
               }
             }
             uses apply-advanced;
           }
         }
         list tag-rule-set {
           key name;
           ordered-by user;
           description "Define a Set of HCM tag rules";
           max-elements 16960;
           leaf name {
             description "Name of the rule set";
             type string {
               length "1 .. 63";
               junos:posix-pattern "^[[:alnum:]][[:alnum:]_-]*$";
               junos:pattern-message "Must be a string beginning with a number or letter and consisting of letters, numbers, dashes and underscores.";
             }
           }
           uses apply-advanced;
           list rule {
             key name;
             ordered-by user;
             description "Rule to be included in this rule set";
             max-elements 16960;
             leaf name {
               description "Rule name";
               junos:must "(\"services hcm tag-rule $$\")";
               junos:must-message "rule must be configured";
               type string {
                 junos:posix-pattern "^[A-Za-z0-9][_0-9A-Za-z-]{0,62}$";
                 junos:pattern-message "Must be a string beginning with a number or letter and consisting of no more than 63 total letters, numbers, dashes and underscores.";
               }
             }
             uses apply-advanced;
           }
         }
         list profile {
           key name;
           ordered-by user;
           description "HCM Profile Name";
           max-elements 101;
           leaf name {
             description "HCM profile name";
             type string {
               length "1 .. 63";
               junos:posix-pattern "^[[:alnum:]][[:alnum:]_-]*$";
               junos:pattern-message "Must be a string beginning with a number or letter and consisting of letters, numbers, dashes and underscores.";
             }
           }
           uses apply-advanced;
           container tag-rule {
             description "Tag rule to be included in this profile";
             uses apply-advanced;
             leaf tag-rule-name {
               description "Tag Rule name";
               junos:must "(\"services hcm tag-rule $$\")";
               junos:must-message "tag rule must be configured";
               type string {
                 junos:posix-pattern "^[A-Za-z0-9][_0-9A-Za-z-]{0,62}$";
                 junos:pattern-message "Must be a string beginning with a number or letter and consisting of no more than 63 total letters, numbers, dashes and underscores.";
               }
             }
           }
         }
       }
       container cos {
         description "Class of Service services configuration";
         uses cos-object;
       }
       container pgcp {
         description "Packet Gateway Control Protocol services configuration";
         uses apply-advanced;
         container traceoptions {
           description "Trace options for packet gateway service";
           uses apply-advanced;
           container flag {
             presence "enable flag";
             description "Per-component trace options";
             uses apply-advanced;
             leaf default {
               description "Default trace level for all the components";
               default "error";
               type enumeration {
                 enum "trace" {
                   description "Trace functions entering and exiting";
                 }
                 enum "debug" {
                   description "Trace code flow, branching, positive style guide check";
                 }
                 enum "info" {
                   description "Summary logs for normal operations";
                 }
                 enum "warning" {
                   description "Failure-recovery or Failure of an external entity";
                 }
                 enum "error" {
                   description "Failure with short-term affect";
                 }
               }
             }
             container h248-stack {
               presence "enable h248-stack";
               description "H248 stack sub-components";
               uses apply-advanced;
               leaf default {
                 description "Default trace level for the H248 stack subcomponents";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf control-association {
                 description "Control association trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf media-gateway {
                 description "Media gateway trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf messages {
                 description "Enable H248 dump messages";
                 type empty;
               }
             }
             container bgf-core {
               presence "enable bgf-core";
               description "BGF core sub-components";
               uses apply-advanced;
               leaf default {
                 description "Default trace level for the bgf core subcomponents";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf firewall {
                 description "Firewall trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf gate-logic {
                 description "Gate trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf policy {
                 description "Policy trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf pic-broker {
                 description "PIC broker trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf statistics {
                 description "Statistics trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf common {
                 description "Common  trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
             }
             container sbc-utils {
               presence "enable sbc-utils";
               description "SBC utils sub-components";
               uses apply-advanced;
               leaf default {
                 description "Default trace level for the sbc-utils subcomponents";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf common {
                 description "Common utils trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf configuration {
                 description "Configuration trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf device-monitor {
                 description "Device-monitor trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf ipc {
                 description "IPC trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf memory-management {
                 description "Memory mgmt trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf messaging {
                 description "Messaging trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf user-interface {
                 description "UI trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
             }
           }
           container file {
             description "Trace file information";
             leaf filename {
               description "Name of file in which to write trace information";
               type string {
                 length "1 .. 1024";
                 junos:posix-pattern "![/ %]";
                 junos:pattern-message "Must not contain '/', % or a space";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
         }
         list media-service {
           key name;
           ordered-by user;
           description "One or more PGCP media service";
           status deprecated;
           max-elements 32;
           uses pgcp_media_service_object;
         }
         list virtual-interface {
           key name;
           ordered-by user;
           description "One or more Virtual Interfaces";
           max-elements 1024;
           uses pgcp_virtual_interface_object;
         }
         list gateway {
           key name;
           ordered-by user;
           description "One or more Packet Gateways";
           max-elements 32;
           uses pgcp_gateway_object;
         }
         list rule {
           key name;
           ordered-by user;
           description "One or more PGCP rules";
           max-elements 64;
           uses pgcp_rule_object;
         }
         list rule-set {
           key name;
           ordered-by user;
           description "Define a Set of PGCP rules";
           max-elements 16960;
           leaf name {
             description "Name of the rule set";
             type string {
               length "1 .. 63";
               junos:posix-pattern "^[[:alnum:]][[:alnum:]_-]*$";
               junos:pattern-message "Must be a string beginning with a number or letter and consisting of letters, numbers, dashes and underscores.";
             }
           }
           uses apply-advanced;
           list rule {
             key name;
             ordered-by user;
             description "Rule to be included in this rule set";
             max-elements 16960;
             leaf name {
               description "Rule name";
               junos:must "(\"services pgcp rule $$\")";
               junos:must-message "rule must be configured";
               type string {
                 junos:posix-pattern "^[A-Za-z0-9][_0-9A-Za-z-]{0,62}$";
                 junos:pattern-message "Must be a string beginning with a number or letter and consisting of no more than 63 total letters, numbers, dashes and underscores.";
               }
             }
             uses apply-advanced;
           }
         }
         container session-mirroring {
           description "Session mirroring configuration";
           uses pgcp_session_mirroring_object;
         }
         leaf notification-rate-limit {
           description "Max number of notifications/second sent to PGC";
           type union {
             type string {
               pattern "<.*>|$.*";
             }
             type int32 {
               range "10 .. 1000";
             }
           }
         }
       }
       container border-signaling-gateway {
         description "Border signaling service configuration";
         uses apply-advanced;
         list gateway {
           key name;
           ordered-by user;
           max-elements 4;
           uses gateway_type;
         }
       }
       container ids {
         description "Configure the intrusion detection system";
         uses apply-advanced;
         list rule {
           key name;
           ordered-by user;
           description "Define an IDS rule";
           uses ids_rule_object;
         }
         list rule-set {
           key name;
           ordered-by user;
           description "Define a set of IDS rules";
           max-elements 16960;
           leaf name {
             description "Name of the rule set";
             type string {
               length "1 .. 63";
               junos:posix-pattern "^[[:alnum:]][[:alnum:]_-]*$";
               junos:pattern-message "Must be a string beginning with a number or letter and consisting of letters, numbers, dashes and underscores.";
             }
           }
           uses apply-advanced;
           list rule {
             key name;
             ordered-by user;
             description "Rule to be included in this rule set";
             max-elements 16960;
             leaf name {
               description "Rule name";
               junos:must "(\"services ids rule $$\")";
               junos:must-message "rule must be configured";
               type string {
                 junos:posix-pattern "^[A-Za-z0-9][_0-9A-Za-z-]{0,62}$";
                 junos:pattern-message "Must be a string beginning with a number or letter and consisting of no more than 63 total letters, numbers, dashes and underscores.";
               }
             }
             uses apply-advanced;
           }
         }
       }
       container nat {
         description "Configure Network Address Translation";
         uses nat-object;
       }
       container pcp {
         description "Configure Port Control Protocol";
         uses apply-advanced;
         list server {
           key name;
           ordered-by user;
           description "Define a PCP server";
           uses pcp-server-object;
         }
         list rule {
           key name;
           ordered-by user;
           description "Define a PCP rule";
           uses pcp-rule-object;
         }
         list rule-set {
           key name;
           ordered-by user;
           description "Defines a set of PCP rules";
           max-elements 16960;
           leaf name {
             description "Name of the rule set";
             type string {
               length "1 .. 63";
               junos:posix-pattern "^[[:alnum:]][[:alnum:]_-]*$";
               junos:pattern-message "Must be a string beginning with a number or letter and consisting of letters, numbers, dashes and underscores.";
             }
           }
           uses apply-advanced;
           list rule {
             key name;
             ordered-by user;
             description "Rule to be included in this rule set";
             max-elements 16960;
             leaf name {
               description "Rule name";
               junos:must "(\"services pcp rule $$\")";
               junos:must-message "rule must be configured";
               type string {
                 junos:posix-pattern "^[A-Za-z0-9][_0-9A-Za-z-]{0,62}$";
                 junos:pattern-message "Must be a string beginning with a number or letter and consisting of no more than 63 total letters, numbers, dashes and underscores.";
               }
             }
             uses apply-advanced;
           }
         }
       }
       container l2tp {
         presence "enable l2tp";
         junos:must "(!(\"forwarding-options hyper-mode\"))";
         junos:must-message "To configure services l2tp, 'forwarding-options hyper-mode' should not be configured";
         description "Configure Layer 2 Tunneling Protocol service";
         uses apply-advanced;
         list tunnel-group {
           key name;
           ordered-by user;
           description "Layer 2 Tunneling Protocol profile";
           uses l2tp_tunnel_group_object;
         }
         container ip-reassembly {
           description "Configure IP Reassembly parameters";
           uses apply-advanced;
           leaf service-set {
             description "Name of IP Reassembly service set";
             junos:must "((\".. .. .. service-set $$ ip-reassembly-rules\" || \".. .. .. service-set $$ ip-reassembly-rule-sets\"))";
             junos:must-message "Referenced IP Reassembly service-set must be defined";
             type string {
               length "1 .. 63";
             }
           }
         }
         container traceoptions {
           description "Layer 2 Tunneling Protocol daemon trace options";
           uses apply-advanced;
           leaf no-remote-trace {
             description "Disable remote tracing";
             junos:must "(\"system tracing\")";
             junos:must-message "'no-remote-trace' is valid only when [system tracing] is configured";
             type empty;
           }
           container file {
             description "Trace file information";
             leaf filename {
               description "Name of file in which to write trace information";
               type string {
                 length "1 .. 1024";
                 junos:posix-pattern "![/ %]";
                 junos:pattern-message "Must not contain '/', % or a space";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           leaf level {
             description "Level of debugging output";
             default "error";
             type enumeration {
               enum "error" {
                 description "Match error conditions";
               }
               enum "warning" {
                 description "Match warning messages";
               }
               enum "notice" {
                 description "Match conditions that should be handled specially";
               }
               enum "info" {
                 description "Match informational messages";
               }
               enum "verbose" {
                 description "Match verbose messages";
               }
               enum "all" {
                 description "Match all levels";
               }
             }
           }
           list flag {
             key name;
             ordered-by user;
             description "Tracing parameters";
             leaf name {
               type enumeration {
                 enum "gres" {
                   description "Trace GRES events";
                 }
                 enum "init" {
                   description "Trace daemon initialization";
                 }
                 enum "events" {
                   description "Trace interface events";
                 }
                 enum "memory" {
                   description "Trace memory management code";
                 }
                 enum "message" {
                   description "Trace message processing code";
                 }
                 enum "packet-error" {
                   description "Trace Packet error events";
                 }
                 enum "parse" {
                   description "Trace parsing events";
                 }
                 enum "receive-packets" {
                   description "Trace received L2TP packets";
                 }
                 enum "session-db" {
                   description "Trace session database interactions";
                 }
                 enum "states" {
                   description "Trace state machine events";
                 }
                 enum "timer" {
                   description "Trace timer events";
                 }
                 enum "transmit-packets" {
                   description "Trace tranmitted L2TP packets";
                 }
                 enum "routing-socket" {
                   description "Trace routing socket events";
                 }
                 enum "routing-process" {
                   description "Trace routing process interactions";
                 }
                 enum "protocol" {
                   description "Trace Layer 2 Tunneling Protocol events";
                 }
                 enum "configuration" {
                   description "Trace configuration events";
                 }
                 enum "ipc-tx" {
                   description "Trace IPC transmit events";
                 }
                 enum "ipc-rx" {
                   description "Trace IPC receive events";
                 }
                 enum "general" {
                   description "Trace general events";
                 }
                 enum "tunnel" {
                   description "Trace tunnel events";
                 }
                 enum "stats" {
                   description "Trace libstats events";
                 }
                 enum "authentication" {
                   description "Trace authentication process interactions";
                 }
                 enum "all" {
                   description "Trace everything";
                 }
               }
             }
           }
           leaf debug-level {
             description "Trace level for PPP, L2TP, RADIUS, and UDP";
             junos:must "((\".. flag protocol\" || \".. flag all\"))";
             junos:must-message "debug-level can be specified only for traceoption flag protocol or all";
             type enumeration {
               enum "error" {
                 description "Errors";
               }
               enum "detail" {
                 description "Detailed debug information";
               }
               enum "packet-dump" {
                 description "Packet decode information";
               }
             }
           }
           container filter {
             presence "enable filter";
             description "Filter to control trace messages";
             uses apply-advanced;
             list protocol {
               key name;
               ordered-by user;
               description "Additional filter for protocol";
               junos:must "((\".. .. flag protocol\" || \".. .. flag all\"))";
               junos:must-message "Filter protocol can be specified only for traceoption flag protocol or all";
               leaf name {
                 type enumeration {
                   enum "ppp" {
                     description "Trace Point-to-Point Protocol events";
                   }
                   enum "l2tp" {
                     description "Trace Layer 2 Tunneling Protocol events";
                   }
                   enum "radius" {
                     description "Trace RADIUS events";
                   }
                   enum "udp" {
                     description "Trace User Datagram Protocol events";
                   }
                 }
               }
             }
             leaf user-name {
               description "Additional filter by user name";
               junos:must "((\".. .. flag protocol\" || \".. .. flag all\"))";
               junos:must-message "Filter user name can be specified only for traceoption flag protocol or all";
               type string {
                 length "1 .. 64";
               }
             }
             container user {
               presence "enable user";
               description "Filter by user name";
               uses apply-advanced;
               leaf username {
                 description "Name of the user to be filtered";
                 type string {
                   length "1 .. 64";
                 }
               }
             }
           }
           list interfaces {
             key name;
             ordered-by user;
             description "Layer 2 Tunneling Protocol service interface";
             uses l2tp_interface_traceoptions;
           }
         }
         leaf weighted-load-balancing {
           description "Enable weighted-load-balancing for LAC sessions";
           junos:must "(!(\".. destination-equal-load-balancing\"))";
           junos:must-message "Both weighted-load-balancing and destination-equal-load-balancing can't be enabled together";
           type empty;
         }
         leaf destination-equal-load-balancing {
           description "Enable equal load balancing of destinations";
           junos:must "(!(\".. weighted-load-balancing\"))";
           junos:must-message "Both weighted-load-balancing and destination-equal-load-balancing can't be enabled together";
           type empty;
         }
         leaf drain {
           description "Prevents creation of destinations, tunnels and sessions";
           type empty;
         }
         leaf failover-within-preference {
           description "Enable failover-within-preference level for LAC sessions";
           type empty;
         }
         leaf disable-calling-number-avp {
           description "Disable the calling number AVP in ICRQ packet";
           type empty;
         }
         leaf disable-failover-protocol {
           description "Disable failover protocol resync mechanism";
           status deprecated;
           type empty;
         }
         leaf rx-connect-speed-when-equal {
           description "Generate rx connect speed AVP when tx equals rx speed";
           type empty;
         }
         leaf tx-connect-speed-method {
           description "TX connect speed method";
           default "static";
           type enumeration {
             enum "none" {
               description "Disable sending tx/rx speed AVPs";
             }
             enum "static" {
               description "Use advisory speed";
             }
             enum "ancp" {
               description "Use ANCP sourced tx/rx speed";
             }
             enum "pppoe-ia-tag" {
               description "Use tx/rx speed sent in the PPPoE IA tag";
             }
             enum "service-profile" {
               description "Use tx/rx speed from service profile configuration";
               junos:must "(\"chassis effective-shaping-rate\")";
               junos:must-message "The chassis 'effective-shaping-rate' must be enabled when service-profile is set";
             }
           }
         }
         leaf maximum-sessions {
           description "Maximum number of sessions per chassis";
           type union {
             type uint32;
             type string {
               pattern "<.*>|$.*";
             }
           }
         }
         container tunnel {
           description "System wide tunnel attributes";
           uses apply-advanced;
           list name {
             key name;
             ordered-by user;
             leaf name {
               description "Locally assigned name of the tunnel(in format Destination name/Tunnel name or Tunnel name)";
               type string {
                 length "1 .. 129";
                 junos:posix-pattern "^[[:alnum:]][[:alnum:]/_-]*$";
                 junos:pattern-message "Must be a string beginning with a number or letter and consisting of letters, numbers, dashes and underscores.";
               }
             }
             list address {
               key name;
               ordered-by user;
               description "Address of the tunnel destination";
               junos:must "(!(\".. drain\"))";
               junos:must-message "Multiple times drain is set or drain is set at incorrect level";
               leaf name {
                 description "Address of remote system";
                 type jt:ipv4addr;
               }
               list routing-instance {
                 key name;
                 ordered-by user;
                 description "Routing instance in which tunnel exists";
                 junos:must "((!(\".. drain\") && !(\".. .. drain\")))";
                 junos:must-message "Multiple times drain is not allowed";
                 leaf name {
                   description "Routing instance in which tunnel exists";
                   type string {
                     junos:posix-pattern "!^((__.*__)|(.*[ ].*)|(.{129,}))$";
                     junos:pattern-message "Must be a string of 128 characters or less with no spaces.";
                   }
                 }
                 leaf drain {
                   description "Prevents assignment of sessions to tunnel";
                   type empty;
                 }
               }
               leaf drain {
                 description "Prevents assignment of sessions to tunnel";
                 type empty;
               }
             }
             leaf drain {
               description "Prevents sessions assignment to tunnel";
               type empty;
             }
           }
           leaf assignment-id-format {
             description "Assignment id format";
             default "assignment-id";
             type enumeration {
               enum "assignment-id" {
                 description "Configure the format to be assignment-id only";
               }
               enum "client-server-id" {
                 description "Configure the format to be client-auth-id + server-auth-id + assignment-id";
               }
             }
           }
           leaf retransmission-count-established {
             description "Max Retransmission count for Established tunnels";
             default "7";
             type union {
               type string {
                 pattern "<.*>|$.*";
               }
               type uint16 {
                 range "2 .. 30";
               }
             }
           }
           leaf retransmission-count-not-established {
             description "Max Retransmission count for Not Established tunnels";
             default "5";
             type union {
               type string {
                 pattern "<.*>|$.*";
               }
               type uint16 {
                 range "2 .. 30";
               }
             }
           }
           leaf nas-port-method {
             description "Tunnel network access server port method";
             type enumeration {
               enum "cisco-avp" {
                 description "Limited Cisco vendor specific mechanism";
               }
             }
           }
           leaf minimum-retransmission-timeout {
             description "Min retransmission timeout for control packets in seconds (default 1)";
             default "1";
             type enumeration {
               enum "1" {
                 description "1 second";
               }
               enum "2" {
                 description "2 seconds";
               }
               enum "4" {
                 description "4 seconds";
               }
               enum "8" {
                 description "8 seconds";
               }
               enum "16" {
                 description "16 seconds";
               }
             }
           }
           leaf idle-timeout {
             description "Tunnel idle timeout value in seconds";
             default "60";
             type union {
               type string {
                 pattern "<.*>|$.*";
               }
               type uint32 {
                 range "0 .. 86400";
               }
             }
           }
           leaf rx-window-size {
             description "Tunnel Receive Window Size";
             default "4";
             type union {
               type string {
                 pattern "<.*>|$.*";
               }
               type uint16 {
                 range "4 .. 128";
               }
             }
           }
           container tx-address-change {
             presence "enable tx-address-change";
             description "Tunnel Tx Address Change";
             uses apply-advanced;
             leaf accept {
               description "Accept Tx IP Address or UDP Port Change";
               junos:must "((!(\".. ignore\") && (!(\".. ignore-ip-address\") && (!(\".. ignore-udp-port\") && (!(\".. reject\") && (!(\".. reject-ip-address\") && !(\".. reject-udp-port\")))))))";
               junos:must-message "Both Accept and Ignore/Reject are not allowed";
               type empty;
             }
             leaf ignore {
               description "Ignore Tx IP Address or UDP Port Change";
               junos:must "((!(\".. reject\") && (!(\".. reject-ip-address\") && !(\".. reject-udp-port\"))))";
               junos:must-message "Both ignore and reject are not allowed";
               type empty;
             }
             leaf ignore-ip-address {
               description "Ignore Tx IP Address Change";
               junos:must "((!(\".. reject\") && !(\".. reject-ip-address\")))";
               junos:must-message "Both ignore-ip-address and reject-ip-address are not allowed";
               type empty;
             }
             leaf ignore-udp-port {
               description "Ignore Tx UDP Port Change";
               junos:must "((!(\".. reject\") && !(\".. reject-udp-port\")))";
               junos:must-message "Both ignore-udp-port and reject-udp-port are not allowed";
               type empty;
             }
             leaf reject {
               description "Reject Tx IP Address or UDP Port Change";
               junos:must "((!(\".. ignore-ip-address\") && !(\".. ignore-udp-port\")))";
               junos:must-message "Both ignore and reject are not allowed";
               type empty;
             }
             leaf reject-ip-address {
               description "Reject Tx IP Address Change";
               junos:must "(!(\".. ignore-ip-address\"))";
               junos:must-message "Both ignore-ip-address and reject-ip-address are not allowed";
               type empty;
             }
             leaf reject-udp-port {
               description "Reject Tx UDP Port Change";
               junos:must "(!(\".. ignore-udp-port\"))";
               junos:must-message "Both ignore-udp-port and reject-udp-port are not allowed";
               type empty;
             }
           }
           leaf maximum-sessions {
             description "Maximum number of sessions per tunnel";
             type union {
               type uint32;
               type string {
                 pattern "<.*>|$.*";
               }
             }
           }
           leaf failover-resync {
             description "Tunnel Failover Resync Mechanism";
             type enumeration {
               enum "silent-failover" {
                 description "Use silent failover as failover resync mechanism";
               }
               enum "failover-protocol" {
                 description "Use L2TP failover protocol as failover resync mechanism if peer supports";
               }
             }
           }
         }
         leaf destruct-timeout {
           description "The destruct timeout in seconds";
           default "300";
           type union {
             type string {
               pattern "<.*>|$.*";
             }
             type uint16 {
               range "10 .. 3600";
             }
           }
         }
         leaf tunnel-switch-profile {
           description "Default tunnel switch profile name";
           junos:must "(\"access tunnel-switch-profile $$\")";
           junos:must-message "Referenced tunnel switch profile must be defined";
           type string {
             length "1 .. 63";
           }
         }
         container destination {
           description "System wide destination attributes";
           uses l2tp_destination_object;
         }
         container access-line-information {
           description "Enable system wide sending of DSL line attributes";
           uses l2tp_access_line_object;
         }
         list session-limit-group {
           key name;
           ordered-by user;
           description "Session-limit-group configuration";
           leaf name {
             description "Name of the group";
             type string {
               length "1 .. 63";
               junos:posix-pattern "^[[:alnum:]][[:alnum:]_-]*$";
               junos:pattern-message "Must be a string beginning with a number or letter and consisting of letters, numbers, dashes and underscores.";
             }
           }
           uses apply-advanced;
           leaf maximum-sessions {
             description "Maximum number of sessions per tunnel-group";
             type union {
               type uint32;
               type string {
                 pattern "<.*>|$.*";
               }
             }
           }
         }
         leaf enable-ipv6-services-for-lac {
           description "Enable IPv6 services for LAC sessions";
           type empty;
         }
         leaf enable-snmp-tunnel-statistics {
           description "Enable L2TP tunnel statistics for availability via SNMP";
           type empty;
         }
       }
       container adaptive-services-pics {
         description "Adaptive Services PIC daemon configuration";
         uses apply-advanced;
         container traceoptions {
           description "Adaptive Services PIC daemon trace options";
           uses apply-advanced;
           leaf no-remote-trace {
             description "Disable remote tracing";
             junos:must "(\"system tracing\")";
             junos:must-message "'no-remote-trace' is valid only when [system tracing] is configured";
             type empty;
           }
           container file {
             description "Trace file information";
             leaf filename {
               description "Name of file in which to write trace information";
               type string {
                 length "1 .. 1024";
                 junos:posix-pattern "![/ %]";
                 junos:pattern-message "Must not contain '/', % or a space";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "routing-socket" {
                   description "Trace routing socket events";
                 }
                 enum "routing-protocol" {
                   description "Trace routing protocol events";
                 }
                 enum "service-identification" {
                   description "Trace service-identification events";
                 }
                 enum "configuration" {
                   description "Trace configuration events";
                 }
                 enum "ipc" {
                   description "Trace IPC related events";
                 }
                 enum "kernel-object" {
                   description "Trace kernel object management";
                 }
                 enum "snmp" {
                   description "Trace SNMP operations";
                 }
                 enum "all" {
                   description "Trace everything";
                 }
               }
             }
           }
         }
       }
       container license-management {
         description "Configure license management server";
         uses apply-advanced;
         container license-server {
           presence "enable license-server";
           uses apply-advanced;
           leaf ip-address {
             description "Address of the license log server";
             type jt:ipv4addr;
           }
           leaf log-interval {
             description "Time interval to send data to Log Collector";
             default "300";
             type union {
               type string {
                 pattern "<.*>|$.*";
               }
               type uint32 {
                 range "60 .. 86400";
               }
             }
           }
           leaf-list services {
             ordered-by user;
             description "List of services that require throughput data export";
             type enumeration {
               enum "jflow" {
                 description "Jflow Service";
               }
               enum "cgnat" {
                 description "CGNAT Service";
               }
               enum "firewall" {
                 description "Firewall Service";
               }
             }
           }
         }
       }
       container rtlog {
         presence "enable rtlog";
         uses apply-advanced;
         container traceoptions {
           description "Security log daemon trace options";
           uses apply-advanced;
           leaf no-remote-trace {
             description "Disable remote tracing";
             junos:must "(\"system tracing\")";
             junos:must-message "'no-remote-trace' is valid only when [system tracing] is configured";
             type empty;
           }
           container file {
             description "Trace file information";
             leaf filename {
               description "Name of file in which to write trace information";
               type string {
                 length "1 .. 1024";
                 junos:posix-pattern "![/ %]";
                 junos:pattern-message "Must not contain '/', % or a space";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "List of things to include in trace";
             leaf name {
               type enumeration {
                 enum "source" {
                   description "Communication with security log forwarder";
                 }
                 enum "configuration" {
                   description "Reading of configuration";
                 }
                 enum "all" {
                   description "Everything";
                 }
                 enum "report" {
                   description "Trace report";
                 }
                 enum "hpl" {
                   description "Trace HPL logging";
                 }
               }
             }
           }
         }
       }
       container soft-gre {
         presence "enable soft-gre";
         description "Soft GRE tunnel definitions";
         uses apply-advanced;
         list tunnel-group {
           key name;
           ordered-by user;
           uses soft_gre_tunnel_group_object;
         }
       }
       container service-interface-pools {
         description "Configure service interface pools";
         uses apply-advanced;
         list pool {
           key name;
           ordered-by user;
           description "Define service interface pool";
           uses service_interface_pool_object;
         }
       }
       container hosted-services {
         description "Configuration for services performed in the remote server";
         uses apply-advanced;
         list client-profile {
           key name;
           ordered-by user;
           description "Configure client profile";
           leaf name {
             description "Client profile name";
             type string {
               length "3 .. 32";
             }
           }
           uses apply-advanced;
           leaf transport-type {
             description "Transport type";
             type enumeration {
               enum "GRE" {
                 description "GRE";
               }
               enum "UDP" {
                 description "UDP";
               }
               enum "TCP" {
                 description "TCP";
               }
             }
           }
           leaf client-address {
             description "Client address";
             type jt:ipv4addr;
           }
           leaf hosted-service-identifier {
             description "Identifier for the service performed on the remote server";
             type union {
               type string {
                 pattern "<.*>|$.*";
               }
               type int32 {
                 range "1 .. 63";
               }
             }
           }
         }
         list server-profile {
           key name;
           ordered-by user;
           description "Configure server profile";
           leaf name {
             description "Server profile name";
             type string {
               length "3 .. 32";
             }
           }
           uses apply-advanced;
           leaf transport-type {
             description "Transport type";
             type enumeration {
               enum "GRE" {
                 description "GRE";
               }
               enum "UDP" {
                 description "UDP";
               }
               enum "TCP" {
                 description "TCP";
               }
             }
           }
           leaf server-address {
             description "Server address";
             type jt:ipv4addr;
           }
           leaf client-address {
             description "Client address";
             type jt:ipv4addr;
           }
           leaf hosted-service-identifier {
             description "Identifier for the service performed in the remote server";
             type union {
               type string {
                 pattern "<.*>|$.*";
               }
               type int32 {
                 range "1 .. 63";
               }
             }
           }
         }
       }
       container jflow-log {
         presence "enable jflow-log";
         description "Configure jflow-logging parameters for services";
         uses apply-advanced;
         list collector {
           key name;
           ordered-by user;
           description "Collector attributes";
           leaf name {
             description "Profile name";
             type string {
               length "1 .. 63";
             }
           }
           uses apply-advanced;
           leaf destination-address {
             description "IPv4 Address or hostname of the collector";
             type string {
               junos:posix-pattern "^[[:alnum:]._-]+$";
               junos:pattern-message "Must be a string of letters, numbers, dashes or underscores";
             }
           }
           leaf destination-port {
             description "Destination port of the collector";
             type union {
               type string {
                 pattern "<.*>|$.*";
               }
               type uint16 {
                 range "1 .. 65535";
               }
             }
           }
           leaf source-ip {
             description "Source IPv4 Address from which logging is to be done";
             type jt:ipv4addr;
           }
         }
         list collector-group {
           key name;
           ordered-by user;
           leaf name {
             description "Name of collector-group";
             type string {
               length "1 .. 63";
             }
           }
           uses apply-advanced;
           leaf-list collector {
             ordered-by user;
             description "List of Collector profiles";
             type string {
               length "1 .. 63";
             }
             max-elements 8;
           }
         }
         list template-profile {
           key name;
           ordered-by user;
           leaf name {
             description "Specify name of the template";
             junos:must "((any \".. collector <*>\" || any \".. collector-group <*>\"))";
             junos:must-message "template-profile must have a collector or collector-group configured";
             type string {
               length "1 .. 63";
             }
           }
           uses apply-advanced;
           leaf collector {
             description "Specify a collector name";
             junos:must "(!(any \".. collector-group <*>\"))";
             junos:must-message "Collector-group is already configured for this template";
             junos:must "(\"services jflow-log collector $$\")";
             junos:must-message "The referenced collector is not defined";
             type string {
               length "1 .. 63";
             }
           }
           leaf-list collector-group {
             ordered-by user;
             description "Specify a collector-group name";
             junos:must "(!(any \".. collector <*>\"))";
             junos:must-message "Collector is already configured for this template profile";
             type string {
               length "1 .. 63";
             }
             max-elements 1;
           }
           leaf template-type {
             description "Allow jflow-log for applications";
             type enumeration {
               enum "nat" {
                 description "Enable jflow-logs for NAT events";
               }
             }
           }
           leaf version {
             description "Version of jflow-logging";
             type enumeration {
               enum "v9" {
                 description "Version 9";
               }
               enum "ipfix" {
                 description "Ipfix";
               }
             }
           }
           container refresh-rate {
             presence "enable refresh-rate";
             uses apply-advanced;
             leaf packets {
               description "Specify number of packets after which templates are sent to collector";
               default "4800";
               type union {
                 type string {
                   pattern "<.*>|$.*";
                 }
                 type uint32 {
                   range "1 .. 48000";
                 }
               }
             }
             leaf seconds {
               description "Specify number of seconds after which templates are sent to collector";
               default "1800";
               type union {
                 type string {
                   pattern "<.*>|$.*";
                 }
                 type uint32 {
                   range "10 .. 1800";
                 }
               }
             }
           }
         }
         container traceoptions {
           description "Trace options for JFLOW-LOG";
           uses apply-advanced;
           leaf no-remote-trace {
             description "Disable remote tracing";
             junos:must "(\"system tracing\")";
             junos:must-message "'no-remote-trace' is valid only when [system tracing] is configured";
             type empty;
           }
           container file {
             description "Trace file information";
             leaf filename {
               description "Name of file in which to write trace information";
               type string {
                 length "1 .. 1024";
                 junos:posix-pattern "![/ %]";
                 junos:pattern-message "Must not contain '/', % or a space";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "configuration" {
                   description "Trace configuration events";
                 }
                 enum "flow" {
                   description "Trace flow events";
                 }
                 enum "all" {
                   description "Trace everything";
                 }
               }
             }
           }
         }
       }
       container service-device-pools {
         description "Configure service device pools";
         uses apply-advanced;
         list pool {
           key name;
           ordered-by user;
           description "Define service device pool";
           uses service_device_pool_object;
         }
       }
       container redundancy-set {
         description "Redundancy-set settings";
         uses apply-advanced;
         container traceoptions {
           description "Services redundancy trace options";
           uses srd-traceoptions-object;
         }
         list rs-id-object {
           key name;
           ordered-by user;
           description "Definition of redundancy-set";
           uses srd-rs-id-object;
         }
       }
       container traffic-load-balance {
         description "Traffic load balance configuration";
         uses tdir_service_load_balance_object;
       }
       container network-monitoring {
         description "Network monitoring probe configuration";
         uses tdir_netmon_object;
       }
       container policies {
         uses policy-object-type;
       }
       list address-book {
         key name;
         ordered-by user;
         description "Services address book";
         max-elements 4096;
         uses named-address-book-type;
       }
       container traceoptions {
         description "Network security daemon tracing options";
         uses apply-advanced;
         leaf no-remote-trace {
           description "Disable remote tracing";
           junos:must "(\"system tracing\")";
           junos:must-message "'no-remote-trace' is valid only when [system tracing] is configured";
           type empty;
         }
         container file {
           description "Trace file information";
           leaf filename {
             description "Name of file in which to write trace information";
             type string {
               length "1 .. 1024";
               junos:posix-pattern "![/ %]";
               junos:pattern-message "Must not contain '/', % or a space";
             }
           }
           leaf size {
             description "Maximum trace file size";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           ordered-by user;
           description "Tracing parameters";
           leaf name {
             type enumeration {
               enum "configuration" {
                 description "Trace configuration events";
               }
               enum "routing-socket" {
                 description "Trace routing socket events";
               }
               enum "compilation" {
                 description "Trace compilation events";
               }
               enum "all" {
                 description "Trace everything";
               }
             }
           }
         }
         leaf rate-limit {
           description "Limit the incoming rate of trace messages";
           default "0";
           type union {
             type string {
               pattern "<.*>|$.*";
             }
             type uint32 {
               range "0 .. 4294967295";
             }
           }
         }
       }
       container web-filter {
         description "Web Filtering service configuration";
         uses apply-advanced;
         list profile {
           key name;
           ordered-by user;
           description "Web Filter profile";
           max-elements 8;
           uses urlf-profile-object;
         }
         container traceoptions {
           description "Trace options for Web Filter ";
           uses urlf-traceoptions-object;
         }
       }
     }
   }
   grouping aacl_rule_object {
     leaf name {
       description "Rule name";
       type string {
         length "1 .. 63";
         junos:posix-pattern "^[[:alnum:]][[:alnum:]_-]*$";
         junos:pattern-message "Must be a string beginning with a number or letter and consisting of letters, numbers, dashes and underscores.";
       }
     }
     uses apply-advanced;
     leaf dynamic {
       description "Make rule dynamic";
       junos:must "(!(\".. term\"))";
       junos:must-message "term can't be combined with dynamic";
       junos:must "(!(\".. match-direction\"))";
       junos:must-message "match-direction can't be combined with dynamic";
       type empty;
     }
     leaf match-direction {
       description "Direction for which the rule match is applied";
       type enumeration {
         enum "input" {
           description "Match on input to interface";
         }
         enum "output" {
           description "Match on output from interface";
         }
         enum "input-output" {
           description "Match on input to or output from interface";
         }
       }
     }
     list term {
       key name;
       ordered-by user;
       description "One or more terms in AACL rule";
       leaf name {
         description "Term name";
         type string {
           length "1 .. 63";
           junos:posix-pattern "^[[:alnum:]][[:alnum:]_-]*$";
           junos:pattern-message "Must be a string beginning with a number or letter and consisting of letters, numbers, dashes and underscores.";
         }
       }
       uses apply-advanced;
       container from {
         description "Match criteria";
         uses aacl_match_object;
       }
       container then {
         description "Action to take if the 'from' condition is matched";
         uses apply-advanced;
         leaf forwarding-class {
           description "Forwarding class assigned to outgoing packets";
           junos:must "(!(\".. discard\"))";
           junos:must-message "Forwarding class must not be combined with Discard";
           junos:must "(\".. accept\")";
           junos:must-message "Forwarding class must be combined with Accept";
           type string {
             junos:posix-pattern "^.{1,64}$";
             junos:pattern-message "Must be string of 64 characters or less";
           }
         }
         leaf count {
           description "Count packets by application or Application group";
           junos:must "(!(\".. discard\"))";
           junos:must-message "Count must not be combined with Discard";
           junos:must "(\".. accept\")";
           junos:must-message "Count must be combined with Accept";
           type enumeration {
             enum "none" {
               description "Do not count any application or group";
             }
             enum "application" {
               description "Count by application name";
             }
             enum "application-group" {
               description "Count by application group";
               junos:must "((!(\".. .. from applications\") && (!(\".. .. from nested-applications\") && (!(\".. .. from application-unknown\") && !(\".. .. from nested-application-unknown\")))))";
               junos:must-message "Count application-group only applies to application-group match";
             }
             enum "application-group-any" {
               description "Count all application groups as a single total in group 'any'";
               junos:must "(\".. .. from application-group-any\")";
               junos:must-message "Count application-group-any only applies to rule application-group-any";
             }
             enum "nested-application" {
               description "Count by nested application name";
             }
           }
         }
         leaf log {
           description "Log session information for this application match";
           junos:must "(\" .. .. .. match-direction input-output\")";
           junos:must-message "Log session must be with match-direction input-output only";
           type enumeration {
             enum "none" {
               description "Do not log session information";
             }
             enum "session-start" {
               description "Log session start information for this match";
             }
             enum "session-start-end" {
               description "Log session start/end information for this match";
             }
             enum "session-start-end-no-stats" {
               description "Log session start/end information with no stats";
             }
             enum "session-start-interim-end" {
               description "Log session start/interim/end information for this match";
               junos:must "(!(\".. discard\"))";
               junos:must-message "Interim stats not allowed with discard action";
             }
             enum "session-interim-end" {
               description "Log session interim/end information for this match";
               junos:must "(!(\".. discard\"))";
               junos:must-message "Interim stats not allowed with discard action";
             }
             enum "session-end" {
               description "Log session end information for this match";
             }
           }
         }
         leaf police {
           description "Policer name";
           junos:must "(!(\".. discard\"))";
           junos:must-message "Police must not be combined with Discard";
           junos:must "(\".. accept\")";
           junos:must-message "Police must be combined with Accept";
           junos:must "(\"firewall policer $$\")";
           junos:must-message "referenced firewall policer must be defined";
           type string {
             junos:posix-pattern "^.{1,64}$";
             junos:pattern-message "Must be string of 64 characters or less";
           }
         }
         choice designation {
           case case_1 {
             leaf accept {
               description "Accept the packet";
               type empty;
             }
           }
           case case_2 {
             leaf discard {
               description "Discard the packet";
               type empty;
             }
           }
         }
       }
     }
   }
   grouping aacl_match_object {
     uses apply-advanced;
     list source-address {
       key name;
       ordered-by user;
       description "Match IP source address";
       uses sfw_addr_object;
     }
     list destination-address {
       key name;
       ordered-by user;
       description "Match IP destination address";
       uses sfw_addr_object;
     }
     list source-address-range {
       key "low high";
       ordered-by user;
       description "Match IP source address range";
       leaf low {
         description "Lower limit of address range";
         type jt:ipaddr;
       }
       leaf high {
         description "Upper limit of address range";
         type jt:ipaddr;
       }
       leaf except {
         description "Match address not in this prefix";
         type empty;
       }
     }
     list source-prefix-list {
       key name;
       ordered-by user;
       description "One or more named lists of source prefixes to match";
       leaf name {
         description "Name of prefix list to match against";
         type string;
       }
       leaf except {
         description "Name of prefix list not to match against";
         type empty;
       }
     }
     list destination-address-range {
       key "low high";
       ordered-by user;
       description "Match IP destination address range";
       leaf low {
         description "Lower limit of address range";
         type jt:ipaddr;
       }
       leaf high {
         description "Upper limit of address range";
         type jt:ipaddr;
       }
       leaf except {
         description "Match address not in this prefix";
         type empty;
       }
     }
     list destination-prefix-list {
       key name;
       ordered-by user;
       description "One or more named lists of destination prefixes to match";
       leaf name {
         description "Name of prefix list to match against";
         type string;
       }
       leaf except {
         description "Name of prefix list not to match against";
         type empty;
       }
     }
     choice app-rule {
       case case_1 {
         leaf application-group-any {
           description "Use to wildcard or match any application group";
           type empty;
         }
       }
       case case_2 {
         leaf application-unknown {
           description "Use to specify unknown application as the match criteria.";
           type empty;
         }
       }
       case case_3 {
         leaf nested-application-unknown {
           description "Use to specify unknown nested application as the match criteria.";
           type empty;
         }
       }
       case case_4 {
         leaf-list applications {
           ordered-by user;
           description "Match one or more applications";
           type string;
         }
       }
       case case_5 {
         leaf-list nested-applications {
           ordered-by user;
           description "Match one or more nested-applications";
           type string;
         }
       }
       case case_6 {
         leaf-list application-groups {
           ordered-by user;
           description "Match one or more applications";
           type string;
         }
       }
     }
   }
   grouping aamwd-traceoptions {
     description "Advanced anti-malware trace options";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Trace flags";
       leaf name {
         type enumeration {
           enum "all" {
             description "Trace everything";
           }
           enum "connection" {
             description "Trace the connection to server";
           }
           enum "content" {
             description "Trace the content buffer management";
           }
           enum "daemon" {
             description "Trace advanced-anti-malware daemon";
           }
           enum "http" {
             description "Trace http protocol operations";
           }
           enum "identification" {
             description "Trace file identification";
           }
           enum "imap" {
             description "Trace imap protocol operations";
           }
           enum "parser" {
             description "Trace protocol context parser";
           }
           enum "plugin" {
             description "Trace advanced-anti-malware plugin";
           }
           enum "policy" {
             description "Trace advanced-anti-malware policy";
           }
           enum "smtp" {
             description "Trace smtp protocol operations";
           }
         }
       }
     }
   }
   grouping action-object-type {
     uses apply-advanced;
     container preferred-route {
       description "Preferred route action";
       uses apply-advanced;
       list routing-instances {
         key name;
         ordered-by user;
         description "Routing-instance";
         leaf name {
           type string;
         }
         uses apply-advanced;
         list route {
           key name;
           ordered-by user;
           description "Route";
           leaf name {
             type jt:ipprefix;
           }
           uses apply-advanced;
           choice next_hop {
             case case_1 {
               leaf-list next-hop {
                 ordered-by user;
                 description "Next hop to destination of route-action";
                 type union {
                   type jt:ipaddr-or-interface;
                   type string {
                     pattern "<.*>|$.*";
                   }
                 }
               }
             }
             case case_2 {
               leaf discard {
                 description "Drop packets to destination; send no ICMP unreachables";
                 type empty;
               }
             }
           }
           leaf preferred-metric {
             description "Preferred metric value assigned to route action";
             type union {
               type string {
                 pattern "<.*>|$.*";
               }
               type uint32 {
                 range "1 .. 255";
               }
             }
           }
         }
       }
       list route {
         key name;
         ordered-by user;
         description "Route";
         leaf name {
           type jt:ipprefix;
         }
         uses apply-advanced;
         choice next_hop {
           case case_1 {
             leaf-list next-hop {
               ordered-by user;
               description "Next hop to destination of route-action";
               type union {
                 type jt:ipaddr-or-interface;
                 type string {
                   pattern "<.*>|$.*";
                 }
               }
             }
           }
           case case_2 {
             leaf discard {
               description "Drop packets to destination; send no ICMP unreachables";
               type empty;
             }
           }
         }
         leaf preferred-metric {
           description "Preferred metric value assigned to route action";
           type union {
             type string {
               pattern "<.*>|$.*";
             }
             type uint32 {
               range "1 .. 255";
             }
           }
         }
       }
     }
     list interface {
       key name;
       ordered-by user;
       description "Interface enabling/disabling action";
       leaf name {
         type union {
           type jt:interface-wildcard;
           type string {
             pattern "<.*>|$.*";
           }
         }
       }
       uses apply-advanced;
       choice action {
         case case_1 {
           leaf enable {
             description "Enable interface";
             type empty;
           }
         }
         case case_2 {
           leaf disable {
             description "Disable interface";
             type empty;
           }
         }
       }
     }
   }
   grouping address-filter-type {
     description "IP address filter";
     uses apply-advanced;
     leaf address-book {
       description "Referenced address book";
       type string;
     }
     leaf address-set {
       description "Referenced address set";
       type string {
         length "1 .. 63";
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping bgp-logical-system {
     description "Logical systems configuration for rpm";
     leaf name {
       description "Logical system name";
       type string {
         junos:posix-pattern "![^a-zA-Z0-9_-]|(^(all|.{64,})$)";
         junos:pattern-message "Logical-system name is a string consisting of up to 63 letters, numbers, dashes and underscores";
       }
     }
     uses apply-advanced;
     list routing-instances {
       key name;
       description "Routing instances";
       uses bgp-routing-instances;
     }
   }
   grouping bgp-routing-instances {
     description "Routing-instance configuration for rpm";
     leaf name {
       description "Routing instance name";
       type string;
     }
     uses apply-advanced;
   }
   grouping collector_destinations_type {
     leaf name {
       description "FTP destination URL (allows {text} macros)";
       type string;
     }
     uses apply-advanced;
     leaf password {
       description "Password for accessing URL";
       type jt:unreadable;
     }
   }
   grouping collector_transfer_log_archive_type {
     uses apply-advanced;
     leaf filename-prefix {
       description "Filename prefix for transfer log";
       type string {
         junos:posix-pattern "^[.A-Za-z0-9_-]{1,32}$";
         junos:pattern-message "Filename prefix is a string consisting of up to 32 letters, numbers, dashes, points and underscores";
       }
     }
     leaf maximum-age {
       description "Maximum age of transfer log file";
       default "15";
       units "minutes";
       type union {
         type string {
           pattern "<.*>|$.*";
         }
         type uint32 {
           range "1 .. 360";
         }
       }
     }
     list archive-sites {
       key name;
       ordered-by user;
       max-elements 5;
       leaf name {
         description "Primary and failover URLs to receive archive files";
         type string;
       }
       leaf password {
         description "Password to log in to the archive site";
         type jt:unreadable;
       }
     }
   }
   grouping cos-object {
     description "Class of Service services configuration";
     uses apply-advanced;
     container traceoptions {
       description "NAT trace options";
       uses apply-advanced;
       leaf no-remote-trace {
         description "Disable remote tracing";
         junos:must "(\"system tracing\")";
         junos:must-message "'no-remote-trace' is valid only when [system tracing] is configured";
         type empty;
       }
       container file {
         description "Trace file information";
         leaf filename {
           description "Name of file in which to write trace information";
           type string {
             length "1 .. 1024";
             junos:posix-pattern "![/ %]";
             junos:pattern-message "Must not contain '/', % or a space";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing parameters";
         leaf name {
           type enumeration {
             enum "configuration" {
               description "Trace configuration events";
             }
             enum "all" {
               description "Trace everything";
             }
             enum "cos-application-profile" {
               description "Trace cos application profile events on RE side";
             }
             enum "cos-rule-compilation" {
               description "Trace cos rule events on RE side";
             }
             enum "cos-ipc" {
               description "Trace cos rule events on PFE-RT side";
             }
             enum "cos-svc-set" {
               description "Trace cos and svc-set events on RE side";
             }
           }
         }
         leaf syslog {
           description "Write cos flow traces to system log also";
           type empty;
         }
       }
     }
     list application-profile {
       key name;
       ordered-by user;
       description "One or more CoS application profiles";
       uses cos_application_profile_object;
     }
     list rule {
       key name;
       ordered-by user;
       description "One or more CoS rules";
       uses cos_rule_object;
     }
     list rule-set {
       key name;
       ordered-by user;
       description "Define a Set of CoS rules";
       max-elements 16960;
       leaf name {
         description "Name of the rule set";
         type string {
           length "1 .. 63";
           junos:posix-pattern "^[[:alnum:]][[:alnum:]_-]*$";
           junos:pattern-message "Must be a string beginning with a number or letter and consisting of letters, numbers, dashes and underscores.";
         }
       }
       uses apply-advanced;
       list rule {
         key name;
         ordered-by user;
         description "Rule to be included in this rule set";
         max-elements 16960;
         leaf name {
           description "Rule name";
           junos:must "(\"services cos rule $$\")";
           junos:must-message "rule must be configured";
           type string {
             junos:posix-pattern "^[A-Za-z0-9][_0-9A-Za-z-]{0,62}$";
             junos:pattern-message "Must be a string beginning with a number or letter and consisting of no more than 63 total letters, numbers, dashes and underscores.";
           }
         }
         uses apply-advanced;
       }
     }
   }
   grouping cos_application_profile_object {
     leaf name {
       description "Profile name";
       type string {
         length "1 .. 63";
         junos:posix-pattern "^[[:alnum:]][[:alnum:]_-]*$";
         junos:pattern-message "Must be a string beginning with a number or letter and consisting of letters, numbers, dashes and underscores.";
       }
     }
     uses apply-advanced;
     container sip {
       presence "enable sip";
       description "CoS treatment of Session Initiation Protocol data";
       uses apply-advanced;
       container voice {
         presence "enable voice";
         description "CoS treatment of SIP voice data";
         uses apply-advanced;
         leaf dscp {
           description "Code point alias or bit string";
           type string {
             junos:posix-pattern "^(([01]{6})|([a-zA-Z].{0,63}))$";
             junos:pattern-message "Not 6-bit pattern or code point alias";
           }
         }
         leaf forwarding-class {
           description "Forwarding class assigned to outgoing packets";
           type string {
             junos:posix-pattern "^.{1,64}$";
             junos:pattern-message "Must be string of 64 characters or less";
           }
         }
       }
       container video {
         presence "enable video";
         description "CoS treatment of SIP video data";
         uses apply-advanced;
         leaf dscp {
           description "Code point alias or bit string";
           type string {
             junos:posix-pattern "^(([01]{6})|([a-zA-Z].{0,63}))$";
             junos:pattern-message "Not 6-bit pattern or code point alias";
           }
         }
         leaf forwarding-class {
           description "Forwarding class assigned to outgoing packets";
           type string {
             junos:posix-pattern "^.{1,64}$";
             junos:pattern-message "Must be string of 64 characters or less";
           }
         }
       }
     }
     container ftp {
       presence "enable ftp";
       description "CoS treatment for FTP data";
       uses apply-advanced;
       container data {
         presence "enable data";
         uses apply-advanced;
         leaf dscp {
           description "Code point alias or bit string";
           type string {
             junos:posix-pattern "^(([01]{6})|([a-zA-Z].{0,63}))$";
             junos:pattern-message "Not 6-bit pattern or code point alias";
           }
         }
         leaf forwarding-class {
           description "Forwarding class assigned to outgoing packets";
           type string {
             junos:posix-pattern "^.{1,64}$";
             junos:pattern-message "Must be string of 64 characters or less";
           }
         }
       }
     }
   }
   grouping cos_rule_object {
     leaf name {
       description "Rule name";
       type string {
         length "1 .. 63";
         junos:posix-pattern "^[[:alnum:]][[:alnum:]_-]*$";
         junos:pattern-message "Must be a string beginning with a number or letter and consisting of letters, numbers, dashes and underscores.";
       }
     }
     uses apply-advanced;
     leaf match-direction {
       description "Direction for which the rule match is applied";
       type enumeration {
         enum "input" {
           description "Match on input to interface";
         }
         enum "output" {
           description "Match on output from interface";
         }
         enum "input-output" {
           description "Match on input to or output from interface";
         }
       }
     }
     list term {
       key name;
       ordered-by user;
       description "One or more terms in CoS rule";
       leaf name {
         description "Term name";
         type string {
           length "1 .. 63";
           junos:posix-pattern "^[[:alnum:]][[:alnum:]_-]*$";
           junos:pattern-message "Must be a string beginning with a number or letter and consisting of letters, numbers, dashes and underscores.";
         }
       }
       uses apply-advanced;
       container from {
         description "Match criteria";
         uses sfw_match_object;
       }
       container then {
         description "Action to take if the 'from' condition is matched";
         uses apply-advanced;
         leaf dscp {
           description "Code point alias or bit string";
           type string {
             junos:posix-pattern "^(([01]{6})|([a-zA-Z].{0,63}))$";
             junos:pattern-message "Not 6-bit pattern or code point alias";
           }
         }
         leaf forwarding-class {
           description "Forwarding class assigned to outgoing packets";
           type string {
             junos:posix-pattern "^.{1,64}$";
             junos:pattern-message "Must be string of 64 characters or less";
           }
         }
         leaf application-profile {
           description "CoS application profile";
           junos:must "(\"services cos application-profile $$\")";
           junos:must-message "referenced cos profile must be defined";
           type string {
             junos:posix-pattern "^.{1,64}$";
             junos:pattern-message "Must be string of 64 characters or less";
           }
         }
         leaf syslog {
           description "System log information about the packet";
           type empty;
         }
         choice designation {
           case case_1 {
             leaf reflexive {
               description "Apply mirror rule to reverse traffic";
               type empty;
             }
           }
           case case_2 {
             leaf revert {
               description "Apply received COS values to reverse traffic";
               type empty;
             }
           }
           case case_3 {
             container reverse {
               presence "enable reverse";
               description "CoS treatment for reverse traffic";
               uses apply-advanced;
               leaf dscp {
                 description "Code point alias or bit string";
                 type string {
                   junos:posix-pattern "^(([01]{6})|([a-zA-Z].{0,63}))$";
                   junos:pattern-message "Not 6-bit pattern or code point alias";
                 }
               }
               leaf forwarding-class {
                 description "Forwarding class assigned to outgoing packets";
                 type string {
                   junos:posix-pattern "^.{1,64}$";
                   junos:pattern-message "Must be string of 64 characters or less";
                 }
               }
               leaf application-profile {
                 description "CoS application profile";
                 junos:must "(\"services cos application-profile $$\")";
                 junos:must-message "referenced cos profile must be defined";
                 type string {
                   junos:posix-pattern "^.{1,64}$";
                   junos:pattern-message "Must be string of 64 characters or less";
                 }
               }
               leaf syslog {
                 description "System log information about the packet";
                 type empty;
               }
             }
           }
         }
       }
     }
   }
   grouping cpcd-rule-object-type {
     leaf name {
       description "Rule name";
       type string {
         length "1 .. 63";
         junos:posix-pattern "^[[:alnum:]][[:alnum:]_-]*$";
         junos:pattern-message "Must be a string beginning with a number or letter and consisting of letters, numbers, dashes and underscores.";
       }
     }
     uses apply-advanced;
     leaf match-direction {
       description "Direction for which the rule match is applied";
       type enumeration {
         enum "input" {
           description "Match on input to interface";
         }
         enum "output" {
           description "Match on output from interface";
         }
         enum "input-output" {
           description "Match on input to or output from interface";
         }
       }
     }
     list term {
       key name;
       ordered-by user;
       description "Define a captive portal content delivery term";
       leaf name {
         description "Term name";
         type string {
           length "1 .. 63";
           junos:posix-pattern "^[[:alnum:]][[:alnum:]_-]*$";
           junos:pattern-message "Must be a string beginning with a number or letter and consisting of letters, numbers, dashes and underscores.";
         }
       }
       uses apply-advanced;
       container from {
         description "Define match criteria";
         uses cpcd-match-object-type;
       }
       container then {
         description "Action to take if the 'from' condition is matched";
         uses cpcd-action-object-type;
       }
     }
   }
   grouping cpcd-action-object-type {
     uses apply-advanced;
     choice designation {
       case case_1 {
         leaf accept {
           description "Accept the packet";
           type empty;
         }
       }
       case case_2 {
         container rewrite {
           presence "enable rewrite";
           description "Rewrite the IP-DA of the packet";
           uses apply-advanced;
           leaf destination-address {
             description "The destination IP address";
             type jt:ipaddr;
           }
           leaf destination-port {
             description "The destination port";
             type union {
               type string {
                 pattern "<.*>|$.*";
               }
               type uint16 {
                 range "1 .. 65535";
               }
             }
           }
         }
       }
       case case_3 {
         container redirect {
           presence "enable redirect";
           description "Redirect the http packet";
           leaf url {
             description "URL of the captive portal file";
             type string {
               junos:posix-pattern "^((http)|(https)):";
               junos:pattern-message "URL must start with http or https";
             }
           }
         }
       }
     }
     leaf syslog {
       description "System log information about the packet";
       type empty;
     }
   }
   grouping cpcd-match-object-type {
     uses apply-advanced;
     list destination-address {
       key name;
       ordered-by user;
       description "Match IP destination address";
       leaf name {
         description "Match IP address";
         type string;
       }
       leaf except {
         description "Match address not in this prefix";
         type empty;
       }
     }
     list destination-address-range {
       key "low high";
       ordered-by user;
       description "Match IP destination address range";
       leaf low {
         description "Lower limit of address range";
         type jt:ipaddr;
       }
       leaf high {
         description "Upper limit of address range";
         type jt:ipaddr;
       }
       leaf except {
         description "Match address not in this prefix";
         type empty;
       }
     }
     list destination-prefix-list {
       key name;
       ordered-by user;
       description "One or more named lists of destination prefixes to match";
       leaf name {
         description "Name of prefix list to match against";
         junos:must "(\"policy-options prefix-list $$\")";
         junos:must-message "referenced policy-options prefix-list must be defined";
         type string;
       }
       leaf except {
         description "Name of prefix list not to match against";
         type empty;
       }
     }
     list applications {
       key name;
       ordered-by user;
       description "Match one or more applications";
       leaf name {
         type string {
           length "1 .. 63";
           junos:posix-pattern "^[[:alnum:]][[:alnum:]_-]*$";
           junos:pattern-message "Must be a string beginning with a number or letter and consisting of letters, numbers, dashes and underscores.";
         }
       }
       uses apply-advanced;
       leaf application-protocol {
         description "Application protocol type";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
         }
       }
       leaf protocol {
         description "Match IP protocol type";
         type string;
       }
       leaf source-port {
         description "Match TCP/UDP source port";
         type string;
       }
       leaf destination-port {
         description "Match TCP/UDP destination port";
         type string;
       }
     }
   }
   grouping cpcd-trace-options-type {
     description "Trace options for captive portal and content delivery service";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Captive portal operations to include in debugging trace";
       leaf name {
         type enumeration {
           enum "configuration" {
             description "Configuration operations";
           }
           enum "clicommand" {
             description "Cli command operations";
           }
           enum "general" {
             description "Miscellaneous operations";
           }
           enum "rtsock" {
             description "Routing socket operations";
           }
           enum "statistics" {
             description "Statistics operations";
           }
           enum "rules" {
             description "Rules operations";
           }
           enum "ssets" {
             description "Service sets operations";
           }
           enum "ipc" {
             description "RE-PIC operations";
           }
           enum "gres" {
             description "GRES operations";
           }
           enum "re-services" {
             description "RE Service Operations";
           }
           enum "re-svc-debug-stat" {
             description "RE Service debug stats";
           }
           enum "all" {
             description "All operations";
           }
         }
       }
     }
   }
   grouping dfc_group_type {
     description "Configure DFC group parameters";
     leaf name {
       description "DFC group name";
       type string {
         length "1 .. 64";
       }
     }
     uses apply-advanced;
     leaf-list interfaces {
       ordered-by user;
       description "DFC PIC(s) in this group";
       type union {
         type jt:interface-device;
         type string {
           pattern "<.*>|$.*";
         }
       }
       max-elements 1;
     }
     leaf input-packet-rate-threshold {
       description " Input pps (max 300k on MO-III, 1M on MS-400)";
       default "1024000";
       units "pps";
       type string;
     }
     leaf max-duplicates {
       description "Maximum content destinations for the capture group";
       type union {
         type string {
           pattern "<.*>|$.*";
         }
         type uint32 {
           range "1 .. 64";
         }
       }
     }
     leaf duplicates-dropped-periodicity {
       description "Periodicity of DuplicatesDropped notification in secs";
       type union {
         type string {
           pattern "<.*>|$.*";
         }
         type uint32 {
           range "1 .. 255";
         }
       }
     }
     container pic-memory-threshold {
       description "PIC memory threshold";
       leaf percentage {
         description "Threshold in percentage";
         units "percent";
         type union {
           type string {
             pattern "<.*>|$.*";
           }
           type uint32 {
             range "10 .. 100";
           }
         }
       }
     }
     list control-source {
       key name;
       ordered-by user;
       description "Configure control source parameters";
       max-elements 64;
       uses dfc_control_source_type;
     }
     list content-destination {
       key name;
       ordered-by user;
       description "Configure content destination parameters";
       max-elements 64;
       uses content_destination_type;
     }
   }
   grouping content_destination_type {
     leaf name {
       description "Content destination identifier";
       type string {
         length "1 .. 48";
       }
     }
     uses apply-advanced;
     leaf address {
       description "Content destination IP address";
       type jt:ipv4addr;
     }
     leaf ttl {
       description "Time to live";
       default "255";
       type union {
         type string {
           pattern "<.*>|$.*";
         }
         type uint32 {
           range "1 .. 255";
         }
       }
     }
     leaf soft-limit-clear {
       description "Soft limit clear threshold";
       units "bps";
       junos:must "(\".. soft-limit\")";
       junos:must-message "soft limit threshold must be configured for the content destination";
       type string;
     }
     leaf soft-limit {
       description "Soft limit threshold";
       units "bps";
       junos:must "(\".. soft-limit-clear\")";
       junos:must-message "soft limit clear threshold must be configured for the content destination";
       type string;
     }
     leaf hard-limit-target {
       description "Hard limit target threshold";
       units "bps";
       junos:must "(\".. hard-limit\")";
       junos:must-message "hard limit threshold must be configured for the content destination";
       type string;
     }
     leaf hard-limit {
       description "Hard limit threshold";
       units "bps";
       junos:must "(\".. hard-limit-target\")";
       junos:must-message "hard limit target threshold must be configured for the content destination";
       type string;
     }
   }
   grouping dfc_control_source_type {
     leaf name {
       description "Control source identifier";
       type string {
         length "1 .. 48";
       }
     }
     uses apply-advanced;
     leaf-list source-addresses {
       ordered-by user;
       description "Allowed control source IP address list";
       type jt:ipv4addr;
       max-elements 8;
     }
     leaf service-port {
       description "Service port";
       type union {
         type uint16;
         type string {
           pattern "<.*>|$.*";
         }
       }
     }
     list notification-targets {
       key name;
       description "Notification target list";
       max-elements 8;
       uses dfc_notification_target_type;
     }
     leaf no-syslog {
       description "Disable syslog";
       type empty;
     }
     leaf shared-key {
       description "Shared key with control source";
       type string {
         length "1 .. 20";
       }
     }
     leaf-list allowed-destinations {
       ordered-by user;
       description "Allowed destinations";
       type string {
         length "1 .. 48";
       }
       max-elements 16;
     }
     leaf minimum-priority {
       description "Minimum priority of the control source";
       default "0";
       type union {
         type string {
           pattern "<.*>|$.*";
         }
         type uint32 {
           range "0 .. 255";
         }
       }
     }
   }
   grouping dfc_notification_target_type {
     leaf name {
       description "Notification target IP address";
       type jt:ipv4addr;
     }
     uses apply-advanced;
     leaf port {
       description "Notification target port";
       type union {
         type uint16;
         type string {
           pattern "<.*>|$.*";
         }
       }
     }
   }
   grouping drop-policy-term {
     description "One or more drop terms";
     leaf name {
       description "Term name";
       type string {
         junos:posix-pattern "^.{1,64}$";
         junos:pattern-message "Must be string of 64 characters or less";
       }
     }
     uses apply-advanced;
     container from {
       description "Define match criteria";
       uses apply-advanced;
       container source-address {
         description "Source IP Address";
         uses li_policy_addr_simple_object;
       }
       container destination-address {
         description "Destination IP Address";
         uses li_policy_addr_simple_object;
       }
       choice source-port_choice {
         case case_1 {
           container source-port {
             description "Match source port";
             uses match_li_simple_port_value;
           }
         }
       }
       choice destination-port_choice {
         case case_1 {
           container destination-port {
             description "Match destination port";
             uses match_li_simple_port_value;
           }
         }
       }
       choice protocol_choice {
         case case_1 {
           container protocol {
             description "Match IP protocol type";
             uses match_li_simple_protocol_value;
           }
         }
       }
       choice dscp_choice {
         case case_1 {
           container dscp {
             description "Match Differentiated Services (DiffServ) code point";
             uses match_li_simple_dscp_value;
           }
         }
       }
     }
   }
   grouping drop-policy6-term {
     description "One or more drop terms";
     leaf name {
       description "Term name";
       type string {
         junos:posix-pattern "^.{1,64}$";
         junos:pattern-message "Must be string of 64 characters or less";
       }
     }
     uses apply-advanced;
     container from {
       description "Define match criteria";
       uses apply-advanced;
       container source-address {
         description "Source IPv6 Address or Prefix";
         uses li_policy_addr6_simple_object;
       }
       container destination-address {
         description "Destination IPv6 Address or Prefix";
         uses li_policy_addr6_simple_object;
       }
       choice source-port_choice {
         case case_1 {
           container source-port {
             description "Match source port";
             uses match_li_simple_port_value;
           }
         }
       }
       choice destination-port_choice {
         case case_1 {
           container destination-port {
             description "Match destination port";
             uses match_li_simple_port_value;
           }
         }
       }
       choice protocol_choice {
         case case_1 {
           container protocol {
             description "Match IP protocol type";
             uses match_li_simple_protocol_value;
           }
         }
       }
       choice dscp_choice {
         case case_1 {
           container dscp {
             description "Match Differentiated Services (DiffServ) code point";
             uses match_li_simple_dscp_value;
           }
         }
       }
     }
   }
   grouping dslite_object {
     leaf name {
       description "DS-Lite concentrator name";
       type string {
         length "1 .. 63";
         junos:posix-pattern "^[[:alnum:]][[:alnum:]_-]*$";
         junos:pattern-message "Must be a string beginning with a number or letter and consisting of letters, numbers, dashes and underscores.";
       }
     }
     uses apply-advanced;
     leaf softwire-address {
       description "Softwire concentrator address";
       type jt:ipv6addr;
     }
     leaf mtu-v6 {
       description "MTU for the softwire tunnel";
       type union {
         type string {
           pattern "<.*>|$.*";
         }
         type uint32 {
           range "1280 .. 9192";
         }
       }
     }
     leaf copy-dscp {
       description "Copy DSCP (type of service) from IPv6 to IPv4 header";
       type empty;
     }
     leaf auto-update-mtu {
       description "Auto update MTU from received ICMPv6 messages";
       type empty;
     }
     leaf flow-limit {
       description "Max Number of IPv4 flows per Softwire";
       default "0";
       type union {
         type string {
           pattern "<.*>|$.*";
         }
         type uint32 {
           range "0 .. 16384";
         }
       }
     }
     leaf session-limit-per-prefix {
       description "Max number of sessions allowed per Softwire prefix";
       default "0";
       junos:must "(!(\".. flow-limit\"))";
       junos:must-message "Cannot configure both flow-limit and session-limit-per-prefix in same softwire-concentrator";
       type union {
         type string {
           pattern "<.*>|$.*";
         }
         type uint32 {
           range "0 .. 16384";
         }
       }
     }
   }
   grouping family {
     container inet {
       description "IPv4 parameters";
       uses apply-advanced;
       choice if-addr {
         case case_1 {
           leaf dhcp {
             description "Enable DHCP on ethernet interface";
             type empty;
           }
         }
         case case_2 {
           leaf address {
             description "Interface address/destination prefix";
             type jt:ipv4prefix;
           }
         }
       }
     }
   }
   grouping file_specification_type {
     leaf name {
       description "Name for file type";
       type string;
     }
     uses apply-advanced;
     leaf name-format {
       description "Format string for filename (allows {text} macros)";
       type string;
     }
     leaf data-format {
       description "Data format for flow collection output";
       type enumeration {
         enum "flow-compressed" {
           description "Flow format (compressed)";
         }
       }
     }
     container transfer {
       leaf timeout {
         description "Timeout in seconds when the file is transferred";
         default "600";
         type union {
           type string {
             pattern "<.*>|$.*";
           }
           type uint32 {
             range "60 .. 1800";
           }
         }
       }
       leaf record-level {
         description "Number of records at which the file is transferred";
         default "500000";
         type union {
           type string {
             pattern "<.*>|$.*";
           }
           type uint32 {
             range "10000 .. 1000000";
           }
         }
       }
     }
   }
   grouping gateway_type {
     leaf name {
       description "Gateway name";
       type string;
     }
     uses apply-advanced;
     leaf service-interface {
       description "Associated services interface";
       junos:must "(\"interfaces $$\")";
       junos:must-message "Interface must be defined in the interfaces hierarchy";
       type union {
         type jt:interface-device;
         type string {
           pattern "<.*>|$.*";
         }
       }
     }
     container sip {
       presence "enable sip";
       uses apply-advanced;
       container timers {
         description "Timers configuration";
         uses sip_timers_type;
       }
       list new-transaction-policy {
         key name;
         ordered-by user;
         description "Definition of a new-transaction policy";
         max-elements 500;
         uses transaction_policy_type;
       }
       list new-transaction-policy-set {
         key name;
         ordered-by user;
         description "Definition of a new-transaction policy set";
         max-elements 5;
         uses new_transaction_set_type;
       }
       list new-registration-policy {
         key name;
         ordered-by user;
         description "Definition of a new-registration policy";
         max-elements 500;
         uses registration_policy_type;
       }
       list new-registration-policy-set {
         key name;
         ordered-by user;
         description "Definition of a new-registration policy set";
         max-elements 5;
         uses new_registration_set_type;
       }
       list new-call-usage-policy {
         key name;
         ordered-by user;
         description "Definition of a new-call usage policy";
         max-elements 500;
         uses call_usage_policy_type;
       }
       list new-call-usage-policy-set {
         key name;
         ordered-by user;
         description "Definition of a new-call usage policy set";
         max-elements 5;
         uses new_call_usage_set_type;
       }
       container routing-destinations {
         description "Definition of routing destinations";
         uses routing-destinations;
       }
       container message-manipulation-rules {
         description "Definition of manipulation rules";
         uses header-manipulation-message-manipulation-rules-type;
       }
       leaf local-tag-prefix {
         description "Local tag prefix";
         default "bsg";
         type string;
       }
       list signaling-realms {
         key name;
         ordered-by user;
         description "Signaling realm";
         uses signaling-realm;
       }
       leaf local-uri-prefix {
         description "Local URI prefix";
         default "J";
         type string;
       }
     }
     list admission-control {
       key name;
       ordered-by user;
       description "Definition of an admission controller";
       max-elements 10;
       uses admission-control-type;
     }
     list service-point {
       key name;
       ordered-by user;
       max-elements 100;
       uses service_point_type;
     }
     container name-resolution-cache {
       uses name-resolution-cache-type;
     }
     container embedded-spdf {
       presence "enable embedded-spdf";
       uses apply-advanced;
       list service-class {
         key name;
         ordered-by user;
         description "Definition of service class policies";
         max-elements 5;
         leaf name {
           description "Service class name";
           type string {
             length "1 .. 63";
           }
         }
         uses apply-advanced;
         list term {
           key name;
           ordered-by user;
           description "Service class settings by media type";
           max-elements 6;
           leaf name {
             description "Term name";
             type string;
           }
           uses apply-advanced;
           container from {
             presence "enable from";
             description "The media-related filter that the rate limiting and DSCP marking are based on";
             uses apply-advanced;
             leaf-list media-type {
               ordered-by user;
               description "Media types to filter on";
               type enumeration {
                 enum "any-media" {
                 }
                 enum "audio" {
                 }
                 enum "video" {
                 }
               }
             }
           }
           container then {
             presence "enable then";
             description "The action to take based on the 'from' filter";
             uses apply-advanced;
             leaf reject {
               description "Reject the request";
               type empty;
             }
             leaf committed-information-rate {
               description "Committed information rate value per stream";
               default "0x7FFFFFFF";
               units "bytes-per-second";
               junos:must "(\".. committed-burst-size\")";
               junos:must-message "Committed Burst Size must also be defined";
               type union {
                 type string {
                   pattern "<.*>|$.*";
                 }
                 type uint32 {
                   range "0 .. 2147483647";
                 }
               }
             }
             leaf committed-burst-size {
               description "Committed burst size value per stream";
               default "0x7FFFFFFF";
               units "bytes";
               junos:must "(\".. committed-information-rate\")";
               junos:must-message "Committed Information Rate must also be defined";
               type union {
                 type string {
                   pattern "<.*>|$.*";
                 }
                 type uint32 {
                   range "20 .. 2147483647";
                 }
               }
             }
             leaf dscp {
               description "Code point alias or 6-bit pattern";
               default "be";
               type string {
                 junos:posix-pattern "^af[1-4][1-3]$|^be$|^cs[1-7]$|^ef$|^nc[1-2]|^[01]{6}$";
                 junos:pattern-message "Not a 6-bit pattern or code point alias";
               }
             }
           }
         }
       }
     }
     container traceoptions {
       description "Trace options for border signaling gateway";
       uses apply-advanced;
       container flag {
         presence "enable flag";
         description "Per-component trace options";
         uses apply-advanced;
         leaf minimum {
           description "Minimum trace level for all the components";
           default "error";
           type enumeration {
             enum "trace" {
               description "Trace functions entering and exiting";
             }
             enum "debug" {
               description "Trace code flow, branching, positive style guide check";
             }
             enum "info" {
               description "Summary logs for normal operations";
             }
             enum "warning" {
               description "Failure-recovery or Failure of an external entity";
             }
             enum "error" {
               description "Failure with short-term affect";
             }
           }
         }
         leaf session-trace {
           description "Trace level for the session tracing component";
           type enumeration {
             enum "trace" {
               description "Trace functions entering and exiting";
             }
             enum "debug" {
               description "Trace code flow, branching, positive style guide check";
             }
             enum "info" {
               description "Summary logs for normal operations";
             }
             enum "warning" {
               description "Failure-recovery or Failure of an external entity";
             }
             enum "error" {
               description "Failure with short-term affect";
             }
           }
         }
         container sip-stack {
           presence "enable sip-stack";
           description "Sip stack trace level options";
           uses apply-advanced;
           leaf event-tracing {
             description "Event tracing";
             type empty;
           }
           leaf ips-tracing {
             description "IPS tracing";
             type empty;
           }
           leaf per-tracing {
             description "Performance tracing";
             type empty;
           }
           leaf dev-logging {
             description "Development tracing";
             type empty;
           }
           leaf verbose-logging {
             description "Verbose tracing";
             type empty;
           }
           leaf pd-log-level {
             description "Set pd trace level";
             type enumeration {
               enum "problem" {
                 description "Record a problem";
               }
               enum "exception" {
                 description "Record and exception that has been encountered in the code";
               }
               enum "audit" {
                 description "Record ordinary events for accounting purposes";
               }
             }
           }
           leaf pd-log-detail {
             description "Set detail level for DC logs";
             type enumeration {
               enum "full" {
                 description "Full details for every entry";
               }
               enum "summary" {
                 description "Summary details for every entry";
               }
             }
           }
         }
         container signaling {
           presence "enable signaling";
           description "Signaling component sub-components";
           uses apply-advanced;
           leaf minimum {
             description "Minimum trace level for the signaling subcomponents";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf sip-stack-wrapper {
             description "Sip stack wrapper trace level ";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf b2b-wrapper {
             description "B2B wrapper trace level ";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf ua {
             description "UA trace level ";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf b2b {
             description "B2B trace level ";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf topology-hiding {
             description "Topology hiding trace level ";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf policy {
             description "Policy trace level ";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf name-resolution-cache {
             description "Name resolution cache trace level";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf accounting-trigger {
             description "Accounting trigger trace level";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf event-trigger {
             description "Event trigger trace level";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf packet-capture {
             description "Packet capture trace level";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
         }
         container framework {
           presence "enable framework";
           description "Framework component sub-components";
           uses apply-advanced;
           leaf minimum {
             description "Minimum trace level for the framework subcomponents";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf executor {
             description "Executor trace level ";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf action {
             description "Action trace level ";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf event {
             description "Event trace level ";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf freezer {
             description "Freezer trace level ";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf memory-pool {
             description "Memory pool trace level ";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
         }
         container datastore {
           presence "enable datastore";
           description "Datastore component sub-components";
           uses apply-advanced;
           leaf minimum {
             description "Minimum trace level for the datastore subcomponents";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf data {
             description "Data trace level ";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf handle {
             description "Handle trace level ";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf db {
             description "DB trace level ";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
         }
         container sbc-utils {
           presence "enable sbc-utils";
           description "SBC utils component sub-components";
           uses apply-advanced;
           leaf minimum {
             description "Minimum trace level for the sbc-utils subcomponents";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf configuration {
             description "Configuration trace level";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf ipc {
             description "IPC trace level";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf device-monitor {
             description "Device-monitor trace level";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf memory-management {
             description "Memory mgmt trace level";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf message {
             description "Messaging trace level";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf common {
             description "Common utils trace level";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf user-interface {
             description "User-interface trace level";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf memory-pool {
             description "Memory-pool trace level";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf packet-capture {
             description "Trace packet capture events";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
         }
       }
       container file {
         description "Trace file information";
         status deprecated;
         leaf filename {
           description "Name of file in which to write trace information";
           type string {
             length "1 .. 1024";
             junos:posix-pattern "![/ %]";
             junos:pattern-message "Must not contain '/', % or a space";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
     }
   }
   grouping admission-control-type {
     leaf name {
       description "Admission control profile name";
       type string;
     }
     uses apply-advanced;
     container dialogs {
       presence "enable dialogs";
       description "Dialog admission control rules";
       uses apply-advanced;
       leaf maximum-concurrent {
         description "Maximum concurrent dialogs allowed";
         type union {
           type string {
             pattern "<.*>|$.*";
           }
           type uint32 {
             range "0 .. 100000";
           }
         }
       }
       leaf committed-attempts-rate {
         description "Committed rate of dialog admission attempts";
         junos:must "(\".. committed-burst-size\")";
         junos:must-message "committed-burst-size must also be defined";
         type union {
           type string {
             pattern "<.*>|$.*";
           }
           type uint32 {
             range "0 .. 500";
           }
         }
       }
       leaf committed-burst-size {
         description "Committed burst size of dialog admission attempts";
         junos:must "(\".. committed-attempts-rate\")";
         junos:must-message "committed-attempts-rate must also be defined";
         type union {
           type string {
             pattern "<.*>|$.*";
           }
           type uint32 {
             range "0 .. 1000";
           }
         }
       }
     }
     container transactions {
       presence "enable transactions";
       description "Transaction admission control rules";
       uses apply-advanced;
       leaf maximum-concurrent {
         description "Maximum concurrent transactions allowed";
         type union {
           type string {
             pattern "<.*>|$.*";
           }
           type uint32 {
             range "0 .. 50000";
           }
         }
       }
       leaf committed-attempts-rate {
         description "Committed rate of transaction admission attempts";
         junos:must "(\".. committed-burst-size\")";
         junos:must-message "committed-burst-size must also be defined";
         type union {
           type string {
             pattern "<.*>|$.*";
           }
           type uint32 {
             range "0 .. 1500";
           }
         }
       }
       leaf committed-burst-size {
         description "Committed burst size of transaction admission attempts";
         junos:must "(\".. committed-attempts-rate\")";
         junos:must-message "committed-attempts-rate must also be defined";
         type union {
           type string {
             pattern "<.*>|$.*";
           }
           type uint32 {
             range "0 .. 3000";
           }
         }
       }
     }
   }
   grouping call_usage_policy_type {
     leaf name {
       description "Policy name";
       type string;
     }
     uses apply-advanced;
     list term {
       key name;
       ordered-by user;
       description "Term definition";
       max-elements 20;
       leaf name {
         description "Term name";
         type string;
       }
       uses apply-advanced;
       container from {
         presence "enable from";
         uses apply-advanced;
         leaf-list source-address {
           ordered-by user;
           description "Source addresses and masks";
           type jt:ipaddr;
           max-elements 5;
         }
         list method {
           key name;
           ordered-by user;
           description "Methods";
           uses call-usage-method-type;
         }
         container request-uri {
           presence "enable request-uri";
           description "Request URI field";
           uses apply-advanced;
           leaf-list regular-expression {
             ordered-by user;
             description "Regular expression matched on incoming Request-URI";
             type jt:regular-expression;
             max-elements 5;
           }
         }
         container contact {
           presence "enable contact";
           description "Contact field";
           uses apply-advanced;
           leaf-list regular-expression {
             ordered-by user;
             description "Regular expression matched on incoming contact";
             type jt:regular-expression;
             max-elements 5;
           }
         }
       }
       container then {
         description "Action";
         uses new_call_then_type;
       }
     }
   }
   grouping call-usage-method-type {
     leaf name {
       type enumeration {
         enum "method-invite" {
         }
       }
     }
     uses apply-advanced;
   }
   grouping hcm_tag_rule_object {
     leaf name {
       description "Rule name";
       junos:must "((!(\"services hcm url-rule $$\") && !(\"services hcm rule $$\")))";
       junos:must-message "Hcm rules must have unique names";
       type string {
         length "1 .. 63";
         junos:posix-pattern "^[[:alnum:]][[:alnum:]_-]*$";
         junos:pattern-message "Must be a string beginning with a number or letter and consisting of letters, numbers, dashes and underscores.";
       }
     }
     uses apply-advanced;
     list term {
       key name;
       ordered-by user;
       description "One or more terms in HCM tag rule";
       leaf name {
         description "Term name";
         type union {
           type string {
             pattern "<.*>|$.*";
           }
           type uint16 {
             range "1 .. 32767";
           }
         }
       }
       uses apply-advanced;
       container from {
         description "Match criteria";
         uses hcm_tag_match_object;
       }
       container then {
         description "Action to take if the 'from' condition is matched";
         uses apply-advanced;
         list tag {
           key name;
           ordered-by user;
           description "One or more terms in HCM tag rule";
           leaf name {
             description "Tag name";
             type string {
               length "1 .. 63";
             }
           }
           uses apply-advanced;
           leaf tag-header {
             description "Tag header string";
             type string {
               length "1 .. 63";
             }
           }
           leaf do-not-rename-existing-tag-header {
             description "Disable renaming of the tag header";
             type empty;
           }
           leaf tag-separator {
             description "Tag separator character";
             type string {
               length 1;
             }
           }
           leaf-list tag-attribute {
             ordered-by user;
             description "One or more tag attributes";
             type enumeration {
               enum "msisdn" {
               }
               enum "imsi" {
               }
               enum "apn" {
               }
               enum "imei" {
               }
               enum "ipv4addr" {
               }
               enum "ipv6addr" {
               }
               enum "ggsnipv4" {
               }
               enum "ggsnipv6" {
               }
               enum "radiusclass" {
               }
             }
           }
           container encrypt {
             description "Specify encryption or hashing algorithm";
             uses apply-advanced;
             leaf hash {
               description "Hashing algorithm";
               type enumeration {
                 enum "md5" {
                   description "Md5 hash";
                 }
               }
             }
             leaf prefix {
               description "Hash prefix key";
               type string {
                 length "1 .. 63";
               }
             }
           }
           leaf ipv4-mask {
             description "Specify a logical and mask for the x-forwarded-for address";
             junos:must "(\".. ipv4-or-value\")";
             junos:must-message "Both mask and or-value must be specified";
             type jt:ipv4addr;
           }
           leaf ipv4-or-value {
             description "Specify a logical or mask for x-forwarded address";
             junos:must "(\".. ipv4-mask\")";
             junos:must-message "Both mask and or-value must be specified";
             type jt:ipv4addr;
           }
           leaf ipv6-mask {
             description "Specify a logical and mask for the x-forwarded-for address";
             junos:must "(\".. ipv6-or-value\")";
             junos:must-message "Both mask and or-value must be specified";
             type jt:ipv6addr;
           }
           leaf ipv6-or-value {
             description "Specify a logical or mask for x-forwarded address";
             junos:must "(\".. ipv6-mask\")";
             junos:must-message "Both mask and or-value must be specified";
             type jt:ipv6addr;
           }
         }
         leaf count {
           description "Enable statistics for term";
           type empty;
         }
       }
     }
   }
   grouping hcm_tag_match_object {
     uses apply-advanced;
     list destination-address {
       key name;
       ordered-by user;
       description "Match IP destination address";
       uses sfw_addr_object;
     }
     list destination-address-range {
       key "low high";
       ordered-by user;
       description "Match IP destination address range";
       leaf low {
         description "Lower limit of address range";
         type jt:ipaddr;
       }
       leaf high {
         description "Upper limit of address range";
         type jt:ipaddr;
       }
       leaf except {
         description "Match address not in this prefix";
         type empty;
       }
     }
     list destination-prefix-list {
       key name;
       ordered-by user;
       description "One or more named lists of destination prefixes to match";
       leaf name {
         description "Name of prefix list to match against";
         junos:must "(\"policy-options prefix-list $$\")";
         junos:must-message "Referenced prefix-list is not defined under 'policy-options prefix-list'";
         type string;
       }
       leaf except {
         description "Name of prefix list not to match against";
         type empty;
       }
     }
     leaf-list destination-ports {
       ordered-by user;
       description "Destination port list specification";
       type union {
         type string {
           pattern "<.*>|$.*";
         }
         type uint32 {
           range "0 .. 65535";
         }
       }
     }
     list destination-port-range {
       key "low high";
       ordered-by user;
       description "Match destination port range";
       leaf low {
         description "Lower limit of port range";
         type union {
           type string {
             pattern "<.*>|$.*";
           }
           type uint32 {
             range "0 .. 65535";
           }
         }
       }
       leaf high {
         description "Upper limit of port range";
         type union {
           type string {
             pattern "<.*>|$.*";
           }
           type uint32 {
             range "0 .. 65535";
           }
         }
       }
     }
   }
   grouping hcm_url_list_object {
     leaf name {
       description "List name";
       type string {
         length "1 .. 63";
         junos:posix-pattern "^[[:alnum:]][[:alnum:]_-]*$";
         junos:pattern-message "Must be a string beginning with a number or letter and consisting of letters, numbers, dashes and underscores.";
       }
     }
     uses apply-advanced;
     list host {
       key name;
       ordered-by user;
       description "One or more host(s)";
       leaf name {
         description "Domain name";
         type string {
           length "1 .. 32";
         }
       }
       uses apply-advanced;
     }
     list request-uri {
       key name;
       ordered-by user;
       description "One or more uri's";
       leaf name {
         description "Uri name";
         type string {
           length "1 .. 40";
         }
       }
       uses apply-advanced;
     }
   }
   grouping hcm_url_rule_object {
     leaf name {
       description "Rule name";
       junos:must "(!(\"services hcm rule $$\"))";
       junos:must-message "Hcm rules must have unique names";
       junos:must "((!(\"services hcm rule $$\") && !(\"services hcm tag-rule $$\")))";
       junos:must-message "Hcm rules must have unique names";
       type string {
         length "1 .. 63";
         junos:posix-pattern "^[[:alnum:]][[:alnum:]_-]*$";
         junos:pattern-message "Must be a string beginning with a number or letter and consisting of letters, numbers, dashes and underscores.";
       }
     }
     uses apply-advanced;
     list term {
       key name;
       ordered-by user;
       description "One or more terms in HCM url_rule";
       leaf name {
         description "Term name";
         type union {
           type string {
             pattern "<.*>|$.*";
           }
           type uint16 {
             range "1 .. 255";
           }
         }
       }
       uses apply-advanced;
       container from {
         description "Match criteria";
         uses hcm_url_match_object;
       }
       container then {
         description "Action to take if the 'from' condition is matched";
         uses apply-advanced;
         leaf count {
           description "Enable statistics for term";
           junos:must "(!(\".. discard\"))";
           junos:must-message "Count must not be combined with Discard";
           junos:must "(\".. accept\")";
           junos:must-message "Count must be combined with Accept";
           type empty;
         }
         leaf log-request {
           description "Enable logging for term";
           type empty;
         }
         choice designation {
           case case_1 {
             leaf accept {
               description "Accept the URL";
               type empty;
             }
           }
           case case_2 {
             leaf discard {
               description "Discard the URL";
               type empty;
             }
           }
         }
       }
     }
   }
   grouping hcm_url_match_object {
     uses apply-advanced;
     list url-list {
       key name;
       ordered-by user;
       description "List of Url lists to referance";
       leaf name {
         description "Url list name";
         junos:must "(\"services hcm url-list $$\")";
         junos:must-message "referenced url-list rule must be defined";
         type string {
           length "1 .. 63";
         }
       }
       uses apply-advanced;
     }
     list url {
       key name;
       ordered-by user;
       description "Rule specific url list";
       leaf name {
         description "Url name";
         type union {
           type string {
             pattern "<.*>|$.*";
           }
           type uint16 {
             range "1 .. 32767";
           }
         }
       }
       uses apply-advanced;
       list host {
         key name;
         ordered-by user;
         description "One or more host(s)";
         leaf name {
           description "Domain name";
           type string {
             length "1 .. 32";
           }
         }
         uses apply-advanced;
       }
       list request-uri {
         key name;
         ordered-by user;
         description "One or more uri's";
         leaf name {
           description "Uri name";
           type string {
             length "1 .. 40";
           }
         }
         uses apply-advanced;
       }
     }
   }
   grouping header-manipulation-message-manipulation-rules-type {
     description "Definition of header manipulation";
     uses apply-advanced;
     list manipulation-rule {
       key name;
       ordered-by user;
       description "Definition of manipulation rules";
       uses header-manipulation-manipulation-rule-type;
     }
   }
   grouping header-manipulation-manipulation-rule-type {
     leaf name {
       description "Header manipulation rule name";
       type string;
     }
     uses apply-advanced;
     container actions {
       description "Header manipulation actions";
       uses header-manipulation-actions-type;
     }
   }
   grouping header-manipulation-actions-type {
     description "Manipulations on sip-headers or request-uri";
     uses apply-advanced;
     list sip-header {
       key name;
       ordered-by user;
       description "Manipulation of the SIP header";
       max-elements 50;
       leaf name {
         description "SIP header field name";
         type string;
       }
       uses apply-advanced;
       container field-value {
         description "Manipulation on the header's field value";
         uses header-manipulation-sip-header-field-value-type;
       }
     }
     container request-uri {
       presence "enable request-uri";
       description "Manipulation of the message request-uri";
       uses apply-advanced;
       container field-value {
         presence "enable field-value";
         description "Manipulation on the request-uri field value";
         uses apply-advanced;
         list modify-regular-expression {
           key name;
           ordered-by user;
           description "Set modify regular expression and patterns";
           max-elements 5;
           uses header-manipulation-modify-type;
         }
       }
     }
   }
   grouping header-manipulation-modify-type {
     description "Modify header using regular expression";
     leaf name {
       description "Regular expression pattern";
       type jt:regular-expression;
     }
     leaf with {
       description "Modification string";
       type string;
     }
   }
   grouping header-manipulation-sip-header-field-value-type {
     uses apply-advanced;
     leaf remove-all {
       description "Remove all headers";
       type empty;
     }
     list remove-regular-expression {
       key name;
       ordered-by user;
       description "Remove field-value";
       max-elements 5;
       uses header-manipulation-remove-type;
     }
     list reject-regular-expression {
       key name;
       ordered-by user;
       description "Reject message using regular expression";
       max-elements 5;
       uses header-manipulation-reject-type;
     }
     list modify-regular-expression {
       key name;
       ordered-by user;
       description "Modify field-value using regular expression";
       max-elements 5;
       uses header-manipulation-modify-type;
     }
     list add {
       key name;
       ordered-by user;
       description "Add field-value to header";
       max-elements 5;
       uses header-manipulation-add-type;
     }
     list add-missing {
       key name;
       ordered-by user;
       description "Add field-value only if header is missing";
       max-elements 5;
       uses header-manipulation-add-missing-type;
     }
     list add-overwrite {
       key name;
       ordered-by user;
       description "Overwrite headers field-value";
       max-elements 5;
       uses header-manipulation-add-overwrite-type;
     }
   }
   grouping header-manipulation-add-missing-type {
     description "Add header only if missing";
     leaf name {
       description "Field-value to add";
       type string;
     }
   }
   grouping header-manipulation-add-overwrite-type {
     description "Overwrite existing header";
     leaf name {
       description "Field-value to add";
       type string;
     }
   }
   grouping header-manipulation-add-type {
     description "Add header";
     leaf name {
       description "Field-value to add";
       type string;
     }
   }
   grouping header-manipulation-reject-type {
     description "Reject messages that match a regular expression";
     leaf name {
       description "Regular expression pattern";
       type jt:regular-expression;
     }
   }
   grouping header-manipulation-remove-type {
     description "Remove headers that match a regular expression";
     leaf name {
       description "Regular expression pattern";
       type jt:regular-expression;
     }
   }
   grouping icap-profile-object {
     leaf name {
       description "ICAP service profile name";
       type string {
         length "1 .. 63";
         junos:posix-pattern "^[[:alnum:]][[:alnum:]_-]*$";
         junos:pattern-message "Must be a string beginning with a number or letter and consisting of letters, numbers, dashes and underscores.";
       }
     }
     uses apply-advanced;
     list server {
       key name;
       ordered-by user;
       description "Configure service redirection server";
       max-elements 16;
       uses icap-redir-server;
     }
     container http {
       description "ICAP methods switch";
       uses http-redirect-object;
     }
     container fallback-option {
       description "Failure event actions";
       uses icap-redirect-fallback;
     }
     leaf timeout {
       description "Server response timeout in milliseconds";
       default "500";
       type union {
         type string {
           pattern "<.*>|$.*";
         }
         type uint16 {
           range "100 .. 50000";
         }
       }
     }
   }
   grouping http-redirect-object {
     uses apply-advanced;
     leaf redirect-request {
       description "Enable redirect service on HTTP request";
       type empty;
     }
     leaf redirect-response {
       description "Enable redirect service on HTTP response";
       type empty;
     }
   }
   grouping icap-redir-server {
     leaf name {
       description "Server name";
       type string {
         length "1 .. 63";
         junos:posix-pattern "^[[:alnum:]][[:alnum:]_-]*$";
         junos:pattern-message "Must be a string beginning with a number or letter and consisting of letters, numbers, dashes and underscores.";
       }
     }
     uses apply-advanced;
     container authorization {
       description "User authentication";
       uses apply-advanced;
       leaf authorization-type {
         description "Authentication type. 'Basic' by default";
         type string {
           length "1 .. 127";
         }
       }
       container credentials {
         description "Credentials text";
         choice credentials-choice {
           case case_1 {
             leaf ascii {
               description "ASCII string";
               type string {
                 length "1 .. 511";
               }
             }
           }
           case case_2 {
             leaf base64 {
               description "Base64 string";
               type string {
                 length "1 .. 511";
               }
             }
           }
         }
       }
     }
     leaf host {
       description "Host name/IP address";
       type string {
         length "1 .. 255";
       }
     }
     leaf port {
       description "Server listening port";
       default "1344";
       type union {
         type string {
           pattern "<.*>|$.*";
         }
         type uint16 {
           range "1025 .. 65535";
         }
       }
     }
     leaf reqmod-uri {
       description "REQMOD option resource identifier";
       type string {
         length "0 .. 1023";
       }
     }
     leaf respmod-uri {
       description "RESPMOD option resource identifier";
       type string {
         length "0 .. 1023";
       }
     }
     container routing-instance {
       description "Routing instance";
       leaf ri-name {
         description "Routing instance name";
         junos:must "(\"routing-instances $$ instance-type virtual-router\")";
         junos:must-message "Virtual router must be defined under [routing-instances]";
         junos:must "(\"routing-instances $$\")";
         junos:must-message "Routing-instance must be defined";
         type string {
           length "1 .. 127";
           junos:posix-pattern "!^((__.*__)|(all)|(.*[ ].*)|(\"\")|(.{129,}))$";
           junos:pattern-message "Must be a non-reserved string of 128 characters or less with no spaces.";
         }
       }
     }
     leaf sockets {
       description "Number of connections to create";
       default "8";
       type union {
         type string {
           pattern "<.*>|$.*";
         }
         type uint8 {
           range "1 .. 64";
         }
       }
     }
     leaf tls-profile {
       description "TLS profile";
       junos:must "(\"services ssl initiation profile $$\")";
       junos:must-message "Referenced SSL initiation profile is not defined";
       type string {
         length "1 .. 63";
       }
     }
   }
   grouping icap-redirect-fallback {
     uses apply-advanced;
     leaf timeout {
       description "Request timeout action";
       default "permit";
       type enumeration {
         enum "permit" {
           description "Direct permit action";
         }
         enum "log-permit" {
           description "Log then permit action";
         }
         enum "block" {
           description "Block action";
         }
       }
     }
     leaf connectivity {
       description "Connection-related failure action";
       default "permit";
       type enumeration {
         enum "permit" {
           description "Direct permit action";
         }
         enum "log-permit" {
           description "Log then permit action";
         }
         enum "block" {
           description "Block action";
         }
       }
     }
     leaf default-action {
       description "Default failure action";
       default "permit";
       type enumeration {
         enum "permit" {
           description "Direct permit action";
         }
         enum "log-permit" {
           description "Log then permit action";
         }
         enum "block" {
           description "Block action";
         }
       }
     }
   }
   grouping icap-redirect-traceoptions {
     description "ICAP redirect traceoptions";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Trace flags";
       leaf name {
         type enumeration {
           enum "all" {
             description "Trace everything";
           }
           enum "icap-redirect-re" {
             description "Trace events on RE side";
           }
           enum "icap-redirect-control" {
             description "Trace events on PFE-ukernel side";
           }
           enum "icap-redirect-connection" {
             description "Trace ICAP server connection events";
           }
           enum "icap-redirect-protocol" {
             description "Trace redirect packet events";
           }
         }
       }
     }
   }
   grouping ids-option-type {
     description "Configure screen object";
     leaf name {
       description "Screen object name";
       type string {
         length "1 .. 64";
       }
     }
     uses apply-advanced;
     leaf description {
       description "Text description of screen";
       type string {
         length "1 .. 900";
         junos:posix-pattern "^[^&<>\n]+$";
         junos:pattern-message "Must be a string excluding '&', '<', '>' and '\n'";
       }
     }
     leaf alarm-without-drop {
       description "Do not drop packet, only generate alarm";
       type empty;
     }
     leaf match-direction {
       description "Match direction";
       type enumeration {
         enum "input" {
           description "Match on input to interface";
         }
         enum "output" {
           description "Match on output from interface";
         }
         enum "input-output" {
           description "Match on input to or output from interface";
         }
       }
     }
     container aggregation {
       presence "enable aggregation";
       description "Configure the source and Destination prefix for a ids-option";
       uses apply-advanced;
       leaf source-prefix-mask {
         description "Source IPV4 prefix";
         type union {
           type string {
             pattern "<.*>|$.*";
           }
           type uint32 {
             range "1 .. 32";
           }
         }
       }
       leaf destination-prefix-mask {
         description "Destination IPV4 prefix";
         type union {
           type string {
             pattern "<.*>|$.*";
           }
           type uint32 {
             range "1 .. 32";
           }
         }
       }
       leaf source-prefix-v6-mask {
         description "Source IPV6 prefix";
         type union {
           type string {
             pattern "<.*>|$.*";
           }
           type uint32 {
             range "1 .. 128";
           }
         }
       }
       leaf destination-prefix-v6-mask {
         description "Destination IPV6 prefix";
         type union {
           type string {
             pattern "<.*>|$.*";
           }
           type uint32 {
             range "1 .. 128";
           }
         }
       }
     }
     container icmp {
       description "Configure ICMP ids options";
       uses apply-advanced;
       container ip-sweep {
         presence "enable ip-sweep";
         description "Configure ip sweep ids option";
         leaf threshold {
           description "Threshold";
           default "5000";
           units "microseconds in which 10 ICMP packets are detected";
           type union {
             type string {
               pattern "<.*>|$.*";
             }
             type uint32 {
               range "1000 .. 1000000";
             }
           }
         }
       }
       leaf fragment {
         description "Enable ICMP fragment ids option";
         type empty;
       }
       leaf large {
         description "Enable large ICMP packet (size > 1024) ids option";
         type empty;
       }
       container flood {
         presence "enable flood";
         description "Configure icmp flood ids option";
         leaf threshold {
           description "Threshold";
           default "1000";
           units "ICMP packets per second";
           type union {
             type string {
               pattern "<.*>|$.*";
             }
             type uint32;
           }
         }
       }
       leaf ping-death {
         description "Enable ping of death ids option";
         type empty;
       }
       leaf icmpv6-malformed {
         description "Enable icmpv6 malformed ids option";
         type empty;
       }
     }
     container ip {
       description "Configure IP layer ids options";
       uses apply-advanced;
       leaf bad-option {
         description "Enable ip with bad option ids option";
         type empty;
       }
       leaf record-route-option {
         description "Enable ip with record route option ids option";
         type empty;
       }
       leaf timestamp-option {
         description "Enable ip with timestamp option ids option";
         type empty;
       }
       leaf security-option {
         description "Enable ip with security option ids option";
         type empty;
       }
       leaf stream-option {
         description "Enable ip with stream option ids option";
         type empty;
       }
       leaf spoofing {
         description "Enable IP address spoofing ids option";
         type empty;
       }
       leaf source-route-option {
         description "Enable ip source route ids option";
         type empty;
       }
       leaf loose-source-route-option {
         description "Enable ip with loose source route ids option";
         type empty;
       }
       leaf strict-source-route-option {
         description "Enable ip with strict source route ids option";
         type empty;
       }
       leaf unknown-protocol {
         description "Enable ip unknown protocol ids option";
         type empty;
       }
       leaf block-frag {
         description "Enable ip fragment blocking ids option";
         type empty;
       }
       leaf tear-drop {
         description "Enable tear drop ids option";
         type empty;
       }
       container ipv6-extension-header {
         description "Configure ipv6 extension header ids option";
         uses apply-advanced;
         container hop-by-hop-header {
           presence "enable hop-by-hop-header";
           description "Enable ipv6 hop by hop option header ids option";
           uses apply-advanced;
           leaf jumbo-payload-option {
             description "Enable jumbo payload option ids option";
             type empty;
           }
           leaf router-alert-option {
             description "Enable router alert option ids option";
             type empty;
           }
           leaf quick-start-option {
             description "Enable quick start option ids option";
             type empty;
           }
           leaf CALIPSO-option {
             description "Enable Common Architecture Label ipv6 Security Option ids option";
             type empty;
           }
           leaf SMF-DPD-option {
             description "Enable Simplified Multicast Forwarding ipv6 Duplicate Packet Detection option ids option";
             type empty;
           }
           leaf RPL-option {
             description "Enable Routing Protocol for Low-power and Lossy networks option ids option";
             type empty;
           }
           list user-defined-option-type {
             key name;
             ordered-by user;
             description "User-defined option type range";
             max-elements 256;
             leaf name {
               description "User-defined option type low value";
               type union {
                 type string {
                   pattern "<.*>|$.*";
                 }
                 type uint32 {
                   range "1 .. 255";
                 }
               }
             }
             container to {
               description "Upper limit of option type range";
               uses apply-advanced;
               leaf type-high {
                 description "User-defined option type high value";
                 type union {
                   type string {
                     pattern "<.*>|$.*";
                   }
                   type uint32 {
                     range "1 .. 255";
                   }
                 }
               }
             }
           }
         }
         leaf routing-header {
           description "Enable ipv6 routing header ids option";
           type empty;
         }
         leaf fragment-header {
           description "Enable ipv6 fragment header ids option";
           type empty;
         }
         leaf ESP-header {
           description "Enable ipv6 Encapsulating Security Payload header ids option";
           type empty;
         }
         leaf AH-header {
           description "Enable ipv6 Authentication Header ids option";
           type empty;
         }
         leaf no-next-header {
           description "Enable ipv6 no next header ids option";
           type empty;
         }
         container destination-header {
           presence "enable destination-header";
           description "Enable ipv6 destination option header ids option";
           uses apply-advanced;
           leaf tunnel-encapsulation-limit-option {
             description "Enable tunnel encapsulation limit option ids option";
             type empty;
           }
           leaf home-address-option {
             description "Enable home address option ids option";
             type empty;
           }
           leaf ILNP-nonce-option {
             description "Enable Identifier-Locator Network Protocol Nonce option ids option";
             type empty;
           }
           leaf line-identification-option {
             description "Enable line identification option ids option";
             type empty;
           }
           list user-defined-option-type {
             key name;
             ordered-by user;
             description "User-defined option type range";
             max-elements 256;
             leaf name {
               description "User-defined option type low value";
               type union {
                 type string {
                   pattern "<.*>|$.*";
                 }
                 type uint32 {
                   range "1 .. 255";
                 }
               }
             }
             container to {
               description "Upper limit of option type range";
               uses apply-advanced;
               leaf type-high {
                 description "User-defined option type high value";
                 type union {
                   type string {
                     pattern "<.*>|$.*";
                   }
                   type uint32 {
                     range "1 .. 255";
                   }
                 }
               }
             }
           }
         }
         leaf shim6-header {
           description "Enable ipv6 shim header ids option";
           type empty;
         }
         leaf mobility-header {
           description "Enable ipv6 mobility header ids option";
           type empty;
         }
         leaf HIP-header {
           description "Enable ipv6 Host Identify Protocol header ids option";
           type empty;
         }
         list user-defined-header-type {
           key name;
           ordered-by user;
           description "User-defined header type range";
           max-elements 256;
           leaf name {
             description "User-defined header type low value";
             type union {
               type string {
                 pattern "<.*>|$.*";
               }
               type uint32 {
                 range "0 .. 255";
               }
             }
           }
           container to {
             description "Upper limit of header type range";
             uses apply-advanced;
             leaf type-high {
               description "User-defined header type high value";
               type union {
                 type string {
                   pattern "<.*>|$.*";
                 }
                 type uint32 {
                   range "0 .. 255";
                 }
               }
             }
           }
         }
       }
       leaf ipv6-extension-header-limit {
         description "Enable ipv6 extension header limit ids option";
         type union {
           type string {
             pattern "<.*>|$.*";
           }
           type uint32 {
             range "0 .. 32";
           }
         }
       }
       leaf ipv6-malformed-header {
         description "Enable ipv6 malformed header ids option";
         type empty;
       }
       container tunnel {
         description "Configure IP tunnel ids options";
         uses apply-advanced;
         leaf bad-inner-header {
           description "Enable IP tunnel bad inner header ids option";
           type empty;
         }
         container gre {
           description "Configure IP tunnel GRE ids option";
           uses apply-advanced;
           leaf gre-6in4 {
             description "Enable IP tunnel GRE 6in4 ids option";
             type empty;
           }
           leaf gre-4in6 {
             description "Enable IP tunnel GRE 4in6 ids option";
             type empty;
           }
           leaf gre-6in6 {
             description "Enable IP tunnel GRE 6in6 ids option";
             type empty;
           }
           leaf gre-4in4 {
             description "Enable IP tunnel GRE 4in4 ids option";
             type empty;
           }
         }
         container ip-in-udp {
           description "Configure IP tunnel IPinUDP ids option";
           uses apply-advanced;
           leaf teredo {
             description "Enable IP tunnel IPinUDP Teredo ids option";
             type empty;
           }
         }
         container ipip {
           description "Configure IP tunnel IPIP ids option";
           uses apply-advanced;
           leaf ipip-6to4relay {
             description "Enable IP tunnel IPIP 6to4 Relay ids option";
             type empty;
           }
           leaf ipip-6in4 {
             description "Enable IP tunnel IPIP 6in4 ids option";
             type empty;
           }
           leaf ipip-4in6 {
             description "Enable IP tunnel IPIP 4in6 ids option";
             type empty;
           }
           leaf ipip-4in4 {
             description "Enable IP tunnel IPIP 4in4 ids option";
             type empty;
           }
           leaf ipip-6in6 {
             description "Enable IP tunnel IPIP 6in6 ids option";
             type empty;
           }
           leaf ipip-6over4 {
             description "Enable IP tunnel IPIP 6over4 ids option";
             type empty;
           }
           leaf isatap {
             description "Enable IP tunnel IPIP ISATAP ids option";
             type empty;
           }
           leaf dslite {
             description "Enable IP tunnel IPIP DS-Lite ids option";
             type empty;
           }
         }
       }
     }
     container tcp {
       description "Configure TCP Layer ids options";
       uses apply-advanced;
       leaf syn-fin {
         description "Enable SYN and FIN bits set attack ids option";
         type empty;
       }
       leaf fin-no-ack {
         description "Enable Fin bit with no ACK bit ids option";
         type empty;
       }
       leaf tcp-no-flag {
         description "Enable TCP packet without flag ids option";
         type empty;
       }
       leaf syn-frag {
         description "Enable SYN fragment ids option";
         type empty;
       }
       container port-scan {
         presence "enable port-scan";
         description "Configure TCP port scan ids option";
         leaf threshold {
           description "Threshold";
           default "5000";
           units "microseconds in which 10 attack packets are detected";
           type union {
             type string {
               pattern "<.*>|$.*";
             }
             type uint32 {
               range "1000 .. 1000000";
             }
           }
         }
       }
       container syn-ack-ack-proxy {
         presence "enable syn-ack-ack-proxy";
         description "Configure syn-ack-ack proxy ids option";
         leaf threshold {
           description "Threshold";
           default "512";
           units "un-authenticated connections";
           type union {
             type string {
               pattern "<.*>|$.*";
             }
             type uint32 {
               range "1 .. 250000";
             }
           }
         }
       }
       container syn-flood {
         presence "enable syn-flood";
         description "Configure SYN flood ids option";
         uses apply-advanced;
         leaf alarm-threshold {
           description "Alarm threshold";
           default "512";
           units "requests per second";
           type union {
             type string {
               pattern "<.*>|$.*";
             }
             type uint32;
           }
         }
         leaf attack-threshold {
           description "Attack threshold";
           default "200";
           units "proxied requests per second";
           type union {
             type string {
               pattern "<.*>|$.*";
             }
             type uint32;
           }
         }
         leaf source-threshold {
           description "Source threshold";
           default "4000";
           units "SYN pps";
           type union {
             type string {
               pattern "<.*>|$.*";
             }
             type uint32;
           }
         }
         leaf destination-threshold {
           description "Destination threshold";
           default "4000";
           units "SYN pps";
           type union {
             type string {
               pattern "<.*>|$.*";
             }
             type uint32;
           }
         }
         leaf queue-size {
           description "Queue size";
           status deprecated;
           default "1024";
           units "proxied requests in queue";
           type union {
             type string {
               pattern "<.*>|$.*";
             }
             type uint32 {
               range "200 .. 20000";
             }
           }
         }
         leaf timeout {
           description "SYN flood ager timeout";
           default "20";
           units "seconds";
           type union {
             type string {
               pattern "<.*>|$.*";
             }
             type uint32 {
               range "1 .. 50";
             }
           }
         }
         list white-list {
           key name;
           description "Set of IP addresses that will not trigger a screen";
           max-elements 2;
           leaf name {
             description "White-list name";
             type string {
               length "1 .. 32";
               junos:posix-pattern "^[[:alnum:]][[:alnum:]_-]*$";
               junos:pattern-message "Must be a string beginning with a number or letter and consisting of letters, numbers, dashes and underscores.";
             }
           }
           uses apply-advanced;
           leaf-list source-address {
             ordered-by user;
             description "Source address";
             type jt:ipprefix;
             max-elements 32;
           }
           leaf-list destination-address {
             ordered-by user;
             description "Destination address";
             type jt:ipprefix;
             max-elements 32;
           }
         }
       }
       leaf land {
         description "Enable land attack ids option";
         type empty;
       }
       leaf winnuke {
         description "Enable winnuke attack ids option";
         type empty;
       }
       container tcp-sweep {
         presence "enable tcp-sweep";
         description "Configure TCP sweep ids option";
         leaf threshold {
           description "Threshold";
           default "5000";
           units "microseconds in which 10 TCP packets are detected";
           type union {
             type string {
               pattern "<.*>|$.*";
             }
             type uint32 {
               range "1000 .. 1000000";
             }
           }
         }
       }
     }
     container udp {
       description "Configure UDP layer ids options";
       uses apply-advanced;
       container flood {
         presence "enable flood";
         description "Configure UDP flood ids option";
         uses apply-advanced;
         leaf threshold {
           description "Threshold";
           default "1000";
           units "UDP packets per second";
           type union {
             type string {
               pattern "<.*>|$.*";
             }
             type uint32;
           }
         }
         leaf-list white-list {
           ordered-by user;
           description "Configure UDP flood white list group name";
           type string;
           max-elements 2;
         }
       }
       container udp-sweep {
         presence "enable udp-sweep";
         description "Configure UDP sweep ids option";
         leaf threshold {
           description "Threshold";
           default "5000";
           units "microseconds in which 10 UDP packets are detected";
           type union {
             type string {
               pattern "<.*>|$.*";
             }
             type uint32 {
               range "1000 .. 1000000";
             }
           }
         }
       }
       container port-scan {
         presence "enable port-scan";
         description "Configure UDP port scan ids option";
         leaf threshold {
           description "Threshold";
           default "5000";
           units "microseconds in which 10 attack packets are detected";
           type union {
             type string {
               pattern "<.*>|$.*";
             }
             type uint32 {
               range "1000 .. 1000000";
             }
           }
         }
       }
     }
     container limit-session {
       description "Limit sessions";
       uses apply-advanced;
       leaf source-ip-based {
         description "Limit sessions from the same source IP";
         type union {
           type string {
             pattern "<.*>|$.*";
           }
           type uint32;
         }
       }
       leaf destination-ip-based {
         description "Limit sessions to the same destination IP";
         type union {
           type string {
             pattern "<.*>|$.*";
           }
           type uint32;
         }
       }
       container by-source {
         presence "enable by-source";
         description "Limit sessions from the same source IP or subnet";
         uses apply-advanced;
         leaf maximum-sessions {
           description "Limit sessions on the basis of maximum concurrent sessions";
           type union {
             type string {
               pattern "<.*>|$.*";
             }
             type uint32;
           }
         }
         leaf packet-rate {
           description "Limit sessions on the basis of packet rate";
           type union {
             type string {
               pattern "<.*>|$.*";
             }
             type uint32 {
               range "1 .. 4294967295";
             }
           }
         }
         leaf session-rate {
           description "Limit sessions on the basis of session rate";
           type union {
             type string {
               pattern "<.*>|$.*";
             }
             type uint32 {
               range "1 .. 4294967295";
             }
           }
         }
         container by-protocol {
           description "Limit sessions on the basis of protocol";
           uses by-protocol-object-type;
         }
       }
       container by-destination {
         presence "enable by-destination";
         description "Limit sessions to the same destination IP or subnet";
         uses apply-advanced;
         leaf maximum-sessions {
           description "Limit sessions on the basis of maximum concurrent sessions";
           type union {
             type string {
               pattern "<.*>|$.*";
             }
             type uint32;
           }
         }
         leaf packet-rate {
           description "Limit sessions on the basis of packet rate";
           type union {
             type string {
               pattern "<.*>|$.*";
             }
             type uint32 {
               range "1 .. 4294967295";
             }
           }
         }
         leaf session-rate {
           description "Limit sessions on the basis of session rate";
           type union {
             type string {
               pattern "<.*>|$.*";
             }
             type uint32 {
               range "1 .. 4294967295";
             }
           }
         }
         container by-protocol {
           description "Limit sessions on the basis of protocol";
           uses by-protocol-object-type;
         }
       }
     }
   }
   grouping by-protocol-object-type {
     description "Configure limit-session on the basis of protocol";
     uses apply-advanced;
     container tcp {
       description "Configure limit-session on the basis of TCP";
       uses by-protocol-object-limit-type;
     }
     container udp {
       description "Configure limit-session on the basis of UDP";
       uses by-protocol-object-limit-type;
     }
     container icmp {
       description "Configure limit-session on the basis of ICMP";
       uses by-protocol-object-limit-type;
     }
   }
   grouping by-protocol-object-limit-type {
     description "Configure the limit-session for each protocol";
     uses apply-advanced;
     leaf maximum-sessions {
       description "Limit sessions on the basis of maximum concurrent sessions";
       type union {
         type string {
           pattern "<.*>|$.*";
         }
         type uint32;
       }
     }
     leaf packet-rate {
       description "Limit sessions on the basis of packet rate";
       type union {
         type string {
           pattern "<.*>|$.*";
         }
         type uint32 {
           range "1 .. 4294967295";
         }
       }
     }
     leaf session-rate {
       description "Limit sessions on the basis of session rate";
       type union {
         type string {
           pattern "<.*>|$.*";
         }
         type uint32 {
           range "1 .. 4294967295";
         }
       }
     }
   }
   grouping ids_rule_object {
     leaf name {
       description "Rule name";
       type string {
         length "1 .. 63";
         junos:posix-pattern "^[[:alnum:]][[:alnum:]_-]*$";
         junos:pattern-message "Must be a string beginning with a number or letter and consisting of letters, numbers, dashes and underscores.";
       }
     }
     uses apply-advanced;
     leaf match-direction {
       description "Direction for which the rule match is applied";
       type enumeration {
         enum "input" {
           description "Match on input to interface";
         }
         enum "output" {
           description "Match on output from interface";
         }
         enum "input-output" {
           description "Match on input to and output from interface";
         }
       }
     }
     list term {
       key name;
       ordered-by user;
       description "Define an IDS term";
       leaf name {
         description "Term name";
         type string {
           length "1 .. 63";
           junos:posix-pattern "^[[:alnum:]][[:alnum:]_-]*$";
           junos:pattern-message "Must be a string beginning with a number or letter and consisting of letters, numbers, dashes and underscores.";
         }
       }
       uses apply-advanced;
       container from {
         description "Define match criteria";
         uses sfw_match_object;
       }
       container then {
         description "Action to take if the 'from' condition is matched";
         uses apply-advanced;
         choice accept_choice {
           case case_1 {
             leaf force-entry {
               description "Force entries in IDS tables for matching traffic";
               type empty;
             }
           }
           case case_2 {
             leaf ignore-entry {
               description "Ignore IDS events for matching traffic";
               type empty;
             }
           }
           case case_3 {
             leaf user-interface {
               description "User-interface trace level";
               default "error";
               type enumeration {
                 enum "trace" {
                   description "Trace functions entering and exiting";
                 }
                 enum "debug" {
                   description "Trace code flow, branching, positive style guide check";
                 }
                 enum "info" {
                   description "Summary logs for normal operations";
                 }
                 enum "warning" {
                   description "Failure-recovery or Failure of an external entity";
                 }
                 enum "error" {
                   description "Failure with short-term affect";
                 }
               }
             }
           }
         }
         container aggregation {
           description "Define aggregation parameters";
           uses apply-advanced;
           leaf source-prefix {
             description "Prefix length for IPv4 source addresses";
             type union {
               type string {
                 pattern "<.*>|$.*";
               }
               type int32 {
                 range "1 .. 32";
               }
             }
           }
           leaf destination-prefix {
             description "Prefix length for IPv4 destination addresses";
             type union {
               type string {
                 pattern "<.*>|$.*";
               }
               type int32 {
                 range "1 .. 32";
               }
             }
           }
           leaf source-prefix-ipv6 {
             description "Prefix length for IPv6 source addresses";
             type union {
               type string {
                 pattern "<.*>|$.*";
               }
               type int32 {
                 range "1 .. 128";
               }
             }
           }
           leaf destination-prefix-ipv6 {
             description "Prefix length for IPv6 destination addresses";
             type union {
               type string {
                 pattern "<.*>|$.*";
               }
               type int32 {
                 range "1 .. 128";
               }
             }
           }
         }
         container logging {
           description "Define system logging parameters";
           uses apply-advanced;
           leaf threshold {
             description "Threshold above which events should be logged";
             type union {
               type int32;
               type string {
                 pattern "<.*>|$.*";
               }
             }
           }
           leaf syslog {
             description "System log information about the packet";
             type empty;
           }
         }
         container syn-cookie {
           description "Define SYN cookie parameters";
           uses apply-advanced;
           leaf threshold {
             description "Threshold above which SYN cookies are enabled";
             type union {
               type int32;
               type string {
                 pattern "<.*>|$.*";
               }
             }
           }
           leaf mss {
             description "MSS value for TCP delayed binding";
             type union {
               type string {
                 pattern "<.*>|$.*";
               }
               type int32 {
                 range "128 .. 8192";
               }
             }
           }
         }
         container session-limit {
           description "Define IDS session limit parameters";
           uses apply-advanced;
           container by-source {
             description "Define IDS session limit parameters by source";
             uses ids_limit_type;
           }
           container by-destination {
             description "Define IDS session limit parameters by destination";
             uses ids_limit_type;
           }
           container by-pair {
             description "Define IDS session limit parameters by source-destination pair";
             uses ids_limit_type;
           }
         }
         leaf-list allow-ip-options {
           ordered-by user;
           type string;
         }
         leaf-list allow-ipv6-extension-header {
           ordered-by user;
           type string;
         }
         leaf tcp-syn-defense {
           description "Enable tcp-syn-defense";
           type empty;
         }
         leaf tcp-syn-fragment-check {
           description "Enable tcp syn fragment check";
           type empty;
         }
         leaf tcp-winnuke-check {
           description "Enable tcp winnuke check";
           type empty;
         }
         leaf icmp-fragment-check {
           description "Enable icmp fragment check";
           type empty;
         }
         leaf icmp-large-packet-check {
           description "Enable icmp large packet check";
           type empty;
         }
         leaf land-attack-check {
           description "Enable land attack checks";
           type enumeration {
             enum "ip-only" {
               description "Land attack check is on IP address only";
             }
             enum "ip-port" {
               description "Land attack check is on both IP and port";
             }
           }
         }
       }
     }
   }
   grouping ids_limit_type {
     uses apply-advanced;
     leaf maximum {
       description "Maximum number of open sessions allowed simultaneously";
       type string;
     }
     leaf rate {
       description "Maximum number of new sessions allowed per second";
       type string;
     }
     leaf packets {
       description "Maximum number of packets allowed per second";
       type string;
     }
     leaf hold-time {
       description "How long to keep limit information after session is deleted";
       units "second";
       type union {
         type string {
           pattern "<.*>|$.*";
         }
         type int32 {
           range "0 .. 60";
         }
       }
     }
     container by-protocol {
       description "Define IDS session limit parameters";
       uses apply-advanced;
       container tcp {
         description "Define TCP IDS session limits";
         uses ids_proto_limit_type;
       }
       container udp {
         description "Define UDP IDS session limits by source";
         uses ids_proto_limit_type;
       }
       container icmp {
         description "Define ICMP IDS session limits by source";
         uses ids_proto_limit_type;
       }
     }
   }
   grouping ids_proto_limit_type {
     uses apply-advanced;
     leaf maximum {
       description "Maximum number of open sessions allowed simultaneously";
       type string;
     }
     leaf rate {
       description "Maximum number of new sessions allowed per second";
       type string;
     }
     leaf packets {
       description "Maximum number of packets allowed per second";
       type string;
     }
   }
   grouping interface_map_type {
     uses apply-advanced;
     leaf file-specification {
       description "Default file specification";
       type string;
     }
     leaf collector {
       description "Default Collector PIC to be used for flow manipulation";
       type union {
         type jt:interface-device;
         type string {
           pattern "<.*>|$.*";
         }
       }
     }
     list input_intf_to_cpic_map {
       key name;
       uses input_intf_to_cpic_map_type;
     }
   }
   grouping input_intf_to_cpic_map_type {
     leaf name {
       description "Input interface for flow collection";
       type union {
         type jt:interface-name;
         type string {
           pattern "<.*>|$.*";
         }
       }
     }
     uses apply-advanced;
     leaf file-specification {
       description "File specification to use for this interface";
       type string;
     }
     leaf collector {
       description "Collector PIC to be used for flow manipulation";
       type union {
         type jt:interface-device;
         type string {
           pattern "<.*>|$.*";
         }
       }
     }
   }
   grouping interface_type {
     description "Physical interface";
     leaf name {
       type string;
     }
     uses apply-advanced;
     choice queue-statistics-choice {
       leaf queue-statistics {
         description "Enable queue statistics collection";
         status deprecated;
         type empty;
       }
       leaf no-queue-statistics {
         description "Don't enable queue statistics collection";
         status deprecated;
         type empty;
       }
     }
     choice traffic-statistics-choice {
       leaf traffic-statistics {
         description "Enable traffic statistics collection";
         status deprecated;
         type empty;
       }
       leaf no-traffic-statistics {
         description "Don't enable traffic statistics collection";
         status deprecated;
         type empty;
       }
     }
     leaf resource-profile {
       description "Resouce profile name";
       junos:must "(\"services analytics resource-profiles $$\")";
       junos:must-message "binded resource-profile in not configured";
       type string {
         length "1 .. 64";
       }
     }
   }
   grouping ipr_profile_object {
     leaf name {
       description "IP-reassembly profile name";
       type string {
         length "1 .. 32";
       }
     }
     uses apply-advanced;
     leaf timeout {
       description "IP-reassembly timeout value";
       type union {
         type string {
           pattern "<.*>|$.*";
         }
         type int32 {
           range "2 .. 60";
         }
       }
     }
     leaf max-reassembly-pending-packets {
       description "IP-reassembly pending packets";
       type union {
         type string {
           pattern "<.*>|$.*";
         }
         type int32 {
           range "100 .. 100000";
         }
       }
     }
   }
   grouping ipr_rule_object {
     leaf name {
       description "Rule name";
       type string {
         length "1 .. 63";
         junos:posix-pattern "^[[:alnum:]][[:alnum:]_-]*$";
         junos:pattern-message "Must be a string beginning with a number or letter and consisting of letters, numbers, dashes and underscores.";
       }
     }
     uses apply-advanced;
     leaf match-direction {
       description "Direction for which the rule match is applied";
       type enumeration {
         enum "input" {
           description "Match on input to interface";
         }
       }
     }
   }
   grouping juniper-pic-services-logging-options {
     uses apply-advanced;
     container traceoptions {
       description "Fsad trace options";
       uses apply-advanced;
       leaf no-remote-trace {
         description "Disable remote tracing";
         junos:must "(\"system tracing\")";
         junos:must-message "'no-remote-trace' is valid only when [system tracing] is configured";
         type empty;
       }
       container file {
         description "Trace file information";
         leaf filename {
           description "Name of file in which to write trace information";
           type string {
             length "1 .. 1024";
             junos:posix-pattern "![/ %]";
             junos:pattern-message "Must not contain '/', % or a space";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing parameters";
         leaf name {
           type enumeration {
             enum "init" {
               description "Trace initialization events";
             }
             enum "bookkeeping" {
               description "Trace bookkeeping events";
             }
             enum "connections" {
               description "Trace connection-specific events";
             }
             enum "charging" {
               description "Trace charging-specific events";
             }
             enum "flow-collector" {
               description "Trace flow collector specific events";
             }
             enum "all" {
               description "Trace everything";
             }
           }
         }
       }
     }
   }
   grouping juniper-services-captive-portal {
     junos:must "((\"services captive-portal secure-authentication\" || \"system services web-management http\"))";
     junos:must-message "HTTP web service should be enabled";
     uses apply-advanced;
     leaf authentication-profile-name {
       description "Access profile name to use for authentication";
       junos:must "(\"access profile $$\")";
       junos:must-message "Access profile name must be defined in the [edit access profile] hierarchy";
       type string {
         length "1 .. 63";
       }
     }
     container traceoptions {
       description "Trace options for CAPTIVE PORTAL";
       status deprecated;
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "dot1x-debug" {
               description "Trace dot1x events";
               junos:must "(!(\"services captive-portal traceoptions flag dot1x-event\"))";
               junos:must-message "Can not configure dot1x-event with dot1x-debug flag";
             }
             enum "parse" {
               description "Trace configuration parsing";
             }
             enum "esw-if" {
               description "Trace ESW Interactions";
               junos:must "(!(\"services captive-portal traceoptions flag dot1x-ipc\"))";
               junos:must-message "Can not configure dot1x-ipc with esw-if flag";
             }
             enum "config-internal" {
               description "Trace configuration internals";
             }
             enum "normal" {
               description "Trace normal events";
             }
             enum "general" {
               description "Trace general events";
             }
             enum "state" {
               description "Trace state transitions";
             }
             enum "task" {
               description "Trace task processing";
             }
             enum "timer" {
               description "Trace task timer processing";
             }
             enum "all" {
               description "Trace everything";
             }
             enum "dot1x-ipc" {
               description "Trace dot1x IPC interactions";
             }
             enum "dot1x-event" {
               description "Trace dot1x events";
             }
           }
         }
         leaf disable {
           description "Disable this trace flag";
           type empty;
         }
       }
     }
     list interface {
       key name;
       description "Captive Portal interface specific options";
       leaf name {
         junos:must "(!(\"system phone-home\"))";
         junos:must-message "Can't configure captive-portal along with Phone-home. Delete phone-home config to enable captive-portal";
         junos:must "(\"system services web-management http\")";
         junos:must-message "HTTP web service should be enabled";
         junos:must "((!(\"switch-options no-mac-learning\") || (!(\".. .. .. .. .. switch-options no-mac-learning\") || !(any \".. .. .. .. .. bridge-domains <*> bridge-options no-mac-learning interface $$-IFL\"))))";
         junos:must-message "Cannot configure captive-portal on this interface since no-mac-learning is enabled on the same interface";
         junos:must "(!(\"interfaces $$-IFL family bridge interface-mode trunk\"))";
         junos:must-message "Cannot configure captive-portal on this interface since the interface-mode is defined as trunk";
         junos:must "(!(\"interfaces $$-IFL family ethernet-switching interface-mode trunk\"))";
         junos:must-message "Cannot configure captive-portal on this interface since the interface-mode is defined as trunk";
         junos:must "(!(\"interfaces $$-IFL family ethernet-switching port-mode trunk\"))";
         junos:must-message "Cannot configure captive-portal on this interface since the port-mode is defined as trunk";
         type string;
       }
       uses apply-advanced;
       leaf supplicant {
         description "Set supplicant mode for this interface";
         type enumeration {
           enum "single" {
             description "Allow multiple clients; authenticate first client only";
           }
           enum "single-secure" {
             description "Allow and authenticate only a single client";
           }
           enum "multiple" {
             description "Allow multiple clients; authenticate each individually";
           }
         }
       }
       leaf retries {
         description "Number of retries after which port is placed into wait state";
         type union {
           type string {
             pattern "<.*>|$.*";
           }
           type uint32 {
             range "1 .. 10";
           }
         }
       }
       leaf quiet-period {
         description "Time to wait after an authentication failure";
         units "seconds";
         type union {
           type string {
             pattern "<.*>|$.*";
           }
           type uint32 {
             range "0 .. 65535";
           }
         }
       }
       leaf server-timeout {
         description "Authentication server timeout interval";
         units "seconds";
         type union {
           type string {
             pattern "<.*>|$.*";
           }
           type uint32 {
             range "1 .. 60";
           }
         }
       }
       leaf session-expiry {
         description "Session Expiry Timeout";
         units "seconds";
         type union {
           type string {
             pattern "<.*>|$.*";
           }
           type uint32 {
             range "1 .. 65535";
           }
         }
       }
       leaf user-keepalive {
         description "Session keepalive after mac-flush";
         units "minutes";
         type union {
           type string {
             pattern "<.*>|$.*";
           }
           type uint32 {
             range "7 .. 65535";
           }
         }
       }
     }
     leaf secure-authentication {
       description "Set secure authentication using encrypted HTTPS or insecure authentication using plain-text HTTP";
       default "http";
       type enumeration {
         enum "http" {
           description "Insecure plain-text HTTP will be used for Captive Portal authentication, username and password can be sniffed";
           junos:must "(\"system services web-management http\")";
           junos:must-message "HTTP web service should be enabled";
         }
         enum "https" {
           description "Encrypted HTTPS will be used for Captive Portal authentication";
           junos:must "((\"system services web-management http\" && \"system services web-management https\"))";
           junos:must-message "HTTP and HTTPS web services should be enabled";
         }
       }
     }
     container custom-options {
       presence "enable custom-options";
       description "Captive Portal html user interface customization options";
       uses apply-advanced;
       leaf header-logo {
         description "Path to logo image file";
         type string {
           length "1 .. 255";
           junos:posix-pattern "^.+.((jpg)|(gif)|(jpeg)|(png))$";
           junos:pattern-message "Only jpg, jpeg, gif, png image types allowed";
         }
       }
       leaf header-bgcolor {
         description "Background color of the html header in hex html format";
         type string {
           length 7;
           junos:posix-pattern "^#[A-Fa-f0-9]{1,6}$";
           junos:pattern-message "Must be Hex color code beginning with # and consisting of six digit hexadecimal numbers";
         }
       }
       leaf header-text-color {
         description "Text color of the html header in hex html format";
         type string {
           length 7;
           junos:posix-pattern "^#[A-Fa-f0-9]{1,6}$";
           junos:pattern-message "Must be Hex color code beginning with # and consisting of six digit hexadecimal numbers";
         }
       }
       leaf header-message {
         description "Message to be displayed in the html header";
         type string {
           length "1 .. 2047";
         }
       }
       leaf banner-message {
         description "Terms and Conditions of usage message";
         type string {
           length "1 .. 2047";
         }
       }
       leaf form-header-message {
         description "Message to be displayed in the login form header";
         type string {
           length "1 .. 255";
         }
       }
       leaf form-header-bgcolor {
         description "Background color of the login form header in hex html format";
         type string {
           length 7;
           junos:posix-pattern "^#[A-Fa-f0-9]{1,6}$";
           junos:pattern-message "Must be Hex color code beginning with # and consisting of six digit hexadecimal numbers";
         }
       }
       leaf form-header-text-color {
         description "Text color of the login form header in hex html format";
         type string {
           length 7;
           junos:posix-pattern "^#[A-Fa-f0-9]{1,6}$";
           junos:pattern-message "Must be Hex color code beginning with # and consisting of six digit hexadecimal numbers";
         }
       }
       leaf form-submit-label {
         description "Label to be displayed for the login form submit button";
         type string {
           length "1 .. 255";
         }
       }
       leaf form-reset-label {
         description "Label to be displayed for the login form reset button";
         type string {
           length "1 .. 255";
         }
       }
       leaf footer-message {
         description "Message to be displayed in the html footer";
         type string {
           length "1 .. 2047";
         }
       }
       leaf footer-bgcolor {
         description "Background color of the html footer in hex html format";
         type string {
           length 7;
           junos:posix-pattern "^#[A-Fa-f0-9]{1,6}$";
           junos:pattern-message "Must be Hex color code beginning with # and consisting of six digit hexadecimal numbers";
         }
       }
       leaf footer-text-color {
         description "Text color of the footer in hex html format";
         type string {
           length 7;
           junos:posix-pattern "^#[A-Fa-f0-9]{1,6}$";
           junos:pattern-message "Must be Hex color code beginning with # and consisting of six digit hexadecimal numbers";
         }
       }
       leaf post-authentication-url {
         description "Post authentication redirection URL";
         type string {
           length "1 .. 255";
         }
       }
     }
   }
   grouping l2tp_access_line_object {
     uses apply-advanced;
     leaf connection-speed-update {
       description "Support connection speed updates";
       type empty;
     }
   }
   grouping l2tp_destination_object {
     uses apply-advanced;
     leaf lockout-timeout {
       description "The lockout timeout in seconds";
       default "300";
       type union {
         type string {
           pattern "<.*>|$.*";
         }
         type uint16 {
           range "60 .. 3600";
         }
       }
     }
     list address {
       key name;
       ordered-by user;
       leaf name {
         description "Address of remote system";
         type jt:ipv4addr;
       }
       container access-line-information {
         presence "enable access-line-information";
         description "Enable sending DSL line attributes";
         uses apply-advanced;
         leaf connection-speed-update {
           description "Support connection speed updates";
           type empty;
         }
       }
       list routing-instance {
         key name;
         ordered-by user;
         description "Routing instance in which destination exists";
         junos:must "(!(\".. drain\"))";
         junos:must-message "Multiple times drain is not allowed";
         leaf name {
           description "Routing instance in which destination exists";
           type string {
             junos:posix-pattern "!^((__.*__)|(.*[ ].*)|(.{129,}))$";
             junos:pattern-message "Must be a string of 128 characters or less with no spaces.";
           }
         }
         leaf drain {
           description "Prevents creation of tunnels and sessions at destination";
           type empty;
         }
       }
       leaf drain {
         description "Prevents creation of tunnels and sessions at destination";
         type empty;
       }
     }
     list name {
       key name;
       ordered-by user;
       leaf name {
         description "Locally assigned name of the destination";
         type string {
           length "1 .. 63";
           junos:posix-pattern "^[[:alnum:]][[:alnum:]_-]*$";
           junos:pattern-message "Must be a string beginning with a number or letter and consisting of letters, numbers, dashes and underscores.";
         }
       }
       leaf drain {
         description "Prevents tunnels and sessions at destination";
         type empty;
       }
     }
   }
   grouping l2tp_interface_traceoptions {
     leaf name {
       description "Name of Layer 2 Tunneling Protocol service interface";
       type union {
         type jt:interface-device;
         type string {
           pattern "<.*>|$.*";
         }
       }
     }
     uses apply-advanced;
     list flag {
       key name;
       ordered-by user;
       description "Tracing parameters";
       leaf name {
         type enumeration {
           enum "ipc" {
             description "Trace L2TP IPC messages between PIC and Routing Engine";
           }
           enum "protocol" {
             description "Trace L2TP, PPP, and multilink handling";
           }
           enum "packet-dump" {
             description "Dump each packet content based on debug level";
           }
           enum "system" {
             description "Trace packet processing on the PIC";
           }
           enum "all" {
             description "Trace everything";
           }
         }
       }
     }
     leaf debug-level {
       description "Trace level for PIC";
       default "error";
       type enumeration {
         enum "error" {
           description "Errors";
         }
         enum "detail" {
           description "Detailed debug information";
         }
         enum "extensive" {
           description "All PIC debug information";
         }
       }
     }
   }
   grouping l2tp_tunnel_group_object {
     leaf name {
       description "Name of Layer 2 Tunneling Protocol profile";
       type string {
         length "1 .. 63";
         junos:posix-pattern "^[[:alnum:]][[:alnum:]_-]*$";
         junos:pattern-message "Must be a string beginning with a number or letter and consisting of letters, numbers, dashes and underscores.";
       }
     }
     uses apply-advanced;
     leaf l2tp-access-profile {
       description "Tunnel profile name";
       junos:must "(\"access profile $$\")";
       junos:must-message "referenced access profile must be defined";
       type string {
         length "1 .. 63";
       }
     }
     leaf ppp-access-profile {
       description "User profile name";
       junos:must "(\"access profile $$\")";
       junos:must-message "referenced access profile must be defined";
       type string {
         length "1 .. 63";
       }
     }
     leaf aaa-access-profile {
       description "AAA profile name";
       junos:must "(\"access profile $$\")";
       junos:must-message "referenced access profile must be defined";
       type string {
         length "1 .. 63";
       }
     }
     leaf receive-window {
       description "Maximum receive window size";
       default "16";
       units "bytes";
       type union {
         type uint16;
         type string {
           pattern "<.*>|$.*";
         }
       }
     }
     leaf maximum-send-window {
       description "Limits the other end receive window size";
       default "32";
       units "bytes";
       type union {
         type uint16;
         type string {
           pattern "<.*>|$.*";
         }
       }
     }
     leaf retransmit-interval {
       description "Retransmit interval";
       default "30";
       units "seconds";
       type union {
         type uint16;
         type string {
           pattern "<.*>|$.*";
         }
       }
     }
     leaf hello-interval {
       description "Hello interval for tunnel keepalive";
       default "60";
       units "seconds";
       type union {
         type string {
           pattern "<.*>|$.*";
         }
         type uint16 {
           range "0 .. 3600";
         }
       }
     }
     leaf hide-avps {
       description "Hide L2TP AVPs";
       type empty;
     }
     leaf no-tos-reflect {
       description "Disable ToS bit reflect onto outer L2TP header";
       type empty;
     }
     leaf tos-reflect {
       description "Enable ToS bit reflect onto outer L2TP header";
       type empty;
     }
     leaf tunnel-timeout {
       description "Time to tear down tunnel when a connection is lost";
       default "120";
       units "seconds";
       type union {
         type uint16;
         type string {
           pattern "<.*>|$.*";
         }
       }
     }
     container local-gateway {
       presence "enable local-gateway";
       uses apply-advanced;
       leaf address {
         description "L2TP network server IP address";
         type jt:ipv4addr;
       }
       leaf gateway-name {
         description "L2TP network server name for use with remote host";
         type string;
       }
     }
     choice anchor-points {
       case case_1 {
         leaf service-interface {
           description "Services interface to use";
           junos:must "(!(any \"interfaces <*> aggregated-inline-services-options secondary-interface $$\"))";
           junos:must-message "must not be defined under asiX aggregated-inline-services-options";
           junos:must "(!(any \"interfaces <*> aggregated-inline-services-options primary-interface $$\"))";
           junos:must-message "must not be defined under asiX aggregated-inline-services-options";
           junos:must "(\"interfaces $$\")";
           junos:must-message "Interface must be defined in the interfaces hierarchy";
           type union {
             type jt:interface-unit;
             type string {
               pattern "<.*>|$.*";
             }
           }
         }
       }
       case case_2 {
         leaf service-device-pool {
           description "Service interface pool name to use";
           junos:must "(\".. dynamic-profile\")";
           junos:must-message "This knob can be used only with dynamic-profile";
           junos:must "(\"services service-device-pools pool $$\")";
           junos:must-message "referenced service device pool must be defined";
           type string {
             length "1 .. 63";
           }
         }
       }
     }
     leaf dynamic-profile {
       description " dynamic profile for interface to use";
       junos:must "(\"dynamic-profiles $$\")";
       junos:must-message "referenced dynamic profile must be defined";
       type string {
         length "1 .. 80";
       }
     }
     leaf tunnel-switch-profile {
       description "Tunnel switch profile name";
       junos:must "(\".. dynamic-profile\")";
       junos:must-message "dynamic profile must be configured with tunnel switch profile";
       junos:must "(\"access tunnel-switch-profile $$\")";
       junos:must-message "Referenced tunnel switch profile must be defined";
       type string {
         length "1 .. 63";
       }
     }
     container syslog {
       description "Define system logging parameters";
       uses log-object;
     }
     leaf maximum-sessions {
       description "Maximum number of sessions per tunnel-group";
       type union {
         type uint32;
         type string {
           pattern "<.*>|$.*";
         }
       }
     }
     leaf service-profile {
       description "Dynamic service profile(s) to be applied to this session";
       type string;
     }
   }
   grouping li_policy_addr6_simple_object {
     uses apply-advanced;
     leaf address {
       description "Prefix to match";
       type jt:ipv6prefix;
     }
   }
   grouping li_policy_addr_simple_object {
     uses apply-advanced;
     leaf address {
       description "Prefix to match";
       type jt:ipv4prefix;
     }
   }
   grouping log-object {
     description "Configure security log";
     uses apply-advanced;
     list exclude {
       key name;
       ordered-by user;
       description "List of security log criteria to exclude from the audit log";
       status deprecated;
       leaf name {
         description "Exclude criteria name";
         type string;
       }
       uses apply-advanced;
       leaf destination-address {
         description "Destination address";
         type jt:ipaddr;
       }
       leaf destination-port {
         description "Destination port";
         type union {
           type uint32;
           type string {
             pattern "<.*>|$.*";
           }
         }
       }
       leaf event-id {
         description "Event ID filter";
         type string;
       }
       leaf failure {
         description "Event was a failure";
         type empty;
       }
       leaf interface-name {
         description "Name of interface";
         type string;
       }
       leaf policy-name {
         description "Policy name filter";
         type string;
       }
       leaf process {
         description "Process that generated the event";
         type string;
       }
       leaf protocol {
         description "Protocol filter";
         type string;
       }
       leaf source-address {
         description "Source address";
         type jt:ipaddr;
       }
       leaf source-port {
         description "Source port";
         type union {
           type uint32;
           type string {
             pattern "<.*>|$.*";
           }
         }
       }
       leaf success {
         description "Event was successful";
         type empty;
       }
       leaf username {
         description "Username filter";
         type string;
       }
     }
     leaf limit {
       description "Limit number of security log entries to keep in memory";
       status deprecated;
       default "10000";
       type union {
         type uint32;
         type string {
           pattern "<.*>|$.*";
         }
       }
     }
     container cache {
       presence "enable cache";
       description "Cache security log events in the audit log buffer";
       uses apply-advanced;
       list exclude {
         key name;
         ordered-by user;
         description "List of security log criteria to exclude from the audit log";
         junos:must "(!(\".. .. exclude\"))";
         junos:must-message "'security log cache exclude' and 'security log exclude' are mutually exclusive";
         leaf name {
           description "Exclude criteria name";
           type string;
         }
         uses apply-advanced;
         leaf destination-address {
           description "Destination address";
           type jt:ipaddr;
         }
         leaf destination-port {
           description "Destination port";
           type union {
             type uint32;
             type string {
               pattern "<.*>|$.*";
             }
           }
         }
         leaf event-id {
           description "Event ID filter";
           type string;
         }
         leaf failure {
           description "Event was a failure";
           type empty;
         }
         leaf interface-name {
           description "Name of interface";
           type string;
         }
         leaf policy-name {
           description "Policy name filter";
           type string;
         }
         leaf process {
           description "Process that generated the event";
           type string;
         }
         leaf protocol {
           description "Protocol filter";
           type string;
         }
         leaf source-address {
           description "Source address";
           type jt:ipaddr;
         }
         leaf source-port {
           description "Source port";
           type union {
             type uint32;
             type string {
               pattern "<.*>|$.*";
             }
           }
         }
         leaf success {
           description "Event was successful";
           type empty;
         }
         leaf username {
           description "Username filter";
           type string;
         }
       }
       leaf limit {
         description "Limit number of security log entries to keep in memory";
         default "10000";
         junos:must "(!(\".. .. limit\"))";
         junos:must-message "'security log cache limit' and 'security log limit' are mutually exclusive";
         type union {
           type uint32;
           type string {
             pattern "<.*>|$.*";
           }
         }
       }
     }
     list host {
       key name;
       ordered-by user;
       max-elements 10;
       leaf name {
         description "Name of host to notify";
         type string {
           junos:posix-pattern "^[[:alnum:]:._-]+$";
           junos:pattern-message "Must be a string of letters, numbers, dashes, colons or underscores";
         }
       }
       uses apply-advanced;
       list contents {
         key name;
         leaf name {
           description "Facility type";
           type enumeration {
             enum "services" {
               description "Adaptive Services PIC";
             }
           }
         }
         choice level {
           case case_1 {
             leaf any {
               description "All levels";
               type empty;
             }
           }
           case case_2 {
             leaf emergency {
               description "Panic conditions";
               type empty;
             }
           }
           case case_3 {
             leaf alert {
               description "Conditions that should be corrected immediately";
               type empty;
             }
           }
           case case_4 {
             leaf critical {
               description "Critical conditions";
               type empty;
             }
           }
           case case_5 {
             leaf error {
               description "Error conditions";
               type empty;
             }
           }
           case case_6 {
             leaf warning {
               description "Warning messages";
               type empty;
             }
           }
           case case_7 {
             leaf notice {
               description "Conditions that should be handled specially";
               type empty;
             }
           }
           case case_8 {
             leaf info {
               description "Informational messages";
               type empty;
             }
           }
           case case_9 {
             leaf none {
               description "No messages";
               type empty;
             }
           }
         }
       }
       leaf facility-override {
         description "Alternate facility for logging to remote host";
         type enumeration {
           enum "authorization" {
             description "Authorization system";
           }
           enum "daemon" {
             description "Various system processes";
           }
           enum "ftp" {
             description "FTP process";
           }
           enum "kernel" {
             description "Kernel";
           }
           enum "user" {
             description "User processes";
           }
           enum "local0" {
             description "Local logging option number 0";
           }
           enum "local1" {
             description "Local logging option number 1";
           }
           enum "local2" {
             description "Local logging option number 2";
           }
           enum "local3" {
             description "Local logging option number 3";
           }
           enum "local4" {
             description "Local logging option number 4";
           }
           enum "local5" {
             description "Local logging option number 5";
           }
           enum "local6" {
             description "Local logging option number 6";
           }
           enum "local7" {
             description "Local logging option number 7";
           }
         }
       }
       leaf log-prefix {
         description "Prefix for all logging to this host";
         type string {
           junos:posix-pattern "![ =:]{1,15}";
           junos:pattern-message "Must be a string of 15 characters or less";
         }
       }
       leaf port {
         description "UDP port for syslogd on the host";
         type union {
           type string {
             pattern "<.*>|$.*";
           }
           type uint16 {
             range "1 .. 65535";
           }
         }
       }
       container class {
         description "Syslog messages classes";
         uses apply-advanced;
         container session-logs {
           presence "enable session-logs";
           description "Allow syslog messages for session events";
           uses apply-advanced;
           container open {
             presence "enable open";
             description "Allow syslog messages for session open events";
           }
           container close {
             presence "enable close";
             description "Allow syslog messages for session close events";
           }
         }
         container packet-logs {
           presence "enable packet-logs";
           description "Allow syslog messages for packet related events";
         }
         container stateful-firewall-logs {
           presence "enable stateful-firewall-logs";
           description "Allow syslog messages for stateful firewall events";
         }
         container alg-logs {
           presence "enable alg-logs";
           description "Allow syslog messages for ALG events";
         }
         container nat-logs {
           presence "enable nat-logs";
           description "Allow syslog messages for NAT events";
           uses apply-advanced;
           container deterministic-nat-configuration-log {
             presence "enable deterministic-nat-configuration-log";
             description "Allow syslog messages for Determinisitic NAT config events";
           }
         }
         container ids-logs {
           presence "enable ids-logs";
           description "Allow syslog messages for IDS events";
         }
         container pcp-logs {
           presence "enable pcp-logs";
           description "PCP logs";
           container map {
             presence "enable map";
             description "Allow syslog messages for PCP";
           }
           container debug {
             presence "enable debug";
             description "Allow PCP debug syslogs";
           }
         }
         container ha-logs {
           description "Stateful high availability logs";
           uses apply-advanced;
           container open-synchronized {
             presence "enable open-synchronized";
             description "Allow syslog message for session open events";
           }
           container close-synchronized {
             presence "enable close-synchronized";
             description "Allow syslog message for session close events";
           }
         }
         container urlf-logs {
           presence "enable urlf-logs";
           description "Allow syslog messages for URLF events";
         }
       }
       leaf source-address {
         description "Use specified address as source address";
         type jt:ipv4addr;
       }
       container tcp-log {
         presence "enable tcp-log";
         description "Enable tcp log for this service-set";
         uses apply-advanced;
         leaf source-address {
           description "Source address for tcp logging";
           junos:must "(!(\".. .. source-address\"))";
           junos:must-message "source-address must not be configured under host when tcp-log is configured";
           type jt:ipaddr;
         }
         leaf vrf-name {
           description "Routing instance name for tcp logging";
           junos:must "(\"routing-instances $$\")";
           junos:must-message "referenced routing instance must be defined";
           type string;
         }
         leaf ssl-profile {
           description "SSL profile name for tcp logging";
           junos:must "(\"services ssl initiation profile $$\")";
           junos:must-message "referenced ssl profile must be defined";
           type string {
             length "1 .. 63";
           }
         }
       }
     }
     leaf message-rate-limit {
       description "Maximum syslog messages per second allowed from this interface. Applies per member if set at aggregate level";
       units "messages per second";
       type union {
         type string {
           pattern "<.*>|$.*";
         }
         type uint32 {
           range "0 .. 2147483647";
         }
       }
     }
     leaf disable {
       description "Disable security logging for the device";
       type empty;
     }
     leaf utc-timestamp {
       description "Use UTC time for security log timestamps";
       type empty;
     }
     leaf mode {
       description "Controls how security logs are processed and exported";
       type enumeration {
         enum "stream" {
           description "Process security logs directly in the forwarding plane";
         }
         enum "event" {
           description "Process security logs in the control plane";
         }
       }
     }
     leaf event-rate {
       description "Control plane event rate";
       units "logs per second";
       junos:must "((\"security log mode event\" || \"services service-set ${service-set} syslog mode event\"))";
       junos:must-message "To configure event-rate, security log must be in event mode";
       type union {
         type string {
           pattern "<.*>|$.*";
         }
         type uint32 {
           range "0 .. 1500";
         }
       }
     }
     leaf format {
       description "Set security log format for the device";
       type enumeration {
         enum "syslog" {
           description "Traditional syslog";
         }
         enum "sd-syslog" {
           description "Structured syslog";
         }
         enum "binary" {
           description "Binary log";
         }
       }
     }
     leaf rate-cap {
       description "Data plane event rate";
       units "logs per second";
       type union {
         type string {
           pattern "<.*>|$.*";
         }
         type uint32 {
           range "0 .. 5000";
         }
       }
     }
     leaf max-database-record {
       description "Maximum records in database";
       default "0";
       type union {
         type string {
           pattern "<.*>|$.*";
         }
         type uint32;
       }
     }
     container report {
       presence "enable report";
       description "Set security log report settings";
     }
     choice source {
       case case_1 {
         leaf source-address {
           description "Source ip address used when exporting security logs";
           type jt:ipaddr;
         }
       }
       case case_2 {
         leaf source-interface {
           description "Source interface used when exporting security logs";
           type union {
             type jt:interface-name;
             type string {
               pattern "<.*>|$.*";
             }
           }
         }
       }
     }
     container transport {
       presence "enable transport";
       description "Set security log transport settings";
       uses apply-advanced;
       leaf tcp-connections {
         description "Set tcp connection number per-stream";
         type union {
           type string {
             pattern "<.*>|$.*";
           }
           type uint32 {
             range "1 .. 5";
           }
         }
       }
       leaf protocol {
         description "Set security log transport protocol for the device";
         type enumeration {
           enum "udp" {
             description "UDP transfer for log";
           }
           enum "tcp" {
             description "TCP transfer for log";
           }
           enum "tls" {
             description "TLS transfer for log";
           }
         }
       }
       leaf tls-profile {
         description "TLS profile";
         type string;
       }
     }
     leaf facility-override {
       description "Alternate facility for logging to remote host";
       type enumeration {
         enum "authorization" {
           description "Authorization system";
         }
         enum "daemon" {
           description "Various system processes";
         }
         enum "ftp" {
           description "FTP process";
         }
         enum "kernel" {
           description "Kernel";
         }
         enum "user" {
           description "User processes";
         }
         enum "local0" {
           description "Local logging option number 0";
         }
         enum "local1" {
           description "Local logging option number 1";
         }
         enum "local2" {
           description "Local logging option number 2";
         }
         enum "local3" {
           description "Local logging option number 3";
         }
         enum "local4" {
           description "Local logging option number 4";
         }
         enum "local5" {
           description "Local logging option number 5";
         }
         enum "local6" {
           description "Local logging option number 6";
         }
         enum "local7" {
           description "Local logging option number 7";
         }
       }
     }
     leaf local-log-tag {
       description "Tag included in logs";
       type string {
         junos:posix-pattern "![ =:]{1,15}";
         junos:pattern-message "Must be a string of 15 characters or less";
       }
     }
     list local-category {
       key name;
       ordered-by user;
       description "Selects the type of events that may be logged locally";
       leaf name {
         type enumeration {
           enum "all" {
             description "All events are logged";
           }
           enum "content-security" {
             description "Content security events are logged";
           }
           enum "fw-auth" {
             description "Fw-auth events are logged";
           }
           enum "screen" {
             description "Screen events are logged";
           }
           enum "alg" {
             description "Alg events are logged";
           }
           enum "nat" {
             description "Nat events are logged";
           }
           enum "flow" {
             description "Flow events are logged";
           }
           enum "sctp" {
             description "Sctp events are logged";
           }
           enum "gtp" {
             description "Gtp events are logged";
           }
           enum "ipsec" {
             description "Ipsec events are logged";
           }
           enum "idp" {
             description "Idp events are logged";
           }
           enum "rtlog" {
             description "Rtlog events are logged";
           }
           enum "pst-ds-lite" {
             description "Pst-ds-lite events are logged";
           }
           enum "appqos" {
             description "Appqos events are logged";
           }
           enum "secintel" {
             description "Secintel events are logged";
           }
           enum "aamw" {
             description "AAMW events are logged";
           }
           enum "sfw" {
             description "Stateful Firewall events are logged";
           }
           enum "session" {
             description "Session events are logged";
           }
         }
       }
       uses apply-advanced;
     }
     list stream {
       key name;
       ordered-by user;
       description "Set security log stream settings";
       max-elements 8;
       leaf name {
         description "Name of security log stream";
         type string {
           length "1 .. 63";
           junos:posix-pattern "^[[:alnum:]._-]+$";
           junos:pattern-message "Must be a string consisting of letters, numbers, dashes and underscores";
         }
       }
       uses apply-advanced;
       leaf severity {
         description "Severity threshold for security logs";
         type enumeration {
           enum "emergency" {
             description "Conditions that cause security functions to stop";
           }
           enum "alert" {
             description "Conditions that require immediate attention";
           }
           enum "critical" {
             description "Critical conditions";
           }
           enum "error" {
             description "General error conditions";
           }
           enum "warning" {
             description "General warning conditions";
           }
           enum "notice" {
             description "Non-error conditions that are of interest";
           }
           enum "info" {
             description "Information about normal security operations";
           }
           enum "debug" {
             description "Information normally used in debugging";
           }
         }
       }
       leaf format {
         description "Specify the log stream format";
         type enumeration {
           enum "syslog" {
             description "Traditional syslog";
           }
           enum "sd-syslog" {
             description "Structured syslog";
           }
           enum "welf" {
             description "Web Trends Extended Log Format";
           }
           enum "binary" {
             description "Binary log";
           }
         }
       }
       list category {
         key name;
         ordered-by user;
         description "Selects the type of events that may be logged";
         junos:must "(!(\"security log stream ${stream} filter\"))";
         junos:must-message "Category is exclusive with filter";
         leaf name {
           type enumeration {
             enum "all" {
               description "All events are logged";
             }
             enum "content-security" {
               description "Content security events are logged";
             }
             enum "fw-auth" {
               description "Fw-auth events are logged";
             }
             enum "screen" {
               description "Screen events are logged";
             }
             enum "alg" {
               description "Alg events are logged";
             }
             enum "nat" {
               description "Nat events are logged";
             }
             enum "flow" {
               description "Flow events are logged";
             }
             enum "sctp" {
               description "Sctp events are logged";
             }
             enum "gtp" {
               description "Gtp events are logged";
             }
             enum "ipsec" {
               description "Ipsec events are logged";
             }
             enum "idp" {
               description "Idp events are logged";
             }
             enum "rtlog" {
               description "Rtlog events are logged";
             }
             enum "pst-ds-lite" {
               description "Pst-ds-lite events are logged";
             }
             enum "appqos" {
               description "Appqos events are logged";
             }
             enum "secintel" {
               description "Secintel events are logged";
             }
             enum "aamw" {
               description "AAMW events are logged";
             }
             enum "sfw" {
               description "Stateful Firewall events are logged";
             }
             enum "session" {
               description "Session events are logged";
             }
           }
         }
         uses apply-advanced;
       }
       list filter {
         key name;
         ordered-by user;
         description "Selects the filter to filter the logs to be logged";
         junos:must "(!(\"security log stream ${stream} category\"))";
         junos:must-message "filter is exclusive with category";
         leaf name {
           type enumeration {
             enum "threat-attack" {
               description "Threat-attack security events are logged";
             }
           }
         }
         uses apply-advanced;
       }
       container host {
         description "Destination to send security logs to";
         junos:must "(!(\"security log stream ${stream} file\"))";
         junos:must-message "host is exclusive with file";
         junos:must "((\"security log source-address\" || (\"security log source-interface\" || (\"services service-set ${service-set} syslog source-interface\" || \"services service-set ${service-set} syslog source-address\"))))";
         junos:must-message "To configure host stream, security log source-address/source-interface must be configured";
         uses host-object;
         junos:must "(!(\"security log stream ${stream} file\"))";
         junos:must-message "host is exclusive with file";
         junos:must "((\"security log source-address\" || (\"security log source-interface\" || (\"services service-set ${service-set} syslog source-interface\" || \"services service-set ${service-set} syslog source-address\"))))";
         junos:must-message "To configure host stream, security log source-address/source-interface must be configured";
       }
       container rate-limit {
         description "Rate-limit for security logs";
         uses apply-advanced;
         leaf rate {
           description "Log rate";
           units "logs per second";
           type union {
             type string {
               pattern "<.*>|$.*";
             }
             type uint32 {
               range "1 .. 65535";
             }
           }
         }
       }
       container file {
         junos:must "(!(\"security log stream ${stream} host\"))";
         junos:must-message "file is exclusive with host";
         description "Security log file options for logs in local file";
         uses apply-advanced;
         leaf localfilename {
           description "Name of local log file";
           type string {
             length "1 .. 256";
             junos:posix-pattern "![/ %]";
             junos:pattern-message "Must not contain '/', % or a space";
           }
         }
         leaf size {
           description "Maximum size of local log file in megabytes";
           type union {
             type string {
               pattern "<.*>|$.*";
             }
             type uint32;
           }
         }
         leaf rotation {
           description "Maximum number of rotate files";
           default "10";
           type union {
             type string {
               pattern "<.*>|$.*";
             }
             type uint32 {
               range "2 .. 19";
             }
           }
         }
         leaf allow-duplicates {
           description "To disable log consolidation";
           type empty;
         }
       }
     }
     container file {
       description "Security log file options for logs in binary format";
       uses apply-advanced;
       leaf filename {
         description "Name of binary log file";
         type string {
           length "1 .. 256";
         }
       }
       leaf size {
         description "Maximum size of binary log file in megabytes";
         type union {
           type string {
             pattern "<.*>|$.*";
           }
           type uint32 {
             range "1 .. 10";
           }
         }
       }
       leaf path {
         description "Path to binary log files";
         type string {
           length "1 .. 256";
         }
       }
       leaf files {
         description "Maximum number of binary log files";
         type union {
           type string {
             pattern "<.*>|$.*";
           }
           type uint32 {
             range "2 .. 10";
           }
         }
       }
     }
     container traceoptions {
       description "Security log daemon trace options";
       uses apply-advanced;
       leaf no-remote-trace {
         description "Disable remote tracing";
         junos:must "(\"system tracing\")";
         junos:must-message "'no-remote-trace' is valid only when [system tracing] is configured";
         type empty;
       }
       container file {
         description "Trace file information";
         leaf filename {
           description "Name of file in which to write trace information";
           type string {
             length "1 .. 1024";
             junos:posix-pattern "![/ %]";
             junos:pattern-message "Must not contain '/', % or a space";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "List of things to include in trace";
         leaf name {
           type enumeration {
             enum "source" {
               description "Communication with security log forwarder";
             }
             enum "configuration" {
               description "Reading of configuration";
             }
             enum "all" {
               description "Everything";
             }
             enum "report" {
               description "Trace report";
             }
             enum "hpl" {
               description "Trace HPL logging";
             }
           }
         }
       }
     }
   }
   grouping host-object {
     uses apply-advanced;
     leaf ipaddr {
       description "IP address";
       type jt:ipaddr;
     }
     leaf port {
       description "Host port number";
       type union {
         type uint16;
         type string {
           pattern "<.*>|$.*";
         }
       }
     }
     leaf routing-instance {
       description "Routing-instance name";
       junos:must "(\"routing-instances $$ instance-type virtual-router\")";
       junos:must-message "Virtual router must be defined under [routing-instances]";
       junos:must "(\"routing-instances $$\")";
       junos:must-message "Routing-instance must be defined";
       type string;
     }
     leaf log-tag {
       description "Tag included in logs to this host";
       type string {
         junos:posix-pattern "![ =:]{1,15}";
         junos:pattern-message "Must be a string of 15 characters or less";
       }
     }
   }
   grouping lrf_profile_object {
     leaf name {
       description "Name of profile";
       type string {
         length "1 .. 63";
         junos:posix-pattern "^[[:alnum:]][[:alnum:]_-]*$";
         junos:pattern-message "Must be a string beginning with a number or letter and consisting of letters, numbers, dashes and underscores.";
       }
     }
     uses apply-advanced;
     leaf policy-based-logging {
       description "Set rule based on policy";
       type empty;
     }
     leaf http-log-multiple-transactions {
       description "Log http multiple transactions";
       type empty;
     }
     list rule {
       key name;
       ordered-by user;
       description "One or more LRF rules";
       max-elements 32;
       uses lrf_rule_object;
     }
     list collector {
       key name;
       ordered-by user;
       description "One or more LRF collectors";
       max-elements 8;
       uses lrf_collector_object;
     }
     leaf-list vendor-support {
       ordered-by user;
       description "LRF 3rd party vendor support sub-template";
       type enumeration {
         enum "ibm" {
           description "IBM supported sub-template";
         }
       }
     }
     list template {
       key name;
       ordered-by user;
       description "LRF template";
       max-elements 16;
       uses lrf_template_object;
     }
     container performance-mode {
       description "Enable performance mode knob for LRF performance";
       uses lrf_perf_object;
     }
   }
   grouping lrf_collector_object {
     leaf name {
       description "Name of collector";
       type string {
         length "1 .. 32";
         junos:posix-pattern "^[[:alnum:]][[:alnum:]_-]*$";
         junos:pattern-message "Must be a string beginning with a number or letter and consisting of letters, numbers, dashes and underscores.";
       }
     }
     uses apply-advanced;
     container destination {
       presence "enable destination";
       description "Destination collector configuration";
       uses apply-advanced;
       leaf address {
         description "Destination IPv4 address of collector";
         type jt:ipv4addr;
       }
       leaf port {
         description "Destination port of collector";
         type union {
           type uint16;
           type string {
             pattern "<.*>|$.*";
           }
         }
       }
     }
     leaf source-address {
       description "Source address to be used in the export packets";
       type jt:ipv4addr;
     }
   }
   grouping lrf_perf_object {
     uses apply-advanced;
     leaf packet-count {
       description "Max packet inspection threshold including both c2s and s2c direction packets ";
       default "20";
       type union {
         type string {
           pattern "<.*>|$.*";
         }
         type uint32 {
           range "20 .. 1000";
         }
       }
     }
   }
   grouping lrf_rule_object {
     leaf name {
       description "Name of rule";
       type string {
         length "1 .. 63";
         junos:posix-pattern "^[[:alnum:]][[:alnum:]_-]*$";
         junos:pattern-message "Must be a string beginning with a number or letter and consisting of letters, numbers, dashes and underscores.";
       }
     }
     uses apply-advanced;
     leaf match-direction {
       description "Match direction";
       default "both";
       junos:must "(!(\".. .. policy-based-logging\"))";
       junos:must-message "Match direction is not valid when policy based logging is enabled";
       type enumeration {
         enum "client-to-server" {
           description "Client to server";
         }
         enum "server-to-client" {
           description "Server to client";
         }
         enum "both" {
           description "Both client-to-server and server-to-client";
         }
       }
     }
     container from {
       description "Match criteria";
       junos:must "(!(\".. .. policy-based-logging\"))";
       junos:must-message "From is not valid when policy based logging is enabled";
       uses lrf_match_object;
       junos:must "(!(\".. .. policy-based-logging\"))";
       junos:must-message "From is not valid when policy based logging is enabled";
     }
     container then {
       description "Action to take for matched condition";
       uses apply-advanced;
       container report {
         description "Report action";
         uses lrf_report_object;
       }
     }
   }
   grouping lrf_match_object {
     uses apply-advanced;
     list source-prefix-list {
       key name;
       ordered-by user;
       description "One or more named lists of source prefixes to match";
       leaf name {
         description "Name of prefix list to match against";
         type string;
       }
       leaf except {
         description "Name of prefix list not to match against";
         type empty;
       }
     }
     list destination-prefix-list {
       key name;
       ordered-by user;
       description "One or more named lists of destination prefixes to match";
       leaf name {
         description "Name of prefix list to match against";
         type string;
       }
       leaf except {
         description "Name of prefix list not to match against";
         type empty;
       }
     }
     leaf-list source-ports {
       ordered-by user;
       description "Source port list specification";
       type union {
         type string {
           pattern "<.*>|$.*";
         }
         type uint32 {
           range "0 .. 65535";
         }
       }
     }
     leaf-list destination-ports {
       ordered-by user;
       description "Destination port list specification";
       type union {
         type string {
           pattern "<.*>|$.*";
         }
         type uint32 {
           range "0 .. 65535";
         }
       }
     }
     leaf app-unknown {
       description "Use to specify unknown application as the match criteria";
       type empty;
     }
     list application-names {
       key name;
       ordered-by user;
       description "Match one or more applications";
       leaf name {
         description "Name of application";
         type string {
           length "1 .. 63";
         }
       }
       uses apply-advanced;
     }
     list application-groups {
       key name;
       ordered-by user;
       description "Match one or more application groups";
       leaf name {
         description "Name of application group";
         type string {
           length "1 .. 63";
         }
       }
       uses apply-advanced;
     }
   }
   grouping lrf_report_object {
     uses apply-advanced;
     leaf volume-limit {
       description "Volume limit";
       units "megabytes";
       type union {
         type string {
           pattern "<.*>|$.*";
         }
         type uint16 {
           range "1 .. 1024";
         }
       }
     }
     leaf time-limit {
       description "Time limit";
       default "300";
       units "seconds";
       type union {
         type string {
           pattern "<.*>|$.*";
         }
         type uint32 {
           range "60 .. 1800";
         }
       }
     }
     leaf template {
       description "Template to be used for export";
       junos:must "(\".. .. .. .. template $$\")";
       junos:must-message "Template must be configured under services lrf profile template";
       type string;
     }
     leaf-list collector {
       ordered-by user;
       description "List of collectors that receive the export packets";
       type string {
         length "1 .. 63";
       }
       max-elements 3;
     }
   }
   grouping lrf_template_object {
     leaf name {
       description "Name of template";
       type string {
         length "1 .. 32";
       }
     }
     uses apply-advanced;
     leaf format {
       description "Template format";
       type enumeration {
         enum "ipfix" {
           description "IPFIX template";
         }
       }
     }
     leaf-list template-type {
       ordered-by user;
       description "Template type";
       type enumeration {
         enum "ipv4" {
           description "IPv4 type";
         }
         enum "ipv4-extended" {
           description "IPv4 Extended type";
         }
         enum "ipv6" {
           description "IPv6 type";
         }
         enum "ipv6-extended" {
           description "IPv6 Extended type";
         }
         enum "transport-layer" {
           description "Transport Layer type";
         }
         enum "flow-id" {
           description "Flow ID type";
         }
         enum "ipflow" {
           description "IPFlow type";
         }
         enum "ipflow-ts" {
           description "IPFlow TS type";
         }
         enum "ipflow-extended" {
           description "IPFlow Extended type";
         }
         enum "device-data" {
           description "Device Data type";
         }
         enum "l7-app" {
           description "L7 APP type";
         }
         enum "http" {
           description "HTTP type";
         }
         enum "subscriber-data" {
           description "Subscriber data type";
         }
         enum "mobile-subscriber" {
           description "Mobile subscriber type";
         }
         enum "ifl-subscriber" {
           description "IFL based subscriber type";
         }
         enum "wireline-subscriber" {
           description "Wireline subscriber type";
         }
         enum "ipflow-tcp-ts" {
           description "IPFlow TCP TS type (IBM specific)";
         }
         enum "ipflow-tcp" {
           description "IPFlow TCP type";
         }
         enum "video" {
           description "Video fields type";
         }
         enum "dns" {
           description "DNS fields type";
         }
         enum "status-code-distribution" {
           description "Status code distribution for HTTP and DNS";
         }
         enum "pcc" {
           description "PCC type";
         }
       }
     }
     leaf-list trigger-type {
       ordered-by user;
       description "Trigger type";
       type enumeration {
         enum "session-close" {
           description "Session close trigger";
         }
         enum "volume" {
           description "Volume trigger";
         }
         enum "time" {
           description "Time limit trigger";
         }
       }
     }
     leaf template-tx-interval {
       description "Template export interval";
       default "60";
       units "seconds";
       type union {
         type string {
           pattern "<.*>|$.*";
         }
         type uint32 {
           range "10 .. 600";
         }
       }
     }
   }
   grouping macro-data-type {
     leaf name {
       description "Keyword part of the keyword-value pair";
       type string;
     }
     leaf value {
       description "Value part of the keyword-value pair";
       type string;
     }
   }
   grouping mape_object {
     leaf name {
       description "MAP-E softwire concentrator name";
       type string {
         length "1 .. 63";
         junos:posix-pattern "^[[:alnum:]][[:alnum:]_-]*$";
         junos:pattern-message "Must be a string beginning with a number or letter and consisting of letters, numbers, dashes and underscores.";
       }
     }
     uses apply-advanced;
     leaf softwire-address {
       description "Softwire concentrator IPV6 Address";
       type jt:ipv6addr;
     }
     leaf ipv4-prefix {
       description "MAP-E domains's rule IPv4 prefix/len";
       type jt:ipv4prefix;
     }
     leaf mape-prefix {
       description "MAP-E domain's rule IPV6 prefix/len";
       type jt:ipv6prefix;
     }
     leaf ea-bits-len {
       description "MAP-E domain's rule EA (Embedded Address) len";
       type union {
         type string {
           pattern "<.*>|$.*";
         }
         type uint32 {
           range "0 .. 48";
         }
       }
     }
     leaf psid-offset {
       description "MAP-E domain's PSID offset";
       default "4";
       type union {
         type string {
           pattern "<.*>|$.*";
         }
         type uint32 {
           range "0 .. 16";
         }
       }
     }
     leaf psid-length {
       description "MAP-E domain's PSID length";
       type union {
         type string {
           pattern "<.*>|$.*";
         }
         type uint32 {
           range "0 .. 16";
         }
       }
     }
     leaf mtu-v6 {
       description "MTU for the MAP-E softwire tunnel";
       default "9192";
       type union {
         type string {
           pattern "<.*>|$.*";
         }
         type int32 {
           range "1280 .. 9192";
         }
       }
     }
     leaf version-03 {
       description "MAP-E map-03 support";
       type empty;
     }
     leaf v4-reassembly {
       description "MAP-E IPv4 reassembly support";
       type empty;
     }
     leaf v6-reassembly {
       description "MAP-E IPv6 reassembly support";
       type empty;
     }
   }
   grouping match_li_simple_dscp_value {
     uses apply-advanced;
     leaf value_keyword {
       type string;
     }
   }
   grouping match_li_simple_port_value {
     uses apply-advanced;
     leaf value_keyword {
       type string;
     }
   }
   grouping match_li_simple_protocol_value {
     uses apply-advanced;
     leaf value_keyword {
       type string;
     }
   }
   grouping monitor-threshold {
     leaf normal {
       description "Usage under normal conditions";
       type union {
         type string {
           pattern "<.*>|$.*";
         }
         type uint8 {
           range "1 .. 100";
         }
       }
     }
     leaf threshold {
       description "Threshold upon which alarm is raised";
       type union {
         type string {
           pattern "<.*>|$.*";
         }
         type uint8 {
           range "1 .. 100";
         }
       }
     }
   }
   grouping name-resolution-cache-type {
     description "Configuration of DNS responses cache";
     uses apply-advanced;
     container maximum-time-in-cache {
       presence "enable maximum-time-in-cache";
       description "Maximum time a DNS response may be held in the cache";
       choice maximum-time-in-cache {
         case case_1 {
           leaf unlimited {
             description "Cache according to TTL";
             type empty;
           }
         }
         case case_2 {
           leaf time {
             description "Seconds";
             type union {
               type string {
                 pattern "<.*>|$.*";
               }
               type uint32 {
                 range "0 .. 604800";
               }
             }
           }
         }
       }
     }
     leaf maximum-records-in-cache {
       description "Maximum number of DNS responses that may be held in the cache";
       default "5000";
       type union {
         type string {
           pattern "<.*>|$.*";
         }
         type uint32 {
           range "0 .. 50000";
         }
       }
     }
     leaf blacklist-period {
       description "Time (in seconds) a record will be held in the blacklist";
       default "600";
       type union {
         type string {
           pattern "<.*>|$.*";
         }
         type uint32 {
           range "0 .. 86400";
         }
       }
     }
     container accelerations {
       presence "enable accelerations";
       description "Mechanisms for accelerating DNS resolving";
       uses apply-advanced;
       leaf no-refresh-before-ttl-expiry {
         description "Don't send a new query for records that are about to expire";
         type empty;
       }
       leaf initiate-next-queries {
         description "Immediately initiate queries for referenced entries (e.g A entries referenced from SRV ones)";
         type empty;
       }
       leaf initiate-alternative-queries {
         description "Initiate NAPTR, SRV and A record queries, in parallel, for every new SIP URI";
         type empty;
       }
     }
   }
   grouping named-address-book-type {
     description "Configure global address book";
     leaf name {
       description "Address book name";
       type string;
     }
     uses apply-advanced;
     leaf description {
       description "Text description of address book";
       type string {
         length "1 .. 900";
         junos:posix-pattern "^[^&<>\n]+$";
         junos:pattern-message "Must be a string excluding '&', '<', '>' and '\n'";
       }
     }
     list address {
       key name;
       ordered-by user;
       description "Define a security address";
       uses address_type;
     }
     list address-set {
       key name;
       ordered-by user;
       description "Define a security address set";
       uses address_set_type;
     }
     container attach {
       junos:must "(!(\"security address-book global attach\"))";
       junos:must-message "It is not allowed to attach the global address book to any particular interface, zone or routing-instance.";
       description "Attach this address book to interface, zone or routing-instance";
       uses apply-advanced;
       list zone {
         key name;
         ordered-by user;
         description "Define a zone to be attached";
         leaf name {
           description "Security zone name";
           junos:must "(unique \"security address-book <*> attach zone $$\")";
           junos:must-message "Security zone must be unique in address books";
           junos:must "(\"security zones security-zone $$\")";
           junos:must-message "Security zone must be defined";
           type string {
             length "1 .. 63";
           }
         }
         uses apply-advanced;
       }
     }
   }
   grouping address_set_type {
     leaf name {
       description "Security address-set name";
       junos:must "(!(\".. .. address $$\"))";
       junos:must-message "Security address and address-set cannot have same name";
       type string {
         length "1 .. 63";
         junos:posix-pattern "^[[:alnum:]][[:alnum:]:./_-]*$";
         junos:pattern-message "Must be a string beginning with a number or letter and consisting of letters, numbers, colons, periods, slashes, dashes and underscores";
       }
     }
     uses apply-advanced;
     leaf description {
       description "Text description of address set";
       type string {
         length "1 .. 900";
         junos:posix-pattern "^[^&<>\n]+$";
         junos:pattern-message "Must be a string excluding '&', '<', '>' and '\n'";
       }
     }
     list address {
       key name;
       ordered-by user;
       description "Address to be included in this set";
       max-elements 4096;
       leaf name {
         description "Security address name";
         junos:must "(\".. .. .. address $$\")";
         junos:must-message "referenced address must be defined under address-book";
         type string {
           length "1 .. 63";
           junos:posix-pattern "^[[:alnum:]][[:alnum:]:./_-]*$";
           junos:pattern-message "Must be a string beginning with a number or letter and consisting of letters, numbers, colons, periods, slashes, dashes and underscores";
         }
       }
       uses apply-advanced;
     }
     list address-set {
       key name;
       ordered-by user;
       description "Define an address-set name";
       max-elements 4096;
       leaf name {
         junos:must "(\".. .. .. address-set $$\")";
         junos:must-message "referenced address must be defined under address-book";
         type string {
           length "1 .. 63";
           junos:posix-pattern "^[[:alnum:]][[:alnum:]:./_-]*$";
           junos:pattern-message "Must be a string beginning with a number or letter and consisting of letters, numbers, colons, periods, slashes, dashes and underscores";
         }
       }
       uses apply-advanced;
     }
   }
   grouping address_type {
     leaf name {
       description "Security address name";
       type string {
         length "1 .. 63";
         junos:posix-pattern "^[[:alnum:]][[:alnum:]:./_-]*$";
         junos:pattern-message "Must be a string beginning with a number or letter and consisting of letters, numbers, colons, periods, slashes, dashes and underscores";
       }
     }
     uses apply-advanced;
     leaf description {
       description "Text description of address";
       type string {
         length "1 .. 900";
         junos:posix-pattern "^[^&<>\n]+$";
         junos:pattern-message "Must be a string excluding '&', '<', '>' and '\n'";
       }
     }
     choice address-content {
       case case_1 {
         leaf ip-prefix {
           description "Numeric IPv4 or IPv6 address with prefix";
           type jt:ipprefix;
         }
       }
       case case_2 {
         list dns-name {
           key name;
           ordered-by user;
           description "DNS address name";
           max-elements 1;
           uses dns-name-type;
         }
       }
       case case_3 {
         list wildcard-address {
           key name;
           ordered-by user;
           description "Numeric IPv4 wildcard address with in the form of a.d.d.r/netmask";
           max-elements 1;
           uses wildcard-address-type;
         }
       }
       case case_4 {
         list range-address {
           key name;
           ordered-by user;
           description "Address range";
           max-elements 1;
           uses range-address-type;
         }
       }
     }
   }
   grouping dns-name-type {
     description "DNS address name";
     leaf name {
       description "Fully qualified hostname";
       type string {
         length "1 .. 63";
         junos:posix-pattern "^[[:alnum:]._-]+$|^\\\\*$";
         junos:pattern-message "Must be a valid DNS name";
       }
     }
     uses apply-advanced;
     leaf ipv4-only {
       description "IPv4 dns address";
       type empty;
     }
     leaf ipv6-only {
       description "IPv6 dns address";
       junos:must "(!(\".. ipv4-only\"))";
       junos:must-message "ipv4-only and ipv6-only cannot be configured together";
       type empty;
     }
   }
   grouping nat-object {
     description "Configure Network Address Translation";
     uses apply-advanced;
     container source {
       description "Configure Source NAT";
       uses ssg-source-nat-object;
     }
     container destination {
       description "Configure Destination NAT";
       uses ssg-destination-nat-object;
     }
     container static {
       description "Configure Static NAT";
       uses ssg-static-nat-object;
     }
     container proxy-arp {
       description "Configure Proxy ARP";
       uses ssg-proxy-arp-object;
     }
     container proxy-ndp {
       description "Configure Proxy NDP";
       uses ssg-proxy-ndp-object;
     }
     container natv6v4 {
       description "Configure NAT between IPv6 and IPv4 options";
       uses apply-advanced;
       leaf no-v6-frag-header {
         description "V6 packet does not always add fragment header when performing nat translation from v4 side to v6 side ";
         type empty;
       }
       leaf clear-dont-fragment-bit {
         description "Clear DF bit in IPv4 header if IPv6 packet size is less than 1280 bytes";
         type empty;
       }
     }
     leaf allow-overlapping-pools {
       description "IP addresses of NAT pools can overlap with other pool";
       type empty;
     }
     container traceoptions {
       description "NAT trace options";
       uses apply-advanced;
       leaf no-remote-trace {
         description "Disable remote tracing";
         junos:must "(\"system tracing\")";
         junos:must-message "'no-remote-trace' is valid only when [system tracing] is configured";
         type empty;
       }
       container file {
         description "Trace file information";
         leaf filename {
           description "Name of file in which to write trace information";
           type string {
             length "1 .. 1024";
             junos:posix-pattern "![/ %]";
             junos:pattern-message "Must not contain '/', % or a space";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing parameters";
         leaf name {
           type enumeration {
             enum "configuration" {
               description "Trace configuration events";
             }
             enum "flow" {
               description "Trace flow events";
             }
             enum "routing-socket" {
               description "Trace routing socket events";
             }
             enum "routing-protocol" {
               description "Trace routing protocol events";
             }
             enum "all" {
               description "Trace everything";
             }
             enum "source-nat-re" {
               description "Trace source nat events on RE side";
             }
             enum "source-nat-rt" {
               description "Trace source nat events on PFE-RT side";
             }
             enum "source-nat-pfe" {
               description "Trace source nat events on PFE-ukernel side";
             }
             enum "destination-nat-re" {
               description "Trace destination nat events on RE side";
             }
             enum "destination-nat-rt" {
               description "Trace destination nat events on PFE-RT side";
             }
             enum "destination-nat-pfe" {
               description "Trace destination nat events on PFE-ukernel side";
             }
             enum "static-nat-re" {
               description "Trace static nat events on RE side";
             }
             enum "static-nat-rt" {
               description "Trace static nat events on PFE-RT side";
             }
             enum "static-nat-pfe" {
               description "Trace static nat events on PFE-ukernel side";
             }
             enum "nat-svc-set-re" {
               description "Trace NAT and svc-set events on RE side";
             }
           }
         }
         leaf syslog {
           description "Write NAT flow traces to system log also";
           type empty;
         }
       }
     }
     list pool {
       key name;
       ordered-by user;
       description "Define a NAT pool";
       uses nat_pool_object;
     }
     list ipv6-multicast-interfaces {
       key name;
       ordered-by user;
       description "Enable IPv6 multicast filter for IPv6 NAT";
       leaf name {
         description "Interface name";
         type string;
       }
       uses apply-advanced;
       leaf disable {
         description "Disable IPv6 multicast filter for IPv6 NAT";
         type empty;
       }
     }
     leaf allow-overlapping-nat-pools {
       description "Allow usage of overlapping and same nat pools in multiple service sets";
       type empty;
     }
     list rule {
       key name;
       ordered-by user;
       description "Define a NAT rule";
       uses nat_rule_object;
     }
     list port-forwarding {
       key name;
       ordered-by user;
       description "Define a port-forwarding pool";
       uses pf_mapping;
     }
     list rule-set {
       key name;
       ordered-by user;
       description "Defines a set of NAT rules";
       max-elements 16960;
       leaf name {
         description "Name of the rule set";
         type string {
           length "1 .. 63";
           junos:posix-pattern "^[[:alnum:]][[:alnum:]/.:_-]*$";
           junos:pattern-message "Must be a string beginning with a number or letter and consisting of letters, numbers, dashes, underscores, forward slashes, colons and dots.";
         }
       }
       uses apply-advanced;
       list rule {
         key name;
         ordered-by user;
         description "Rule to be included in this rule set";
         max-elements 16960;
         leaf name {
           description "Rule name";
           junos:must "(\"services nat rule $$\")";
           junos:must-message "rule must be configured";
           type string {
             junos:posix-pattern "^[[:alnum:]][[:alnum:]/.:_-]{0,62}$";
             junos:pattern-message "Must be a string beginning with a number or letter and consisting of no more than 63 total letters, numbers, dashes, underscores, forward slashes, colons and dots.";
           }
         }
         uses apply-advanced;
       }
     }
   }
   grouping nat_pool_object {
     leaf name {
       description "Pool name";
       type string {
         length "1 .. 63";
         junos:posix-pattern "^[[:alnum:]][[:alnum:]_-]*$";
         junos:pattern-message "Must be a string beginning with a number or letter and consisting of letters, numbers, dashes and underscores.";
       }
     }
     uses apply-advanced;
     container pgcp {
       presence "enable pgcp";
       description "NAT pool should be used exclusive by the pgcp service";
       uses apply-advanced;
       leaf remotely-controlled {
         description "Remotely controlled NAT pool allocation";
         type empty;
       }
       leaf ports-per-session {
         description "Number of ports to allocate in each call setup";
         default "2";
         type union {
           type uint8;
           type string {
             pattern "<.*>|$.*";
           }
         }
       }
       list hint {
         key name;
         ordered-by user;
         description "NAT-hint list (Any string available up to 3 characters, not mandatory field)";
         max-elements 5;
         uses nat_pgcp_hint_list_object;
       }
       leaf-list transport {
         ordered-by user;
         description "NAT pool transport types list";
         type enumeration {
           enum "tcp" {
             description "TCP";
           }
           enum "udp" {
             description "UDP";
           }
           enum "rtp-avp" {
             description "RTP/AVP";
           }
         }
       }
     }
     list address {
       key name;
       ordered-by user;
       description "Address or address prefix for NAT";
       leaf name {
         type jt:ipprefix-only;
       }
       uses apply-advanced;
     }
     container interface {
       description "Interface for nat pool";
       leaf interface-name {
         junos:must "(\".. .. address-overload\")";
         junos:must-message "interface must be configured with address-overload in a pool";
         junos:must "(!(\".. .. address-range\"))";
         junos:must-message "interface cannot be configured along with address-range in a pool";
         junos:must "(!(\".. .. address\"))";
         junos:must-message "interface cannot be configured along with address in a pool";
         junos:must "((\"interfaces $$-IFL family inet address\" || \"interfaces $$-IFL family inet dhcp\"))";
         junos:must-message "Interface with ipv4 address or dhcp-client must be defined in the interfaces hierarchy";
         type union {
           type jt:interface-unit;
           type string {
             pattern "<.*>|$.*";
           }
         }
       }
     }
     leaf address-overload {
       description "Nat pool address overload with JunOS";
       junos:must "(\".. port\")";
       junos:must-message "port range must be configured with address-overload in a pool";
       type empty;
     }
     list address-range {
       key "low high";
       ordered-by user;
       description "Range of addresses for NAT";
       leaf low {
         description "Lower limit of address range";
         type jt:ipaddr;
       }
       leaf high {
         description "Upper limit of address range";
         type jt:ipaddr;
       }
     }
     container port {
       description "Specify ports for NAT";
       uses apply-advanced;
       choice port_choice {
         case case_1 {
           container automatic {
             presence "enable automatic";
             uses apply-advanced;
             choice automatic_choice {
               case case_1 {
                 leaf auto {
                   description "Automatically choose ports";
                   status deprecated;
                   type empty;
                 }
               }
               case case_2 {
                 leaf sequential {
                   description "Allocate ports in sequence";
                   type empty;
                 }
               }
               case case_3 {
                 leaf random-allocation {
                   description "Allocate ports randomly";
                   type empty;
                 }
               }
             }
           }
         }
         case case_2 {
           container range {
             description "Range of ports";
             leaf low {
               description "Lower limit of port range";
               type union {
                 type string {
                   pattern "<.*>|$.*";
                 }
                 type uint16 {
                   range "1 .. 65535";
                 }
               }
             }
             leaf high {
               description "Upper limit of port range";
               type union {
                 type string {
                   pattern "<.*>|$.*";
                 }
                 type uint16 {
                   range "1 .. 65535";
                 }
               }
             }
             leaf random-allocation {
               description "Allocate ports randomly";
               type empty;
             }
           }
         }
       }
       choice block-allocation-choice {
         case case_1 {
           container secured-port-block-allocation {
             presence "enable secured-port-block-allocation";
             description "Secured Port block allocation";
             leaf block-size {
               description "Number of port per block.";
               default "128";
               type union {
                 type string {
                   pattern "<.*>|$.*";
                 }
                 type uint16 {
                   range "1 .. 64512";
                 }
               }
             }
             leaf max-blocks-per-address {
               description "Max block per address";
               default "8";
               type union {
                 type string {
                   pattern "<.*>|$.*";
                 }
                 type uint16 {
                   range "1 .. 512";
                 }
               }
             }
             leaf active-block-timeout {
               description "Active block timeout";
               default "120";
               type union {
                 type string {
                   pattern "<.*>|$.*";
                 }
                 type uint32 {
                   range "0 .. 86400";
                 }
               }
             }
           }
         }
         case case_2 {
           container deterministic-port-block-allocation {
             presence "enable deterministic-port-block-allocation";
             junos:must "(!(\".. preserve-range\"))";
             junos:must-message "preserve-range is not supported with deterministic-port-block-allocation";
             junos:must "(!(\".. preserve-parity\"))";
             junos:must-message "preserve-parity is not supported with deterministic-port-block-allocation";
             description "Deterministic Port Block Allocation";
             leaf block-size {
               description "Number of ports per block";
               default "512";
               type union {
                 type string {
                   pattern "<.*>|$.*";
                 }
                 type uint16 {
                   range "0 .. 64512";
                 }
               }
             }
             leaf include-boundary-addresses {
               description "Include network and broadcast in 'from' src-addresses";
               type empty;
             }
           }
         }
       }
       leaf preserve-parity {
         description "Allocate port with same parity as original port";
         type empty;
       }
       leaf preserve-range {
         description "Preserve privileged port range after NAT";
         type empty;
       }
     }
     container address-allocation {
       presence "enable address-allocation";
       junos:must "((\".. port automatic random-allocation\" || (\".. port range random-allocation\" || \".. port secured-port-block-allocation\")))";
       junos:must-message "address-allocation applies only with port automatic random-allocation or port range random-allocation or secured-port-block-allocation";
       description "Address allocation method for NAPT";
       uses apply-advanced;
       leaf round-robin {
         description "Round robin method of allocation";
         type empty;
       }
     }
     leaf mapping-timeout {
       description "Address-pooling paired and endpoint-independent mapping timeout (120..86400)";
       default "300";
       units "second";
       type union {
         type int32;
         type string {
           pattern "<.*>|$.*";
         }
       }
     }
     leaf flow-timeout {
       description "Default flow timeout for NAT flows";
       default "300";
       units "second";
       type union {
         type string {
           pattern "<.*>|$.*";
         }
         type int32 {
           range "30 .. 86400";
         }
       }
     }
     leaf ei-mapping-timeout {
       description "Endpoint-independent mapping timeout (120..86400)";
       units "second";
       type union {
         type int32;
         type string {
           pattern "<.*>|$.*";
         }
       }
     }
     leaf app-mapping-timeout {
       description "Address-pooling paired mapping timeout (120..86400)";
       units "second";
       junos:must "(!(\".. mapping-timeout\"))";
       junos:must-message "Both app-mapping-timeout and mapping-timeout should not be configured, any one only is allowed";
       type union {
         type int32;
         type string {
           pattern "<.*>|$.*";
         }
       }
     }
     leaf limit-ports-per-address {
       description "Limit number of ports allocated per host (IP address)";
       units "connections";
       type union {
         type string {
           pattern "<.*>|$.*";
         }
         type int32 {
           range "2 .. 65435";
         }
       }
     }
     container snmp-trap-thresholds {
       presence "enable snmp-trap-thresholds";
       description "Define snmp traps for service sets";
       uses apply-advanced;
       container address-port {
         presence "enable address-port";
         description "Nat pool address and port usage trap threshold range";
         leaf low {
           description "Lower limit of pool trap threshold";
           units "percent";
           type union {
             type string {
               pattern "<.*>|$.*";
             }
             type uint16 {
               range "0 .. 100";
             }
           }
         }
         leaf high {
           description "Upper limit of pool trap threshold";
           units "percent";
           type union {
             type string {
               pattern "<.*>|$.*";
             }
             type uint16 {
               range "0 .. 100";
             }
           }
         }
       }
     }
   }
   grouping nat_pgcp_hint_list_object {
     description "NAT hints";
     leaf name {
       description "NAT-hint string list";
       type string {
         length "1 .. 4";
         junos:posix-pattern "^[[:alnum:]][[:alnum:]_-]{0,3}$";
         junos:pattern-message "NAT-hint is a string which should begin with a digit or a letter only. And consist of up to 3 numbers, dashes and underscores";
       }
     }
   }
   grouping nat_rule_object {
     leaf name {
       description "Rule name";
       type string {
         length "1 .. 63";
         junos:posix-pattern "^[[:alnum:]][[:alnum:]/.:_-]*$";
         junos:pattern-message "Must be a string beginning with a number or letter and consisting of letters, numbers, dashes, underscores, forward slashes, colons and dots.";
       }
     }
     uses apply-advanced;
     leaf match-direction {
       description "Direction for which the rule match is applied";
       type enumeration {
         enum "input" {
           description "Match on input to interface";
         }
         enum "output" {
           description "Match on output from interface";
         }
         enum "input-output" {
           description "Match an input to or output from on interface";
         }
       }
     }
     list term {
       key name;
       ordered-by user;
       description "Define a NAT term";
       leaf name {
         description "Term name";
         type string {
           length "1 .. 63";
           junos:posix-pattern "^[[:alnum:]][[:alnum:]/.:_-]*$";
           junos:pattern-message "Must be a string beginning with a number or letter and consisting of letters, numbers, dashes, underscores, forward slashes, colons and dots.";
         }
       }
       uses apply-advanced;
       leaf nat-type {
         description "NAT type (symmetric/full-cone)";
         type enumeration {
           enum "symmetric" {
             description "Symmetric NAT";
           }
           enum "full-cone" {
             description "Full Cone NAT";
           }
         }
       }
       container from {
         description "Define match criteria";
         uses sfw_match_object;
       }
       container then {
         description "Action to take if the 'from' condition is matched";
         uses apply-advanced;
         choice designation {
           case case_1 {
             leaf no-translation {
               description "Do not perform translation";
               junos:must "(!(\".. translated\"))";
               junos:must-message "translated should not be configured when no-translation is configured";
               type empty;
             }
           }
         }
         choice port-forwarding {
           case case_1 {
             leaf port-forwarding-mappings {
               description "Port forwarding mappings";
               type string {
                 length "1 .. 63";
                 junos:posix-pattern "^[[:alnum:]][[:alnum:]_-]*$";
                 junos:pattern-message "Must be a string beginning with a number or letter and consisting of letters, numbers, dashes and underscores.";
               }
             }
           }
         }
         container translated {
           description "Define translation parameters";
           uses apply-advanced;
           choice source-pool-choice {
             case case_1 {
               leaf source-pool {
                 description "NAT pool for source translation";
                 junos:must "((!(\"services nat pool $$ port deterministic-port-block-allocation\") || (\".. translation-type deterministic-napt44\" || \".. translation-type deterministic-napt64\")))";
                 junos:must-message "Deterministic source pool must be used with deterministic-napt44 or deterministic-napt64 rule only";
                 junos:must "((!(\".. address-pooling\") || \"services nat pool $$ port\"))";
                 junos:must-message "Port configuration is mandatory in the pool used with Address Pooling";
                 junos:must "((!(\".. mapping-type\") || \"services nat pool $$ port\"))";
                 junos:must-message "Port configuration is mandatory in the pool used with End Point Independent Mapping";
                 type string {
                   length "1 .. 63";
                   junos:posix-pattern "^[[:alnum:]][[:alnum:]_-]*$";
                   junos:pattern-message "Must be a string beginning with a number or letter and consisting of letters, numbers, dashes and underscores.";
                 }
               }
             }
             case case_2 {
               leaf source-prefix {
                 description "NAT prefix for source translation";
                 junos:must "(!(\".. translation-type stateful-nat64\"))";
                 junos:must-message "Source prefix is not supported with NAT64";
                 type jt:ipprefix-only;
               }
             }
           }
           leaf clat-prefix {
             description "Clat-prefix to be used for 464 translation type";
             junos:must "(\".. translation-type stateful-nat464\")";
             junos:must-message "Clat-prefix should only be used with stateful-nat464";
             type jt:ipprefix-only;
           }
           choice destination-pool-choice {
             case case_1 {
               leaf destination-pool {
                 description "NAT pool for destination translation";
                 type string {
                   length "1 .. 63";
                   junos:posix-pattern "^[[:alnum:]][[:alnum:]_-]*$";
                   junos:pattern-message "Must be a string beginning with a number or letter and consisting of letters, numbers, dashes and underscores.";
                 }
               }
             }
             case case_2 {
               leaf destination-prefix {
                 description "NAT prefix for destination translation";
                 type jt:ipprefix-only;
               }
             }
           }
           choice dns-alg-pool-choice {
             case case_1 {
               leaf dns-alg-pool {
                 description "NAT pool for dns alg mappings";
                 type string {
                   length "1 .. 63";
                   junos:posix-pattern "^[[:alnum:]][[:alnum:]_-]*$";
                   junos:pattern-message "Must be a string beginning with a number or letter and consisting of letters, numbers, dashes and underscores.";
                 }
               }
             }
             case case_2 {
               leaf dns-alg-prefix {
                 description "DNS ALG 96 bit prefix for mapping IPv4 addresses to IPv6 addresses";
                 type jt:ipprefix-only;
               }
             }
           }
           choice dns-map-address-for-destination-translation-choice {
             case case_1 {
               leaf use-dns-map-for-destination-translation {
                 description "Use dns alg address map for destination translation";
                 status deprecated;
                 type empty;
               }
             }
           }
           choice overload-pool-choice {
             case case_1 {
               leaf overload-pool {
                 description "NAT pool to be used when source pool is overloaded";
                 type string {
                   length "1 .. 63";
                   junos:posix-pattern "^[[:alnum:]][[:alnum:]_-]*$";
                   junos:pattern-message "Must be a string beginning with a number or letter and consisting of letters, numbers, dashes and underscores.";
                 }
               }
             }
             case case_2 {
               leaf overload-prefix {
                 description "NAT prefix to be used when source pool is overloaded";
                 type jt:ipprefix-only;
               }
             }
           }
           container translation-type {
             description "Type of translation to perform";
             uses apply-advanced;
             leaf source {
               description "Type of source translation";
               status deprecated;
               type enumeration {
                 enum "static" {
                   description "Static translation";
                   status deprecated;
                 }
                 enum "dynamic" {
                   description "Dynamic translation";
                   status deprecated;
                 }
               }
             }
             leaf destination {
               description "Type of destination translation";
               status deprecated;
               type enumeration {
                 enum "static" {
                   description "Static translation";
                   status deprecated;
                 }
               }
             }
             container basic-nat44 {
               presence "enable basic-nat44";
               description "Static source address (IPv4 to IPv4) translation";
             }
             container dynamic-nat44 {
               presence "enable dynamic-nat44";
               description "Dynamic source address only (IPv4 to IPv4) translation";
             }
             container napt-44 {
               presence "enable napt-44";
               description "Source address (IPv4 to IPv4) and port translation";
             }
             container dnat-44 {
               presence "enable dnat-44";
               description "Static Destination address (IPv4 to IPv4) translation";
             }
             container stateful-nat64 {
               presence "enable stateful-nat64";
               description "Dynamic source address (IPv6 to IPv4) and prefix removal for destination address (IPv6 to IPv4)translation";
             }
             container stateful-nat464 {
               presence "enable stateful-nat464";
               junos:must "((\".. .. .. translated clat-prefix\" && (\".. .. .. translated destination-prefix\" && (\".. .. .. .. from destination-address\" && (\".. .. .. .. from source-address\" && \".. .. .. translated source-pool\")))))";
               junos:must-message "All clat-prefix/destination-prefix/source-address/destination-address/source-pool are required for NAT464";
               description "Prefix removal for Src and Dest address (IPv6 to IPv4) translation";
             }
             container basic-nat-pt {
               presence "enable basic-nat-pt";
               description "NAT-PT (static source address (IPv6 to IPv4) and prefix removal for destination address (IPv6 to IPv4) translation)";
             }
             container napt-pt {
               presence "enable napt-pt";
               description "NAT-PT (source address (IPv6 to IPv4) and source port and prefix removal for destination address (IPv6 to IPv4) translation)";
             }
             container basic-nat66 {
               presence "enable basic-nat66";
               description "Static source address (IPv6 to IPv6) translation [same as basic-nat44 but for IPv6 address family]";
             }
             container nptv6 {
               presence "enable nptv6";
               description "Stateless source address (IPv6 to IPv6) translation";
             }
             container napt-66 {
               presence "enable napt-66";
               description "Source address (IPv6 to IPv6) and port translation [same as napt-44 but for IPv6 address family]";
             }
             container twice-napt-44 {
               presence "enable twice-napt-44";
               description "Source NAPT and destination static translation for IPv4 address family";
             }
             container twice-basic-nat-44 {
               presence "enable twice-basic-nat-44";
               description "Source static and destination static translation for IPv4 address family";
             }
             container twice-dynamic-nat-44 {
               presence "enable twice-dynamic-nat-44";
               description "Source dynamic and destination static translation for IPv4 address family";
             }
             container deterministic-napt44 {
               presence "enable deterministic-napt44";
               junos:must "((\".. .. .. .. from source-address\" || (\".. .. .. .. from source-address-range\" || \".. .. .. .. from source-prefix-list\")))";
               junos:must-message "Deterministic NAT translation requires source-address or source-prefix-list in the from clause";
               description "Deterministic source NAPT for IPv4 family";
               uses apply-advanced;
             }
             container deterministic-napt64 {
               presence "enable deterministic-napt64";
               junos:must "((\".. .. .. .. from source-address\" || (\".. .. .. .. from source-address-range\" || \".. .. .. .. from source-prefix-list\")))";
               junos:must-message "Deterministic NAT translation requires source-address or source-prefix-list in the from clause";
               description "Deterministic source NAPT for IPv6 family";
             }
           }
           leaf mapping-type {
             description "Source NAT mapping type";
             junos:must "((\".. translation-type source\" || (\".. translation-type napt-44\" || (\".. translation-type deterministic-napt44\" || (\".. translation-type deterministic-napt64\" || (\".. translation-type stateful-nat64\" || \".. translation-type stateful-nat464\"))))))";
             junos:must-message "mapping-type applies only to source NAPT";
             type enumeration {
               enum "endpoint-independent" {
                 description "Endpoint independent mapping";
               }
             }
           }
           leaf flow-type {
             description "Source NAT flow type";
             junos:must "((\".. translation-type napt-44\" || \".. translation-type dynamic-nat44\"))";
             junos:must-message "flow-type applies only to napt-44 or dynamic-nat44";
             type enumeration {
               enum "endpoint-independent" {
                 description "Endpoint independent flow";
               }
             }
           }
           leaf ignore-dst-nat-1to1-limitation {
             description "Ignore destination NAT 1:1 limitation";
             type empty;
           }
           container secure-nat-mapping {
             presence "enable secure-nat-mapping";
             description "Mapping options for enhanced security";
             uses apply-advanced;
             leaf eif-flow-limit {
               description "Number of inbound flows to be allowed for a EIF mapping";
               junos:must "(\".. .. filtering-type\")";
               junos:must-message "eif-flow-limit applies only to filtering-type";
               type union {
                 type string {
                   pattern "<.*>|$.*";
                 }
                 type uint16 {
                   range "0 .. 65534";
                 }
               }
             }
             leaf mapping-refresh {
               description "Enable timer refresh option";
               type enumeration {
                 enum "inbound" {
                   description "Enable timer refresh for inbound connections only";
                 }
                 enum "outbound" {
                   description "Enable timer refresh for outbound connections only";
                 }
                 enum "inbound-outbound" {
                   description "Enable timer refresh for inbound & outbound connections";
                 }
               }
             }
             leaf flow-refresh {
               description "Enable timer refresh option";
               type enumeration {
                 enum "inbound" {
                   description "Enable timer refresh for inbound connections only";
                 }
                 enum "outbound" {
                   description "Enable timer refresh for outbound connections only";
                 }
                 enum "inbound-outbound" {
                   description "Enable timer refresh for inbound & outbound connections";
                 }
               }
             }
           }
           container filtering-type {
             junos:must "(\".. mapping-type endpoint-independent\")";
             junos:must-message "endpoint independent filtering can be configured with endpoint-independent mapping only";
             junos:must "((\".. translation-type source\" || (\".. translation-type napt-44\" || (\".. translation-type deterministic-napt44\" || (\".. translation-type deterministic-napt64\" || (\".. translation-type stateful-nat64\" || \".. translation-type stateful-nat464\"))))))";
             junos:must-message "filtering-type applies only to source NAPT";
             description "Source NAT filtering type";
             uses apply-advanced;
             container endpoint-independent {
               presence "enable endpoint-independent";
               description "Endpoint independent filtering";
               uses apply-advanced;
               list prefix-list {
                 key name;
                 ordered-by user;
                 description "One or more named lists of source prefixes to match";
                 leaf name {
                   description "Name of prefix list to match against";
                   type string;
                 }
                 leaf except {
                   description "Name of prefix list not to match against";
                   type empty;
                 }
               }
             }
           }
           leaf address-pooling {
             description "Address pooling behavior for source NAT";
             junos:must "((\".. translation-type source\" || (\".. translation-type napt-44\" || (\".. translation-type stateful-nat64\" || (\".. translation-type stateful-nat464\" || (\".. translation-type deterministic-napt44\" || \".. translation-type deterministic-napt64\"))))))";
             junos:must-message "address-pooling applies only to source NAPT, stateful NAT64 and stateful NAT464";
             type enumeration {
               enum "paired" {
                 description "Address pooling behavior of paired";
               }
             }
           }
         }
         leaf syslog {
           description "System log information about the packet";
           type empty;
         }
       }
     }
   }
   grouping new_call_then_type {
     uses apply-advanced;
     leaf trace {
       description "Trace messages accepted on this policy";
       type empty;
     }
     container media-policy {
       description "Media policy parameters";
       uses apply-advanced;
       choice anchoring-policy {
         case case_1 {
           leaf no-anchoring {
             description "Setting this would bypass media packet gateway processing";
             type empty;
           }
         }
         case case_2 {
           leaf media-release {
             description "Release media - media will not be anchored";
             type empty;
           }
         }
       }
       container nat-traversal {
         presence "enable nat-traversal";
         description "Choose when to perform NAT traversal";
         uses apply-advanced;
         leaf nat-traversal-strategy {
           description "Choose when to perform NAT traversal";
           type enumeration {
             enum "never" {
               description "Never perform NAT traversal";
             }
             enum "always" {
               description "Always perform NAT traversal";
             }
             enum "same-as-signaling" {
               description "Perform NAT traversal according to signaling";
             }
           }
         }
         leaf force-bidirectional-media {
           description "Force bidirectional media";
           type empty;
         }
       }
       container data-inactivity-detection {
         description "Configuration of data inactivity indicators";
         uses apply-advanced;
         leaf inactivity-duration {
           description "The amount of time in seconds a stream is inactive before a notification is sent to the SPDF";
           units "seconds";
           type union {
             type string {
               pattern "<.*>|$.*";
             }
             type uint16 {
               range "30 .. 3600";
             }
           }
         }
       }
       leaf service-class {
         description "Rate limiting and dscp marking based on the media type";
         junos:must "(\"services border-signaling-gateway gateway ${gateway} embedded-spdf service-class $$\")";
         junos:must-message "Referenced service class must be defined";
         type string {
           length "1 .. 63";
         }
       }
     }
   }
   grouping new_call_usage_set_type {
     leaf name {
       description "Policy set name";
       type string;
     }
     uses apply-advanced;
     leaf-list policy-name {
       ordered-by user;
       description "Policy name";
       type string;
       max-elements 500;
     }
   }
   grouping new_registration_set_type {
     leaf name {
       description "Policy set name";
       type string;
     }
     uses apply-advanced;
     leaf-list policy-name {
       ordered-by user;
       description "Policy name";
       type string;
       max-elements 500;
     }
   }
   grouping new_transaction_set_type {
     leaf name {
       description "Policy set name";
       type string;
     }
     uses apply-advanced;
     leaf-list policy-name {
       ordered-by user;
       description "Policy name";
       type string;
       max-elements 500;
     }
   }
   grouping output-plugin {
     leaf name {
       description "Plugin name";
       type string;
     }
     uses apply-advanced;
     list parameters {
       key name;
       ordered-by user;
       description "List of key:value parameters for plugin";
       uses parameter-pair;
     }
   }
   grouping parameter-pair {
     leaf name {
       description "Parameter key";
       type string;
     }
     uses apply-advanced;
     leaf value {
       description "Parameter value";
       type string;
     }
   }
   grouping pcp-rule-object {
     leaf name {
       description "Rule name";
       type string {
         length "1 .. 63";
         junos:posix-pattern "^[[:alnum:]][[:alnum:]_-]*$";
         junos:pattern-message "Must be a string beginning with a number or letter and consisting of letters, numbers, dashes and underscores.";
       }
     }
     uses apply-advanced;
     leaf match-direction {
       description "Define direction for which the rule match is applied";
       type enumeration {
         enum "input" {
           description "Match on input to interface";
         }
         enum "output" {
           description "Match on output from interface";
         }
       }
     }
     list term {
       key name;
       ordered-by user;
       description "Define a PCP term";
       leaf name {
         description "Term name";
         type string {
           length "1 .. 63";
           junos:posix-pattern "^[[:alnum:]][[:alnum:]_-]*$";
           junos:pattern-message "Must be a string beginning with a number or letter and consisting of letters, numbers, dashes and underscores.";
         }
       }
       uses apply-advanced;
       container from {
         description "Define match criteria";
         uses sfw_match_object;
       }
       container then {
         description "Action to take if the 'from' condition is matched";
         uses apply-advanced;
         leaf pcp-server {
           description "Define PCP server";
           junos:must "(\"services pcp server $$\")";
           junos:must-message "Referenced PCP server must be defined";
           type string {
             length "1 .. 63";
             junos:posix-pattern "^[[:alnum:]][[:alnum:]_-]*$";
             junos:pattern-message "Must be a string beginning with a number or letter and consisting of letters, numbers, dashes and underscores.";
           }
         }
       }
     }
   }
   grouping pcp-server-object {
     leaf name {
       description "Name of PCP server";
       type string {
         length "1 .. 63";
         junos:posix-pattern "^[[:alnum:]][[:alnum:]_-]*$";
         junos:pattern-message "Must be a string beginning with a number or letter and consisting of letters, numbers, dashes and underscores.";
       }
     }
     uses apply-advanced;
     leaf ipv4-address {
       description "Configure IPv4 address for this PCP server";
       type jt:ipv4addr;
     }
     leaf ipv6-address {
       description "Configure IPv6 address for this PCP server";
       junos:must "(\".. softwire-concentrator\")";
       junos:must-message "softwire-concentrator is a must with ipv6-address, please configure it under this pcp-server";
       type jt:ipv6addr;
     }
     leaf softwire-concentrator {
       description "Softwire ds-lite concentrator";
       junos:must "(!(\".. ipv4-address\"))";
       junos:must-message "referenced softwire-concentrator must be used only with DS-LITE, please remove ipv4-address in this pcp-server";
       junos:must "(\".. ipv6-address\")";
       junos:must-message "referenced softwire-concentrator must be used only with DS-LITE, must define ipv6-address in this pcp-server";
       junos:must "(\"services softwire softwire-concentrator ds-lite $$\")";
       junos:must-message "referenced softwire-concentrator must be defined under 'services softwire softwire-concentrator ds-lite'";
       type string {
         length "1 .. 63";
       }
     }
     leaf mapping-lifetime-minimum {
       description "Configure the minimum lifetime for any mapping";
       default "120";
       units "second";
       type union {
         type string {
           pattern "<.*>|$.*";
         }
         type uint16 {
           range "120 .. 3600";
         }
       }
     }
     leaf mapping-lifetime-maximum {
       description "Configure the maximum lifetime for any mapping";
       default "86400";
       units "second";
       type union {
         type string {
           pattern "<.*>|$.*";
         }
         type uint32 {
           range "120 .. 4294667";
         }
       }
     }
     leaf short-lifetime-error {
       description "Configure duration of a short-lifetime error";
       default "30";
       units "second";
       type union {
         type string {
           pattern "<.*>|$.*";
         }
         type uint16 {
           range "15 .. 300";
         }
       }
     }
     leaf long-lifetime-error {
       description "Configure duration of a long-lifetime error";
       default "1800";
       units "second";
       type union {
         type string {
           pattern "<.*>|$.*";
         }
         type uint16 {
           range "900 .. 18000";
         }
       }
     }
     leaf max-mappings-per-client {
       description "Configure maximum mappings permitted per client";
       default "32";
       type union {
         type string {
           pattern "<.*>|$.*";
         }
         type uint16 {
           range "1 .. 128";
         }
       }
     }
     container pcp-options {
       description "Configure PCP options supported by this server";
       leaf third-party {
         description "Enable Third Party option";
         type empty;
       }
       leaf prefer-failure {
         description "Enable Prefer Failure option";
         type empty;
       }
     }
     container nat-options {
       description "NAT options of this PCP server";
       uses apply-advanced;
       list pool {
         key name;
         ordered-by user;
         description "NAT pool name";
         uses nat_pool_list_object;
       }
     }
   }
   grouping nat_pool_list_object {
     description "One or more nat pools";
     leaf name {
       junos:must "(\"services nat pool $$\")";
       junos:must-message "referenced nat pool must be defined";
       type string {
         length "1 .. 63";
         junos:posix-pattern "^[[:alnum:]][[:alnum:]_-]*$";
         junos:pattern-message "Must be a string beginning with a number or letter and consisting of letters, numbers, dashes and underscores.";
       }
     }
   }
   grouping pf_mapping {
     leaf name {
       description "Port Forwarding name";
       type string {
         length "1 .. 63";
         junos:posix-pattern "^[[:alnum:]][[:alnum:]_-]*$";
         junos:pattern-message "Must be a string beginning with a number or letter and consisting of letters, numbers, dashes and underscores.";
       }
     }
     uses apply-advanced;
     list destined-port {
       key "port translated-port";
       ordered-by user;
       description "Port forwarding mappings";
       max-elements 32;
       leaf port {
         description "Destination port";
         type union {
           type string {
             pattern "<.*>|$.*";
           }
           type uint16 {
             range "1 .. 65535";
           }
         }
       }
       leaf translated-port {
         description "Translated port";
         type union {
           type string {
             pattern "<.*>|$.*";
           }
           type uint16 {
             range "1 .. 65535";
           }
         }
       }
     }
   }
   grouping pgcp_gateway_object {
     description "One or more Packet Gateways";
     leaf name {
       description "Gateway Name";
       type string {
         length "1 .. 63";
       }
     }
     uses apply-advanced;
     leaf gateway-address {
       description "Local Gateway IP address";
       type jt:ipv4addr;
     }
     leaf routing-instance {
       description "Routing instance";
       default "inet.0";
       type string;
     }
     leaf gateway-port {
       description "Local Gateway transport port";
       default "2944";
       type union {
         type uint16;
         type string {
           pattern "<.*>|$.*";
         }
       }
     }
     leaf cleanup-timeout {
       description "When expires the PG will clean its gate state (Applicable in disconnections)";
       units "seconds";
       type union {
         type string {
           pattern "<.*>|$.*";
         }
         type uint16 {
           range "5 .. 65535";
         }
       }
     }
     leaf service-state {
       description "Service state";
       type enumeration {
         enum "in-service" {
           description "Gateway is operational";
         }
         enum "out-of-service-forced" {
           description "Gateway is nonoperational";
         }
         enum "out-of-service-graceful" {
           description "Gateway becomes nonoperational by draining";
         }
       }
     }
     container h248-timers {
       uses pgcp_h248_timers_object;
     }
     container h248-properties {
       uses pgcp_h248_properties_object;
     }
     container h248-options {
       uses pgcp_h248_options_object;
     }
     leaf max-concurrent-calls {
       description "Maximum number of concurrent calls";
       default "0";
       type union {
         type string {
           pattern "<.*>|$.*";
         }
         type uint32 {
           range "0 .. 20000";
         }
       }
     }
     list gateway-controller {
       key name;
       ordered-by user;
       max-elements 32;
       uses pgcp_controller_object;
     }
     container monitor {
       description "Monitor voice traffic";
       uses apply-advanced;
       container media {
         presence "enable media";
         description "Monitor media traffic";
         uses apply-advanced;
         leaf rtp {
           description "Monitor RTP traffic";
           type empty;
         }
         leaf rtcp {
           description "Monitor RTCP traffic";
           type empty;
         }
       }
     }
     container graceful-restart {
       presence "enable graceful-restart";
       uses apply-advanced;
       leaf maximum-synchronization-time {
         description "Maximum time for synchronization procedure with the PIC";
         status deprecated;
         default "720";
         units "seconds";
         type union {
           type string {
             pattern "<.*>|$.*";
           }
           type uint16 {
             range "0 .. 720";
           }
         }
       }
       leaf maximum-synchronization-mismatches {
         description "Maximum number of mismatches for synchronization procedure with the PIC";
         default "250";
         type union {
           type string {
             pattern "<.*>|$.*";
           }
           type uint32 {
             range "0 .. 20000";
           }
         }
       }
       leaf no-synchronization {
         description "Disable the synchronization procedure with the PIC";
         type empty;
       }
       leaf catchup-replication-delay {
         description "Delay between replication of new updates and catch-up";
         default "300";
         type union {
           type string {
             pattern "<.*>|$.*";
           }
           type uint16 {
             range "0 .. 600";
           }
         }
       }
     }
     container fast-update-filters {
       presence "enable fast-update-filters";
       uses apply-advanced;
       leaf maximum-terms {
         description "Maximum gate rate-limit terms to install at PFE";
         default "2000";
         type union {
           type string {
             pattern "<.*>|$.*";
           }
           type uint64 {
             range "0 .. 20000";
           }
         }
       }
       leaf maximum-term-percentage {
         description "Maximum percentage of gates with rate-limit terms at PFE";
         default "10";
         type union {
           type string {
             pattern "<.*>|$.*";
           }
           type uint8 {
             range "0 .. 100";
           }
         }
       }
     }
     container session-mirroring {
       uses pgcp_gateway_session_mirroring_object;
     }
     container data-inactivity-detection {
       uses apply-advanced;
       leaf inactivity-delay {
         description "Delay before data inactivity detection starts";
         default "0";
         units "seconds";
         type union {
           type string {
             pattern "<.*>|$.*";
           }
           type uint16 {
             range "0 .. 3600";
           }
         }
       }
       leaf latch-deadlock-delay {
         description "Delay value used for gates employing NAPT traversal";
         default "0";
         units "seconds";
         type union {
           type string {
             pattern "<.*>|$.*";
           }
           type uint16 {
             range "0 .. 3600";
           }
         }
       }
       leaf send-notification-on-delay {
         description "Send inactivity notification when delay expires";
         type empty;
       }
       leaf inactivity-duration {
         description "Default data inactivity duration (Q-MI)";
         default "15";
         units "seconds";
         type union {
           type string {
             pattern "<.*>|$.*";
           }
           type uint32 {
             range "5 .. 86400";
           }
         }
       }
       leaf stop-detection-on-drop {
         description "Stop detection when gate action is set to drop";
         type empty;
       }
       leaf no-rtcp-check {
         description "Do not detect data inactivity on rtcp stream";
         type empty;
       }
       container report-service-change {
         description "Configure the data-inactivity service-change behavior";
         uses apply-advanced;
         leaf service-change-type {
           description "Configure the service-change type to be sent upon data-inactivity";
           type enumeration {
             enum "forced-910" {
               description "Send FO/910 service change";
             }
             enum "forced-906" {
               description "Send FO/906 service change";
             }
           }
         }
       }
     }
     container overload-control {
       presence "enable overload-control";
       uses apply-advanced;
       leaf queue-limit-percentage {
         description "Overload control queue limit percentage";
         default "70";
         type union {
           type string {
             pattern "<.*>|$.*";
           }
           type uint8 {
             range "0 .. 100";
           }
         }
       }
       leaf reject-new-calls-threshold {
         description "Overload control reject new calls threshold";
         default "80";
         type union {
           type string {
             pattern "<.*>|$.*";
           }
           type uint8 {
             range "0 .. 100";
           }
         }
       }
       leaf reject-all-commands-threshold {
         description "Overload control reject all commands threshold";
         default "90";
         type union {
           type string {
             pattern "<.*>|$.*";
           }
           type uint8 {
             range "0 .. 100";
           }
         }
       }
       leaf queue-maximum-length {
         description "Overload control queue maximum length";
         default "100";
         type union {
           type string {
             pattern "<.*>|$.*";
           }
           type uint16 {
             range "10 .. 1000";
           }
         }
       }
       leaf error-code {
         description "Overload control error code";
         default "511";
         type union {
           type string {
             pattern "<.*>|$.*";
           }
           type uint16 {
             range "510 .. 511";
           }
         }
       }
     }
     container platform {
       presence "enable platform";
       description "Define the platform on which the gateway should be activated";
       uses apply-advanced;
       choice values {
         case case_1 {
           leaf routing-engine {
             description "The gateway should be activated on the RE";
             type empty;
           }
         }
         case case_2 {
           leaf device {
             description "The gateway should be activated on a services device";
             junos:must "(\"interfaces $$\")";
             junos:must-message "The device name should be defined as an interface";
             type union {
               type jt:interface-device;
               type string {
                 pattern "<.*>|$.*";
               }
             }
           }
         }
       }
     }
     leaf ipsec-transport-security-association {
       description "IPsec transport security association name";
       type string {
         length "1 .. 63";
       }
     }
   }
   grouping pgcp_controller_object {
     leaf name {
       description "PGCP Controller Name";
       type string {
         length "1 .. 63";
       }
     }
     uses apply-advanced;
     leaf controller-address {
       description "Gateway controller IP address";
       type jt:ipv4addr;
     }
     leaf controller-port {
       description "Gateway controller port";
       default "2944";
       type union {
         type uint16;
         type string {
           pattern "<.*>|$.*";
         }
       }
     }
     container interim-ah-scheme {
       uses pgcp_interim_ah_scheme_object;
     }
     choice controller-type {
       case case_1 {
         leaf remote-controller {
           description "The gateway controller is remote";
           junos:must "(\"services pgcp gateway ${gateway} gateway-controller ${gateway-controller} controller-address\")";
           junos:must-message "remote-controller requires gateway-controller-address";
           junos:must "(\"services pgcp gateway ${gateway} gateway-address\")";
           junos:must-message "remote-controller requires gateway-address";
           type empty;
         }
       }
       case case_2 {
         leaf local-controller {
           description "The gateway controller is local";
           junos:must "(\"services border-signaling-gateway gateway $$\")";
           junos:must-message "local-controller name should be defined as border-signaling-gateway";
           type string {
             length "1 .. 63";
           }
         }
       }
     }
   }
   grouping pgcp_gateway_session_mirroring_object {
     description "Gateway session mirroring properties";
     uses apply-advanced;
     list delivery-function {
       key name;
       ordered-by user;
       description "Interface for delivering mirrored packets";
       max-elements 1;
       uses pgcp_delivery_function_list_object;
     }
     leaf disable-session-mirroring {
       description "Disable session mirroring for this gateway";
       type empty;
     }
   }
   grouping pgcp_delivery_function_list_object {
     description "Session-mirroring delivery functions";
     leaf name {
       junos:must "((\"services pgcp session-mirroring delivery-function $$\" && !(\"services pgcp session-mirroring disable-session-mirroring\")))";
       junos:must-message "referenced delivery-function must be defined and enabled";
       type string {
         length "1 .. 63";
       }
     }
   }
   grouping pgcp_h248_options_object {
     uses apply-advanced;
     container service-change {
       uses pgcp-h248-service-change-object;
     }
     leaf audit-observed-events-returns {
       description "Activation of history buffer for audit observed events";
       type empty;
     }
     container encoding {
       presence "enable encoding";
       uses apply-advanced;
       leaf no-octet-string-bit-mirroring {
         description "No octet string bit mirroring";
         type empty;
       }
       leaf no-dscp-bit-mirroring {
         description "No DSCP bit mirroring";
         status deprecated;
         type empty;
       }
       leaf use-lower-case {
         description "Encode H248 message in lower case";
         type empty;
       }
     }
     container h248-profile {
       uses apply-advanced;
       leaf profile-name {
         description "The H.248 profile declared by the BGF";
         type string {
           length "1 .. 64";
           junos:posix-pattern "^[A-Za-z][_0-9A-Za-z]{0,63}$";
           junos:pattern-message "Must be a string beginning with a letter and consisting of no more than 64 total letters, numbers and underscores.";
         }
       }
       leaf profile-version {
         description "The H.248 profile-version declared by the BGF";
         type union {
           type string {
             pattern "<.*>|$.*";
           }
           type uint32 {
             range "1 .. 99";
           }
         }
       }
     }
     leaf accept-emergency-calls-while-graceful {
       description "Accept emergency calls while BGF is in OOS gracefull state";
       type empty;
     }
     leaf implicit-tcp-latch {
       description "Latch implicitly upon TCP transport usage";
       type empty;
     }
     leaf implicit-tcp-source-filter {
       description "Implicitly filter TCP source addresses";
       type empty;
     }
   }
   grouping pgcp-h248-service-change-object {
     uses apply-advanced;
     container control-association-indications {
       description "Control association indications";
       uses control-association-indications-object;
     }
     container virtual-interface-indications {
       description "Virtual interface indications";
       uses virtual-interface-indications-object;
     }
     container context-indications {
       description "Context indications";
       uses context-indications-object;
     }
     leaf use-wildcard-response {
       description "Request short response to service-change messages";
       type empty;
     }
   }
   grouping context-indications-object {
     description "Context indications";
     uses apply-advanced;
     leaf state-loss {
       description "Configure state loss service change";
       type enumeration {
         enum "forced-915" {
           description "State loss";
         }
         enum "forced-910" {
           description "State loss reason fo/910";
         }
         enum "none" {
           description "Suppress state loss 918 service change";
         }
       }
     }
   }
   grouping control-association-indications-object {
     description "Control association indications";
     uses apply-advanced;
     container up {
       uses pgcp-association-up-object;
     }
     container down {
       uses pgcp-association-down-object;
     }
     container disconnect {
       uses pgcp-association-disconnect-object;
     }
   }
   grouping pgcp-association-disconnect-object {
     description "Control association disconnect";
     uses apply-advanced;
     leaf reconnect {
       description "Configure reconnect service change";
       type enumeration {
         enum "disconnected-900" {
           description "Service restored";
         }
         enum "restart-902" {
           description "Warm boot";
         }
       }
     }
     leaf controller-failure {
       description "Configure controller failure service change";
       type enumeration {
         enum "restart-902" {
           description "Warm boot";
         }
         enum "failover-909" {
           description "Gateway controller impending failure";
         }
       }
     }
   }
   grouping pgcp-association-down-object {
     description "Control association down";
     uses apply-advanced;
     leaf administrative {
       description "Configure administrative service change";
       type enumeration {
         enum "forced-905" {
           description "Termination taken out of service";
         }
         enum "forced-908" {
           description "Gateway impending failure";
         }
         enum "none" {
           description "Suppress service change";
         }
       }
     }
     leaf failure {
       description "Configure failure service change";
       type enumeration {
         enum "forced-904" {
           description "Termination malfunctioning";
         }
         enum "forced-908" {
           description "Gateway impending failure";
         }
         enum "none" {
           description "Suppress service change";
         }
       }
     }
     leaf graceful {
       description "Configure graceful service change";
       type enumeration {
         enum "none" {
           description "Suppress graceful-905 service change";
         }
         enum "graceful-905" {
           description "Termination taken out of service";
         }
       }
     }
   }
   grouping pgcp-association-up-object {
     description "Control association up";
     uses apply-advanced;
     leaf failover-cold {
       description "Configure failover-cold service change";
       type enumeration {
         enum "restart-901" {
           description "Cold boot";
         }
         enum "failover-920" {
           description "Cold failover";
         }
       }
     }
     leaf failover-warm {
       description "Configure failover-warm service change";
       type enumeration {
         enum "restart-902" {
           description "Warm boot";
         }
         enum "failover-919" {
           description "Warm failover";
         }
       }
     }
     leaf cancel-graceful {
       description "Configure cancel-graceful service change";
       type enumeration {
         enum "none" {
           description "Suppress restart-918 service change";
         }
         enum "restart-918" {
           description "Cancel graceful";
         }
       }
     }
   }
   grouping pgcp_h248_properties_object {
     description "Gateway H248 properties";
     uses apply-advanced;
     container base-root {
       description "Setting H248 mg-mgc transaction time values";
       uses pgcp_h248_base_root_object;
     }
     container segmentation {
       uses pgcp_h248_segmentation_object;
     }
     container diffserv {
       uses pgcp_h248_diffserv_object;
     }
     container hanging-termination-detection {
       description "Enabling Hanging termination detection";
       uses pgcp-h248-hangterm-object;
     }
     container traffic-management {
       description "Setting of h248 traffic management default values";
       uses pgcp_h248_traffic_management_object;
     }
     container notification-behavior {
       description "Setting of h248 Notify behavior values";
       uses pgcp-h248-notification-behavior-object;
     }
     container application-data-inactivity-detection {
       description "Setting application data inactivity detection";
       uses pgcp-h248-application-data-inactivity-detection-object;
     }
     container event-timestamp-notification {
       description "Setting event timestamp notification";
       uses pgcp-h248-event-timestamp-notification-object;
     }
     container inactivity-timer {
       description "Default values for inactivity timeout";
       uses pgcp-h248-inactivity-timer-object;
     }
   }
   grouping pgcp-h248-application-data-inactivity-detection-object {
     description "Application data inactivity detection";
     uses apply-advanced;
     leaf ip-flow-stop-detection {
       description "Setting ip flow stop detection";
       type enumeration {
         enum "immediate-notify" {
           description "Report all notifications";
         }
         enum "regulated-notify" {
           description "Suppress notification according to notification-count";
         }
       }
     }
   }
   grouping pgcp-h248-event-timestamp-notification-object {
     description "Event timestamp notification";
     uses apply-advanced;
     leaf request-timestamp {
       description "Notification timestamp";
       type enumeration {
         enum "requested" {
           description "Send event timestamp";
         }
         enum "suppressed" {
           description "Dont send event timestamp";
         }
         enum "autonomous" {
           description "Show timestamp at notify request";
         }
       }
     }
   }
   grouping pgcp-h248-hangterm-object {
     description "Hanging termination detection timer";
     uses apply-advanced;
     leaf timerx {
       description "Setting timerx value";
       default "0";
       units "seconds";
       type union {
         type string {
           pattern "<.*>|$.*";
         }
         type uint32 {
           range "0 .. 2147480";
         }
       }
     }
   }
   grouping pgcp-h248-inactivity-timer-object {
     description "A timer to verify PGC connectivity";
     uses apply-advanced;
     container inactivity-timeout {
       presence "enable inactivity-timeout";
       uses apply-advanced;
       leaf detect {
         description "Enable/Disable inactivity timer detection";
         type empty;
       }
       container maximum-inactivity-time {
         uses apply-advanced;
         leaf default {
           description "Default maximum inactivity timeout";
           default "12000";
           units "10-milliseconds";
           type union {
             type string {
               pattern "<.*>|$.*";
             }
             type uint16 {
               range "100 .. 65535";
             }
           }
         }
         leaf minimum {
           description "Minimum range for maximum inactivity timeout";
           default "100";
           units "10-milliseconds";
           type union {
             type string {
               pattern "<.*>|$.*";
             }
             type uint16 {
               range "100 .. 65535";
             }
           }
         }
         leaf maximum {
           description "Maximum range for maximum inactivity timeout";
           default "65535";
           units "10-milliseconds";
           type union {
             type string {
               pattern "<.*>|$.*";
             }
             type uint16 {
               range "100 .. 65535";
             }
           }
         }
       }
     }
   }
   grouping pgcp-h248-notification-behavior-object {
     description "Notify behavior parameters";
     uses apply-advanced;
     container notification-regulation {
       presence "enable notification-regulation";
       uses apply-advanced;
       leaf default {
         description "Default suppression percentage of Notification behavior Regulation ";
         type string {
           junos:posix-pattern "^(once|100|[0-9]{1,2})$";
           junos:pattern-message "Regulation can be 0-100 percentage or 'once'";
         }
       }
     }
   }
   grouping pgcp_h248_base_root_object {
     uses apply-advanced;
     container normal-mg-execution-time {
       presence "enable normal-mg-execution-time";
       description "MG transaction response time expected by MGC.";
       uses apply-advanced;
       leaf default {
         default "500";
         units "milliseconds";
         type union {
           type string {
             pattern "<.*>|$.*";
           }
           type uint16 {
             range "500 .. 29000";
           }
         }
       }
       leaf minimum {
         description "Minimum range of execution time value";
         default "500";
         units "milliseconds";
         type union {
           type string {
             pattern "<.*>|$.*";
           }
           type uint16 {
             range "500 .. 29000";
           }
         }
       }
       leaf maximum {
         description "Maximum range of execution time value";
         default "29000";
         units "milliseconds";
         type union {
           type string {
             pattern "<.*>|$.*";
           }
           type uint16 {
             range "500 .. 29000";
           }
         }
       }
     }
     container mg-provisional-response-timer-value {
       presence "enable mg-provisional-response-timer-value";
       description "MG pending response time upon incomplete transaction.";
       uses apply-advanced;
       leaf default {
         default "2000";
         units "milliseconds";
         type union {
           type string {
             pattern "<.*>|$.*";
           }
           type uint16 {
             range "500 .. 30000";
           }
         }
       }
       leaf minimum {
         description "Minimum range of timers value";
         default "500";
         units "milliseconds";
         type union {
           type string {
             pattern "<.*>|$.*";
           }
           type uint16 {
             range "500 .. 30000";
           }
         }
       }
       leaf maximum {
         description "Maximum range of timer value";
         default "30000";
         units "milliseconds";
         type union {
           type string {
             pattern "<.*>|$.*";
           }
           type uint16 {
             range "500 .. 30000";
           }
         }
       }
     }
     container mg-originated-pending-limit {
       presence "enable mg-originated-pending-limit";
       description "Max MG TransactionPendings num recieved.";
       uses apply-advanced;
       leaf default {
         default "4";
         type union {
           type string {
             pattern "<.*>|$.*";
           }
           type uint16 {
             range "1 .. 512";
           }
         }
       }
       leaf minimum {
         description "Minimum range of pending limit value";
         default "1";
         type union {
           type string {
             pattern "<.*>|$.*";
           }
           type uint16 {
             range "1 .. 512";
           }
         }
       }
       leaf maximum {
         description "Maximum range of pending limit value";
         default "512";
         type union {
           type string {
             pattern "<.*>|$.*";
           }
           type uint16 {
             range "1 .. 512";
           }
         }
       }
     }
     container normal-mgc-execution-time {
       presence "enable normal-mgc-execution-time";
       description "MGC transaction response time expected by MG.";
       uses apply-advanced;
       leaf default {
         default "500";
         units "milliseconds";
         type union {
           type string {
             pattern "<.*>|$.*";
           }
           type uint16 {
             range "500 .. 29000";
           }
         }
       }
       leaf minimum {
         description "Minimum range of execution time value";
         default "500";
         units "milliseconds";
         type union {
           type string {
             pattern "<.*>|$.*";
           }
           type uint16 {
             range "500 .. 29000";
           }
         }
       }
       leaf maximum {
         description "Maximum range of execution time value";
         default "29000";
         units "milliseconds";
         type union {
           type string {
             pattern "<.*>|$.*";
           }
           type uint16 {
             range "500 .. 29000";
           }
         }
       }
     }
     container mgc-provisional-response-timer-value {
       presence "enable mgc-provisional-response-timer-value";
       description "MGC pending response time upon incomplete transaction.";
       uses apply-advanced;
       leaf default {
         default "4000";
         units "milliseconds";
         type union {
           type string {
             pattern "<.*>|$.*";
           }
           type uint16 {
             range "500 .. 30000";
           }
         }
       }
       leaf minimum {
         description "Minimum range of timers value";
         default "500";
         units "milliseconds";
         type union {
           type string {
             pattern "<.*>|$.*";
           }
           type uint16 {
             range "500 .. 30000";
           }
         }
       }
       leaf maximum {
         description "Maximum range of timers value";
         default "30000";
         units "milliseconds";
         type union {
           type string {
             pattern "<.*>|$.*";
           }
           type uint16 {
             range "500 .. 30000";
           }
         }
       }
     }
     container mgc-originated-pending-limit {
       presence "enable mgc-originated-pending-limit";
       description "Max MGC TransactionPendings num recieved.";
       uses apply-advanced;
       leaf default {
         default "4";
         type union {
           type string {
             pattern "<.*>|$.*";
           }
           type uint16 {
             range "1 .. 512";
           }
         }
       }
       leaf minimum {
         description "Minimum range of pending limit value";
         default "1";
         type union {
           type string {
             pattern "<.*>|$.*";
           }
           type uint16 {
             range "1 .. 512";
           }
         }
       }
       leaf maximum {
         description "Maximum range of pending limit value";
         default "512";
         type union {
           type string {
             pattern "<.*>|$.*";
           }
           type uint16 {
             range "1 .. 512";
           }
         }
       }
     }
   }
   grouping pgcp_h248_diffserv_object {
     uses apply-advanced;
     container dscp {
       presence "enable dscp";
       description "Differentiated Services Code Point (DSCP)";
       uses apply-advanced;
       leaf default {
         default "be";
         type string;
       }
       leaf ignore-signaled-value {
         description "Ignore property value appearing in H.248 signaling";
         type empty;
       }
     }
   }
   grouping pgcp_h248_segmentation_object {
     uses apply-advanced;
     container mgc-segmentation-timer {
       presence "enable mgc-segmentation-timer";
       description "Time the MG waits for remaining segments from MGC";
       uses apply-advanced;
       leaf default {
         default "4000";
         units "milliseconds";
         type union {
           type string {
             pattern "<.*>|$.*";
           }
           type int32 {
             range "500 .. 30000";
           }
         }
       }
       leaf minimum {
         description "Minimum range of timer value";
         default "500";
         units "milliseconds";
         type union {
           type string {
             pattern "<.*>|$.*";
           }
           type int32 {
             range "500 .. 30000";
           }
         }
       }
       leaf maximum {
         description "Maximum range of timer value";
         default "30000";
         units "milliseconds";
         type union {
           type string {
             pattern "<.*>|$.*";
           }
           type int32 {
             range "500 .. 30000";
           }
         }
       }
     }
     container mgc-maximum-pdu-size {
       presence "enable mgc-maximum-pdu-size";
       description "Maximum size of the MGC's incoming messages from MG";
       uses apply-advanced;
       leaf default {
         default "1472";
         units "bytes";
         type union {
           type string {
             pattern "<.*>|$.*";
           }
           type int32 {
             range "512 .. 65507";
           }
         }
       }
       leaf minimum {
         description "Minimum range of pdu size value";
         default "512";
         units "bytes";
         type union {
           type string {
             pattern "<.*>|$.*";
           }
           type int32 {
             range "512 .. 65507";
           }
         }
       }
       leaf maximum {
         description "Maximum range of pdu size value";
         default "65507";
         units "bytes";
         type union {
           type string {
             pattern "<.*>|$.*";
           }
           type int32 {
             range "512 .. 65507";
           }
         }
       }
     }
     container mg-segmentation-timer {
       presence "enable mg-segmentation-timer";
       description "Time the MGC waits for remaining segments from MGC";
       uses apply-advanced;
       leaf default {
         default "4000";
         units "milliseconds";
         type union {
           type string {
             pattern "<.*>|$.*";
           }
           type int32 {
             range "500 .. 30000";
           }
         }
       }
       leaf minimum {
         description "Minimum range of timer value";
         default "500";
         units "milliseconds";
         type union {
           type string {
             pattern "<.*>|$.*";
           }
           type int32 {
             range "500 .. 30000";
           }
         }
       }
       leaf maximum {
         description "Maximum range of timer value";
         default "30000";
         units "milliseconds";
         type union {
           type string {
             pattern "<.*>|$.*";
           }
           type int32 {
             range "500 .. 30000";
           }
         }
       }
     }
     container mg-maximum-pdu-size {
       presence "enable mg-maximum-pdu-size";
       description "Maximum size of the MG's incoming messages from MGC";
       uses apply-advanced;
       leaf default {
         default "1472";
         units "bytes";
         type union {
           type string {
             pattern "<.*>|$.*";
           }
           type int32 {
             range "512 .. 65507";
           }
         }
       }
       leaf minimum {
         description "Minimum range of pdu size value";
         default "512";
         units "bytes";
         type union {
           type string {
             pattern "<.*>|$.*";
           }
           type int32 {
             range "512 .. 65507";
           }
         }
       }
       leaf maximum {
         description "Maximum range of pdu size value";
         default "65507";
         units "bytes";
         type union {
           type string {
             pattern "<.*>|$.*";
           }
           type int32 {
             range "512 .. 65507";
           }
         }
       }
     }
   }
   grouping pgcp_h248_timers_object {
     uses apply-advanced;
     leaf maximum-waiting-delay {
       description "Randomly determined delay before retraversing PGC list (MWD)";
       default "2000";
       units "milliseconds";
       type union {
         type string {
           pattern "<.*>|$.*";
         }
         type uint32 {
           range "100 .. 300000";
         }
       }
     }
     leaf tmax-retransmission-delay {
       description "Delay before PGC is considered down (T-MAX)";
       default "25000";
       units "milliseconds";
       type union {
         type string {
           pattern "<.*>|$.*";
         }
         type uint16 {
           range "1000 .. 60000";
         }
       }
     }
     leaf initial-average-ack-delay {
       description "Assumed initial average reply time (for retransmission rate) (I-AAD)";
       default "1000";
       units "milliseconds";
       type union {
         type string {
           pattern "<.*>|$.*";
         }
         type uint16 {
           range "500 .. 4000";
         }
       }
     }
     leaf maximum-net-propagation-delay {
       description "Worst case network propagation delay (M-NPD), used for calculating LONG-TIMER";
       default "5000";
       units "milliseconds";
       type union {
         type string {
           pattern "<.*>|$.*";
         }
         type uint16 {
           range "500 .. 10000";
         }
       }
     }
   }
   grouping pgcp_h248_traffic_management_object {
     uses apply-advanced;
     container sustained-data-rate {
       presence "enable sustained-data-rate";
       description "SDR permitted for the stream";
       uses apply-advanced;
       leaf default {
         description "Default rate value";
         default "10000";
         units "bytes-per-second";
         type union {
           type string {
             pattern "<.*>|$.*";
           }
           type uint32 {
             range "0 .. 2147483647";
           }
         }
       }
       leaf minimum {
         description "Minimum range of rate value";
         default "0";
         units "bytes-per-second";
         type union {
           type string {
             pattern "<.*>|$.*";
           }
           type uint32 {
             range "0 .. 2147483647";
           }
         }
       }
       leaf maximum {
         description "Maximum range of rate value";
         default "0x7FFFFFFF";
         units "bytes-per-second";
         type union {
           type string {
             pattern "<.*>|$.*";
           }
           type uint32 {
             range "0 .. 2147483647";
           }
         }
       }
       container rtcp {
         description "Default rtcp rate";
         uses pgcp_h248_rtcp_rate_units_object;
       }
       leaf rtcp-include {
         description "TMAN SDR includes RTCP bandwidth";
         type empty;
       }
     }
     container peak-data-rate {
       presence "enable peak-data-rate";
       description "PDR permitted for the stream";
       uses apply-advanced;
       leaf default {
         description "Default rate value";
         default "0";
         units "bytes-per-second";
         type union {
           type string {
             pattern "<.*>|$.*";
           }
           type uint32 {
             range "0 .. 2147483647";
           }
         }
       }
       leaf minimum {
         description "Minimum range of rate value";
         default "0";
         units "bytes-per-second";
         type union {
           type string {
             pattern "<.*>|$.*";
           }
           type uint32 {
             range "0 .. 2147483647";
           }
         }
       }
       leaf maximum {
         description "Maximum range of rate value";
         default "0x7FFFFFFF";
         units "bytes-per-second";
         type union {
           type string {
             pattern "<.*>|$.*";
           }
           type uint32 {
             range "0 .. 2147483647";
           }
         }
       }
       container rtcp {
         description "Default rtcp rate";
         uses pgcp_h248_rtcp_rate_units_object;
       }
     }
     container max-burst-size {
       presence "enable max-burst-size";
       description "MBS for the stream";
       uses apply-advanced;
       leaf default {
         description "Default rate value";
         default "1000";
         units "bytes-per-second";
         type union {
           type string {
             pattern "<.*>|$.*";
           }
           type uint32 {
             range "20 .. 2147483647";
           }
         }
       }
       leaf minimum {
         description "Minimum range of rate value";
         default "20";
         units "bytes-per-second";
         type union {
           type string {
             pattern "<.*>|$.*";
           }
           type uint32 {
             range "20 .. 2147483647";
           }
         }
       }
       leaf maximum {
         description "Maximum range of rate value";
         default "0x7FFFFFFF";
         units "bytes-per-second";
         type union {
           type string {
             pattern "<.*>|$.*";
           }
           type uint32 {
             range "20 .. 2147483647";
           }
         }
       }
       container rtcp {
         description "Default rtcp rate";
         uses pgcp_h248_rtcp_burst_units_object;
       }
     }
   }
   grouping pgcp_h248_rtcp_burst_units_object {
     description "RTCP burst parameter settings";
     uses apply-advanced;
     choice values {
       case case_1 {
         leaf percentage {
           description "Value entered is percentage of RTP's parallel value";
           default "100";
           units "percent";
           type union {
             type string {
               pattern "<.*>|$.*";
             }
             type uint32 {
               range "0 .. 1000";
             }
           }
         }
       }
       case case_2 {
         leaf fixed-value {
           description "Value entered is a fixed one";
           units "bytes-per-second";
           type union {
             type string {
               pattern "<.*>|$.*";
             }
             type uint32 {
               range "20 .. 2147483647";
             }
           }
         }
       }
     }
   }
   grouping pgcp_h248_rtcp_rate_units_object {
     description "RTCP rate parameter settings";
     uses apply-advanced;
     choice values {
       case case_1 {
         leaf percentage {
           description "Value entered is percentage of RTP's parallel value";
           default "5";
           units "percent";
           type union {
             type string {
               pattern "<.*>|$.*";
             }
             type uint32 {
               range "0 .. 1000";
             }
           }
         }
       }
       case case_2 {
         leaf fixed-value {
           description "Value entered is a fixed one";
           units "bytes-per-second";
           type union {
             type string {
               pattern "<.*>|$.*";
             }
             type uint32 {
               range "0 .. 2147483647";
             }
           }
         }
       }
     }
   }
   grouping pgcp_interim_ah_scheme_object {
     uses apply-advanced;
     leaf algorithm {
       description "Define authentication algorithm";
       type enumeration {
         enum "hmac-null" {
           description "NULL authentication algorithm";
         }
       }
     }
   }
   grouping pgcp_media_service_object {
     description "One or more PGCP media service";
     leaf name {
       description "Media Service name";
       type string {
         length "1 .. 63";
         junos:posix-pattern "^[[:alnum:]][[:alnum:]_-]*$";
         junos:pattern-message "Must be a string beginning with a number or letter and consisting of letters, numbers, dashes and underscores.";
       }
     }
     uses apply-advanced;
     leaf nat-pool {
       description "Pool name";
       junos:must "(\"services nat pool $$\")";
       junos:must-message "referenced nat pool must be defined";
       type string {
         length "1 .. 63";
         junos:posix-pattern "^[[:alnum:]][[:alnum:]_-]*$";
         junos:pattern-message "Must be a string beginning with a number or letter and consisting of letters, numbers, dashes and underscores.";
       }
     }
   }
   grouping pgcp_rule_object {
     description "One or more PGCP rules";
     leaf name {
       description "Rule name";
       type string {
         length "1 .. 63";
         junos:posix-pattern "^[[:alnum:]][[:alnum:]_-]*$";
         junos:pattern-message "Must be a string beginning with a number or letter and consisting of letters, numbers, dashes and underscores.";
       }
     }
     uses apply-advanced;
     leaf gateway {
       description "Gateway Name";
       junos:must "(\"services pgcp gateway $$\")";
       junos:must-message "referenced gateway must be defined";
       type string {
         length "1 .. 63";
       }
     }
     choice media-svc-nat-pool {
       case case_1 {
         list media-service {
           key name;
           ordered-by user;
           status deprecated;
           uses pgcp_media_service_list_object;
         }
       }
       case case_2 {
         list nat-pool {
           key name;
           ordered-by user;
           description "Define a NAT pool";
           uses nat_pool_list_object;
         }
       }
     }
   }
   grouping pgcp_media_service_list_object {
     description "One or more PGCP media service";
     leaf name {
       junos:must "(\"services pgcp media-service $$\")";
       junos:must-message "referenced media service must be defined";
       type string {
         length "1 .. 63";
         junos:posix-pattern "^[[:alnum:]][[:alnum:]_-]*$";
         junos:pattern-message "Must be a string beginning with a number or letter and consisting of letters, numbers, dashes and underscores.";
       }
     }
   }
   grouping pgcp_session_mirroring_object {
     description "PGCP session mirroring properties";
     uses apply-advanced;
     list delivery-function {
       key name;
       ordered-by user;
       description "Interface for delivering mirrored packets";
       max-elements 32;
       uses pgcp_delivery_function_object;
     }
     leaf disable-session-mirroring {
       description "Disable PGCP session mirroring";
       type empty;
     }
   }
   grouping pgcp_delivery_function_object {
     leaf name {
       description "Delivery function name";
       type string {
         length "1 .. 63";
       }
     }
     uses apply-advanced;
     leaf destination-address {
       description "Delivery function destination IP address";
       type jt:ipv4addr;
     }
     leaf destination-port {
       description "Delivery function destination port";
       type union {
         type uint16;
         type string {
           pattern "<.*>|$.*";
         }
       }
     }
     leaf network-operator-id {
       description "Network operator ID";
       type string {
         length 5;
       }
     }
     leaf source-address {
       description "Network-element-id";
       type jt:ipv4addr;
     }
     leaf source-port {
       description "Network-element-port";
       type union {
         type uint16;
         type string {
           pattern "<.*>|$.*";
         }
       }
     }
     container memory-managment {
       description "Measure memory usage";
       uses pgcp_debug_mem_mgmt_object;
     }
   }
   grouping pgcp_debug_mem_mgmt_object {
     uses apply-advanced;
     leaf operational-mode {
       description "Memory managment operation mode";
       type enumeration {
         enum "fast" {
           description "Fast memory allocation [does not affect performance]";
         }
         enum "type-tracking" {
           description "Track all allocation types [affects performance]";
         }
         enum "location-tracking" {
           description "Track all allocation types and functions [affects performance]";
         }
       }
     }
   }
   grouping pgcp_virtual_interface_object {
     description "One or more Virtual Interfaces";
     leaf name {
       description "Virtual Interface Name";
       type string {
         length "1 .. 4";
         junos:posix-pattern "^[0-9]$|^[1-9][0-9]$|^[1-9][0-9]{1,2}$|^10[0-2][0-3]$";
         junos:pattern-message "The interface name must be a number in the range 0-1023";
       }
     }
     uses apply-advanced;
     leaf routing-instance {
       description "Routing instance of server to which to forward";
       default "inet.0";
       type string;
     }
     leaf service-state {
       description "Service state";
       default "in-service";
       type enumeration {
         enum "in-service" {
           description "Virtual Interface is operational";
         }
         enum "out-of-service-forced" {
           description "Virtual Interface is nonoperational";
         }
         enum "out-of-service-graceful" {
           description "Virtual Interface becomes nonoperational by draining";
         }
       }
     }
     choice media-svc-nat-pool {
       case case_1 {
         list media-service {
           key name;
           ordered-by user;
           status deprecated;
           uses pgcp_media_service_list_object;
         }
       }
       case case_2 {
         list nat-pool {
           key name;
           ordered-by user;
           description "Define a NAT pool";
           uses nat_pool_list_object;
         }
       }
     }
     leaf interface {
       description "Interface name";
       status deprecated;
       junos:must "(\"interfaces $$\")";
       junos:must-message "referenced interface must be defined";
       type union {
         type jt:interface-name;
         type string {
           pattern "<.*>|$.*";
         }
       }
     }
   }
   grouping policy-object-type {
     uses apply-advanced;
     container traceoptions {
       description "Network Security Policy Tracing Options";
       uses apply-advanced;
       leaf no-remote-trace {
         description "Disable remote tracing";
         junos:must "(\"system tracing\")";
         junos:must-message "'no-remote-trace' is valid only when [system tracing] is configured";
         type empty;
       }
       container file {
         description "Trace file information";
         leaf filename {
           description "Name of file in which to write trace information";
           type string {
             length "1 .. 1024";
             junos:posix-pattern "![/ %]";
             junos:pattern-message "Must not contain '/', % or a space";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing parameters";
         leaf name {
           type enumeration {
             enum "configuration" {
               description "Trace configuration events";
             }
             enum "routing-socket" {
               description "Trace routing socket events";
             }
             enum "compilation" {
               description "Policy compilation events";
             }
             enum "ipc" {
               description "Inter-process communication events";
             }
             enum "rules" {
               description "Policy rules related events";
             }
             enum "lookup" {
               description "Policy lookup events";
             }
             enum "all" {
               description "Trace everything";
             }
           }
         }
       }
     }
     list policy {
       key "from-zone-name to-zone-name";
       ordered-by user;
       description "Define a policy context from this zone";
       leaf from-zone-name {
         description "Source zone";
         junos:must "((\".. .. .. .. security zones security-zone $$\" || \".. .. .. .. .. security zones security-zone $$\"))";
         junos:must-message "Security zone must be defined";
         type string {
           length "1 .. 63";
         }
       }
       leaf to-zone-name {
         description "Destination zone";
         junos:must "((\".. .. .. .. security zones security-zone $$\" || \".. .. .. .. .. security zones security-zone $$\"))";
         junos:must-message "Security zone must be defined";
         type string {
           length "1 .. 63";
         }
       }
       uses apply-advanced;
       list policy {
         key name;
         ordered-by user;
         description "Define security policy in specified zone-to-zone direction";
         uses policy_type;
       }
     }
     container global {
       description "Define a global policy context";
       uses apply-advanced;
       list policy {
         key name;
         ordered-by user;
         description "Define security policy in global context";
         uses policy_type;
       }
     }
     container default-policy {
       description "Configure default action when no user-defined policy match";
       uses apply-advanced;
       leaf default-action {
         description "Default action";
         default "deny-all";
         type enumeration {
           enum "permit-all" {
             description "Permit all traffic if no policy match";
           }
           enum "deny-all" {
             description "Deny all traffic if no policy match";
           }
         }
       }
     }
     container policy-rematch {
       presence "enable policy-rematch";
       description "Re-evaluate the policy when changed";
       leaf extensive {
         description "Perform policy extensive rematch";
         type empty;
       }
     }
     container policy-stats {
       presence "enable policy-stats";
       description "Parameters for policy statistics";
       uses apply-advanced;
       leaf system-wide {
         description "Enable/Disable system-wide policy statistics";
         type enumeration {
           enum "enable" {
             description "Enable policy system-wide statistics";
           }
           enum "disable" {
             description "Disable policy system-wide statistics";
           }
         }
       }
     }
     container pre-id-default-policy {
       description "Configure default policy action before dynamic application is finally identified";
       uses apply-advanced;
       container then {
         description "Specify policy action to take when packet match criteria";
         uses apply-advanced;
         container log {
           description "Enable log";
           uses log_type;
         }
         container session-timeout {
           description "Session timeout";
           uses session_timeout_type;
         }
       }
     }
     list stateful-firewall-rule {
       key name;
       ordered-by user;
       description "Define a stateful-firewall-rule";
       max-elements 16960;
       leaf name {
         description "Stateful-firewall-rule name";
         type string {
           length "1 .. 63";
           junos:posix-pattern "^[[:alnum:]][[:alnum:]/.:_-]*$";
           junos:pattern-message "Must be a string beginning with a number or letter and consisting of letters, numbers, dashes, underscores, forward slashes, colons and dots.";
         }
       }
       uses apply-advanced;
       leaf match-direction {
         description "Direction for which the rule match is applied";
         type enumeration {
           enum "input" {
             description "Match on input to interface";
           }
           enum "output" {
             description "Match on output from interface";
           }
           enum "input-output" {
             description "Match on input to or output from interface";
           }
         }
       }
       list policy {
         key name;
         ordered-by user;
         description "Define a stateful-firewall policy";
         uses policy_type;
       }
     }
     list stateful-firewall-rule-set {
       key name;
       ordered-by user;
       description "Defines a set of stateful firewall rules";
       max-elements 16960;
       leaf name {
         description "Name of the stateful firewall rule set";
         type string {
           length "1 .. 63";
           junos:posix-pattern "^[[:alnum:]][[:alnum:]/.:_-]*$";
           junos:pattern-message "Must be a string beginning with a number or letter and consisting of letters, numbers, dashes, underscores, forward slashes, colons and dots.";
         }
       }
       uses apply-advanced;
       list stateful-firewall-rule {
         key name;
         ordered-by user;
         description "Rule to be included in this stateful firewall rule set";
         max-elements 16960;
         leaf name {
           description "Stateful-firewall-rule name";
           junos:must "(\"services policies stateful-firewall-rule $$\")";
           junos:must-message "Undefined stateful-firewall-rule. Rule must be configured under policies";
           type string {
             junos:posix-pattern "^[[:alnum:]][[:alnum:]/.:_-]{0,62}$";
             junos:pattern-message "Must be a string beginning with a number or letter and consisting of no more than 63 total letters, numbers, dashes, underscores, forward slashes, colons and dots.";
           }
         }
         uses apply-advanced;
       }
     }
   }
   grouping log_type {
     uses apply-advanced;
     leaf session-init {
       description "Log at session init time";
       type empty;
     }
     leaf session-close {
       description "Log at session close time";
       type empty;
     }
   }
   grouping policy_type {
     leaf name {
       description "Security policy name";
       type string {
         length "1 .. 63";
         junos:posix-pattern "^[[:alnum:]][[:alnum:]_-]*$";
         junos:pattern-message "Must be a string beginning with a number or letter and consisting of letters, numbers, dashes and underscores.";
       }
     }
     uses apply-advanced;
     leaf description {
       description "Text description of policy";
       type string {
         length "1 .. 900";
         junos:posix-pattern "^[^&<>\n]+$";
         junos:pattern-message "Must be a string excluding '&', '<', '>' and '\n'";
       }
     }
     container match {
       description "Specify security policy match-criteria";
       uses apply-advanced;
       choice source-address_choice {
         case case_1 {
           leaf-list source-address {
             ordered-by user;
             type string;
           }
         }
       }
       choice destination-address_choice {
         case case_1 {
           leaf-list destination-address {
             ordered-by user;
             type string;
           }
         }
       }
       leaf source-address-excluded {
         description "Exclude source addresses";
         type empty;
       }
       leaf destination-address-excluded {
         description "Exclude destination addresses";
         type empty;
       }
       choice application_type_choice {
         case case_1 {
           leaf-list application {
             ordered-by user;
             type string;
           }
         }
       }
       choice source_identity_choice {
         case case_1 {
           leaf-list source-identity {
             ordered-by user;
             type string;
           }
         }
       }
       choice source_end_user_profile_choice {
         case case_1 {
           container source-end-user-profile {
             description "Match source end user profile";
             uses match_source_end_user_profile_value;
           }
         }
       }
       choice dynamic_application_type_choice {
         case case_1 {
           leaf-list dynamic-application {
             ordered-by user;
             type string;
           }
         }
       }
       choice url_category_type_choice {
         case case_1 {
           leaf-list url-category {
             ordered-by user;
             type string;
           }
         }
       }
       choice from_zone_choice {
         case case_1 {
           leaf-list from-zone {
             ordered-by user;
             type string;
           }
         }
       }
       choice to_zone_choice {
         case case_1 {
           leaf-list to-zone {
             ordered-by user;
             type string;
           }
         }
       }
     }
     container then {
       description "Specify policy action to take when packet match criteria";
       uses apply-advanced;
       choice action {
         case case_1 {
           leaf deny {
             description "Deny packets";
             type empty;
           }
         }
         case case_2 {
           container reject {
             presence "enable reject";
             description "Reject packets";
             uses apply-advanced;
             leaf profile {
               description "Profile for redirect HTTP/S traffic";
               junos:must "(\"security dynamic-application profile $$\")";
               junos:must-message "Dynamic-application profile must be defined";
               type string;
             }
             container ssl-proxy {
               presence "enable ssl-proxy";
               description "SSL proxy services";
               uses apply-advanced;
               leaf profile-name {
                 description "Specify SSL proxy service profile name";
                 junos:must "(\"services ssl proxy profile $$\")";
                 junos:must-message "Referenced SSL proxy profile is not defined";
                 type string;
               }
             }
           }
         }
         case case_3 {
           container permit {
             presence "enable permit";
             description "Permit packets";
             uses apply-advanced;
             container tunnel {
               description "Tunnel packets";
               junos:must "(!(\".. .. .. match dynamic-application\"))";
               junos:must-message "Tunnel and dynamic-application can't be applied to same policy";
               uses tunnel_type;
               junos:must "(!(\".. .. .. match dynamic-application\"))";
               junos:must-message "Tunnel and dynamic-application can't be applied to same policy";
             }
             container firewall-authentication {
               description "Enable authentication for this policy if permit or tunnel";
               junos:must "((!(\".. .. .. match dynamic-application\") || (\".. .. .. match dynamic-application\" && \".. .. .. match dynamic-application none\")))";
               junos:must-message "Firewall-authentication and dynamic-application can't be applied to same policy";
               uses firewall_authentication_type;
               junos:must "((!(\".. .. .. match dynamic-application\") || (\".. .. .. match dynamic-application\" && \".. .. .. match dynamic-application none\")))";
               junos:must-message "Firewall-authentication and dynamic-application can't be applied to same policy";
             }
             container destination-address {
               description "Enable destination address translation";
               uses destination_nat_enable_type;
             }
             container application-services {
               description "Application Services";
               uses application_services_type;
             }
             container tcp-options {
               description "Transmission Control Protocol session configuration";
               uses apply-advanced;
               leaf syn-check-required {
                 description "Enable per policy SYN-flag check";
                 type empty;
               }
               leaf sequence-check-required {
                 description "Enable per policy sequence-number checking";
                 type empty;
               }
               leaf initial-tcp-mss {
                 description "Override MSS value for initial direction";
                 type union {
                   type string {
                     pattern "<.*>|$.*";
                   }
                   type uint32 {
                     range "64 .. 65535";
                   }
                 }
               }
               leaf reverse-tcp-mss {
                 description "Override MSS value for reverse direction";
                 type union {
                   type string {
                     pattern "<.*>|$.*";
                   }
                   type uint32 {
                     range "64 .. 65535";
                   }
                 }
               }
               leaf window-scale {
                 description "Enable per policy window-scale";
                 type empty;
               }
             }
             leaf services-offload {
               description "Enable services offloading";
               type empty;
             }
           }
         }
       }
       container log {
         description "Enable log";
         uses log_type;
       }
       container count {
         description "Enable count";
         uses count_type;
       }
     }
     leaf scheduler-name {
       description "Name of scheduler";
       junos:must "(\"schedulers scheduler $$\")";
       junos:must-message "scheduler must be defined";
       type string {
         length "1 .. 63";
         junos:posix-pattern "^[[:alnum:]][[:alnum:]_-]*$";
         junos:pattern-message "Must be a string beginning with a number or letter and consisting of letters, numbers, dashes and underscores.";
       }
     }
   }
   grouping application_services_type {
     description "Application Services";
     uses apply-advanced;
     leaf gprs-gtp-profile {
       description "Specify GPRS Tunneling Protocol profile name";
       junos:must "(!(\".. .. .. .. match dynamic-application\"))";
       junos:must-message "gprs gtp and dynamic-application can't be applied to same policy";
       junos:must "(\"security gprs gtp profile $$\")";
       junos:must-message "gprs gtp profile must be defined";
       type string {
         length "1 .. 63";
       }
     }
     leaf gprs-sctp-profile {
       description "Specify GPRS stream control protocol profile name";
       junos:must "(!(\".. .. .. .. match dynamic-application\"))";
       junos:must-message "gprs sctp and dynamic-application can't be applied to same policy";
       junos:must "(\"security gprs sctp profile $$\")";
       junos:must-message "gprs sctp profile must be defined";
       type string {
         length "1 .. 63";
       }
     }
     leaf idp {
       description "Intrusion detection and prevention";
       type empty;
     }
     leaf idp-policy {
       description "Specify idp policy name";
       type string {
         length "1 .. 255";
       }
     }
     container ssl-proxy {
       presence "enable ssl-proxy";
       description "SSL proxy services";
       uses apply-advanced;
       leaf profile-name {
         description "Specify SSL proxy service profile name";
         junos:must "(\"services ssl proxy profile $$\")";
         junos:must-message "Referenced SSL proxy profile is not defined";
         type string;
       }
     }
     container uac-policy {
       presence "enable uac-policy";
       description "Enable unified access control enforcement of policy";
       uses apply-advanced;
       leaf captive-portal {
         junos:must "(\"services unified-access-control captive-portal $$\")";
         junos:must-message "Captive portal policy must be defined";
         type string {
           length "1 .. 128";
         }
       }
     }
     leaf utm-policy {
       description "Specify utm policy name";
       junos:must "(\"security utm utm-policy $$\")";
       junos:must-message "utm-policy must be defined";
       type string {
         length "1 .. 255";
       }
     }
     leaf icap-redirect {
       description "Specify icap redirect profile name";
       junos:must "(\"services icap-redirect profile $$\")";
       junos:must-message "icap-redirect profile must be defined";
       type string {
         length "1 .. 31";
       }
     }
     container application-firewall {
       description "Application firewall services";
       status deprecated;
       junos:must "((!(\".. .. .. .. match dynamic-application\") || (\".. .. .. .. match dynamic-application\" && \".. .. .. .. match dynamic-application none\")))";
       junos:must-message "Traditional AppFW and dynamic-application can't be applied to same policy";
       uses jsf_service_rule_set_type;
       junos:must "((!(\".. .. .. .. match dynamic-application\") || (\".. .. .. .. match dynamic-application\" && \".. .. .. .. match dynamic-application none\")))";
       junos:must-message "Traditional AppFW and dynamic-application can't be applied to same policy";
     }
     container application-traffic-control {
       description "Application traffic control services";
       uses jsf_application_traffic_control_rule_set_type;
     }
     choice wx-redirection {
       case case_1 {
         leaf redirect-wx {
           description "Set WX redirection";
           type empty;
         }
       }
       case case_2 {
         leaf reverse-redirect-wx {
           description "Set WX reverse redirection";
           type empty;
         }
       }
     }
     leaf security-intelligence-policy {
       description "Specify security-intelligence policy name";
       junos:must "(\"services security-intelligence policy $$\")";
       junos:must-message "security-intelligence policy must be defined";
       type string {
         length "1 .. 255";
       }
     }
     leaf advanced-anti-malware-policy {
       description "Specify advanced-anti-malware policy name";
       junos:must "(\"services advanced-anti-malware policy $$\")";
       junos:must-message "advanced-anti-malware policy must be defined";
       type string {
         length "1 .. 255";
       }
     }
   }
   grouping count_type {
     uses apply-advanced;
   }
   grouping destination_nat_enable_type {
     description "Enable Destination NAT";
     uses apply-advanced;
     choice destination_nat {
       case case_1 {
         leaf drop-translated {
           description "Drop the policy if NAT translated";
           type empty;
         }
       }
       case case_2 {
         leaf drop-untranslated {
           description "Drop the policy if NAT untranslated";
           type empty;
         }
       }
     }
   }
   grouping firewall_authentication_type {
     uses apply-advanced;
     choice auth-type {
       case case_1 {
         container pass-through {
           presence "enable pass-through";
           junos:must "((\".. .. .. .. .. .. .. access firewall-authentication pass-through\" || \".. .. .. .. .. .. .. .. access firewall-authentication pass-through\"))";
           junos:must-message "access firewall-authentication pass-through must be configured";
           description "Pass-through firewall authentication settings";
           uses apply-advanced;
           leaf access-profile {
             description "Specify access profile name";
             junos:must "(\"access profile $$\")";
             junos:must-message "access-profile must be defined";
             type string {
               length "1 .. 63";
             }
           }
           leaf-list client-match {
             ordered-by user;
             description "Name of user or group to match";
             type string {
               length "1 .. 63";
             }
           }
           leaf web-redirect {
             description "Redirect unauthenticated HTTP requests to the device's internal web server";
             type empty;
           }
           leaf web-redirect-to-https {
             description "Redirect unauthenticated HTTP requests to the device's internal HTTPS web server";
             type empty;
           }
           leaf ssl-termination-profile {
             description "Specify SSL termination profile used to the SSL offload";
             type string {
               length "1 .. 63";
             }
           }
           leaf auth-only-browser {
             description "Authenticate only browser traffic";
             type empty;
           }
           list auth-user-agent {
             key name;
             ordered-by user;
             description "Authenticate HTTP traffic with specified user agent";
             leaf name {
               description "Authenticate HTTP traffic with specified user agent";
               type string {
                 length "1 .. 16";
               }
             }
             uses apply-advanced;
           }
         }
       }
       case case_2 {
         container web-authentication {
           presence "enable web-authentication";
           junos:must "((\".. .. .. .. .. .. .. access firewall-authentication web-authentication\" || \".. .. .. .. .. .. .. .. access firewall-authentication web-authentication\"))";
           junos:must-message "access firewall-authentication web-authentication must be configured";
           description "Web-authentication settings";
           uses apply-advanced;
           leaf-list client-match {
             ordered-by user;
             description "Name of user or group to match";
             type string {
               length "1 .. 63";
             }
           }
         }
       }
       case case_3 {
         container user-firewall {
           description "User-firewall firewall authentication settings";
           uses apply-advanced;
           leaf access-profile {
             description "Specify access profile name";
             junos:must "(\"access profile $$\")";
             junos:must-message "access-profile must be defined";
             type string {
               length "1 .. 63";
             }
           }
           leaf web-redirect {
             description "Redirect unauthenticated HTTP req to web server";
             type empty;
           }
           leaf web-redirect-to-https {
             description "Redirect unauthenticated HTTP req to HTTPS web server";
             type empty;
           }
           leaf ssl-termination-profile {
             description "Specify SSL termination profile used to the SSL offload";
             type string {
               length "1 .. 63";
             }
           }
           leaf auth-only-browser {
             description "Authenticate only browser traffic";
             type empty;
           }
           list auth-user-agent {
             key name;
             ordered-by user;
             description "Authenticate HTTP traffic with specified user agent";
             leaf name {
               description "Authenticate HTTP traffic with specified user agent";
               type string {
                 length "1 .. 16";
               }
             }
             uses apply-advanced;
           }
           leaf domain {
             description "Specify domain name";
             type string {
               length "1 .. 64";
             }
           }
         }
       }
     }
     leaf push-to-identity-management {
       description "Push auth entry to identity management server";
       type empty;
     }
   }
   grouping jsf_application_traffic_control_rule_set_type {
     description "Define service application traffic rule-set reference";
     uses apply-advanced;
     leaf rule-set {
       description "Service rule-set name";
       junos:must "(\"class-of-service application-traffic-control rule-sets $$\")";
       junos:must-message "rule-set must be defined";
       type string {
         length "1 .. 64";
       }
     }
   }
   grouping jsf_service_rule_set_type {
     description "Define service rule set reference";
     uses apply-advanced;
     leaf rule-set {
       description "Service rule set name";
       junos:must "(\"security application-firewall rule-sets $$\")";
       junos:must-message "rule set must be defined";
       type string {
         length "1 .. 64";
       }
     }
   }
   grouping match_source_end_user_profile_value {
     uses apply-advanced;
     leaf source-end-user-profile-name {
       description "Specify source-end-user-profile name from list to match";
       junos:must "((\".. .. .. .. .. .. services user-identification device-information end-user-profile profile-name $$\" || \".. .. .. .. .. .. .. services user-identification device-information end-user-profile profile-name $$\"))";
       junos:must-message "Services user-identification device-information end-user-profile profile-name must be defined";
       type string;
     }
   }
   grouping proxy-profile-setting {
     description "Proxy profile settings";
     leaf name {
       description "Proxy profile name";
       type string {
         length "1 .. 64";
       }
     }
     uses apply-advanced;
     container protocol {
       description "Protocol level proxy setting";
       uses apply-advanced;
       container http {
         description "HTTP proxy setting";
         uses apply-advanced;
         leaf host {
           description "Proxy server name or IP address";
           type string {
             length "1 .. 256";
           }
         }
         leaf port {
           description "Proxy server port";
           default "3128";
           type union {
             type string {
               pattern "<.*>|$.*";
             }
             type uint16 {
               range "0 .. 65535";
             }
           }
         }
       }
     }
   }
   grouping range-address-type {
     description "Range address";
     leaf name {
       description "Lower limit of address range";
       type jt:ipv4addr;
     }
     uses apply-advanced;
     container to {
       description "Port range upper limit";
       uses apply-advanced;
       leaf range-high {
         description "Upper limit of address range";
         type jt:ipv4addr;
       }
     }
   }
   grouping registration_policy_type {
     leaf name {
       description "Policy name";
       type string;
     }
     uses apply-advanced;
     list term {
       key name;
       ordered-by user;
       description "Term definition";
       max-elements 20;
       leaf name {
         description "Term name";
         type string;
       }
       uses apply-advanced;
       container from {
         description "From action";
         uses new_transaction_from_type;
       }
       container then {
         description "Action";
         uses new_registration_then_type;
       }
     }
   }
   grouping new_registration_then_type {
     uses apply-advanced;
     container nat-traversal {
       description "How to traverse NAT devices";
       uses nat_traversal_action;
     }
   }
   grouping nat_traversal_action {
     uses apply-advanced;
     leaf nat-traversal-strategy {
       description "Choose when to perform NAT traversal";
       type enumeration {
         enum "never" {
           description "Never perform NAT traversal";
         }
         enum "always" {
           description "Always perform NAT traversal";
         }
         enum "by-via" {
           description "Perform NAT traversal only if transport source address does not match VIA header";
         }
       }
     }
     leaf keepalive-interval {
       description "Keepalive interval";
       default "45";
       units "seconds";
       type union {
         type string {
           pattern "<.*>|$.*";
         }
         type uint32 {
           range "15 .. 86400";
         }
       }
     }
     leaf minimum-registration-interval {
       description "Minimum registration interval allowed in register packet";
       default "1";
       units "seconds";
       type union {
         type string {
           pattern "<.*>|$.*";
         }
         type uint32 {
           range "1 .. 86400";
         }
       }
     }
     container keepalive-mechanisms {
       description "A prioritized list of keepalive mechanisms";
       uses apply-advanced;
       leaf register-fast-expiration {
         description "Reduce the expiration interval in REGISTER responses";
         type empty;
       }
     }
   }
   grouping new_transaction_from_type {
     uses apply-advanced;
     leaf-list source-address {
       ordered-by user;
       description "Source addresses and masks";
       type jt:ipaddr;
       max-elements 5;
     }
     list method {
       key name;
       ordered-by user;
       description "Methods";
       uses transaction-method-type;
     }
     container request-uri {
       description "Request URI field";
       leaf-list regular-expression {
         ordered-by user;
         description "Regular expression matched on incoming Request-URI";
         type jt:regular-expression;
         max-elements 5;
       }
       leaf registration-state {
         description "Registration state";
         type enumeration {
           enum "registered" {
           }
           enum "not-registered" {
           }
         }
       }
       leaf uri-hiding {
         description "URI hidden";
         type enumeration {
           enum "hidden-uri" {
           }
           enum "not-hidden-uri" {
           }
         }
       }
     }
     container contact {
       description "Contact field";
       leaf-list regular-expression {
         ordered-by user;
         description "Regular expression matched on incoming contact";
         type jt:regular-expression;
         max-elements 5;
       }
       leaf registration-state {
         description "Registration state";
         type enumeration {
           enum "registered" {
           }
           enum "not-registered" {
           }
         }
       }
       leaf uri-hiding {
         description "URI hidden";
         type enumeration {
           enum "hidden-uri" {
           }
           enum "not-hidden-uri" {
           }
         }
       }
     }
   }
   grouping rmopd-traceoptions {
     description "Trace options for remote-monitoring";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing parameters";
       leaf name {
         type enumeration {
           enum "configuration" {
             description "Trace configuration events";
           }
           enum "ipc" {
             description "Trace ipc messages";
           }
           enum "ppm" {
             description "Trace ppm";
           }
           enum "rpd" {
             description "Trace rpd events";
           }
           enum "info" {
             description "Trace info events";
           }
           enum "statistics" {
             description "Trace statistics";
           }
           enum "error" {
             description "Trace events related to catastrophic errors in daemon";
           }
           enum "all" {
             description "Trace everything";
           }
         }
       }
     }
   }
   grouping routing-destinations {
     uses apply-advanced;
     leaf default-availability-check-profile {
       description "Profile that will be used if no other profile was attached to a server";
       type string {
         length "1 .. 256";
       }
     }
     list availability-check-profiles {
       key name;
       ordered-by user;
       description "Definitions of servers availability check profiles";
       max-elements 100;
       uses availability-check-profile;
     }
     list servers {
       key name;
       ordered-by user;
       description "Servers definitions";
       max-elements 5000;
       uses routing-destination-server;
     }
     list clusters {
       key name;
       ordered-by user;
       description "Clusters definitions";
       max-elements 1000;
       uses routing-destination-cluster;
     }
   }
   grouping availability-check-profile {
     leaf name {
       type string {
         length "1 .. 256";
       }
     }
     uses apply-advanced;
     container keepalive-method {
       description "How will availability check be done";
       choice ping-method {
         case case_1 {
           leaf sip-options {
             description "Check availability by sending a SIP OPTIONS message";
             type empty;
           }
         }
       }
     }
     container keepalive-strategy {
       presence "enable keepalive-strategy";
       description "When will the server be checked for availability";
       choice keepalive-strategy {
         case case_1 {
           container send-always {
             presence "enable send-always";
             description "Always check the server availability";
             uses apply-advanced;
             leaf failures-before-unavailable {
               description "A server is assumed to be unavailable when a keepalive message was not answered this number of times";
               default "1";
               type union {
                 type string {
                   pattern "<.*>|$.*";
                 }
                 type uint32 {
                   range "1 .. 10";
                 }
               }
             }
             leaf successes-before-available {
               description "A server is assumed to be available when a keepalive message was successfully answered this number of times";
               default "1";
               type union {
                 type string {
                   pattern "<.*>|$.*";
                 }
                 type uint32 {
                   range "1 .. 10";
                 }
               }
             }
           }
         }
         case case_2 {
           container send-when-unavailable {
             presence "enable send-when-unavailable";
             description "Check the server availability only when it is marked as unavailable";
             leaf successes-before-available {
               description "A server is assumed to be available when a keepalive message was successfully answered this number of times";
               default "1";
               type union {
                 type string {
                   pattern "<.*>|$.*";
                 }
                 type uint32 {
                   range "1 .. 10";
                 }
               }
             }
           }
         }
         case case_3 {
           container do-not-send {
             presence "enable do-not-send";
             description "Never perform availability checks of the server";
             leaf blackout-period {
               description "Time a server will be considered unavailable";
               default "600";
               units "seconds";
               type union {
                 type string {
                   pattern "<.*>|$.*";
                 }
                 type uint32 {
                   range "0 .. 86400";
                 }
               }
             }
           }
         }
       }
     }
     container keepalive-interval {
       description "How often should the server be checked for availability";
       uses apply-advanced;
       leaf available-server {
         description "How often should a server that is marked as available be checked for availablility";
         default "32";
         units "seconds";
         type union {
           type string {
             pattern "<.*>|$.*";
           }
           type uint32 {
             range "10 .. 86400";
           }
         }
       }
       leaf unavailable-server {
         description "How often should a server that is marked as unavailable be checked for availablility";
         default "32";
         units "seconds";
         type union {
           type string {
             pattern "<.*>|$.*";
           }
           type uint32 {
             range "10 .. 86400";
           }
         }
       }
     }
     leaf transaction-timeout {
       description "A server is assumed to be unavailable when a keepalive message was not answered in this time";
       default "32";
       units "seconds";
       type union {
         type string {
           pattern "<.*>|$.*";
         }
         type uint32 {
           range "10 .. 32";
         }
       }
     }
   }
   grouping routing-destination-cluster {
     leaf name {
       type string {
         length "1 .. 256";
       }
     }
     uses apply-advanced;
     list server {
       key name;
       ordered-by user;
       max-elements 25;
       leaf name {
         description "Server name";
         junos:must "(\"services border-signaling-gateway gateway ${gateway} sip routing-destinations servers $$\")";
         junos:must-message "Referenced server must be defined";
         type string {
           length "1 .. 256";
         }
       }
       uses apply-advanced;
       leaf priority {
         description "Defines the redundency order";
         default "1";
         type union {
           type uint16;
           type string {
             pattern "<.*>|$.*";
           }
         }
       }
       leaf weight {
         description "Defines the load balancing ratio";
         default "1";
         type union {
           type uint16;
           type string {
             pattern "<.*>|$.*";
           }
         }
       }
     }
   }
   grouping routing-destination-server {
     leaf name {
       type string {
         length "1 .. 256";
       }
     }
     uses apply-advanced;
     container address {
       description "Server's address";
       uses routing-destination-address;
     }
     leaf service-point {
       description "Exit point";
       junos:must "(\"services border-signaling-gateway gateway ${gateway} service-point $$\")";
       junos:must-message "Referenced egress-service-point must be defined";
       type string;
     }
     leaf admission-control {
       description "Admission control profile for the server";
       junos:must "(\"services border-signaling-gateway gateway ${gateway} admission-control $$\")";
       junos:must-message "Referenced admission control profile must be defined";
       type string;
     }
     leaf availability-check-profile {
       description "Availability check profile for the server";
       junos:must "(\"services border-signaling-gateway gateway ${gateway} sip routing-destinations availability-check-profiles $$\")";
       junos:must-message "Referenced availability check profile must be defined";
       type string {
         length "1 .. 256";
       }
     }
   }
   grouping routing-destination-address {
     leaf ip4-address {
       description "IP address";
       type jt:ipaddr;
     }
     leaf port {
       description "Port number";
       default "5060";
       type union {
         type string {
           pattern "<.*>|$.*";
         }
         type uint32 {
           range "0 .. 65535";
         }
       }
     }
     container transport-protocol {
       description "Transport protocol";
       uses transport_protocol;
     }
   }
   grouping secintel-category-disable {
     description "Security intelligence category";
     leaf name {
       description "Name of security intelligence category";
       type enumeration {
         enum "IPFilter" {
           description "IPFilter";
         }
         enum "GeoIP" {
           description "GeoIP";
         }
         enum "CC" {
           description "Command and control";
         }
         enum "JWAS" {
           description "JWAS";
         }
         enum "Blacklist" {
           description "Blacklist";
         }
         enum "Whitelist" {
           description "Whitelist";
         }
         enum "Infected-Hosts" {
           description "Infected-Hosts";
         }
       }
     }
     uses apply-advanced;
     container disable {
       presence "enable disable";
       description "To disable category for feed update";
     }
   }
   grouping secintel-policy-setting {
     description "Security intelligence policy setting";
     leaf name {
       description "Security intelligence policy name";
       type string {
         length "1 .. 63";
       }
     }
     uses apply-advanced;
     leaf description {
       description "Text description of policy";
       type string {
         length "1 .. 900";
         junos:posix-pattern "^[^&<>\n]+$";
         junos:pattern-message "Must be a string excluding '&', '<', '>' and '\n'";
       }
     }
     list category-profiles {
       key name;
       ordered-by user;
       description "Security intelligence category profiles";
       leaf name {
         description "Name of security intelligence category";
         type string;
       }
       uses apply-advanced;
       leaf profile-name {
         description "Name of profile";
         junos:must "(\"services security-intelligence profile $$\")";
         junos:must-message "security intelligence profile must be defined";
         type string;
       }
     }
   }
   grouping secintel-profile-setting {
     description "Security intelligence profile settings";
     leaf name {
       description "Security intelligence profile name";
       type string {
         length "1 .. 63";
       }
     }
     uses apply-advanced;
     leaf description {
       description "Text description of profile";
       type string {
         length "1 .. 900";
         junos:posix-pattern "^[^&<>\n]+$";
         junos:pattern-message "Must be a string excluding '&', '<', '>' and '\n'";
       }
     }
     leaf category {
       description "Profile category name";
       type string;
     }
     list rule {
       key name;
       ordered-by user;
       description "Profile rule name";
       uses secintel-profile-rule;
     }
     container default-rule {
       presence "enable default-rule";
       description "Profile default rule";
       uses apply-advanced;
       container then {
         presence "enable then";
         description "Profile default rule action";
         uses apply-advanced;
         container action {
           description "Security intelligence profile action";
           uses apply-advanced;
           choice action {
             case case_1 {
               leaf permit {
                 description "Permit action";
                 type empty;
               }
             }
             case case_2 {
               container block {
                 description "Block action";
                 uses apply-advanced;
                 choice action {
                   case case_1 {
                     container drop {
                       presence "enable drop";
                       description "Drop packet";
                     }
                   }
                   case case_2 {
                     container close {
                       presence "enable close";
                       description "Close session";
                       uses apply-advanced;
                       container http {
                         description "Http content for block action";
                         uses apply-advanced;
                         choice http-choice {
                           case case_1 {
                             leaf file {
                               description "File name for http response to client";
                               type string;
                             }
                           }
                           case case_2 {
                             leaf message {
                               description "Block message to client";
                               type string;
                             }
                           }
                           case case_3 {
                             leaf redirect-url {
                               description "Redirect url to client";
                               type string {
                                 length "1 .. 1023";
                                 junos:posix-pattern "^https?://.*";
                                 junos:pattern-message "URL must begin with http:// or https://";
                               }
                             }
                           }
                         }
                       }
                     }
                   }
                 }
               }
             }
             case case_3 {
               container recommended {
                 presence "enable recommended";
                 description "Recommended action from feed server";
               }
             }
           }
         }
         choice log-choice {
           leaf log {
             description "Log security intelligence block action";
             type empty;
           }
           leaf no-log {
             description "Don't log security intelligence block action";
             type empty;
           }
         }
       }
     }
   }
   grouping secintel-profile-rule {
     description "Security intelligence profile rule";
     leaf name {
       description "Profile rule name";
       type string {
         length "1 .. 63";
       }
     }
     uses apply-advanced;
     container match {
       description "Profile matching feed name and threat levels";
       uses apply-advanced;
       leaf-list feed-name {
         ordered-by user;
         description "Profile matching feed name";
         type string;
         max-elements 32;
       }
       leaf-list threat-level {
         ordered-by user;
         description "Profile matching threat levels, higher number is more severe";
         type union {
           type uint32;
           type string {
             pattern "<.*>|$.*";
           }
         }
       }
     }
     container then {
       description "Profile action and log";
       uses apply-advanced;
       container action {
         description "Security intelligence profile action";
         uses apply-advanced;
         choice action {
           case case_1 {
             leaf permit {
               description "Permit action";
               type empty;
             }
           }
           case case_2 {
             container block {
               description "Block action";
               uses apply-advanced;
               choice action {
                 case case_1 {
                   container drop {
                     presence "enable drop";
                     description "Drop packet";
                   }
                 }
                 case case_2 {
                   container close {
                     presence "enable close";
                     description "Close session";
                     uses apply-advanced;
                     container http {
                       description "Http content for block action";
                       uses apply-advanced;
                       choice http-choice {
                         case case_1 {
                           leaf file {
                             description "File name for http response to client";
                             type string;
                           }
                         }
                         case case_2 {
                           leaf message {
                             description "Block message to client";
                             type string;
                           }
                         }
                         case case_3 {
                           leaf redirect-url {
                             description "Redirect url to client";
                             type string {
                               length "1 .. 1023";
                               junos:posix-pattern "^https?://.*";
                               junos:pattern-message "URL must begin with http:// or https://";
                             }
                           }
                         }
                       }
                     }
                   }
                 }
               }
             }
           }
           case case_3 {
             container recommended {
               presence "enable recommended";
               description "Recommended action from feed server";
             }
           }
         }
       }
       container log {
         presence "enable log";
         description "Log security intelligence block action";
       }
     }
   }
   grouping secintel-traceoptions {
     description "Security intelligence trace options";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Trace flags";
       leaf name {
         type enumeration {
           enum "all" {
             description "Trace everything";
           }
           enum "blacklist" {
             description "Trace security intelligence Blacklist category";
           }
           enum "cc" {
             description "Trace security intelligence CC category";
           }
           enum "infected-hosts" {
             description "Trace security intelligence Infected-Hosts category";
           }
           enum "control" {
             description "Trace control plane";
           }
           enum "feed" {
             description "Trace feed operation";
           }
           enum "ipc" {
             description "Trace ipc module";
           }
           enum "infrastucture" {
             description "Trace infrastucture functions";
           }
           enum "jwas" {
             description "Trace security intelligence JWAS category";
           }
           enum "plugin" {
             description "Trace security intelligence plugin services";
           }
           enum "whitelist" {
             description "Trace security intelligence Whitelist category";
           }
         }
       }
     }
   }
   grouping server-connection-type {
     description "Connection parameters per server";
     uses apply-advanced;
     leaf address {
       description "IP address";
       type jt:ipaddr;
     }
     leaf ca-certificate {
       description "Ca-certificate file name";
       type string {
         length "1 .. 256";
       }
     }
     leaf client-id {
       description "Client ID for OAuth2 grant";
       type string {
         length "1 .. 64";
       }
     }
     leaf client-secret {
       description "Client secret for OAuth2 grant";
       type string {
         length "1 .. 128";
       }
     }
   }
   grouping service_device_pool_object {
     leaf name {
       description "Service device pool name";
       type string {
         length "1 .. 63";
         junos:posix-pattern "^[[:alnum:]][[:alnum:]_-]*$";
         junos:pattern-message "Must be a string beginning with a number or letter and consisting of letters, numbers, dashes and underscores.";
       }
     }
     uses apply-advanced;
     list interface {
       key name;
       ordered-by user;
       description "Service device name";
       leaf name {
         junos:must "(!(any \"interfaces <*> aggregated-inline-services-options secondary-interface $$\"))";
         junos:must-message "must not be defined under asiX aggregated-inline-services-options";
         junos:must "(!(any \"interfaces <*> aggregated-inline-services-options primary-interface $$\"))";
         junos:must-message "must not be defined under asiX aggregated-inline-services-options";
         junos:must "(\"interfaces $$\")";
         junos:must-message "referenced interface must be defined";
         type union {
           type jt:interface-unit;
           type string {
             pattern "<.*>|$.*";
           }
         }
       }
       uses apply-advanced;
     }
   }
   grouping service_interface_pool_object {
     leaf name {
       description "Service interface pool name";
       type string {
         length "1 .. 63";
         junos:posix-pattern "^[[:alnum:]][[:alnum:]_-]*$";
         junos:pattern-message "Must be a string beginning with a number or letter and consisting of letters, numbers, dashes and underscores.";
       }
     }
     uses apply-advanced;
     list interface {
       key name;
       ordered-by user;
       description "Service interface name";
       leaf name {
         junos:must "(\"interfaces $$\")";
         junos:must-message "referenced interface must be defined";
         type union {
           type jt:interface-unit;
           type string {
             pattern "<.*>|$.*";
           }
         }
       }
       uses apply-advanced;
     }
   }
   grouping service_point_type {
     leaf name {
       description "Service point name";
       type string;
     }
     uses apply-advanced;
     leaf service-point-type {
       description "Service point type";
       default "sip";
       type enumeration {
         enum "sip" {
         }
       }
     }
     container transport-details {
       presence "enable transport-details";
       description "IP address, port number and transport-protocols for the service-point";
       leaf port-number {
         description "Port number";
         type union {
           type string {
             pattern "<.*>|$.*";
           }
           type uint32 {
             range "0 .. 65535";
           }
         }
       }
       leaf ip-address {
         description "IP address";
         type jt:ipaddr;
       }
       leaf tcp {
         description "Transport protocol - TCP";
         type empty;
       }
       leaf udp {
         description "Transport protocol - UDP";
         type empty;
       }
       leaf fqdn {
         description "Fully Qualified Domain Name";
         type string {
           length "1 .. 128";
         }
       }
     }
     leaf service-interface {
       description "Associated service interface";
       type union {
         type jt:interface-unit;
         type string {
           pattern "<.*>|$.*";
         }
       }
     }
     container service-policies {
       uses service_policies_type;
     }
     leaf default-media-realm {
       description "Use this realm for allocating media resources for calls initiated to/from this service-point";
       junos:must "(\"services pgcp virtual-interface $$\")";
       junos:must-message "Referenced Virtual Interface must be defined";
       type string {
         length "1 .. 4";
       }
     }
   }
   grouping service_policies_type {
     uses apply-advanced;
     leaf-list new-transaction-input-policies {
       ordered-by user;
       description "New transaction input policy name";
       type string;
       max-elements 10;
     }
     leaf-list new-transaction-output-policies {
       ordered-by user;
       description "New transaction output policy name";
       type string;
       max-elements 10;
     }
     leaf-list new-registration-input-policies {
       ordered-by user;
       description "New registration input policy name";
       type string;
       max-elements 10;
     }
     leaf-list new-call-usage-input-policies {
       ordered-by user;
       description "New call usage input policy name";
       type string;
       max-elements 10;
     }
     leaf-list new-call-usage-output-policies {
       ordered-by user;
       description "New call usage output policy name";
       type string;
       max-elements 10;
     }
   }
   grouping services-pcef {
     description "PCEF configuration";
     uses apply-advanced;
     container traceoptions {
       description "Trace options related to PCEF";
       uses pcef-traceoptions;
     }
     container event-trigger-profiles {
       description "Event trigger profiles";
       uses apply-advanced;
       list profile {
         key name;
         uses evt-trigger-profile;
       }
     }
     container flow-descriptions {
       description "PCC flow descriptions";
       uses apply-advanced;
       list definition {
         key name;
         uses pcc-flow;
       }
     }
     container pcc-action-profiles {
       description "PCC action profiles";
       uses apply-advanced;
       list definition {
         key name;
         uses pcc-action-profile;
       }
     }
     container pcc-rules {
       description "PCC rules";
       uses apply-advanced;
       list definition {
         key name;
         uses pcc-rule;
       }
     }
     container pcc-rulebases {
       description "PCC rulebases";
       uses apply-advanced;
       list definition {
         key name;
         ordered-by user;
         uses pcc-rulebase;
       }
     }
     container profile {
       description "PCEF profiles";
       uses apply-advanced;
       list definition {
         key name;
         ordered-by user;
         uses pcef-profiles;
       }
     }
   }
   grouping evt-trigger-profile {
     description "Event trigger profile";
     leaf name {
       description "Event trigger profile name";
       type string {
         length "1 .. 63";
       }
     }
     uses apply-advanced;
     leaf rat-change {
       description "RAT change trigger";
       type empty;
     }
     leaf sgsn-change {
       description "SGSN change trigger";
       type empty;
     }
     leaf plmn-change {
       description "PLMN change trigger";
       type empty;
     }
     leaf ip-can-change {
       description "IP-CAN change trigger";
       type empty;
     }
     leaf tft-change {
       description "TFT change trigger";
       type empty;
     }
     leaf rai-change {
       description "RAI change trigger";
       type empty;
     }
     leaf user-location-change {
       description "User location change";
       type empty;
     }
     leaf ue-timezone-change {
       description "UE timezone change";
       type empty;
     }
   }
   grouping pcc-action-profile {
     description "PCC action profiles";
     leaf name {
       description "PCC action profile identifier";
       type string {
         length "1 .. 63";
       }
     }
     uses apply-advanced;
     leaf logging-rule {
       description "Policy based logging rule name";
       junos:must "(any \"services lrf profile <*> rule $$\")";
       junos:must-message "Specified rule should be configured under services lrf profile rule";
       type string {
         length "1 .. 63";
       }
     }
     container maximum-bit-rate {
       presence "enable maximum-bit-rate";
       description "Maximum bit rate";
       leaf uplink {
         description "Maximum bit rate uplink";
         default "0";
         units "kilobits";
         type union {
           type string {
             pattern "<.*>|$.*";
           }
           type uint32 {
             range "0 .. 6144000";
           }
         }
       }
       leaf downlink {
         description "Maximum bit rate downlink";
         default "0";
         units "kilobits";
         type union {
           type string {
             pattern "<.*>|$.*";
           }
           type uint32 {
             range "0 .. 6144000";
           }
         }
       }
     }
     container burst-size {
       presence "enable burst-size";
       description "Burst Size";
       uses apply-advanced;
       leaf uplink {
         description "Burst size uplink";
         units "bytes";
         type union {
           type string {
             pattern "<.*>|$.*";
           }
           type uint32 {
             range "1500 .. 1500000000";
           }
         }
       }
       leaf downlink {
         description "Burst size downlink";
         units "bytes";
         type union {
           type string {
             pattern "<.*>|$.*";
           }
           type uint32 {
             range "1500 .. 1500000000";
           }
         }
       }
     }
     leaf gate-status {
       description "Control gate status";
       type enumeration {
         enum "uplink" {
           description "Enable uplink traffic";
         }
         enum "downlink" {
           description "Enable downlink traffic";
         }
         enum "uplink-downlink" {
           description "Enable uplink and downlink traffic";
         }
         enum "disable-both" {
           description "Disable any traffic";
         }
       }
     }
     container charging {
       description "Charing related configuration";
       uses apply-advanced;
       leaf rating-group {
         description "Rating group";
         type union {
           type string {
             pattern "<.*>|$.*";
           }
           type uint32 {
             range "0 .. 4294967294";
           }
         }
       }
       leaf service-identifier {
         description "Service identifier";
         default "0";
         type union {
           type string {
             pattern "<.*>|$.*";
           }
           type uint32 {
             range "0 .. 4294967294";
           }
         }
       }
       leaf charging-method {
         description "Charging method";
         type enumeration {
           enum "online" {
             description "Use online charging method";
           }
           enum "offline" {
             description "Use offline charging method";
           }
           enum "both" {
             description "Use online and offline charging method";
           }
           enum "none" {
             description "Use no charging";
           }
         }
       }
       leaf measurement-method {
         description "Charging measure method";
         default "volume-time";
         type enumeration {
           enum "none" {
             description "No default measuring method for charging";
           }
           enum "volume" {
             description "Volume based charging";
           }
           enum "time" {
             description "Time based charging";
           }
           enum "volume-time" {
             description "Volume and time based charging";
           }
           enum "event" {
             description "Event based charging";
           }
         }
       }
       container application-function-record-info {
         presence "enable application-function-record-info";
         description "Application function record information";
         uses apply-advanced;
         leaf af-charging-identifier {
           description "Application function charging identifier";
           type string {
             length "1 .. 63";
           }
         }
       }
       leaf service-id-level-reporting {
         description "Toggle service-id level reporting";
         type empty;
       }
     }
     container redirect {
       description "Redirect to different destination";
       uses apply-advanced;
       leaf url {
         description "Redirect url name";
         junos:must "(!(\".. routing-instance\"))";
         junos:must-message "Either url or routing instance can be defined";
         type string {
           length "1 .. 512";
         }
       }
     }
     container forwarding-class {
       description "Classify packet to forwarding class";
       uses apply-advanced;
       leaf class-name {
         description "Forwarding class name";
         type string {
           junos:posix-pattern "^.{1,64}$";
           junos:pattern-message "Must be string of 64 characters or less";
         }
       }
     }
     container steering {
       description "Steering information";
       uses apply-advanced;
       container routing-instance {
         description "Routing instance information";
         leaf uplink {
           description "Instance name uplink";
           junos:must "(\"routing-instances $$\")";
           junos:must-message "routing instance must be defined";
           type string;
         }
         leaf downlink {
           description "Instance name downlink";
           junos:must "(\"routing-instances $$\")";
           junos:must-message "routing instance must be defined";
           type string;
         }
       }
       container path {
         description "HTTP steering information";
         choice ip-address-type {
           case case_1 {
             leaf ipv4-address {
               description "IPv4 address of the steering destination";
               type jt:ipv4prefix;
             }
           }
           case case_2 {
             leaf ipv6-address {
               description "IPv6 address of the steering destination";
               type jt:ipv6prefix;
             }
           }
         }
       }
       leaf keep-existing-steering {
         description "Keep existing steering";
         type empty;
       }
     }
     container hcm-profile {
       description "HCM Profile";
       uses apply-advanced;
       leaf profile-name {
         description "HCM Profile Name";
         junos:must "(\"services hcm profile $$\")";
         junos:must-message "HCM Profile must be configured";
         type string;
       }
     }
     leaf monitoring-key {
       description "Usage Monitoring key";
       type string {
         length "1 .. 63";
       }
     }
   }
   grouping pcc-flow {
     description "Configure PCC flow";
     leaf name {
       description "PCC flow identifier";
       type string {
         length "1 .. 63";
       }
     }
     uses apply-advanced;
     leaf direction {
       description "PCC flow direction";
       type enumeration {
         enum "downlink" {
           description "Downlink direction";
         }
         enum "uplink" {
           description "Uplink direction";
         }
         enum "both" {
           description "Both uplink and downlink directons";
         }
       }
     }
     leaf protocol {
       description "PCC flow IPv4 protocol";
       type union {
         type string {
           pattern "<.*>|$.*";
         }
         type uint8 {
           range "0 .. 255";
         }
       }
     }
     leaf-list local-ports {
       description "Local port or port list";
       junos:must "(!(\".. local-port-range\"))";
       junos:must-message "Either port list or port range can be defined";
       type union {
         type string {
           pattern "<.*>|$.*";
         }
         type uint16 {
           range "1 .. 65535";
         }
       }
       max-elements 3;
     }
     list local-port-range {
       key "low high";
       ordered-by user;
       description "Local port range";
       junos:must "(!(\".. local-ports\"))";
       junos:must-message "Either port list or port range can be defined";
       max-elements 3;
       leaf low {
         description "Lower limit of port range";
         type union {
           type string {
             pattern "<.*>|$.*";
           }
           type uint16 {
             range "1 .. 65535";
           }
         }
       }
       leaf high {
         description "Upper limit of port range";
         type union {
           type string {
             pattern "<.*>|$.*";
           }
           type uint16 {
             range "1 .. 65535";
           }
         }
       }
     }
     leaf-list remote-ports {
       description "Remote port or port list";
       junos:must "(!(\".. remote-port-range\"))";
       junos:must-message "Either port list or port range can be defined";
       type union {
         type string {
           pattern "<.*>|$.*";
         }
         type uint16 {
           range "1 .. 65535";
         }
       }
       max-elements 3;
     }
     list remote-port-range {
       key "low high";
       ordered-by user;
       description "Remote port range";
       junos:must "(!(\".. remote-ports\"))";
       junos:must-message "Either port list or port range can be defined";
       max-elements 3;
       leaf low {
         description "Lower limit of port range";
         type union {
           type string {
             pattern "<.*>|$.*";
           }
           type uint16 {
             range "1 .. 65535";
           }
         }
       }
       leaf high {
         description "Upper limit of port range";
         type union {
           type string {
             pattern "<.*>|$.*";
           }
           type uint16 {
             range "1 .. 65535";
           }
         }
       }
     }
     container remote-address {
       description "Remote address";
       choice ip-address-type {
         case case_1 {
           leaf ipv4-address {
             description "IPv4 address for the flow";
             type jt:ipv4prefix;
           }
         }
         case case_2 {
           leaf ipv6-address {
             description "IPv6 address for the flow";
             type jt:ipv6prefix;
           }
         }
       }
     }
   }
   grouping pcc-rule {
     description "PCC rules configuration";
     leaf name {
       description "PCC Rule identifier";
       type string {
         junos:posix-pattern "^[.0-9A-Za-z_-]{1,63}$";
         junos:pattern-message "Must be a string of 63 or fewer characters and may contain letters, numbers, decimals and dashes.";
       }
     }
     uses apply-advanced;
     container from {
       description "Aggregate of flows using same pcc-action-profile";
       uses apply-advanced;
       list flows {
         key name;
         ordered-by user;
         description "Associate PCC Flows";
         max-elements 64;
         leaf name {
           description "PCC Flow identifier";
           junos:must "(\".. .. .. .. .. flow-descriptions $$\")";
           junos:must-message "Referenced flow must be defined";
           type string {
             length "1 .. 63";
           }
         }
         uses apply-advanced;
       }
       list applications {
         key name;
         ordered-by user;
         description "Associated application signature names";
         max-elements 10;
         leaf name {
           description "Signature names";
           type string {
             length "1 .. 63";
           }
         }
         uses apply-advanced;
       }
       list nested-applications {
         key name;
         ordered-by user;
         description "Associated nested application signature names";
         status deprecated;
         max-elements 10;
         leaf name {
           description "Nested application signature names";
           type string {
             length "1 .. 63";
           }
         }
         uses apply-advanced;
       }
       list application-groups {
         key name;
         ordered-by user;
         description "Application Group signature names";
         max-elements 10;
         leaf name {
           description "Application group names";
           type string {
             length "1 .. 63";
           }
         }
         uses apply-advanced;
       }
     }
     container then {
       description "Specified pcc-action-profile";
       uses apply-advanced;
       leaf pcc-action-profile {
         description "PCC Action profile name";
         junos:must "(\".. .. .. .. pcc-action-profiles $$\")";
         junos:must-message "Referenced action profile must be defined";
         type string {
           length "1 .. 63";
         }
       }
     }
   }
   grouping pcc-rulebase {
     description "PCC rulebases";
     leaf name {
       description "PCC Rulebase identifier";
       type string {
         junos:posix-pattern "^[.0-9A-Za-z_-]{1,63}$";
         junos:pattern-message "Must be a string of 63 or fewer charactars and may contain letters, numbers, decimals and dashes";
       }
     }
     uses apply-advanced;
     list pcc-rule {
       key name;
       ordered-by user;
       max-elements 32;
       leaf name {
         description "PCC rule name";
         junos:must "(\".. .. .. .. pcc-rules $$\")";
         junos:must-message "Referenced rule must be defined";
         type string {
           length "1 .. 63";
           junos:posix-pattern "^[.0-9A-Za-z_-]{1,63}$";
           junos:pattern-message "Must be a string of 63 or fewer charactars and may contain letters, numbers, decimals and dashes";
         }
       }
       leaf precedence {
         description "PCC rule precedence";
         junos:must "(unique \".. .. pcc-rule <*> precedence $$\")";
         junos:must-message "Precedence has to unique among rules";
         type union {
           type string {
             pattern "<.*>|$.*";
           }
           type uint16 {
             range "1 .. 4000";
           }
         }
       }
     }
   }
   grouping pcef-profiles {
     description "PCEF profiles";
     leaf name {
       description "PCEF profile name";
       type string {
         length "1 .. 63";
       }
     }
     uses apply-advanced;
     leaf control-byte-rating-group {
       description "Rating group id";
       type union {
         type string {
           pattern "<.*>|$.*";
         }
         type uint32 {
           range "0 .. 4294967294";
         }
       }
     }
     leaf unresolved-flow-action {
       description "Flow action";
       type enumeration {
         enum "forward" {
           description "Forward";
         }
         enum "drop" {
           description "Drop";
         }
       }
     }
     container maximum-per-pdn-service-flows {
       description "Max service flows per PDN";
       leaf num {
         description "Value";
         type union {
           type uint32;
           type string {
             pattern "<.*>|$.*";
           }
         }
       }
     }
     container dynamic-policy-control {
       junos:must "((\"diameter-profile\" || \".. .. .. .. .. system services subscriber-management enable\"))";
       junos:must-message "diameter-profile must be configured when 'system services subscriber-management' is not enabled";
       junos:must "((!(\".. static-policy-control\") && !(\".. aaa-policy-control\")))";
       junos:must-message "Either static or dynamic or AAA policy control can be specified";
       description "Dynamic policy control";
       uses apply-advanced;
       container pcc-rules {
         description "PCC rules association";
         uses apply-advanced;
         list rule-assoc {
           key name;
           ordered-by user;
           max-elements 64;
           uses profile-rule-assoc;
         }
       }
       list pcc-rulebases {
         key name;
         ordered-by user;
         description "PCC rulebase association";
         leaf name {
           description "PCC rulebase name";
           junos:must "(\".. .. .. .. .. pcc-rulebases $$\")";
           junos:must-message "Referenced rulebase must be defined";
           type string {
             length "1 .. 63";
           }
         }
         uses apply-advanced;
       }
       leaf diameter-profile {
         description "Diameter profile name";
         junos:must "(\".. .. .. .. .. diameter-profiles gx-profile $$\")";
         junos:must-message "Referenced diameter profile must be defined";
         type string {
           length "1 .. 63";
         }
       }
       leaf event-trigger-profile {
         description "Event trigger profile name";
         junos:must "(\".. .. .. .. event-trigger-profiles $$\")";
         junos:must-message "Referenced event trigger profile must be defined";
         type string {
           length "1 .. 63";
         }
       }
       leaf session-failover-not-supported {
         description "Session failover not supported";
         type empty;
       }
       leaf release {
         description "To override Gx release to R8|R9";
         type enumeration {
           enum "r8" {
             description "Gx release 8";
           }
           enum "r9" {
             description "Gx release 9";
           }
         }
       }
     }
     container static-policy-control {
       junos:must "((!(\".. dynamic-policy-control\") && !(\".. aaa-policy-control\")))";
       junos:must-message "Either static or dynamic or AAA policy control can be specified";
       description "Static policy control";
       uses apply-advanced;
       container pcc-rules {
         description "PCC rules association";
         uses apply-advanced;
         list rule-assoc {
           key name;
           ordered-by user;
           max-elements 64;
           uses profile-static-rule-association;
         }
       }
       list pcc-rulebases {
         key name;
         ordered-by user;
         description "PCC rulebase association";
         leaf name {
           description "PCC rulebase name";
           junos:must "(\".. .. .. .. .. pcc-rulebases $$\")";
           junos:must-message "Referenced rulebase must be defined";
           type string {
             length "1 .. 63";
           }
         }
         uses apply-advanced;
         leaf time-of-day-profile {
           description "Time of day profile name";
           junos:must "(\".. .. .. .. .. pcc-time-of-day-profiles $$\")";
           junos:must-message "Referenced time-of-day profile must be defined";
           type string {
             length "1 .. 63";
           }
         }
       }
       leaf-list activate-dedicated-bearers {
         description "Enable dedicated bearer activation on initial attach with qci";
         type union {
           type string {
             pattern "<.*>|$.*";
           }
           type uint8 {
             range "1 .. 9";
           }
         }
         max-elements 9;
       }
     }
     container aaa-policy-control {
       junos:must "((!(\".. static-policy-control\") && !(\".. dynamic-policy-control\")))";
       junos:must-message "Either static or dynamic or AAA policy control can be specified";
       description "AAA policy control";
       uses apply-advanced;
       leaf profile {
         description "AAA profile name";
         junos:must "(\".. .. .. .. .. aaa profiles $$\")";
         junos:must-message "Referenced AAA profile must be defined";
         type string {
           length "1 .. 32";
         }
       }
       leaf user-password {
         description "User password";
         type string {
           length "1 .. 32";
         }
       }
       list pcc-rulebases {
         key name;
         ordered-by user;
         description "PCC rulebase association";
         leaf name {
           description "PCC rulebase name";
           junos:must "(\".. .. .. .. .. pcc-rulebases $$\")";
           junos:must-message "Referenced rulebase must be defined";
           type string {
             length "1 .. 63";
           }
         }
         uses apply-advanced;
       }
     }
   }
   grouping pcef-traceoptions {
     description "Trace options related to PCEF";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing parameters";
       leaf name {
         type enumeration {
           enum "init" {
             description "Trace initialization events";
           }
           enum "config" {
             description "Trace configuration events";
           }
           enum "general" {
             description "Trace general events";
           }
           enum "high-availability" {
             description "Trace high availability events";
           }
           enum "debug" {
             description "Trace debug internal events";
           }
           enum "fsm" {
             description "Trace fsm events";
           }
           enum "tftmgr" {
             description "Trace tftmgr events";
           }
           enum "all" {
             description "Trace everything";
           }
         }
       }
     }
   }
   grouping profile-rule-assoc {
     leaf name {
       description "PCC rule name";
       junos:must "(\".. .. .. .. .. .. pcc-rules $$\")";
       junos:must-message "Referenced rule must be defined";
       type string {
         length "1 .. 63";
       }
     }
     leaf precedence {
       description "PCC rule precedence";
       junos:must "(unique \".. .. <*> precedence $$\")";
       junos:must-message "Precedence has to unique among rules";
       type union {
         type string {
           pattern "<.*>|$.*";
         }
         type uint16 {
           range "1 .. 4000";
         }
       }
     }
   }
   grouping profile-static-rule-association {
     leaf name {
       description "PCC rule name";
       junos:must "(\".. .. .. .. .. .. pcc-rules $$\")";
       junos:must-message "Referenced rule must be defined";
       type string {
         length "1 .. 63";
       }
     }
     leaf precedence {
       description "PCC rule precedence";
       junos:must "(unique \".. .. <*> precedence $$\")";
       junos:must-message "Precedence has to unique among rules";
       type union {
         type string {
           pattern "<.*>|$.*";
         }
         type uint16 {
           range "1 .. 4000";
         }
       }
     }
     leaf time-of-day-profile {
       description "Time of day profile name";
       junos:must "(\".. .. .. .. .. .. pcc-time-of-day-profiles $$\")";
       junos:must-message "Referenced time-of-day profile must be defined";
       type string {
         length "1 .. 63";
       }
     }
     container pcc-action-profile {
       description "PCC action profile association";
       status deprecated;
       leaf rules-action-profile {
         description "PCC action profile name";
         junos:must "(\".. .. .. .. .. .. .. pcc-action-profiles $$\")";
         junos:must-message "Referenced action profile must be defined";
         type string {
           length "1 .. 63";
         }
       }
     }
   }
   grouping session_timeout_type {
     uses apply-advanced;
     leaf tcp {
       description "Timeout value for tcp sessions";
       units "seconds";
       type union {
         type string {
           pattern "<.*>|$.*";
         }
         type uint32 {
           range "4 .. 86400";
         }
       }
     }
     leaf udp {
       description "Timeout value for udp sessions";
       units "seconds";
       type union {
         type string {
           pattern "<.*>|$.*";
         }
         type uint32 {
           range "4 .. 86400";
         }
       }
     }
     leaf ospf {
       description "Timeout value for ospf sessions";
       units "seconds";
       type union {
         type string {
           pattern "<.*>|$.*";
         }
         type uint32 {
           range "4 .. 86400";
         }
       }
     }
     leaf icmp {
       description "Timeout value for icmp sessions";
       units "seconds";
       type union {
         type string {
           pattern "<.*>|$.*";
         }
         type uint32 {
           range "4 .. 86400";
         }
       }
     }
     leaf icmp6 {
       description "Timeout value for icmp6 sessions";
       units "seconds";
       type union {
         type string {
           pattern "<.*>|$.*";
         }
         type uint32 {
           range "4 .. 86400";
         }
       }
     }
     leaf others {
       description "Timeout value for other sessions";
       units "seconds";
       type union {
         type string {
           pattern "<.*>|$.*";
         }
         type uint32 {
           range "4 .. 86400";
         }
       }
     }
   }
   grouping sfw_addr_object {
     leaf name {
       description "Match IP address";
       type string;
     }
     leaf except {
       description "Match address not in this prefix";
       type empty;
     }
   }
   grouping sfw_match_object {
     uses apply-advanced;
     list source-address {
       key name;
       ordered-by user;
       description "Match IP source address";
       uses sfw_addr_object;
     }
     list destination-address {
       key name;
       ordered-by user;
       description "Match IP destination address";
       uses sfw_addr_object;
     }
     container destination-port {
       presence "enable destination-port";
       uses apply-advanced;
       choice port_choice {
         case case_1 {
           container range {
             description "Range of ports";
             leaf low {
               description "Lower limit of port range";
               type union {
                 type string {
                   pattern "<.*>|$.*";
                 }
                 type uint16 {
                   range "1 .. 65535";
                 }
               }
             }
             leaf high {
               description "Upper limit of port range";
               type union {
                 type string {
                   pattern "<.*>|$.*";
                 }
                 type uint16 {
                   range "1 .. 65535";
                 }
               }
             }
           }
         }
       }
     }
     list source-address-range {
       key "low high";
       ordered-by user;
       description "Match IP source address range";
       leaf low {
         description "Lower limit of address range";
         type jt:ipaddr;
       }
       leaf high {
         description "Upper limit of address range";
         type jt:ipaddr;
       }
       leaf except {
         description "Match address not in this prefix";
         type empty;
       }
     }
     list source-prefix-list {
       key name;
       ordered-by user;
       description "One or more named lists of source prefixes to match";
       leaf name {
         description "Name of prefix list to match against";
         type string;
       }
       leaf except {
         description "Name of prefix list not to match against";
         type empty;
       }
     }
     list destination-address-range {
       key "low high";
       ordered-by user;
       description "Match IP destination address range";
       leaf low {
         description "Lower limit of address range";
         type jt:ipaddr;
       }
       leaf high {
         description "Upper limit of address range";
         type jt:ipaddr;
       }
       leaf except {
         description "Match address not in this prefix";
         type empty;
       }
     }
     list destination-prefix-list {
       key name;
       ordered-by user;
       description "One or more named lists of destination prefixes to match";
       leaf name {
         description "Name of prefix list to match against";
         type string;
       }
       leaf except {
         description "Name of prefix list not to match against";
         type empty;
       }
     }
     leaf-list applications {
       ordered-by user;
       description "Match one or more applications";
       type string;
     }
     list application-sets {
       key name;
       ordered-by user;
       description "Match one or more application sets";
       leaf name {
         type string {
           length "1 .. 63";
           junos:posix-pattern "^[[:alnum:]][[:alnum:]_-]*$";
           junos:pattern-message "Must be a string beginning with a number or letter and consisting of letters, numbers, dashes and underscores.";
         }
       }
       uses apply-advanced;
     }
     leaf-list application {
       ordered-by user;
       type string;
     }
   }
   grouping sfw_rule_object {
     leaf name {
       description "Rule name";
       type string {
         length "1 .. 63";
         junos:posix-pattern "^[[:alnum:]][[:alnum:]/.:_-]*$";
         junos:pattern-message "Must be a string beginning with a number or letter and consisting of letters, numbers, dashes, underscores, forward slashes, colons and dots.";
       }
     }
     uses apply-advanced;
     leaf match-direction {
       description "Direction for which the rule match is applied";
       type enumeration {
         enum "input" {
           description "Match on input to interface";
         }
         enum "output" {
           description "Match on output from interface";
         }
         enum "input-output" {
           description "Match on input to or output from interface";
         }
       }
     }
     list term {
       key name;
       ordered-by user;
       description "Define a stateful firewall term";
       leaf name {
         description "Term name";
         type string {
           length "1 .. 63";
           junos:posix-pattern "^[[:alnum:]][[:alnum:]/.:_-]*$";
           junos:pattern-message "Must be a string beginning with a number or letter and consisting of letters, numbers, dashes, underscores, forward slashes, colons and dots.";
         }
       }
       uses apply-advanced;
       container from {
         description "Define match criteria";
         uses sfw_match_object;
       }
       container then {
         description "Action to take if the 'from' condition is matched";
         uses apply-advanced;
         choice designation {
           case case_1 {
             leaf accept {
               description "Accept the packet";
               type empty;
             }
           }
           case case_2 {
             container discard {
               presence "enable discard";
               description "Discard the packet";
               uses apply-advanced;
             }
           }
           case case_3 {
             leaf reject {
               description "Reject the packet";
               type empty;
             }
           }
         }
         leaf-list allow-ip-options {
           ordered-by user;
           type string;
         }
         leaf syslog {
           description "System log information about the packet";
           type empty;
         }
         leaf skip-ids {
           description "No IDS processing will be done on a matching packet";
           type empty;
         }
       }
     }
   }
   grouping signaling-realm {
     description "Signaling realm";
     leaf name {
       description "Realm name";
       type string;
     }
     uses apply-advanced;
   }
   grouping sip_timers_type {
     uses apply-advanced;
     leaf inactive-call {
       description "Maximum time for signaling inactivity";
       default "86400";
       units "seconds";
       type union {
         type string {
           pattern "<.*>|$.*";
         }
         type uint32 {
           range "300 .. 86400";
         }
       }
     }
     leaf timer-c {
       description "Maximum time to wait for final response on invite";
       default "180";
       units "seconds";
       type union {
         type string {
           pattern "<.*>|$.*";
         }
         type uint32 {
           range "180 .. 300";
         }
       }
     }
   }
   grouping soft_gre_tunnel_group_object {
     leaf name {
       description "Tunnel group name";
       type string {
         junos:posix-pattern "^[[:alnum:]][[:alnum:]_-]*$";
         junos:pattern-message "Must be a string beginning with a number or letter and consisting of letters, numbers, dashes and underscores.";
       }
     }
     uses apply-advanced;
     leaf source-address {
       description "Local address of tunnel";
       type jt:ipaddr;
     }
     list destination-networks {
       key name;
       ordered-by user;
       description "Create tunnels for routes in these destination networks";
       uses soft_gre_destination_network_object;
     }
     leaf service-interface {
       description "Pseudowire interface to use";
       junos:must "(\"interfaces $$\")";
       junos:must-message "Interface must be defined in the interfaces hierarchy";
       type union {
         type jt:interface-unit;
         type string {
           pattern "<.*>|$.*";
         }
       }
     }
     leaf tunnel-idle-timeout {
       description "Time to tear down tunnel when idle";
       default "120";
       units "seconds";
       type union {
         type uint16;
         type string {
           pattern "<.*>|$.*";
         }
       }
     }
     leaf dynamic-profile {
       description "Dynamic profile for tunnel interface";
       junos:must "(\"dynamic-profiles $$\")";
       junos:must-message "Referenced dynamic profile must be defined";
       type string {
         length "1 .. 80";
       }
     }
   }
   grouping soft_gre_destination_network_object {
     leaf name {
       description "Network prefix";
       type jt:ipprefix;
     }
     uses apply-advanced;
   }
   grouping softwires-object {
     description "Configure softwire feature";
     uses apply-advanced;
     list softwire-name {
       key name;
       description "Configure softwire object";
       uses softwire-option-type;
     }
     container traceoptions {
       description "Trace options for Network Security DS-Lite";
       uses apply-advanced;
       leaf no-remote-trace {
         description "Disable remote tracing";
         junos:must "(\"system tracing\")";
         junos:must-message "'no-remote-trace' is valid only when [system tracing] is configured";
         type empty;
       }
       container file {
         description "Trace file information";
         leaf filename {
           description "Name of file in which to write trace information";
           type string {
             length "1 .. 1024";
             junos:posix-pattern "![/ %]";
             junos:pattern-message "Must not contain '/', % or a space";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing parameters";
         leaf name {
           type enumeration {
             enum "configuration" {
               description "Trace configuration events";
             }
             enum "flow" {
               description "Trace flow events";
             }
             enum "all" {
               description "Trace everything";
             }
           }
         }
       }
     }
     list rule-set {
       key name;
       ordered-by user;
       description "Define a softwire rule set";
       uses sw-rule-set-object;
     }
   }
   grouping softwire-option-type {
     description "Configure softwire object";
     leaf name {
       description "DS-Lite/Softwire object name";
       type string {
         length "1 .. 23";
       }
     }
     uses apply-advanced;
     leaf softwire-concentrator {
       description "Concentrator address";
       type jt:ipaddr;
     }
     leaf softwire-type {
       description "Softwire-type";
       default "IPv4-in-IPv6";
       type enumeration {
         enum "IPv4-in-IPv6" {
           description "Ipv4-in-IPv6";
         }
         enum "v6rd" {
           description "V6rd";
         }
       }
     }
     leaf ipv4-prefix {
       description "6rd customer edge IPV4 prefix";
       type jt:ipv4prefix;
     }
     leaf v6rd-prefix {
       description "6rd domain's IPV6 prefix";
       type jt:ipv6prefix;
     }
     leaf mtu-v4 {
       description "MTU for the softwire tunnel";
       type union {
         type string {
           pattern "<.*>|$.*";
         }
         type uint32 {
           range "576 .. 9192";
         }
       }
     }
   }
   grouping srd-rs-id-object {
     description "Definition of redundancy-set";
     leaf name {
       description "Redundancy set identifier";
       type union {
         type string {
           pattern "<.*>|$.*";
         }
         type uint32 {
           range "1 .. 100";
         }
       }
     }
     uses apply-advanced;
     leaf redundancy-group {
       description "Name of redundancy-group";
       type union {
         type string {
           pattern "<.*>|$.*";
         }
         type uint32 {
           range "1 .. 16";
         }
       }
     }
     leaf-list redundancy-policy {
       description "Redundancy-policy list";
       type string;
     }
     leaf keepalive {
       description "Frequency of SRD hello messages";
       default "10";
       units "seconds";
       type union {
         type string {
           pattern "<.*>|$.*";
         }
         type uint32 {
           range "1 .. 60";
         }
       }
     }
     leaf hold-time {
       description "Time before SRD peer is declared down";
       default "30";
       units "seconds";
       type union {
         type string {
           pattern "<.*>|$.*";
         }
         type uint32 {
           range "0 .. 3600";
         }
       }
     }
     leaf healthcheck-timer-interval {
       description "Healthcheck timer interval";
       default "5";
       units "seconds";
       type union {
         type string {
           pattern "<.*>|$.*";
         }
         type uint32 {
           range "1 .. 3600";
         }
       }
     }
   }
   grouping srd-traceoptions-object {
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing flag parameters";
       leaf name {
         type enumeration {
           enum "config" {
             description "Trace parse events";
           }
           enum "connect" {
             description "Trace ipc events";
           }
           enum "route" {
             description "Trace route events";
           }
           enum "ssd" {
             description "Trace SDK Service events";
           }
           enum "snmp" {
             description "Trace snmp events";
           }
           enum "system" {
             description "Trace services redundancy system events";
           }
           enum "opcmd" {
             description "Trace operational command events";
           }
           enum "state-machine" {
             description "Trace finite-state-machine events";
           }
           enum "kcom" {
             description "Trace KCOM events";
           }
           enum "database" {
             description "Trace database events";
           }
           enum "swithover" {
             description "Trace switchover events";
           }
           enum "stateful-sync" {
             description "Trace stateful-sync related events";
           }
           enum "redundancy-group" {
             description "Trace redundancy-group related events";
           }
           enum "all" {
             description "Trace everything";
           }
         }
       }
     }
   }
   grouping ssg-destination-nat-object {
     uses apply-advanced;
     list pool {
       key name;
       ordered-by user;
       description "Define a destination address pool";
       leaf name {
         description "Pool name";
         type string {
           length "1 .. 31";
           junos:posix-pattern "^[[:alnum:]][[:alnum:]_-]*$";
           junos:pattern-message "Must be a string beginning with a number or letter and consisting of letters, numbers, dashes and underscores.";
         }
       }
       uses apply-advanced;
       leaf description {
         description "Text description of pool";
         type string {
           length "1 .. 900";
           junos:posix-pattern "^[^&<>\n]+$";
           junos:pattern-message "Must be a string excluding '&', '<', '>' and '\n'";
         }
       }
       container routing-instance {
         description "Routing instance";
         uses apply-advanced;
         choice ri-name-choice {
           case case_1 {
             leaf default {
               description "Default routing-instance";
               type empty;
             }
           }
           case case_2 {
             leaf ri-name {
               description "Routing-instance name";
               junos:must "(\"routing-instances $$ instance-type virtual-router\")";
               junos:must-message "Instance-type virtual-router must be defined under [routing-instances]";
               junos:must "(\"routing-instances $$\")";
               junos:must-message "Routing-instance must be defined";
               type string {
                 junos:posix-pattern "^[[:alnum:]][[:alnum:]_-]*$";
                 junos:pattern-message "Must be a string beginning with a number or letter and consisting of letters, numbers, dashes and underscores.";
               }
             }
           }
         }
       }
       container address {
         description "Add address or address range to pool";
         leaf ipaddr {
           description "IPv4 or IPv6 address or address range";
           type jt:ipprefix;
         }
         choice range-port-choice {
           case case_1 {
             container to {
               description "Upper limit of address range";
               uses apply-advanced;
               leaf ipaddr {
                 description "IPv4 or IPv6 upper limit of address range";
                 type jt:ipprefix;
               }
             }
           }
           case case_2 {
             leaf port {
               description "Specify the port value";
               type union {
                 type uint16;
                 type string {
                   pattern "<.*>|$.*";
                 }
               }
             }
           }
         }
       }
     }
     list port-forwarding {
       key name;
       ordered-by user;
       description "Define a port-forwarding mapping pool";
       leaf name {
         description "Port Forwarding mapping name";
         type string {
           length "1 .. 31";
           junos:posix-pattern "^[[:alnum:]][[:alnum:]_-]*$";
           junos:pattern-message "Must be a string beginning with a number or letter and consisting of letters, numbers, dashes and underscores.";
         }
       }
       uses apply-advanced;
       leaf description {
         description "Text description of port forwarding mapping";
         type string {
           length "1 .. 900";
           junos:posix-pattern "^[^&<>\n]+$";
           junos:pattern-message "Must be a string excluding '&', '<', '>' and '\n'";
         }
       }
       list destined-port {
         key "port translated-port";
         ordered-by user;
         description "Port forwarding mappings";
         max-elements 32;
         leaf port {
           description "Destination port";
           type union {
             type string {
               pattern "<.*>|$.*";
             }
             type uint16 {
               range "1 .. 65535";
             }
           }
         }
         leaf translated-port {
           description "Translated port";
           type union {
             type string {
               pattern "<.*>|$.*";
             }
             type uint16 {
               range "1 .. 65535";
             }
           }
         }
       }
     }
     list rule-set {
       key name;
       ordered-by user;
       description "Configurate a set of rules";
       leaf name {
         description "Rule-set name";
         junos:must "((!(\"services nat source rule-set $$\") && !(\"services nat static rule-set $$\")))";
         junos:must-message "the rule set name should be unique across all types of nat";
         type string {
           length "1 .. 31";
           junos:posix-pattern "^[[:alnum:]][[:alnum:]_-]*$";
           junos:pattern-message "Must be a string beginning with a number or letter and consisting of letters, numbers, dashes and underscores.";
         }
       }
       uses apply-advanced;
       leaf description {
         description "Text description of rule set";
         type string {
           length "1 .. 900";
           junos:posix-pattern "^[^&<>\n]+$";
           junos:pattern-message "Must be a string excluding '&', '<', '>' and '\n'";
         }
       }
       container from {
         description "Where is the traffic from";
         choice from-context-choice {
           case case_1 {
             leaf-list routing-instance {
               description "Source routing instance list";
               type string;
               max-elements 8;
             }
           }
           case case_2 {
             leaf-list zone {
               description "Source zone list";
               type string;
               max-elements 8;
             }
           }
           case case_3 {
             leaf-list interface {
               description "Source interface list";
               type union {
                 type jt:interface-name;
                 type string {
                   pattern "<.*>|$.*";
                 }
               }
               max-elements 8;
             }
           }
         }
       }
       list rule {
         key name;
         ordered-by user;
         description "Destination NAT rule";
         uses dest-nat-rule-object;
       }
       leaf match-direction {
         description "Match direction";
         type enumeration {
           enum "input" {
             description "Match on input to interface";
           }
           enum "output" {
             description "Match on output from interface";
           }
         }
       }
     }
   }
   grouping dest-nat-rule-object {
     leaf name {
       description "Rule name";
       type string {
         length "1 .. 31";
         junos:posix-pattern "^[[:alnum:]][[:alnum:]_-]*$";
         junos:pattern-message "Must be a string beginning with a number or letter and consisting of letters, numbers, dashes and underscores.";
       }
     }
     uses apply-advanced;
     leaf description {
       description "Text description of rule";
       type string {
         length "1 .. 900";
         junos:posix-pattern "^[^&<>\n]+$";
         junos:pattern-message "Must be a string excluding '&', '<', '>' and '\n'";
       }
     }
     container dest-nat-rule-match {
       description "Specify Destination NAT rule match criteria";
       uses apply-advanced;
       leaf-list source-address {
         ordered-by user;
         description "Source address";
         type string;
         max-elements 8;
       }
       leaf-list source-address-name {
         ordered-by user;
         description "Address/address-set from address book";
         type string;
         max-elements 8;
       }
       choice dst-choice {
         case case_1 {
           container destination-address {
             description "Destination address";
             choice dst-addr-choice {
               case case_1 {
                 leaf dst-addr {
                   description "IPv4 or IPv6 destination address";
                   type jt:ipprefix;
                 }
               }
               case case_2 {
                 leaf any-unicast {
                   description "Match any unicast address";
                   type empty;
                 }
               }
             }
           }
         }
         case case_2 {
           container destination-address-name {
             description "Address from address book";
             leaf dst-addr-name {
               description "Address from address book";
               type string {
                 length "1 .. 63";
               }
             }
           }
         }
       }
       list destination-port {
         key name;
         ordered-by user;
         description "Destination port";
         max-elements 8;
         leaf name {
           description "Port or lower limit of port range";
           type union {
             type uint16;
             type string {
               pattern "<.*>|$.*";
             }
           }
         }
         container to {
           description "Port range upper limit";
           uses apply-advanced;
           leaf high {
             description "Upper limit of port range";
             type union {
               type uint16;
               type string {
                 pattern "<.*>|$.*";
               }
             }
           }
         }
       }
       leaf-list protocol {
         ordered-by user;
         description "IP Protocol";
         type string;
         max-elements 4;
       }
       leaf-list application {
         ordered-by user;
         type string;
       }
     }
     container then {
       description "Then action";
       uses apply-advanced;
       container destination-nat {
         description "Destination NAT action";
         uses apply-advanced;
         choice action {
           case case_1 {
             leaf off {
               description "No action";
               type empty;
             }
           }
           case case_2 {
             container pool {
               description "Use Destination NAT pool";
               uses apply-advanced;
               leaf pool-name {
                 description "Name of Destination NAT pool";
                 junos:must "(\".. .. .. .. .. .. .. .. nat destination pool $$\")";
                 junos:must-message "Destination NAT pool name must be defined";
                 type string {
                   length "1 .. 31";
                 }
               }
             }
           }
           case case_3 {
             leaf destination-prefix {
               description "Destination prefix to be used for NAT64 and 464 translation type";
               type jt:ipprefix-only;
             }
           }
         }
         container port-forwarding-mappings {
           description "Use Destination NAT port forwarding mapping pool";
           uses apply-advanced;
           leaf pf-name {
             description "Name of Port forwarding mappings";
             junos:must "(\".. .. .. .. .. .. .. .. nat destination port-forwarding $$\")";
             junos:must-message "Port forwarding pool mappings must be defined";
             type string {
               length "1 .. 31";
             }
           }
         }
         container rule-session-count-alarm {
           description "Config rule-session-count-alarm to destination rule";
           uses nat-rule-session-count-alarm-object;
         }
       }
       leaf syslog {
         description "System log information about the packet";
         type empty;
       }
     }
   }
   grouping nat-rule-session-count-alarm-object {
     uses apply-advanced;
     leaf raise-threshold {
       description "Raise threshold for rule session count alarm";
       type union {
         type string {
           pattern "<.*>|$.*";
         }
         type uint32 {
           range "1 .. 4294967295";
         }
       }
     }
     leaf clear-threshold {
       description "Clear threshold for session count hit alarm";
       type union {
         type string {
           pattern "<.*>|$.*";
         }
         type uint32 {
           range "1 .. 4294967295";
         }
       }
     }
   }
   grouping ssg-proxy-arp-object {
     uses apply-advanced;
     list interface {
       key name;
       ordered-by user;
       description "Interface with proxy arp configured";
       uses ssg-interface-object;
     }
   }
   grouping ssg-interface-object {
     leaf name {
       description "Interface name";
       type union {
         type jt:interface-name;
         type string {
           pattern "<.*>|$.*";
         }
       }
     }
     uses apply-advanced;
     list address {
       key name;
       ordered-by user;
       description "Proxy ARP address";
       leaf name {
         description "Address or address range";
         type jt:ipv4prefix;
       }
       container to {
         description "Upper limit of address range";
         uses apply-advanced;
         leaf ipaddr {
           description "Upper limit of address range";
           type jt:ipv4prefix;
         }
       }
     }
   }
   grouping ssg-proxy-ndp-object {
     uses apply-advanced;
     list interface {
       key name;
       ordered-by user;
       description "Interface with proxy arp configured";
       uses ssg-proxy-ndp-interface-object;
     }
   }
   grouping ssg-proxy-ndp-interface-object {
     leaf name {
       description "Interface name";
       type union {
         type jt:interface-name;
         type string {
           pattern "<.*>|$.*";
         }
       }
     }
     uses apply-advanced;
     list address {
       key name;
       ordered-by user;
       description "Proxy ndp address";
       leaf name {
         description "Address or address range";
         type jt:ipv6prefix;
       }
       container to {
         description "Upper limit of address range";
         uses apply-advanced;
         leaf ipv6addr {
           description "Upper limit of address range";
           type jt:ipv6addr;
         }
       }
     }
   }
   grouping ssg-source-nat-object {
     uses apply-advanced;
     list pool {
       key name;
       ordered-by user;
       description "Define a source address pool";
       leaf name {
         description "Pool name";
         type string {
           length "1 .. 31";
           junos:posix-pattern "^[[:alnum:]][[:alnum:]_-]*$";
           junos:pattern-message "Must be a string beginning with a number or letter and consisting of letters, numbers, dashes and underscores.";
         }
       }
       uses apply-advanced;
       leaf description {
         description "Text description of pool";
         type string {
           length "1 .. 900";
           junos:posix-pattern "^[^&<>\n]+$";
           junos:pattern-message "Must be a string excluding '&', '<', '>' and '\n'";
         }
       }
       container routing-instance {
         description "Routing instance";
         uses apply-advanced;
         leaf ri-name {
           description "Routing instance name";
           junos:must "(\"routing-instances $$ instance-type virtual-router\")";
           junos:must-message "Instance-type virtual-router must be defined under [routing-instances]";
           junos:must "(\"routing-instances $$\")";
           junos:must-message "Routing-instance must be defined";
           type string {
             junos:posix-pattern "^[[:alnum:]][[:alnum:]_-]*$";
             junos:pattern-message "Must be a string beginning with a number or letter and consisting of letters, numbers, dashes and underscores.";
           }
         }
       }
       list address {
         key name;
         ordered-by user;
         description "Add address to pool";
         max-elements 8;
         leaf name {
           description "IPv4 or IPv6 address or address range";
           type jt:ipprefix;
         }
         container to {
           description "Upper limit of address range";
           uses apply-advanced;
           leaf ipaddr {
             description "IPv4 or IPv6 upper limit of address range";
             type jt:ipprefix;
           }
         }
       }
       container host-address-base {
         description "The base of host address";
         leaf ipaddr {
           description "IPv4 or IPv6 base address";
           junos:must "(!(\".. .. port range\"))";
           junos:must-message "'port range...' must not be configured when configure host-address-base";
           type jt:ipprefix;
         }
       }
       container port {
         description "Config port attribute to pool";
         uses apply-advanced;
         choice port-choice {
           case case_1 {
             leaf no-translation {
               description "Do not perform port translation";
               junos:must "(!(\".. automatic\"))";
               junos:must-message "'automatic' must not be configured when configure port no-translation";
               junos:must "(!(\".. preserve-range\"))";
               junos:must-message "'preserve-range' must not be configured when configure port no-translation";
               junos:must "(!(\".. preserve-parity\"))";
               junos:must-message "'preserve-parity' must not be configured when configure port no-translation";
               type empty;
             }
           }
           case case_2 {
             container range {
               description "Port range";
               uses apply-advanced;
               leaf low {
                 description "Lower limit of port range";
                 junos:must "(!(\".. .. .. host-address-base\"))";
                 junos:must-message "'host-address-base' must not be configured when configure port range";
                 type union {
                   type string {
                     pattern "<.*>|$.*";
                   }
                   type uint16 {
                     range "1024 .. 65535";
                   }
                 }
               }
               container to {
                 description "Port range upper limit";
                 uses apply-advanced;
                 leaf high {
                   description "Upper limit of port range";
                   junos:must "(!(\".. .. .. .. host-address-base\"))";
                   junos:must-message "'host-address-base' must not be configured when configure port range";
                   type union {
                     type string {
                       pattern "<.*>|$.*";
                     }
                     type uint16 {
                       range "1024 .. 65535";
                     }
                   }
                 }
               }
               container twin-port {
                 description "Twin port range";
                 uses apply-advanced;
                 leaf low {
                   description "Lower limit of twin port range";
                   junos:must "(!(\".. .. .. .. host-address-base\"))";
                   junos:must-message "'host-address-base' must not be configured when configure twin port range";
                   type union {
                     type string {
                       pattern "<.*>|$.*";
                     }
                     type uint16 {
                       range "63488 .. 65535";
                     }
                   }
                 }
                 container to {
                   description "Twin port range upper limit";
                   uses apply-advanced;
                   leaf high {
                     description "Upper limit of twin port range";
                     junos:must "(!(\".. .. .. .. .. host-address-base\"))";
                     junos:must-message "'host-address-base' must not be configured when configure twin port range";
                     type union {
                       type string {
                         pattern "<.*>|$.*";
                       }
                       type uint16 {
                         range "63488 .. 65535";
                       }
                     }
                   }
                 }
               }
             }
           }
         }
         leaf port-overloading-factor {
           description "Port overloading factor for each IP";
           type union {
             type string {
               pattern "<.*>|$.*";
             }
             type uint16 {
               range "2 .. 32";
             }
           }
         }
         container block-allocation {
           description "Port block allocation";
           uses block-allocation-object;
         }
         container deterministic {
           description "Deterministic nat allocation";
           uses deterministic-object;
         }
         leaf preserve-parity {
           description "Allocate port as the same parity as incoming port";
           junos:must "(!(\".. .. .. .. .. source pool $$ port no-translation\"))";
           junos:must-message "'port no-translation' must not be configured when configure preserve-parity";
           type empty;
         }
         leaf preserve-range {
           description "Allocate port from the same port range as incoming port";
           junos:must "(!(\".. .. .. .. .. source pool $$ port no-translation\"))";
           junos:must-message "'port no-translation' must not be configured when configure preserve-range";
           type empty;
         }
         container automatic {
           description "Port assignment";
           uses apply-advanced;
           choice port-assign-choice {
             case case_1 {
               leaf random-allocation {
                 description "Allocate port randomly";
                 junos:must "(!(\".. .. .. .. .. .. source pool $$ port no-translation\"))";
                 junos:must-message "'port no-translation' must not be configured when configure port assignment as random";
                 type empty;
               }
             }
             case case_2 {
               leaf round-robin {
                 description "Allocate port by round-robin";
                 junos:must "(!(\".. .. .. .. .. .. source pool $$ port no-translation\"))";
                 junos:must-message "'port no-translation' must not be configured when configure port assignment as round-robin";
                 type empty;
               }
             }
           }
         }
       }
       container overflow-pool {
         junos:must "(\".. .. .. source pool ${pool} port no-translation\")";
         junos:must-message "'port no-translation' must be configured on original address pool";
         description "Specify an overflow pool";
         choice overflow-pool-choice {
           case case_1 {
             leaf pool-name {
               description "Name of source address pool";
               junos:must "(!(\".. .. .. .. source pool $$ host-address-base\"))";
               junos:must-message "'host-address-base' must not be configured on overflow address pool";
               junos:must "(!(\".. .. .. .. source pool $$ port no-translation\"))";
               junos:must-message "'port no-translation' must not be configured on overflow address pool";
               junos:must "(!(\".. .. .. .. source pool ${pool} overflow-pool ${pool}\"))";
               junos:must-message "Overflow address pool must not be original address pool";
               junos:must "(\".. .. .. .. source pool $$\")";
               junos:must-message "Overflow address pool must be defined under [nat source pool]";
               type string {
                 length "1 .. 31";
                 junos:posix-pattern "^[[:alnum:]][[:alnum:]_-]*$";
                 junos:pattern-message "Must be a string beginning with a number or letter and consisting of letters, numbers, dashes and underscores.";
               }
             }
           }
           case case_2 {
             leaf interface {
               description "Allow interface pool to support overflow";
               type empty;
             }
           }
         }
       }
       leaf address-shared {
         description "Allow multiple hosts to share an externel address";
         type empty;
       }
       container address-pooling {
         description "Specify the address-pooling behavior";
         choice pooling-choice {
           case case_1 {
             leaf paired {
               description "Allow address-pooling paired for a source pool with port translation";
               type empty;
             }
           }
           case case_2 {
             leaf no-paired {
               description "Allow address-pooling no-paired for a source pool without port translation";
               type empty;
             }
           }
         }
       }
       container address-persistent {
         description "Specify the address-persistent behavior";
         container subscriber {
           description "Configure address persistent for subscriber";
           leaf ipv6-prefix-length {
             description "Ipv6 prefix length for address persistent";
             type union {
               type string {
                 pattern "<.*>|$.*";
               }
               type uint16 {
                 range "8 .. 128";
               }
             }
           }
         }
       }
       container pool-utilization-alarm {
         description "Config pool-utilization-alarm to pool";
         uses source-nat-pool-utilization-alarm-object;
       }
       leaf ei-mapping-timeout {
         description "Endpoint-independent mapping timeout";
         units "second";
         type union {
           type string {
             pattern "<.*>|$.*";
           }
           type uint32 {
             range "120 .. 86400";
           }
         }
       }
       leaf mapping-timeout {
         description "Address-pooling paired and endpoint-independent mapping timeout";
         units "second";
         type union {
           type string {
             pattern "<.*>|$.*";
           }
           type uint32 {
             range "120 .. 86400";
           }
         }
       }
       leaf limit-ports-per-host {
         description "Number of ports allocated per host";
         type union {
           type string {
             pattern "<.*>|$.*";
           }
           type uint16 {
             range "2 .. 65535";
           }
         }
       }
     }
     leaf address-persistent {
       description "Allow source address to maintain same translation";
       type empty;
     }
     leaf session-persistence-scan {
       description "Allow source to maintain session when session scan";
       type empty;
     }
     leaf session-drop-hold-down {
       description "Session drop hold down time";
       type union {
         type string {
           pattern "<.*>|$.*";
         }
         type uint16 {
           range "30 .. 28800";
         }
       }
     }
     container pool-utilization-alarm {
       description "Configure pool utilization alarm";
       uses source-nat-pool-utilization-alarm-object;
     }
     container port-randomization {
       description "Configure Source NAT port randomization";
       choice enable-disable {
         case case_1 {
           leaf disable {
             description "Disable Source NAT port randomization";
             type empty;
           }
         }
       }
     }
     container port-round-robin {
       description "Configure Source NAT port randomization";
       choice enable-disable {
         case case_1 {
           leaf disable {
             description "Disable Source NAT port randomization";
             type empty;
           }
         }
       }
     }
     leaf port-scaling-enlargement {
       description "Configure source port scaling to 2.4G only for NGSPC";
       type empty;
     }
     leaf pool-distribution {
       description "Configure Source pool distribution, the APPCP bottleneck of NAT CPS can be alleviated.";
       type empty;
     }
     container pool-default-port-range {
       description "Configure Source NAT default port range";
       leaf low {
         description "Lower limit of port range";
         junos:must "(!(any \"security nat source pool <*> host-address-base\"))";
         junos:must-message "'host-address-base' must not be configured when configure port range";
         type union {
           type string {
             pattern "<.*>|$.*";
           }
           type uint16;
         }
       }
       container to {
         description "Port range upper limit";
         uses apply-advanced;
         leaf high {
           description "Upper limit of port range";
           junos:must "(!(any \"security nat source pool <*> host-address-base\"))";
           junos:must-message "'host-address-base' must not be configured when configure port range";
           type union {
             type string {
               pattern "<.*>|$.*";
             }
             type uint16;
           }
         }
       }
     }
     container pool-default-twin-port-range {
       description "Configure Source NAT default twin port range";
       leaf low {
         description "Lower limit of twin port range";
         type union {
           type string {
             pattern "<.*>|$.*";
           }
           type uint16 {
             range "63488 .. 65535";
           }
         }
       }
       container to {
         description "Twin port range upper limit";
         uses apply-advanced;
         leaf high {
           description "Upper limit of twin port range";
           type union {
             type string {
               pattern "<.*>|$.*";
             }
             type uint16 {
               range "63488 .. 65535";
             }
           }
         }
       }
     }
     container interface {
       description "Configure interface port overloading for persistent NAT";
       uses apply-advanced;
       choice interface-choice {
         case case_1 {
           container port-overloading {
             description "Configure port overloading";
             leaf off {
               description "Turn off interface port over-loading";
               type empty;
             }
           }
         }
         case case_2 {
           leaf port-overloading-factor {
             description "Port overloading factor for interface NAT";
             type union {
               type uint16;
               type string {
                 pattern "<.*>|$.*";
               }
             }
           }
         }
       }
     }
     list rule-set {
       key name;
       ordered-by user;
       description "Configurate a set of rules";
       leaf name {
         description "Rule-set name";
         junos:must "((!(\"services nat destination rule-set $$\") && !(\"services nat static rule-set $$\")))";
         junos:must-message "the rule set name should be unique across all types of nat";
         type string {
           length "1 .. 31";
           junos:posix-pattern "^[[:alnum:]][[:alnum:]_-]*$";
           junos:pattern-message "Must be a string beginning with a number or letter and consisting of letters, numbers, dashes and underscores.";
         }
       }
       uses apply-advanced;
       leaf description {
         description "Text description of rule set";
         type string {
           length "1 .. 900";
           junos:posix-pattern "^[^&<>\n]+$";
           junos:pattern-message "Must be a string excluding '&', '<', '>' and '\n'";
         }
       }
       container from {
         description "Where is the traffic from";
         choice from-context-choice {
           case case_1 {
             leaf-list routing-instance {
               description "Source routing instance list";
               type string;
               max-elements 8;
             }
           }
           case case_2 {
             leaf-list zone {
               description "Source zone list";
               type string;
               max-elements 8;
             }
           }
           case case_3 {
             leaf-list interface {
               description "Source interface list";
               type union {
                 type jt:interface-name;
                 type string {
                   pattern "<.*>|$.*";
                 }
               }
               max-elements 8;
             }
           }
         }
       }
       container to {
         description "Where is the traffic to";
         choice from-context-choice {
           case case_1 {
             leaf-list routing-instance {
               description "Destination routing instance list";
               type string;
               max-elements 8;
             }
           }
           case case_2 {
             leaf-list zone {
               description "Destination zone list";
               type string;
               max-elements 8;
             }
           }
           case case_3 {
             leaf-list interface {
               description "Destination interface list";
               type union {
                 type jt:interface-name;
                 type string {
                   pattern "<.*>|$.*";
                 }
               }
               max-elements 8;
             }
           }
         }
       }
       list rule {
         key name;
         ordered-by user;
         description "Source NAT rule";
         uses src-nat-rule-object;
       }
       leaf match-direction {
         description "Match direction";
         type enumeration {
           enum "input" {
             description "Match on input to interface";
           }
           enum "output" {
             description "Match on output from interface";
           }
         }
       }
     }
   }
   grouping block-allocation-object {
     description "Port block allocation";
     uses apply-advanced;
     leaf block-size {
       description "Block size";
       type union {
         type string {
           pattern "<.*>|$.*";
         }
         type uint16;
       }
     }
     leaf maximum-blocks-per-host {
       description "Maximum block number per host";
       type union {
         type string {
           pattern "<.*>|$.*";
         }
         type uint16 {
           range "1 .. 512";
         }
       }
     }
     leaf active-block-timeout {
       description "Active block timeout interval";
       type union {
         type string {
           pattern "<.*>|$.*";
         }
         type uint32;
       }
     }
     leaf interim-logging-interval {
       description "Interim Logging interval";
       type union {
         type string {
           pattern "<.*>|$.*";
         }
         type uint32 {
           range "1800 .. 86400";
         }
       }
     }
     leaf last-block-recycle-timeout {
       description "Last Block recycle timeout interval";
       type union {
         type string {
           pattern "<.*>|$.*";
         }
         type uint32 {
           range "120 .. 864000";
         }
       }
     }
     container log {
       description "Configure port block log";
       choice enable-disable {
         case case_1 {
           leaf disable {
             description "Disable PBA port block log";
             type empty;
           }
         }
       }
     }
   }
   grouping deterministic-object {
     description "Deterministic nat allocation";
     uses apply-advanced;
     leaf block-size {
       description "Block size";
       type union {
         type string {
           pattern "<.*>|$.*";
         }
         type uint16;
       }
     }
     leaf det-nat-configuration-log-interval {
       description "Deterministic nat configuration logging interval";
       type union {
         type string {
           pattern "<.*>|$.*";
         }
         type uint32 {
           range "1800 .. 86400";
         }
       }
     }
     container host {
       description "Host address";
       leaf-list address {
         ordered-by user;
         description "Host ip address";
         type jt:ipprefix;
         max-elements 8;
       }
       leaf-list address-name {
         ordered-by user;
         description "Host address/address-set from address book";
         type string;
         max-elements 8;
       }
     }
     leaf include-boundary-addresses {
       description "Include network and broadcast in 'match' source address";
       type empty;
     }
   }
   grouping source-nat-pool-utilization-alarm-object {
     uses apply-advanced;
     leaf raise-threshold {
       description "Raise threshold for pool utilization alarm";
       type union {
         type string {
           pattern "<.*>|$.*";
         }
         type uint16 {
           range "50 .. 100";
         }
       }
     }
     leaf clear-threshold {
       description "Clear threshold for pool utilization alarm";
       type union {
         type string {
           pattern "<.*>|$.*";
         }
         type uint16 {
           range "40 .. 100";
         }
       }
     }
   }
   grouping src-nat-rule-object {
     leaf name {
       description "Source NAT Rule name";
       type string {
         length "1 .. 31";
         junos:posix-pattern "^[[:alnum:]][[:alnum:]_-]*$";
         junos:pattern-message "Must be a string beginning with a number or letter and consisting of letters, numbers, dashes and underscores.";
       }
     }
     uses apply-advanced;
     leaf description {
       description "Text description of rule";
       type string {
         length "1 .. 900";
         junos:posix-pattern "^[^&<>\n]+$";
         junos:pattern-message "Must be a string excluding '&', '<', '>' and '\n'";
       }
     }
     container src-nat-rule-match {
       description "Specify Source NAT rule match criteria";
       uses apply-advanced;
       leaf-list source-address {
         ordered-by user;
         description "Source address";
         type string;
         max-elements 8;
       }
       leaf-list source-address-name {
         ordered-by user;
         description "Address/address-set from address book";
         type string;
         max-elements 8;
       }
       list source-port {
         key name;
         ordered-by user;
         description "Source port";
         max-elements 8;
         leaf name {
           description "Port or lower limit of port range";
           type union {
             type uint16;
             type string {
               pattern "<.*>|$.*";
             }
           }
         }
         container to {
           description "Port range upper limit";
           uses apply-advanced;
           leaf high {
             description "Upper limit of port range";
             type union {
               type uint16;
               type string {
                 pattern "<.*>|$.*";
               }
             }
           }
         }
       }
       leaf-list destination-address {
         ordered-by user;
         description "Destination address";
         type string;
         max-elements 8;
       }
       leaf-list destination-address-name {
         ordered-by user;
         description "Address/address-set from address book";
         type string;
         max-elements 8;
       }
       list destination-port {
         key name;
         ordered-by user;
         description "Destination port";
         max-elements 8;
         leaf name {
           description "Port or lower limit of port range";
           type union {
             type uint16;
             type string {
               pattern "<.*>|$.*";
             }
           }
         }
         container to {
           description "Port range upper limit";
           uses apply-advanced;
           leaf high {
             description "Upper limit of port range";
             type union {
               type uint16;
               type string {
                 pattern "<.*>|$.*";
               }
             }
           }
         }
       }
       leaf-list protocol {
         ordered-by user;
         description "IP Protocol";
         type string;
         max-elements 4;
       }
       leaf-list application {
         ordered-by user;
         type string;
       }
     }
     container then {
       description "Then action";
       uses apply-advanced;
       container source-nat {
         description "Source NAT action";
         uses apply-advanced;
         choice action {
           case case_1 {
             leaf off {
               description "No action";
               type empty;
             }
           }
           case case_2 {
             container pool {
               description "Use Source NAT pool";
               uses apply-advanced;
               leaf pool-name {
                 description "Name of Source NAT pool";
                 junos:must "(\".. .. .. .. .. .. .. .. nat source pool $$\")";
                 junos:must-message "Source NAT pool name must be defined";
                 type string {
                   length "1 .. 31";
                 }
               }
               container persistent-nat {
                 description "Persistent NAT info";
                 uses persistent-nat-object;
               }
             }
           }
           case case_3 {
             container interface {
               presence "enable interface";
               description "Use egress interface address";
               uses apply-advanced;
               container persistent-nat {
                 description "Persistent NAT info";
                 uses persistent-nat-object;
               }
             }
           }
         }
         leaf clat-prefix {
           description "An IPv6 prefix to be used for XLAT464 and prefix length can only be 32/40/48/56/64/96";
           junos:must "((\".. .. .. match source-address\" || \".. .. .. match source-address-name\"))";
           junos:must-message "source-address or source-address-name is required for Clat-prefix";
           type jt:ipprefix-only;
         }
         container rule-session-count-alarm {
           description "Config rule-session-count-alarm to source rule";
           uses nat-rule-session-count-alarm-object;
         }
         container mapping-type {
           description "Source nat mapping type";
           leaf endpoint-independent {
             description "Endpoint independent mapping";
             type empty;
           }
         }
         container secure-nat-mapping {
           description "Mapping options for enhanced security";
           leaf eif-flow-limit {
             description "Number of inbound flows to be allowed for a EIF mapping";
             junos:must "(\".. .. filtering-type\")";
             junos:must-message "eif-flow-limit applies only to filtering-type";
             type union {
               type string {
                 pattern "<.*>|$.*";
               }
               type uint16 {
                 range "0 .. 65534";
               }
             }
           }
           container mapping-refresh {
             description "Enable timer refresh option";
             choice refresh-choice {
               case case_1 {
                 leaf inbound {
                   description "Enable timer refresh for inbound connections only";
                   type empty;
                 }
               }
               case case_2 {
                 leaf outbound {
                   description "Enable timer refresh for outbound connections only";
                   type empty;
                 }
               }
               case case_3 {
                 leaf inbound-outbound {
                   description "Enable timer refresh for inbound & outbound connections";
                   type empty;
                 }
               }
             }
           }
         }
         container filtering-type {
           junos:must "(\".. mapping-type endpoint-independent\")";
           junos:must-message "endpoint independent filtering can not be configured with endpoint-independent mapping only";
           description "Source NAT filtering type";
           uses apply-advanced;
           container endpoint-independent {
             presence "enable endpoint-independent";
             description "Endpoint independent filtering";
             uses apply-advanced;
             list prefix-list {
               key name;
               ordered-by user;
               description "One or more named lists of source prefixes to match";
               leaf name {
                 description "Name of prefix list to match against";
                 type string {
                   length "1 .. 63";
                 }
               }
               leaf except {
                 description "Name of prefix list not to match against";
                 type empty;
               }
             }
           }
         }
       }
       leaf syslog {
         description "System log information about the packet";
         type empty;
       }
     }
   }
   grouping persistent-nat-object {
     uses apply-advanced;
     container permit {
       description "Persistent NAT permit configure";
       choice persistent-nat-type-choice {
         case case_1 {
           leaf any-remote-host {
             description "Permit any remote host";
             type empty;
           }
         }
         case case_2 {
           leaf target-host {
             description "Permit target host";
             type empty;
           }
         }
         case case_3 {
           leaf target-host-port {
             description "Permit target host port";
             type empty;
           }
         }
       }
     }
     leaf address-mapping {
       description "Address-to-address mapping";
       type empty;
     }
     leaf inactivity-timeout {
       description "Inactivity timeout value";
       type union {
         type string {
           pattern "<.*>|$.*";
         }
         type uint16 {
           range "60 .. 7200";
         }
       }
     }
     leaf max-session-number {
       description "The maximum session number value";
       type union {
         type string {
           pattern "<.*>|$.*";
         }
         type uint32 {
           range "8 .. 65536";
         }
       }
     }
   }
   grouping ssg-static-nat-object {
     uses apply-advanced;
     list rule-set {
       key name;
       ordered-by user;
       description "Configurate a set of rules";
       leaf name {
         description "Rule-set name";
         type string {
           length "1 .. 31";
           junos:posix-pattern "^[[:alnum:]][[:alnum:]_-]*$";
           junos:pattern-message "Must be a string beginning with a number or letter and consisting of letters, numbers, dashes and underscores.";
         }
       }
       uses apply-advanced;
       leaf description {
         description "Text description of rule set";
         type string {
           length "1 .. 900";
           junos:posix-pattern "^[^&<>\n]+$";
           junos:pattern-message "Must be a string excluding '&', '<', '>' and '\n'";
         }
       }
       container from {
         description "Where is the traffic from";
         choice from-context-choice {
           case case_1 {
             leaf-list routing-instance {
               description "Source routing instance list";
               type string;
               max-elements 8;
             }
           }
           case case_2 {
             leaf-list zone {
               description "Source zone list";
               type string;
               max-elements 8;
             }
           }
           case case_3 {
             leaf-list interface {
               description "Source interface list";
               type union {
                 type jt:interface-name;
                 type string {
                   pattern "<.*>|$.*";
                 }
               }
               max-elements 8;
             }
           }
         }
       }
       list rule {
         key name;
         ordered-by user;
         description "Static NAT rule";
         uses static-nat-rule-object;
       }
     }
   }
   grouping ssl-initiation-config {
     uses apply-advanced;
     list profile {
       key name;
       ordered-by user;
       description "SSL client profile";
       leaf name {
         description "Profile identifier";
         type string {
           length "1 .. 63";
         }
       }
       uses apply-advanced;
       leaf enable-flow-tracing {
         description "Enable flow tracing for the profile";
         type empty;
       }
       leaf protocol-version {
         description "Protocol SSL version accepted";
         default "all";
         type enumeration {
           enum "all" {
             description "TLS version 1 or TLS version 1.1 or TLS version 1.2";
           }
           enum "ssl3" {
             description "SSL version 3";
           }
           enum "tls1" {
             description "TLS version 1";
           }
           enum "tls11" {
             description "TLS version 1.1";
           }
           enum "tls12" {
             description "TLS version 1.2";
           }
         }
       }
       leaf preferred-ciphers {
         description "Select preferred ciphers";
         default "medium";
         type enumeration {
           enum "strong" {
             description "Use ciphers with key strength of 168-bits or greater";
           }
           enum "medium" {
             description "Use ciphers with key strength of 128-bits or greater";
           }
           enum "weak" {
             description "Use ciphers with key strength of 40-bits or greater";
           }
           enum "custom" {
             description "Configure custom cipher suite and order of preference";
             junos:must "(\".. custom-ciphers\")";
             junos:must-message "custom-ciphers must be configured for this choice";
           }
         }
       }
       leaf-list custom-ciphers {
         ordered-by user;
         description "Custom cipher list";
         type enumeration {
           enum "rsa-with-rc4-128-md5" {
             description "RSA, 128bit rc4, md5 hash";
           }
           enum "rsa-with-rc4-128-sha" {
             description "RSA, 128bit rc4, sha hash";
           }
           enum "rsa-with-des-cbc-sha" {
             description "RSA, des cbc, sha hash";
           }
           enum "rsa-with-3des-ede-cbc-sha" {
             description "RSA, 3des ede/cbc, sha hash";
           }
           enum "rsa-with-aes-128-cbc-sha" {
             description "RSA, 128 bit aes/cbc, sha hash";
             junos:must "((!(\".. .. preferred-ciphers custom\") || !(\".. .. protocol-version ssl3\")))";
             junos:must-message "protocol-version must be tls1 or all to use the aes cipher";
           }
           enum "rsa-with-aes-256-cbc-sha" {
             description "RSA, 256 bit aes/cbc, sha hash";
             junos:must "((!(\".. .. preferred-ciphers custom\") || !(\".. .. protocol-version ssl3\")))";
             junos:must-message "protocol-version must be tls1 or all to use the aes cipher";
           }
           enum "rsa-export-with-rc4-40-md5" {
             description "RSA-export, 40 bit rc4, md5 hash";
           }
           enum "rsa-export-with-des40-cbc-sha" {
             description "RSA-export, 40 bit des/cbc, sha hash";
           }
           enum "rsa-export1024-with-des-cbc-sha" {
             description "RSA 1024 bit export, des/cbc, sha hash";
           }
           enum "rsa-export1024-with-rc4-56-md5" {
             description "RSA 1024 bit export, 56 bit rc4, md5 hash";
           }
           enum "rsa-export1024-with-rc4-56-sha" {
             description "RSA 1024 bit export, 56 bit rc4, sha hash";
           }
           enum "rsa-with-aes-256-gcm-sha384" {
             description "RSA, 256 bit aes/gcm, sha384 hash ";
           }
           enum "rsa-with-aes-256-cbc-sha256" {
             description "RSA, 256 bit aes/cbc, sha256 hash";
           }
           enum "rsa-with-aes-128-gcm-sha256" {
             description "RSA, 128 bit aes/gcm, sha256 hash";
           }
           enum "rsa-with-aes-128-cbc-sha256" {
             description "RSA, 128 bit aes/cbc, sha256 hash";
           }
           enum "ecdhe-rsa-with-aes-256-gcm-sha384" {
             description "ECDHE/rsa, 256 bit aes/gcm, sha384 hash";
           }
           enum "ecdhe-rsa-with-aes-256-cbc-sha" {
             description "ECDHE/rsa, 256 bit aes/cbc, sha hash";
           }
           enum "ecdhe-rsa-with-aes-256-cbc-sha384" {
             description "ECDHE/rsa, 256 bit aes/cbc, sha384 hash";
           }
           enum "ecdhe-rsa-with-3des-ede-cbc-sha" {
             description "ECDHE/rsa, 3des ede/cbc, sha hash";
           }
           enum "ecdhe-rsa-with-aes-128-gcm-sha256" {
             description "ECDHE/rsa, 128 bit aes/gcm, sha256 hash";
           }
           enum "ecdhe-rsa-with-aes-128-cbc-sha" {
             description "ECDHE/rsa, 128 bit aes/cbc, sha hash";
           }
           enum "ecdhe-rsa-with-aes-128-cbc-sha256" {
             description "ECDHE/rsa, 128 bit aes/cbc, sha256 hash";
           }
           enum "ecdhe-ecdsa-with-aes-256-gcm-sha384" {
             description "ECDHE,ECDSA, 256 bit aes/gcm, sha384 hash";
           }
           enum "ecdhe-ecdsa-with-aes-256-cbc-sha" {
             description "ECDHE,ECDSA, 256 bit aes/cbc, sha hash";
           }
           enum "ecdhe-ecdsa-with-aes-256-cbc-sha384" {
             description "ECDHE,ECDSA, 256 bit aes/cbc, sha384 hash";
           }
           enum "ecdhe-ecdsa-with-aes-128-gcm-sha256" {
             description "ECDHE,ECDSA, 128 bit aes/gcm, sha256 hash";
           }
           enum "ecdhe-ecdsa-with-aes-128-cbc-sha" {
             description "ECDHE,ECDSA, 128 bit aes/cbc, sha hash";
           }
           enum "ecdhe-ecdsa-with-aes-128-cbc-sha256" {
             description "ECDHE,ECDSA, 128 bit aes/cbc, sha256 hash";
           }
           enum "ecdhe-ecdsa-with-3des-ede-cbc-sha" {
             description "ECDHE,ECDSA, 3des ede/cbc, sha hash";
           }
         }
         max-elements 64;
       }
       leaf enable-session-cache {
         description "Enable SSL session cache";
         type empty;
       }
       leaf-list trusted-ca {
         ordered-by user;
         description "List of trusted certificate authority profiles";
         type string;
         max-elements 1024;
       }
       leaf client-certificate {
         description "Local certificate identifier";
         type string {
           junos:posix-pattern "^.{1,32}$";
           junos:pattern-message "Must be string of 32 characters or less";
         }
       }
       container actions {
         description "Traffic related actions";
         uses apply-advanced;
         leaf ignore-server-auth-failure {
           description "Ignore server authentication failure";
           type empty;
         }
         container crl {
           description "Certificate Revocation actions.";
           leaf disable {
             description "Disable CRL validation.";
             type empty;
           }
           leaf if-not-present {
             description "Action if CRL information is not present.";
             default "allow";
             type enumeration {
               enum "allow" {
                 description "Allow session if CRL information is not present.";
               }
               enum "drop" {
                 description "Drop session if CRL information is not present.";
               }
             }
           }
           leaf ignore-hold-instruction-code {
             description "Ignore 'Hold Instruction Code' present in the CRL entry.";
             type empty;
           }
         }
         leaf unsupported-cipher-on-hw {
           description "Unsupported cipher processing on hardware mode";
           default "drop";
           type enumeration {
             enum "drop" {
               description "Drop session if cipher isn't supported on hardware mode";
             }
             enum "software-inspection" {
               description "Allow session in software mode";
             }
           }
         }
       }
     }
   }
   grouping ssl-proxy-config {
     uses apply-advanced;
     container global-config {
       description "Global proxy configuration";
       uses apply-advanced;
       leaf session-cache-timeout {
         description "Session cache timeout";
         units "seconds";
         type union {
           type string {
             pattern "<.*>|$.*";
           }
           type uint32 {
             range "300 .. 3600";
           }
         }
       }
       leaf disable-cert-cache {
         description "Disable proxy mode certificate cache";
         type empty;
       }
       leaf certificate-cache-timeout {
         description "Certificate cache timeout";
         units "seconds";
         type union {
           type string {
             pattern "<.*>|$.*";
           }
           type uint32 {
             range "300 .. 3600";
           }
         }
       }
       leaf invalidate-cache-on-crl-update {
         description "Invalidate certificate cache on crl update";
         type empty;
       }
     }
     list profile {
       key name;
       ordered-by user;
       description "SSL Proxy profile";
       leaf name {
         description "Profile identifier";
         type string {
           length "1 .. 63";
         }
       }
       uses apply-advanced;
       leaf enable-flow-tracing {
         description "Enable flow tracing for the profile";
         type empty;
       }
       leaf preferred-ciphers {
         description "Select preferred ciphers";
         default "medium";
         type enumeration {
           enum "strong" {
             description "Use ciphers with key strength of 168-bits or greater";
           }
           enum "medium" {
             description "Use ciphers with key strength of 128-bits or greater";
           }
           enum "weak" {
             description "Use ciphers with key strength of 40-bits or greater";
           }
           enum "custom" {
             description "Configure custom cipher suite and order of preference";
             junos:must "(\".. custom-ciphers\")";
             junos:must-message "custom-ciphers must be configured for this choice";
           }
         }
       }
       leaf-list custom-ciphers {
         ordered-by user;
         description "Custom cipher list";
         type enumeration {
           enum "rsa-with-rc4-128-md5" {
             description "RSA, 128bit rc4, md5 hash";
           }
           enum "rsa-with-rc4-128-sha" {
             description "RSA, 128bit rc4, sha hash";
           }
           enum "rsa-with-des-cbc-sha" {
             description "RSA, des cbc, sha hash";
           }
           enum "rsa-with-3des-ede-cbc-sha" {
             description "RSA, 3des ede/cbc, sha hash";
           }
           enum "rsa-with-aes-128-cbc-sha" {
             description "RSA, 128 bit aes/cbc, sha hash";
             junos:must "((!(\".. .. preferred-ciphers custom\") || !(\".. .. protocol-version ssl3\")))";
             junos:must-message "protocol-version must be tls1 or all to use the aes cipher";
           }
           enum "rsa-with-aes-256-cbc-sha" {
             description "RSA, 256 bit aes/cbc, sha hash";
             junos:must "((!(\".. .. preferred-ciphers custom\") || !(\".. .. protocol-version ssl3\")))";
             junos:must-message "protocol-version must be tls1 or all to use the aes cipher";
           }
           enum "rsa-export-with-rc4-40-md5" {
             description "RSA-export, 40 bit rc4, md5 hash";
           }
           enum "rsa-export-with-des40-cbc-sha" {
             description "RSA-export, 40 bit des/cbc, sha hash";
           }
           enum "rsa-export1024-with-des-cbc-sha" {
             description "RSA 1024 bit export, des/cbc, sha hash";
           }
           enum "rsa-export1024-with-rc4-56-md5" {
             description "RSA 1024 bit export, 56 bit rc4, md5 hash";
           }
           enum "rsa-export1024-with-rc4-56-sha" {
             description "RSA 1024 bit export, 56 bit rc4, sha hash";
           }
           enum "rsa-with-aes-256-gcm-sha384" {
             description "RSA, 256 bit aes/gcm, sha384 hash ";
           }
           enum "rsa-with-aes-256-cbc-sha256" {
             description "RSA, 256 bit aes/cbc, sha256 hash";
           }
           enum "rsa-with-aes-128-gcm-sha256" {
             description "RSA, 128 bit aes/gcm, sha256 hash";
           }
           enum "rsa-with-aes-128-cbc-sha256" {
             description "RSA, 128 bit aes/cbc, sha256 hash";
           }
           enum "ecdhe-rsa-with-aes-256-gcm-sha384" {
             description "ECDHE/rsa, 256 bit aes/gcm, sha384 hash";
           }
           enum "ecdhe-rsa-with-aes-256-cbc-sha" {
             description "ECDHE/rsa, 256 bit aes/cbc, sha hash";
           }
           enum "ecdhe-rsa-with-aes-256-cbc-sha384" {
             description "ECDHE/rsa, 256 bit aes/cbc, sha384 hash";
           }
           enum "ecdhe-rsa-with-3des-ede-cbc-sha" {
             description "ECDHE/rsa, 3des ede/cbc, sha hash";
           }
           enum "ecdhe-rsa-with-aes-128-gcm-sha256" {
             description "ECDHE/rsa, 128 bit aes/gcm, sha256 hash";
           }
           enum "ecdhe-rsa-with-aes-128-cbc-sha" {
             description "ECDHE/rsa, 128 bit aes/cbc, sha hash";
           }
           enum "ecdhe-rsa-with-aes-128-cbc-sha256" {
             description "ECDHE/rsa, 128 bit aes/cbc, sha256 hash";
           }
           enum "ecdhe-ecdsa-with-aes-256-gcm-sha384" {
             description "ECDHE,ECDSA, 256 bit aes/gcm, sha384 hash";
           }
           enum "ecdhe-ecdsa-with-aes-256-cbc-sha" {
             description "ECDHE,ECDSA, 256 bit aes/cbc, sha hash";
           }
           enum "ecdhe-ecdsa-with-aes-256-cbc-sha384" {
             description "ECDHE,ECDSA, 256 bit aes/cbc, sha384 hash";
           }
           enum "ecdhe-ecdsa-with-aes-128-gcm-sha256" {
             description "ECDHE,ECDSA, 128 bit aes/gcm, sha256 hash";
           }
           enum "ecdhe-ecdsa-with-aes-128-cbc-sha" {
             description "ECDHE,ECDSA, 128 bit aes/cbc, sha hash";
           }
           enum "ecdhe-ecdsa-with-aes-128-cbc-sha256" {
             description "ECDHE,ECDSA, 128 bit aes/cbc, sha256 hash";
           }
           enum "ecdhe-ecdsa-with-3des-ede-cbc-sha" {
             description "ECDHE,ECDSA, 3des ede/cbc, sha hash";
           }
         }
         max-elements 64;
       }
       leaf-list trusted-ca {
         ordered-by user;
         description "List of trusted certificate authority profiles";
         type string;
         max-elements 1024;
       }
       choice certificate {
         case case_1 {
           leaf-list root-ca {
             ordered-by user;
             description "Root certificate for interdicting server certificates in proxy mode";
             type string;
             max-elements 2;
           }
         }
         case case_2 {
           leaf-list server-certificate {
             ordered-by user;
             description "Local certificate identifier";
             junos:must "(!(\"security idp sensor-configuration ssl-inspection sessions\"))";
             junos:must-message "IDP SSL Inspection should not be configured with ssl proxy profile <> server-certificate";
             junos:must "(!(\".. actions crl\"))";
             junos:must-message "actions crl <>  should not be configured with server- certificate";
             junos:must "(!(\".. actions ignore-server-auth-failure\"))";
             junos:must-message "ignore-server-auth-failure  should not be configured with server-certificate";
             junos:must "(!(\".. trusted-ca\"))";
             junos:must-message "trusted-ca <>  should not be configured with server-certificate";
             type string;
             max-elements 1024;
           }
         }
       }
       container mirror-decrypt-traffic {
         description "Configure mirror interface and Destination MAC address";
         uses apply-advanced;
         leaf interface {
           description "Interface on which SSL decrypted traffic is mirrored";
           junos:must "(\"interfaces $$\")";
           junos:must-message "Interface must be defined";
           type union {
             type jt:interface-name;
             type string {
               pattern "<.*>|$.*";
             }
           }
         }
         leaf destination-mac-address {
           description "Mac address of host/server to which decrypted traffic is mirrored";
           type jt:mac-addr;
         }
         leaf only-after-security-policies-enforcement {
           description "Enables decrypted Traffic mirroring after policy enforcement";
           type empty;
         }
       }
       leaf-list whitelist {
         ordered-by user;
         description "Addresses exempted from SSL Proxy ";
         type string;
       }
       leaf-list whitelist-url-categories {
         ordered-by user;
         type string;
       }
       container actions {
         description "Logging and traffic related actions";
         uses apply-advanced;
         leaf ignore-server-auth-failure {
           description "Ignore server authentication failure";
           type empty;
         }
         container log {
           presence "enable log";
           description "Logging actions";
           leaf all {
             description "Log all events";
             type empty;
           }
           leaf sessions-dropped {
             description "Log only ssl session drop events";
             type empty;
           }
           leaf sessions-allowed {
             description "Log ssl session allow events after an error";
             type empty;
           }
           leaf sessions-ignored {
             description "Log  session ignore events ";
             type empty;
           }
           leaf sessions-whitelisted {
             description "Log ssl session whitelist events ";
             type empty;
           }
           leaf errors {
             description "Log all error events ";
             type empty;
           }
           leaf warning {
             description "Log all warning events ";
             type empty;
           }
           leaf info {
             description "Log all information events ";
             type empty;
           }
         }
         container crl {
           description "Certificate Revocation actions.";
           leaf disable {
             description "Disable CRL validation.";
             type empty;
           }
           leaf if-not-present {
             description "Action if CRL information is not present.";
             default "allow";
             type enumeration {
               enum "allow" {
                 description "Allow session if CRL information is not present.";
               }
               enum "drop" {
                 description "Drop session if CRL information is not present.";
               }
             }
           }
           leaf ignore-hold-instruction-code {
             description "Ignore 'Hold Instruction Code' present in the CRL entry.";
             type empty;
           }
         }
         leaf renegotiation {
           description "Renegotiation options";
           default "allow-secure";
           type enumeration {
             enum "allow" {
               description "Allow secure as well as non secure renegotiation";
             }
             enum "allow-secure" {
               description "Allow secure negotiation only (RFC 5746)";
             }
             enum "drop" {
               description "Drop session on renegotiation request";
             }
           }
         }
         leaf disable-session-resumption {
           description "Disable session resumption";
           type empty;
         }
         leaf unsupported-cipher-on-hw {
           description "Unsupported cipher processing on hardware mode";
           default "drop";
           type enumeration {
             enum "drop" {
               description "Drop session if cipher isn't supported on hardware mode";
             }
             enum "software-inspection" {
               description "Allow session in software mode";
             }
           }
         }
       }
     }
   }
   grouping ssl-termination-config {
     uses apply-advanced;
     list profile {
       key name;
       ordered-by user;
       description "SSL server profile";
       leaf name {
         description "Profile identifier";
         type string {
           length "1 .. 63";
         }
       }
       uses apply-advanced;
       leaf enable-flow-tracing {
         description "Enable flow tracing for the profile";
         type empty;
       }
       leaf protocol-version {
         description "Protocol SSL version accepted";
         default "all";
         type enumeration {
           enum "all" {
             description "TLS version 1 or TLS version 1.1 or TLS version 1.2";
           }
           enum "ssl3" {
             description "SSL version 3";
           }
           enum "tls1" {
             description "TLS version 1";
           }
           enum "tls11" {
             description "TLS version 1.1";
           }
           enum "tls12" {
             description "TLS version 1.2";
           }
         }
       }
       leaf preferred-ciphers {
         description "Select preferred ciphers";
         default "medium";
         type enumeration {
           enum "strong" {
             description "Use ciphers with key strength of 168-bits or greater";
           }
           enum "medium" {
             description "Use ciphers with key strength of 128-bits or greater";
           }
           enum "weak" {
             description "Use ciphers with key strength of 40-bits or greater";
           }
           enum "custom" {
             description "Configure custom cipher suite and order of preference";
             junos:must "(\".. custom-ciphers\")";
             junos:must-message "custom-ciphers must be configured for this choice";
           }
         }
       }
       leaf-list custom-ciphers {
         ordered-by user;
         description "Custom cipher list";
         type enumeration {
           enum "rsa-with-rc4-128-md5" {
             description "RSA, 128bit rc4, md5 hash";
           }
           enum "rsa-with-rc4-128-sha" {
             description "RSA, 128bit rc4, sha hash";
           }
           enum "rsa-with-des-cbc-sha" {
             description "RSA, des cbc, sha hash";
           }
           enum "rsa-with-3des-ede-cbc-sha" {
             description "RSA, 3des ede/cbc, sha hash";
           }
           enum "rsa-with-aes-128-cbc-sha" {
             description "RSA, 128 bit aes/cbc, sha hash";
             junos:must "((!(\".. .. preferred-ciphers custom\") || !(\".. .. protocol-version ssl3\")))";
             junos:must-message "protocol-version must be tls1 or all to use the aes cipher";
           }
           enum "rsa-with-aes-256-cbc-sha" {
             description "RSA, 256 bit aes/cbc, sha hash";
             junos:must "((!(\".. .. preferred-ciphers custom\") || !(\".. .. protocol-version ssl3\")))";
             junos:must-message "protocol-version must be tls1 or all to use the aes cipher";
           }
           enum "rsa-export-with-rc4-40-md5" {
             description "RSA-export, 40 bit rc4, md5 hash";
           }
           enum "rsa-export-with-des40-cbc-sha" {
             description "RSA-export, 40 bit des/cbc, sha hash";
           }
           enum "rsa-export1024-with-des-cbc-sha" {
             description "RSA 1024 bit export, des/cbc, sha hash";
           }
           enum "rsa-export1024-with-rc4-56-md5" {
             description "RSA 1024 bit export, 56 bit rc4, md5 hash";
           }
           enum "rsa-export1024-with-rc4-56-sha" {
             description "RSA 1024 bit export, 56 bit rc4, sha hash";
           }
           enum "rsa-with-aes-256-gcm-sha384" {
             description "RSA, 256 bit aes/gcm, sha384 hash ";
           }
           enum "rsa-with-aes-256-cbc-sha256" {
             description "RSA, 256 bit aes/cbc, sha256 hash";
           }
           enum "rsa-with-aes-128-gcm-sha256" {
             description "RSA, 128 bit aes/gcm, sha256 hash";
           }
           enum "rsa-with-aes-128-cbc-sha256" {
             description "RSA, 128 bit aes/cbc, sha256 hash";
           }
           enum "ecdhe-rsa-with-aes-256-gcm-sha384" {
             description "ECDHE/rsa, 256 bit aes/gcm, sha384 hash";
           }
           enum "ecdhe-rsa-with-aes-256-cbc-sha" {
             description "ECDHE/rsa, 256 bit aes/cbc, sha hash";
           }
           enum "ecdhe-rsa-with-aes-256-cbc-sha384" {
             description "ECDHE/rsa, 256 bit aes/cbc, sha384 hash";
           }
           enum "ecdhe-rsa-with-3des-ede-cbc-sha" {
             description "ECDHE/rsa, 3des ede/cbc, sha hash";
           }
           enum "ecdhe-rsa-with-aes-128-gcm-sha256" {
             description "ECDHE/rsa, 128 bit aes/gcm, sha256 hash";
           }
           enum "ecdhe-rsa-with-aes-128-cbc-sha" {
             description "ECDHE/rsa, 128 bit aes/cbc, sha hash";
           }
           enum "ecdhe-rsa-with-aes-128-cbc-sha256" {
             description "ECDHE/rsa, 128 bit aes/cbc, sha256 hash";
           }
           enum "ecdhe-ecdsa-with-aes-256-gcm-sha384" {
             description "ECDHE,ECDSA, 256 bit aes/gcm, sha384 hash";
           }
           enum "ecdhe-ecdsa-with-aes-256-cbc-sha" {
             description "ECDHE,ECDSA, 256 bit aes/cbc, sha hash";
           }
           enum "ecdhe-ecdsa-with-aes-256-cbc-sha384" {
             description "ECDHE,ECDSA, 256 bit aes/cbc, sha384 hash";
           }
           enum "ecdhe-ecdsa-with-aes-128-gcm-sha256" {
             description "ECDHE,ECDSA, 128 bit aes/gcm, sha256 hash";
           }
           enum "ecdhe-ecdsa-with-aes-128-cbc-sha" {
             description "ECDHE,ECDSA, 128 bit aes/cbc, sha hash";
           }
           enum "ecdhe-ecdsa-with-aes-128-cbc-sha256" {
             description "ECDHE,ECDSA, 128 bit aes/cbc, sha256 hash";
           }
           enum "ecdhe-ecdsa-with-3des-ede-cbc-sha" {
             description "ECDHE,ECDSA, 3des ede/cbc, sha hash";
           }
         }
         max-elements 64;
       }
       leaf enable-session-cache {
         description "Enable SSL session cache";
         type empty;
       }
       leaf server-certificate {
         description "Local certificate identifier";
         type string {
           junos:posix-pattern "^.{1,32}$";
           junos:pattern-message "Must be string of 32 characters or less";
         }
       }
     }
   }
   grouping ssl-traceoptions {
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "brief";
       type enumeration {
         enum "brief" {
           description "Brief debugging output";
         }
         enum "detail" {
           description "Detailed debugging output";
         }
         enum "extensive" {
           description "Extensive debugging output";
         }
         enum "verbose" {
           description "Verbose debugging output";
         }
       }
     }
     list flag {
       key name;
       ordered-by user;
       description "Tracing parameters";
       leaf name {
         type enumeration {
           enum "cli-configuration" {
             description "Trace CLI configuration events";
           }
           enum "termination" {
             description "Trace termination service events";
           }
           enum "initiation" {
             description "Trace initiation service events";
           }
           enum "proxy" {
             description "Trace proxy service events";
           }
           enum "selected-profile" {
             description "Trace events for profiles with enable-flow-tracing set";
           }
           enum "all" {
             description "Trace everything";
           }
         }
       }
     }
   }
   grouping static-nat-rule-object {
     leaf name {
       description "Static Rule name";
       type string {
         length "1 .. 31";
         junos:posix-pattern "^[[:alnum:]][[:alnum:]_-]*$";
         junos:pattern-message "Must be a string beginning with a number or letter and consisting of letters, numbers, dashes and underscores.";
       }
     }
     uses apply-advanced;
     leaf description {
       description "Text description of rule";
       type string {
         length "1 .. 900";
         junos:posix-pattern "^[^&<>\n]+$";
         junos:pattern-message "Must be a string excluding '&', '<', '>' and '\n'";
       }
     }
     container static-nat-rule-match {
       description "Specify Static NAT rule match criteria";
       uses apply-advanced;
       leaf-list source-address {
         ordered-by user;
         description "Source address";
         type jt:ipprefix;
         max-elements 8;
       }
       leaf-list source-address-name {
         ordered-by user;
         description "Address from address book";
         type string;
         max-elements 8;
       }
       list source-port {
         key name;
         ordered-by user;
         description "Source port";
         max-elements 8;
         leaf name {
           description "Port or lower limit of port range";
           type union {
             type uint16;
             type string {
               pattern "<.*>|$.*";
             }
           }
         }
         container to {
           description "Port range upper limit";
           uses apply-advanced;
           leaf high {
             description "Upper limit of port range";
             type union {
               type uint16;
               type string {
                 pattern "<.*>|$.*";
               }
             }
           }
         }
       }
       choice dst-choice {
         case case_1 {
           container destination-address {
             description "Destination address";
             leaf dst-addr {
               description "IPv4 or IPv6 Destination address prefix";
               type jt:ipprefix;
             }
           }
         }
         case case_2 {
           container destination-address-name {
             description "Address from address book";
             leaf dst-addr-name {
               description "Address from address book";
               type string {
                 length "1 .. 63";
               }
             }
           }
         }
       }
       container destination-port {
         description "Destination port";
         leaf low {
           description "Port or lower limit of port range";
           junos:must "((\".. .. .. then static-nat prefix mapped-port\" || \".. .. .. then static-nat prefix-name mapped-port\"))";
           junos:must-message "'then static-nat prefix mapped-port ...' or 'then static-nat prefix-name mapped-port' must be configured when configure 'destination-port'";
           type union {
             type uint16;
             type string {
               pattern "<.*>|$.*";
             }
           }
         }
         container to {
           description "Port range upper limit";
           uses apply-advanced;
           leaf high {
             description "Upper limit of port range";
             type union {
               type uint16;
               type string {
                 pattern "<.*>|$.*";
               }
             }
           }
         }
       }
     }
     container then {
       description "Then action";
       uses apply-advanced;
       container static-nat {
         description "Static NAT action";
         uses apply-advanced;
         choice prefix-choice {
           case case_1 {
             container inet {
               presence "enable inet";
               description "Translated to IPv4 address";
               uses apply-advanced;
               leaf routing-instance {
                 description "Routing instance";
                 type string;
               }
             }
           }
           case case_2 {
             container prefix {
               description "Address prefix";
               uses apply-advanced;
               leaf addr-prefix {
                 description "IPv4 or IPv6 address prefix value";
                 type jt:ipprefix;
               }
               container mapped-port {
                 description "Mapped port";
                 uses static-nat-rule-mapped-port-object;
               }
               leaf routing-instance {
                 description "Routing instance";
                 type string;
               }
             }
           }
           case case_3 {
             container prefix-name {
               description "Address from address book";
               uses apply-advanced;
               leaf addr-prefix-name {
                 description "Address from address book";
                 type string {
                   length "1 .. 63";
                 }
               }
               container mapped-port {
                 description "Mapped port";
                 uses static-nat-rule-mapped-port-object;
               }
               leaf routing-instance {
                 description "Routing instance";
                 type string;
               }
             }
           }
           case case_4 {
             container nptv6-prefix {
               description "NPTv6 address prefix, the longest prefix will be supported is /64";
               uses apply-advanced;
               leaf addr-prefix {
                 description "IPv6 address prefix value, the longest prefix will be supported is /64";
                 type jt:ipprefix;
               }
               leaf routing-instance {
                 description "Routing instance";
                 type string;
               }
             }
           }
           case case_5 {
             container nptv6-prefix-name {
               description "NPTv6 address from address book";
               uses apply-advanced;
               leaf addr-prefix-name {
                 description "IPv6 address from address book";
                 type string {
                   length "1 .. 63";
                 }
               }
               leaf routing-instance {
                 description "Routing instance";
                 type string;
               }
             }
           }
         }
         container rule-session-count-alarm {
           description "Config rule-session-count-alarm to static rule";
           uses nat-rule-session-count-alarm-object;
         }
       }
     }
   }
   grouping static-nat-rule-mapped-port-object {
     uses apply-advanced;
     leaf low {
       description "Port or lower limit of port range";
       junos:must "(\".. .. .. .. .. match destination-port\")";
       junos:must-message "'match destination-port ...' must be configured when configure 'mapped-port'";
       type union {
         type uint16;
         type string {
           pattern "<.*>|$.*";
         }
       }
     }
     container to {
       description "Port range upper limit";
       uses apply-advanced;
       leaf high {
         description "Upper limit of port range";
         type union {
           type uint16;
           type string {
             pattern "<.*>|$.*";
           }
         }
       }
     }
   }
   grouping sw-rule-set-object {
     leaf name {
       description "Define Rule Set name";
       type string {
         length "1 .. 63";
         junos:posix-pattern "^[[:alnum:]][[:alnum:]_-]*$";
         junos:pattern-message "Must be a string beginning with a number or letter and consisting of letters, numbers, dashes and underscores.";
       }
     }
     uses apply-advanced;
     list rule {
       key name;
       ordered-by user;
       description "Define a rule term";
       leaf name {
         description "Rule name";
         type string {
           length "1 .. 63";
           junos:posix-pattern "^[[:alnum:]][[:alnum:]_-]*$";
           junos:pattern-message "Must be a string beginning with a number or letter and consisting of letters, numbers, dashes and underscores.";
         }
       }
       uses apply-advanced;
       container then {
         description "Action to take if the condition is matched";
         uses apply-advanced;
         choice designation {
           case case_1 {
             leaf v6rd {
               description "Apply 6rd softwire";
               type string {
                 length "1 .. 63";
                 junos:posix-pattern "^[[:alnum:]][[:alnum:]_-]*$";
                 junos:pattern-message "Must be a string beginning with a number or letter and consisting of letters, numbers, dashes and underscores.";
               }
             }
           }
         }
       }
     }
     leaf match-direction {
       description "Match direction";
       type enumeration {
         enum "input" {
           description "Match on input to interface";
         }
         enum "output" {
           description "Match on output from interface";
         }
       }
     }
   }
   grouping sw_rule_object {
     leaf name {
       description "Rule name";
       type string {
         length "1 .. 63";
         junos:posix-pattern "^[[:alnum:]][[:alnum:]_-]*$";
         junos:pattern-message "Must be a string beginning with a number or letter and consisting of letters, numbers, dashes and underscores.";
       }
     }
     uses apply-advanced;
     leaf match-direction {
       description "Direction for which the rule match is applied";
       type enumeration {
         enum "input" {
           description "Match on input to interface";
         }
         enum "output" {
           description "Match on output from interface";
         }
       }
     }
     list term {
       key name;
       ordered-by user;
       description "Define a softwire term";
       leaf name {
         description "Term name";
         type string {
           length "1 .. 63";
           junos:posix-pattern "^[[:alnum:]][[:alnum:]_-]*$";
           junos:pattern-message "Must be a string beginning with a number or letter and consisting of letters, numbers, dashes and underscores.";
         }
       }
       uses apply-advanced;
       container then {
         description "Action to take if the 'from' condition is matched";
         uses apply-advanced;
         choice designation {
           case case_1 {
             leaf ds-lite {
               description "Apply DS-Lite softwire";
               junos:must "(\"services softwire softwire-concentrator ds-lite $$\")";
               junos:must-message "referenced softwire concentrator must be defined under 'services softwire softwire-concentrator ds-lite'";
               type string {
                 length "1 .. 63";
                 junos:posix-pattern "^[[:alnum:]][[:alnum:]_-]*$";
                 junos:pattern-message "Must be a string beginning with a number or letter and consisting of letters, numbers, dashes and underscores.";
               }
             }
           }
           case case_2 {
             leaf v6rd {
               description "Apply 6rd softwire";
               junos:must "(\"services softwire softwire-concentrator v6rd $$\")";
               junos:must-message "referenced softwire concentrator must be defined under 'services softwire softwire-concentrator v6rd'";
               type string {
                 length "1 .. 63";
                 junos:posix-pattern "^[[:alnum:]][[:alnum:]_-]*$";
                 junos:pattern-message "Must be a string beginning with a number or letter and consisting of letters, numbers, dashes and underscores.";
               }
             }
           }
           case case_3 {
             leaf map-e {
               description "Apply map-e softwire";
               junos:must "(\"services softwire softwire-concentrator map-e $$\")";
               junos:must-message "referenced softwire concentrator must be defined under 'services softwire softwire-concentrator map-e'";
               type string {
                 length "1 .. 63";
                 junos:posix-pattern "^[[:alnum:]][[:alnum:]_-]*$";
                 junos:pattern-message "Must be a string beginning with a number or letter and consisting of letters, numbers, dashes and underscores.";
               }
             }
           }
         }
       }
     }
   }
   grouping tdir_netmon_object {
     description "Network monitoring probe configuration";
     uses apply-advanced;
     container traceoptions {
       description "Net Monitoring trace options";
       uses tdir_netmon_traceoptions_object;
     }
     list profile {
       key name;
       description "Network monitoring probe profile configuration";
       max-elements 32;
       uses tdir_netmon_profile_object;
     }
     list source-interface {
       key name;
       description "Network monitoring probe sending interface";
       max-elements 32;
       uses tdir_netmon_src_iface;
     }
   }
   grouping tdir_netmon_profile_object {
     leaf name {
       description "Network monitoring probe profile name";
       type string {
         length "1 .. 20";
       }
     }
     uses apply-advanced;
     choice probe-type {
       case case_1 {
         container http {
           description "HTTP probe options";
           uses tdir_http_probe_object;
         }
       }
       case case_2 {
         leaf icmp {
           description "ICMP probe options";
           type empty;
         }
       }
       case case_3 {
         container tcp {
           description "TCP probe options";
           uses tdir_tcp_probe_object;
         }
       }
       case case_4 {
         container ssl-hello {
           description "SSL hello probe options";
           uses tdir_ssl_hello_probe_object;
         }
       }
       case case_5 {
         container custom {
           description "Custom probe options";
           uses tdir_netmon_custom_probe_object;
         }
       }
     }
     leaf probe-interval {
       description "Probe interval";
       default "5";
       units "seconds";
       type union {
         type string {
           pattern "<.*>|$.*";
         }
         type uint32 {
           range "1 .. 180";
         }
       }
     }
     leaf failure-retries {
       description "Probe failure retries";
       default "5";
       type union {
         type string {
           pattern "<.*>|$.*";
         }
         type uint32 {
           range "1 .. 255";
         }
       }
     }
     leaf recovery-retries {
       description "Probe recovery retries";
       default "5";
       type union {
         type string {
           pattern "<.*>|$.*";
         }
         type uint32 {
           range "1 .. 255";
         }
       }
     }
   }
   grouping tdir_http_probe_object {
     description "HTTP probe information";
     uses apply-advanced;
     leaf port {
       description "Port number";
       default "80";
       type union {
         type string {
           pattern "<.*>|$.*";
         }
         type uint16 {
           range "1 .. 65535";
         }
       }
     }
     leaf url {
       description "URL name";
       type string {
         length "1 .. 127";
       }
     }
     leaf method {
       description "HTTP method";
       default "get";
       type enumeration {
         enum "get" {
           description "HTTP method GET";
         }
         enum "options" {
           description "HTTP method OPTIONS";
         }
       }
     }
     leaf hostname {
       description "Hostname";
       type string {
         length "1 .. 63";
       }
     }
   }
   grouping tdir_netmon_custom_probe_object {
     description "Custom probe information";
     uses apply-advanced;
     leaf protocol {
       description "Custom protocol";
       type enumeration {
         enum "tcp" {
           description "TCP protocol";
         }
         enum "udp" {
           description "UDP protocol";
         }
       }
     }
     list cmd {
       key name;
       description "Custom probe command configuration";
       max-elements 1;
       uses tdir_netmon_custom_probe_command_object;
     }
   }
   grouping tdir_netmon_custom_probe_command_object {
     description "Command information in custom probe";
     leaf name {
       description "Custom probe command priority";
       type union {
         type string {
           pattern "<.*>|$.*";
         }
         type uint16 {
           range "1 .. 2";
         }
       }
     }
     uses apply-advanced;
     leaf port {
       description "Port number";
       type union {
         type string {
           pattern "<.*>|$.*";
         }
         type uint16 {
           range "1 .. 65535";
         }
       }
     }
     leaf default-real-service-status {
       description "Default status of real service";
       default "down";
       type enumeration {
         enum "down" {
           description "RS marked down by default";
         }
         enum "up" {
           description "RS marked up by default";
         }
       }
     }
     container send {
       description "Send ASCII string or binary buffer";
       uses tdir_netmon_custom_probe_send_object;
     }
     container expect {
       description "Expect ASCII string or binary buffer";
       uses tdir_netmon_custom_probe_expect_object;
     }
   }
   grouping tdir_netmon_custom_probe_expect_object {
     uses apply-advanced;
     choice expect_choice {
       case case_1 {
         container ascii {
           description "Expect ASCII string";
           uses tdir_netmon_cust_probe_ascii_expect_obj;
         }
       }
       case case_2 {
         container binary {
           description "Expect binary buffer";
           uses tdir_netmon_cust_probe_binary_expect_obj;
         }
       }
     }
   }
   grouping tdir_netmon_cust_probe_ascii_expect_obj {
     leaf ascii-buf {
       type string {
         length "1 .. 512";
       }
     }
     container offset {
       description "Expect buffer offset";
       uses tdir_netmon_cust_probe_expect_offset_obj;
     }
     leaf real-service-action {
       description "Action on expect match";
       default "up";
       type enumeration {
         enum "up" {
           description "Mark RS up";
         }
         enum "down" {
           description "Mark RS down";
         }
       }
     }
   }
   grouping tdir_netmon_cust_probe_binary_expect_obj {
     leaf binary-buf {
       type string {
         length "1 .. 512";
         junos:posix-pattern "^[[:xdigit:]]+$";
         junos:pattern-message "Must be hexadecimal digits (0-9, a-f, A-F)";
       }
     }
     container offset {
       description "Expect buffer offset";
       uses tdir_netmon_cust_probe_expect_offset_obj;
     }
     leaf real-service-action {
       description "Action on expect match";
       default "up";
       type enumeration {
         enum "up" {
           description "Mark RS up";
         }
         enum "down" {
           description "Mark RS down";
         }
       }
     }
   }
   grouping tdir_netmon_cust_probe_expect_offset_obj {
     leaf offset {
       type union {
         type uint16;
         type string {
           pattern "<.*>|$.*";
         }
       }
     }
     leaf length {
       description "Expect buffer offset length";
       type union {
         type string {
           pattern "<.*>|$.*";
         }
         type uint16 {
           range "1 .. 65535";
         }
       }
     }
   }
   grouping tdir_netmon_custom_probe_send_object {
     choice send_choice {
       case case_1 {
         leaf ascii {
           description "Send ASCII string";
           type string {
             length "1 .. 512";
           }
         }
       }
       case case_2 {
         leaf binary {
           description "Send binary buffer";
           type string {
             length "1 .. 512";
             junos:posix-pattern "^[[:xdigit:]]+$";
             junos:pattern-message "Must be hexadecimal digits (0-9, a-f, A-F)";
           }
         }
       }
     }
   }
   grouping tdir_netmon_src_iface {
     leaf name {
       description "Network monitoring probe source interface name";
       type string {
         length "1 .. 20";
       }
     }
     uses apply-advanced;
     container family {
       description "Address family";
       uses apply-advanced;
       container inet {
         description "Address family IPv4";
         uses apply-advanced;
         leaf address {
           description "Address family IPv4 address";
           type jt:ipv4addr;
         }
       }
       container inet6 {
         description "Address family IPv6";
         uses apply-advanced;
         leaf address {
           description "Address family IPv6 address";
           type jt:ipv6addr;
         }
       }
     }
   }
   grouping tdir_netmon_traceoptions_object {
     description "Network Monitoring trace options";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing flag parameters";
       leaf name {
         type enumeration {
           enum "all-real-services" {
             description "Trace all real services";
           }
           enum "messages" {
             description "Trace normal events";
           }
           enum "probe" {
             description "Trace probe events";
           }
           enum "inter-thread" {
             description "Trace inter thread communication events";
           }
           enum "database" {
             description "Trace database events";
           }
           enum "file-descriptor-queue" {
             description "Trace file descriptor queue events";
           }
           enum "probe-infra" {
             description "Trace probe infra events";
           }
           enum "all" {
             description "Trace everything";
           }
         }
       }
     }
     list monitor {
       key name;
       leaf name {
         description "Monitor name";
         type string {
           length "1 .. 20";
         }
       }
       uses apply-advanced;
       leaf group-name {
         description "Group name";
         type string {
           length "1 .. 20";
         }
       }
       leaf real-services-name {
         description "Real service";
         type string {
           length "1 .. 20";
         }
       }
     }
   }
   grouping tdir_service_load_balance_object {
     uses apply-advanced;
     container traceoptions {
       description "Traffic load balance trace options";
       uses tdir_traceoptions_object;
     }
     leaf route-hold-timer {
       description "Route hold timer, when PIC is down";
       default "180";
       type union {
         type string {
           pattern "<.*>|$.*";
         }
         type uint32 {
           range "1 .. 600";
         }
       }
     }
     list instance {
       key name;
       description "Traffic load balance instance configuration";
       max-elements 2048;
       uses tdir_slb_instance_object;
     }
   }
   grouping tdir_slb_instance_object {
     leaf name {
       description "Instance name";
       type string {
         length "1 .. 20";
       }
     }
     uses apply-advanced;
     leaf interface {
       description "Interface name";
       type union {
         type jt:interface-name;
         type string {
           pattern "<.*>|$.*";
         }
       }
     }
     leaf server-inet-bypass-filter {
       description "Server Implicit inet bypass filter reference";
       type string;
     }
     leaf server-inet6-bypass-filter {
       description "Server Implicit inet6 bypass filter reference";
       type string;
     }
     leaf-list client-interface {
       ordered-by user;
       description "Client facing interface name";
       type union {
         type jt:interface-unit;
         type string {
           pattern "<.*>|$.*";
         }
       }
     }
     leaf-list server-interface {
       ordered-by user;
       description "Server facing interface name";
       type union {
         type jt:interface-unit;
         type string {
           pattern "<.*>|$.*";
         }
       }
     }
     leaf client-vrf {
       description "Client-side VRF";
       type string {
         length "1 .. 30";
         junos:posix-pattern "!^((__.*__)|(all)|(.*[ ].*)|(\"\")|(.{129,}))$";
         junos:pattern-message "Must be a non-reserved string of 128 characters or less with no spaces.";
       }
     }
     leaf server-vrf {
       description "Server-side VRF";
       type string {
         length "1 .. 30";
         junos:posix-pattern "!^((__.*__)|(all)|(.*[ ].*)|(\"\")|(.{129,}))$";
         junos:pattern-message "Must be a non-reserved string of 128 characters or less with no spaces.";
       }
     }
     list group {
       key name;
       description "Group configuration";
       max-elements 32;
       uses tdir_slb_group_object;
     }
     list real-service {
       key name;
       description "Real service configuration";
       max-elements 8160;
       uses tdir_real_service_object;
     }
     list virtual-service {
       key name;
       description "Virtual service configuration";
       max-elements 32;
       uses tdir_virtual_service_object;
     }
   }
   grouping tdir_real_service_object {
     leaf name {
       description "Real service name";
       type string {
         length "1 .. 20";
       }
     }
     uses apply-advanced;
     leaf address {
       description "IP address";
       type jt:ipaddr;
     }
     leaf admin-down {
       description "Set the real service to DOWN state";
       type empty;
     }
   }
   grouping tdir_slb_group_object {
     leaf name {
       description "Group name";
       type string {
         length "1 .. 20";
       }
     }
     uses apply-advanced;
     leaf-list real-services {
       ordered-by user;
       description "Real services group association";
       type string {
         length "1 .. 20";
       }
       max-elements 255;
     }
     leaf routing-instance {
       description "Routing instance name";
       type string {
         length "1 .. 30";
         junos:posix-pattern "!^((__.*__)|(all)|(.*[ ].*)|(\"\")|(.{129,}))$";
         junos:pattern-message "Must be a non-reserved string of 128 characters or less with no spaces.";
       }
     }
     leaf health-check-interface-subunit {
       description "Subunit on which the health-check is to be initiated";
       default "0";
       type union {
         type uint16;
         type string {
           pattern "<.*>|$.*";
         }
       }
     }
     leaf-list network-monitoring-profile {
       description "Network monitoring profile name";
       type string {
         length "1 .. 20";
       }
       max-elements 2;
     }
     container real-service-rejoin-options {
       description "Real service rejoin options";
       uses tdir_auto_rejoin_object;
     }
   }
   grouping tdir_auto_rejoin_object {
     uses apply-advanced;
     leaf no-auto-rejoin {
       description "Disable real service auto-rejoin, when it comes up";
       type empty;
     }
   }
   grouping tdir_ssl_hello_probe_object {
     description "SSL hello probe information";
     uses apply-advanced;
     leaf port {
       description "Port number";
       default "443";
       type union {
         type string {
           pattern "<.*>|$.*";
         }
         type uint16 {
           range "1 .. 65535";
         }
       }
     }
     leaf version {
       description "SSL version";
       default "3";
       type enumeration {
         enum "2" {
           description "SSL version 2";
         }
         enum "3" {
           description "SSL version 3";
         }
       }
     }
   }
   grouping tdir_tcp_probe_object {
     description "TCP probe information";
     uses apply-advanced;
     leaf port {
       description "Port number";
       type union {
         type string {
           pattern "<.*>|$.*";
         }
         type uint16 {
           range "1 .. 65535";
         }
       }
     }
   }
   grouping tdir_traceoptions_object {
     description "Traffic load balance trace options";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing flag parameters";
       leaf name {
         type enumeration {
           enum "normal" {
             description "Trace normal events";
           }
           enum "config" {
             description "Trace traffic load balance config events";
           }
           enum "connect" {
             description "Trace traffic load balance ipc events";
           }
           enum "health" {
             description "Trace traffic load balance health events";
           }
           enum "parse" {
             description "Trace traffic load balance parse events";
           }
           enum "probe" {
             description "Trace traffic load balance probe events";
           }
           enum "route" {
             description "Trace traffic load balance route events";
           }
           enum "snmp" {
             description "Trace traffic load balance snmp events";
           }
           enum "statistics" {
             description "Trace traffic load balance statistics events";
           }
           enum "system" {
             description "Trace traffic load balance system events";
           }
           enum "operational-commands" {
             description "Trace traffic load balance show events";
           }
           enum "filter" {
             description "Trace traffic load balance filter programming events";
           }
           enum "batch" {
             description "Trace traffic load balance Batching related events";
           }
           enum "all" {
             description "Trace everything";
           }
         }
       }
     }
     list monitor {
       key name;
       leaf name {
         description "Monitor name";
         type string {
           length "1 .. 20";
         }
       }
       uses apply-advanced;
       leaf virtual-svc-name {
         description "Virtual service name";
         type string {
           length "1 .. 20";
         }
       }
       leaf instance-name {
         description "Instance name";
         type string {
           length "1 .. 20";
         }
       }
     }
     container in-memory-tracing {
       presence "enable in-memory-tracing";
       leaf max-lines {
         description "Number of max lines in memory tracing";
         type union {
           type string {
             pattern "<.*>|$.*";
           }
           type uint32 {
             range "5120 .. 20480";
           }
         }
       }
     }
   }
   grouping tdir_virtual_service_object {
     leaf name {
       description "Virtual service name";
       type string {
         length "1 .. 20";
       }
     }
     uses apply-advanced;
     leaf mode {
       description "Virtual service mode";
       type enumeration {
         enum "layer2-direct-server-return" {
           description "Layer2 Direct Server Return mode";
         }
         enum "direct-server-return" {
           description "Direct Server Return mode";
         }
         enum "translated" {
           description "Translated mode";
         }
       }
     }
     leaf address {
       description "IP address";
       type jt:ipaddr;
     }
     leaf route-metric {
       description "Route metric";
       default "1";
       type union {
         type string {
           pattern "<.*>|$.*";
         }
         type uint16 {
           range "1 .. 255";
         }
       }
     }
     leaf rebalance-threshold {
       description "Rebalance threshold";
       default "25";
       type union {
         type string {
           pattern "<.*>|$.*";
         }
         type uint16 {
           range "1 .. 100";
         }
       }
     }
     leaf routing-instance {
       description "Routing instance name";
       type string {
         length "1 .. 30";
         junos:posix-pattern "!^((__.*__)|(all)|(.*[ ].*)|(\"\")|(.{129,}))$";
         junos:pattern-message "Must be a non-reserved string of 128 characters or less with no spaces.";
       }
     }
     list service {
       key name;
       description "Listening service configuration";
       max-elements 1;
       uses tdir_virtual_service_svc_object;
     }
     leaf-list server-interface {
       ordered-by user;
       description "Server facing interface name";
       type union {
         type jt:interface-unit;
         type string {
           pattern "<.*>|$.*";
         }
       }
     }
     leaf group {
       description "Group name";
       junos:must "(\".. .. group $$\")";
       junos:must-message "group is not defined";
       type string {
         length "1 .. 20";
       }
     }
     container load-balance-method {
       presence "enable load-balance-method";
       description "Load balance method";
       uses apply-advanced;
       choice method-type {
         case case_1 {
           container hash {
             presence "enable hash";
             description "Load balance hash method";
             uses apply-advanced;
             container hash-key {
               description "Hash-key type";
               uses tdir_virtual_service_lb_hash_method_obj;
             }
           }
         }
         case case_2 {
           leaf random {
             description "Load balance random method";
             type empty;
           }
         }
       }
     }
   }
   grouping tdir_virtual_service_lb_hash_method_obj {
     uses apply-advanced;
     leaf source-ip {
       description "Source-address based hashing";
       type empty;
     }
     leaf destination-ip {
       description "Destination-address based hashing";
       type empty;
     }
     leaf protocol {
       description "Protocol based hashing";
       type empty;
     }
   }
   grouping tdir_virtual_service_svc_object {
     description "Service information in virtual service";
     leaf name {
       description "Service name";
       type string {
         length "1 .. 20";
       }
     }
     uses apply-advanced;
     leaf virtual-port {
       description "Virtual port number";
       type union {
         type string {
           pattern "<.*>|$.*";
         }
         type uint16 {
           range "1 .. 65535";
         }
       }
     }
     leaf server-listening-port {
       description "Server listening port";
       type union {
         type string {
           pattern "<.*>|$.*";
         }
         type uint16 {
           range "1 .. 65535";
         }
       }
     }
     leaf protocol {
       description "Service transport portocol";
       type string;
     }
     leaf include-real-server-ips-in-server-filter {
       description "Includes list of all real server ip address in server filter";
       type empty;
     }
   }
   grouping transaction-method-type {
     leaf name {
       type enumeration {
         enum "method-invite" {
         }
         enum "method-options" {
         }
         enum "method-refer" {
         }
         enum "method-subscribe" {
         }
         enum "method-publish" {
         }
         enum "method-message" {
         }
         enum "method-register" {
         }
       }
     }
     uses apply-advanced;
   }
   grouping transaction_policy_type {
     leaf name {
       description "Policy name";
       type string;
     }
     uses apply-advanced;
     list term {
       key name;
       ordered-by user;
       description "Term definition";
       max-elements 20;
       leaf name {
         description "Term name";
         type string;
       }
       uses apply-advanced;
       container from {
         description "From action";
         uses new_transaction_from_type;
       }
       container then {
         description "Action";
         uses new_transaction_then_type;
       }
     }
   }
   grouping new_transaction_then_type {
     uses apply-advanced;
     leaf accept {
       description "Accept the request";
       type empty;
     }
     leaf reject {
       description "Reject the request";
       type empty;
     }
     container route {
       description "How to route the request";
       uses route_action;
     }
     leaf trace {
       description "Trace messages accepted on this policy";
       type empty;
     }
     leaf admission-control {
       description "Admission controller for the request";
       junos:must "(\"services border-signaling-gateway gateway ${gateway} admission-control $$\")";
       junos:must-message "Referenced admission controller must be defined";
       type string;
     }
     container message-manipulation {
       presence "enable message-manipulation";
       description "Definitions of forward and reverse manipulations ";
       uses apply-advanced;
       list forward-manipulation {
         key name;
         ordered-by user;
         max-elements 5;
         leaf name {
           description "Forward manipulation rules";
           junos:must "(\"services border-signaling-gateway gateway ${gateway}                        sip message-manipulation-rules manipulation-rule $$\")";
           junos:must-message "Referenced message manipulation must be defined";
           type string;
         }
         uses apply-advanced;
       }
       list reverse-manipulation {
         key name;
         ordered-by user;
         max-elements 5;
         leaf name {
           description "Reverse manipulation rules";
           junos:must "(\"services border-signaling-gateway gateway ${gateway}                        sip message-manipulation-rules manipulation-rule $$\")";
           junos:must-message "Referenced message manipulation must be defined";
           type string;
         }
         uses apply-advanced;
       }
     }
     leaf signaling-realm {
       description "Signaling realm";
       junos:must "(\"services border-signaling-gateway gateway ${gateway} sip signaling-realms $$\")";
       junos:must-message "Referenced signaling realm must be defined";
       type string;
     }
     container on-3xx-response {
       presence "enable on-3xx-response";
       description "Behavior on receiving a 3XX Response";
       uses apply-advanced;
       choice _3xx_recursion {
         case case_1 {
           leaf recursion-limit {
             description "The number of recursion to manage";
             default "16";
             type union {
               type string {
                 pattern "<.*>|$.*";
               }
               type uint32 {
                 range "1 .. 16";
               }
             }
           }
         }
       }
     }
   }
   grouping route_action {
     uses apply-advanced;
     container next-hop {
       presence "enable next-hop";
       junos:must "(!(\".. server-cluster\"))";
       junos:must-message "Definition of a next-hop excludes the definition of a server-cluster";
       uses apply-advanced;
       choice next-hop {
         case case_1 {
           container address {
             description "Static route by IP address";
             uses routing-destination-address;
           }
         }
         case case_2 {
           leaf request-uri {
             description "Route by request-uri";
             type empty;
           }
         }
         case case_3 {
           leaf sip-based {
             description "Routing based on the SIP procedures";
             status deprecated;
             type empty;
           }
         }
       }
     }
     leaf egress-service-point {
       description "Exit point";
       junos:must "((\"services border-signaling-gateway gateway ${gateway} service-point $$\" && !(\".. server-cluster\")))";
       junos:must-message "egress-service-point must be defined. Definition of an egress-service-point excludes the definition of a server-cluster";
       type string;
     }
     leaf server-cluster {
       description "Cluster name";
       junos:must "((\"services border-signaling-gateway gateway ${gateway} sip routing-destinations clusters $$\" && (!(\".. egress-service-point\") && !(\".. next-hop\"))))";
       junos:must-message "Referenced cluster must be defined. Definition of a server-cluster excludes the definition of egress-service-point or next-hop";
       type string;
     }
   }
   grouping transport_protocol {
     uses apply-advanced;
     choice transport-protocol {
       case case_1 {
         leaf udp {
           type empty;
         }
       }
       case case_2 {
         leaf tcp {
           type empty;
         }
       }
     }
   }
   grouping tunnel_interface_type {
     description "One or more tunnel interfaces on which to configure flow-tap service";
     leaf name {
       description "Tunnel Interface name";
       junos:must "(!(\"services dynamic-flow-capture\"))";
       junos:must-message "Dynamic flow capture cannot be configured when flow-tap is configured";
       junos:must "(!(\"interfaces $$-IFL family inet filter\"))";
       junos:must-message "Tunnel Interface assigned for Radius-Flow-Tap cannot be configured with firewall filter";
       junos:must "(\"interfaces $$-IFL family inet\")";
       junos:must-message "Interface with family inet must be defined in the [edit interfaces] hierarchy";
       type union {
         type jt:interface-unit;
         type string {
           pattern "<.*>|$.*";
         }
       }
     }
     uses apply-advanced;
   }
   grouping tunnel_type {
     description "Tunnel packets";
     uses apply-advanced;
     choice ipsec-vpn-choice {
       case case_1 {
         leaf ipsec-vpn {
           description "Enable VPN with name";
           junos:must "(!(\"security ipsec vpn $$ bind-interface\"))";
           junos:must-message "Route based ipsec-vpn cannot be referenced for policy";
           junos:must "(\"security ipsec vpn $$\")";
           junos:must-message "Security VPN must be defined";
           type string {
             length "1 .. 63";
           }
         }
       }
       case case_2 {
         leaf ipsec-group-vpn {
           description "Enable dynamic IPSEC group with name";
           status deprecated;
           junos:must "(\"security group-vpn member ipsec vpn $$\")";
           junos:must-message "Security group VPN must be defined";
           type string {
             length "1 .. 63";
           }
         }
       }
     }
     leaf pair-policy {
       description "Policy in the reverse direction, to form a pair";
       type string {
         length "1 .. 63";
         junos:posix-pattern "^[[:alnum:]][[:alnum:]_-]*$";
         junos:pattern-message "Must be a string beginning with a number or letter and consisting of letters, numbers, dashes and underscores.";
       }
     }
   }
   grouping twamp-authentication-key-chain {
     leaf name {
       description "Name of authentication key chain";
       type string {
         junos:posix-pattern "^.{1,32}$";
         junos:pattern-message "Must be string of 32 characters or less";
       }
     }
     uses apply-advanced;
     list key-id {
       key name;
       description "Authentication element configuration";
       leaf name {
         description "Authentication element identifier";
         type string {
           length "1 .. 80";
         }
       }
       uses apply-advanced;
       leaf secret {
         description "Authentication key";
         type string {
           length "1 .. 256";
         }
       }
     }
   }
   grouping urlf-profile-object {
     leaf name {
       description "Name of profile";
       type string {
         length "1 .. 64";
         junos:posix-pattern "^[[:alnum:]][[:alnum:]_-]*$";
         junos:pattern-message "Must be a string beginning with a number or letter and consisting of letters, numbers, dashes and underscores.";
       }
     }
     uses apply-advanced;
     leaf url-filter-database {
       description "Full path of the file";
       junos:must "(!(\".. security-intelligence-policy\"))";
       junos:must-message "Not applicable for security intelligence based profiles";
       type string {
         length "1 .. 1024";
       }
     }
     leaf global-dns-filter-stats-log-timer {
       description "Global DNS filtering statistics log timer in minutes";
       default "5";
       units "minutes";
       junos:must "(!(\".. security-intelligence-policy\"))";
       junos:must-message "Not applicable for security intelligence based profiles";
       type union {
         type string {
           pattern "<.*>|$.*";
         }
         type uint32 {
           range "0 .. 60";
         }
       }
     }
     container security-intelligence-policy {
       presence "enable security-intelligence-policy";
       description "Use the database supplied by security intelligence for blacklisted traffic.";
       uses apply-advanced;
       leaf file-type {
         type enumeration {
           enum "txt" {
             description "Policy DB is a text file";
           }
           enum "json" {
             description "Policy DB is in json format";
           }
         }
       }
       list threat-level {
         key name;
         ordered-by user;
         description "Define a URL filtering threat level";
         max-elements 10;
         uses threat-level-object;
       }
     }
     container dns-filter {
       description "DNS filter information";
       junos:must "(!(\".. security-intelligence-policy\"))";
       junos:must-message "Not applicable for security intelligence based profiles";
       uses dns-filter-object;
       junos:must "(!(\".. security-intelligence-policy\"))";
       junos:must-message "Not applicable for security intelligence based profiles";
     }
     list url-filter-template {
       key name;
       ordered-by user;
       description "URL filter template";
       max-elements 32;
       uses urlf-template-object;
     }
     list dns-filter-template {
       key name;
       ordered-by user;
       description "DNS filter template";
       max-elements 32;
       junos:must "(!(\".. security-intelligence-policy\"))";
       junos:must-message "Not applicable for security intelligence based profiles";
       uses dnsf-template-object;
     }
   }
   grouping dns-filter-object {
     uses apply-advanced;
     leaf database-file {
       description "Full path of the DNS filter database file";
       type string {
         length "1 .. 1024";
       }
     }
     leaf-list dns-server {
       ordered-by user;
       description "One or more DNS servers addresses";
       type jt:ipaddr;
       max-elements 20;
     }
     container hash-key {
       description "Define hash key for domains key";
       choice key-choice {
         case case_1 {
           leaf ascii-text {
             description "Format as text";
             type string {
               length "1 .. 255";
             }
           }
         }
         case case_2 {
           leaf hexadecimal {
             description "Format as hexadecimal";
             type string {
               length "1 .. 255";
               junos:posix-pattern "^[[:xdigit:]]+$";
               junos:pattern-message "Must be hexadecimal digits (0-9, a-f, A-F)";
             }
           }
         }
       }
     }
     leaf hash-method {
       description "Define authentication algorithm";
       junos:must "(\".. hash-key\")";
       junos:must-message "hash-key is mandatory";
       type enumeration {
         enum "hmac-sha2-256" {
           description "HMAC-SHA2-256 authentication algorithm";
         }
       }
     }
     leaf statistics-log-timer {
       description "DNS log timer in minutes";
       default "5";
       units "minutes";
       type union {
         type string {
           pattern "<.*>|$.*";
         }
         type uint32 {
           range "0 .. 60";
         }
       }
     }
     leaf dns-resp-ttl {
       description "TTL to be used in DNS response";
       default "1800";
       units "seconds";
       type union {
         type string {
           pattern "<.*>|$.*";
         }
         type uint32 {
           range "0 .. 3600";
         }
       }
     }
     leaf wildcarding-level {
       description "Wildcarding level for exact match";
       default "2";
       type union {
         type string {
           pattern "<.*>|$.*";
         }
         type uint32 {
           range "0 .. 10";
         }
       }
     }
   }
   grouping dnsf-template-object {
     leaf name {
       description "Name of template";
       type string {
         length "1 .. 64";
         junos:posix-pattern "^[[:alnum:]][[:alnum:]_-]*$";
         junos:pattern-message "Must be a string beginning with a number or letter and consisting of letters, numbers, dashes and underscores.";
       }
     }
     uses apply-advanced;
     container dns-filter {
       description "DNS filter information";
       uses dns-filter-object;
     }
     leaf-list client-interfaces {
       ordered-by user;
       description "Client facing interfaces on which the dns filtering is applied";
       type union {
         type jt:interface-unit;
         type string {
           pattern "<.*>|$.*";
         }
       }
       max-elements 64;
     }
     leaf-list server-interfaces {
       ordered-by user;
       description "Server facing interfaces to which traffic destined to";
       type union {
         type jt:interface-unit;
         type string {
           pattern "<.*>|$.*";
         }
       }
       max-elements 64;
     }
     leaf client-routing-instance {
       description "Routing instance name";
       type string;
     }
     leaf server-routing-instance {
       description "Routing instance name";
       type string;
     }
     list term {
       key name;
       ordered-by user;
       description "Define a DNS filtering term";
       max-elements 64;
       leaf name {
         description "Term name";
         type string {
           length "1 .. 64";
           junos:posix-pattern "^[[:alnum:]][[:alnum:]/.:_-]*$";
           junos:pattern-message "Must be a string beginning with a number or letter and consisting of letters, numbers, dashes, underscores, forward slashes, colons and dots.";
         }
       }
       uses apply-advanced;
       container from {
         description "Define match criteria";
         uses dnsf-match-object;
       }
       container then {
         presence "enable then";
         description "Action to take if the 'from' condition is matched";
         uses apply-advanced;
         choice dns-filter-action {
           case case_1 {
             leaf dns-sinkhole {
               description "DNS sinkhole";
               type empty;
             }
           }
         }
       }
     }
   }
   grouping dnsf-match-object {
     uses apply-advanced;
     leaf-list src-ip-prefix {
       ordered-by user;
       description "Source IP Prefix list specification";
       type jt:ipprefix;
       max-elements 64;
     }
   }
   grouping threat-level-object {
     leaf name {
       description "Threat level value";
       type union {
         type string {
           pattern "<.*>|$.*";
         }
         type uint32 {
           range "1 .. 10";
         }
       }
     }
     uses apply-advanced;
     container threat-action {
       presence "enable threat-action";
       description "Action to be taken for the given threat level ";
       uses apply-advanced;
       choice secintl-action {
         case case_1 {
           leaf accept {
             description "Accept";
             type empty;
           }
         }
         case case_2 {
           leaf log {
             description "Log";
             type empty;
           }
         }
         case case_3 {
           leaf drop {
             description "Drop";
             type empty;
           }
         }
         case case_4 {
           leaf drop-and-log {
             description "Drop and log";
             type empty;
           }
         }
       }
     }
   }
   grouping urlf-template-object {
     leaf name {
       description "Name of template";
       type string {
         length "1 .. 64";
         junos:posix-pattern "^[[:alnum:]][[:alnum:]_-]*$";
         junos:pattern-message "Must be a string beginning with a number or letter and consisting of letters, numbers, dashes and underscores.";
       }
     }
     uses apply-advanced;
     leaf-list client-interfaces {
       ordered-by user;
       description "Client facing interfaces on which the url filtering is applied";
       type union {
         type jt:interface-unit;
         type string {
           pattern "<.*>|$.*";
         }
       }
       max-elements 64;
     }
     leaf-list server-interfaces {
       ordered-by user;
       description "Server facing interfaces to which traffic destined to";
       junos:must "(!(\".. ..  security-intelligence-policy\"))";
       junos:must-message "Not applicable for security intelligence based profiles";
       type union {
         type jt:interface-unit;
         type string {
           pattern "<.*>|$.*";
         }
       }
       max-elements 64;
     }
     leaf dns-source-interface {
       description "Interface on which the DNS queries are originated";
       junos:must "(!(\".. ..  security-intelligence-policy\"))";
       junos:must-message "Not applicable for security intelligence based profiles";
       type union {
         type jt:interface-unit;
         type string {
           pattern "<.*>|$.*";
         }
       }
     }
     leaf dns-routing-instance {
       description "Routing instance for DNS queries";
       junos:must "(!(\".. ..  security-intelligence-policy\"))";
       junos:must-message "Not applicable for security intelligence based profiles";
       type string;
     }
     leaf client-routing-instance {
       description "Routing instance name";
       type string;
     }
     leaf-list dns-server {
       ordered-by user;
       description "One or more DNS servers addresses";
       junos:must "(!(\".. ..  security-intelligence-policy\"))";
       junos:must-message "DNS server must not be configured for security intelligence based profiles";
       type jt:ipaddr;
       max-elements 2;
     }
     leaf dns-resolution-interval {
       description "DNS resolution timer in minutes";
       default "1440";
       units "minutes";
       junos:must "(!(\".. ..  security-intelligence-policy\"))";
       junos:must-message "Not applicable for security intelligence based profiles";
       type union {
         type string {
           pattern "<.*>|$.*";
         }
         type uint32 {
           range "60 .. 1440";
         }
       }
     }
     leaf dns-retries {
       description "DNS resolution attempts";
       default "3";
       junos:must "(!(\".. ..  security-intelligence-policy\"))";
       junos:must-message "Not applicable for security intelligence based profiles";
       type union {
         type string {
           pattern "<.*>|$.*";
         }
         type uint32 {
           range "1 .. 5";
         }
       }
     }
     leaf dns-resolution-rate {
       description "DNS resolution rate per chunk interval";
       default "50";
       junos:must "(!(\".. ..  security-intelligence-policy\"))";
       junos:must-message "Not applicable for security intelligence based profiles";
       type union {
         type string {
           pattern "<.*>|$.*";
         }
         type uint32 {
           range "50 .. 100";
         }
       }
     }
     leaf url-filter-database {
       description "Full path of the file";
       junos:must "(!(\".. ..  security-intelligence-policy\"))";
       junos:must-message "Not applicable for security intelligence based profiles";
       type string {
         length "1 .. 1024";
       }
     }
     leaf disable-url-ip-filtering {
       description "Disable filtering of IPs belonging to blocklisted domains";
       junos:must "(!(\".. ..  security-intelligence-policy\"))";
       junos:must-message "Not applicable for security intelligence based profiles";
       type empty;
     }
     list term {
       key name;
       ordered-by user;
       description "Define a url filtering term";
       max-elements 8;
       leaf name {
         description "Term name";
         type string {
           length "1 .. 64";
           junos:posix-pattern "^[[:alnum:]][[:alnum:]/.:_-]*$";
           junos:pattern-message "Must be a string beginning with a number or letter and consisting of letters, numbers, dashes, underscores, forward slashes, colons and dots.";
         }
       }
       uses apply-advanced;
       container from {
         description "Define match criteria";
         uses urlf-match-object;
       }
       container then {
         presence "enable then";
         description "Action to take if the 'from' condition is matched";
         uses apply-advanced;
         choice url-filter-action {
           case case_1 {
             leaf redirect-url {
               description "Redirect URL";
               type string {
                 length "1 .. 1024";
               }
             }
           }
           case case_2 {
             leaf custom-page {
               description "Custome page string";
               type string {
                 length "1 .. 128";
               }
             }
           }
           case case_3 {
             leaf http-status-code {
               description "HTTP status code value";
               type union {
                 type string {
                   pattern "<.*>|$.*";
                 }
                 type uint16 {
                   range "400 .. 599";
                 }
               }
             }
           }
           case case_4 {
             leaf tcp-reset {
               description "TCP Reset";
               type empty;
             }
           }
           case case_5 {
             leaf accept {
               description "Accept";
               type empty;
             }
           }
         }
       }
     }
   }
   grouping urlf-match-object {
     uses apply-advanced;
     leaf-list src-ip-prefix {
       ordered-by user;
       description "Source IP Prefix list specification";
       type jt:ipprefix;
       max-elements 10;
     }
     leaf-list dest-ports {
       ordered-by user;
       description " Destination port list specification";
       type union {
         type string {
           pattern "<.*>|$.*";
         }
         type uint16 {
           range "1 .. 65535";
         }
       }
       max-elements 10;
     }
   }
   grouping urlf-traceoptions-object {
     description "URL filtering trace options";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing flag parameters";
       leaf name {
         type enumeration {
           enum "normal" {
             description "Trace normal events";
           }
           enum "config" {
             description "Trace url filtering config events";
           }
           enum "dns" {
             description "Trace url filtering DNS crawler events";
           }
           enum "timer" {
             description "Trace url filtering timer events";
           }
           enum "connect" {
             description "Trace url filtering ipc events";
           }
           enum "parse" {
             description "Trace url filtering parse events";
           }
           enum "statistics" {
             description "Trace url filtering statistics events";
           }
           enum "system" {
             description "Trace url filtering system events";
           }
           enum "operational-commands" {
             description "Trace url filtering show events";
           }
           enum "filter" {
             description "Trace url filtering filter programming events";
           }
           enum "gencfg" {
             description "Trace url filtering gencfg events";
           }
           enum "routing" {
             description "Trace url filtering route programming events";
           }
           enum "snmp" {
             description "Trace url filtering snmp events";
           }
           enum "all" {
             description "Trace everything";
           }
         }
       }
     }
   }
   grouping user-group-mapping-type {
     uses apply-advanced;
     container ldap {
       description "LDAP";
       uses apply-advanced;
       leaf authentication-algorithm {
         description "Authentication-algorithm";
         type enumeration {
           enum "simple" {
             description "Simple authentication";
           }
         }
       }
       leaf ssl {
         description "SSL";
         type empty;
       }
       leaf base {
         description "Base distinguished name";
         type string {
           length "1 .. 128";
         }
       }
       container user {
         description "User name";
         uses apply-advanced;
         leaf user-name {
           description "User name";
           type string {
             length "1 .. 64";
             junos:posix-pattern "^[[:alnum:]._-]+$|^\\\\*$";
             junos:pattern-message "Must be a string consisting of letters, numbers, dashes, underscores and dots";
           }
         }
         leaf password {
           description "Password string";
           type string {
             length "1 .. 128";
           }
         }
       }
       list address {
         key name;
         ordered-by user;
         description "Address of LDAP server";
         leaf name {
           description "Address";
           type jt:ipaddr;
         }
         uses apply-advanced;
         leaf port {
           description "LDAP port";
           type union {
             type string {
               pattern "<.*>|$.*";
             }
             type uint16 {
               range "1 .. 65535";
             }
           }
         }
       }
     }
   }
   grouping v6rd_object {
     leaf name {
       description "6rd concentrator name";
       type string {
         length "1 .. 63";
         junos:posix-pattern "^[[:alnum:]][[:alnum:]_-]*$";
         junos:pattern-message "Must be a string beginning with a number or letter and consisting of letters, numbers, dashes and underscores.";
       }
     }
     uses apply-advanced;
     leaf softwire-address {
       description "Softwire concentrator IPV4 prefix";
       type jt:ipv4addr;
     }
     leaf ipv4-prefix {
       description "6rd customer edge IPV4 prefix";
       type jt:ipv4prefix;
     }
     leaf v6rd-prefix {
       description "6rd domain's IPV6 prefix";
       type jt:ipv6prefix;
     }
     leaf mtu-v4 {
       description "MTU for the softwire tunnel";
       type union {
         type string {
           pattern "<.*>|$.*";
         }
         type int32 {
           range "576 .. 9192";
         }
       }
     }
   }
   grouping version-ipfix-template {
     description "One or more version-ipfix  templates for flow monitoring";
     leaf name {
       description "Name of template";
       type string;
     }
     uses apply-advanced;
     leaf flow-active-timeout {
       description "Interval after which active flow is exported";
       default "60";
       type union {
         type string {
           pattern "<.*>|$.*";
         }
         type uint32 {
           range "10 .. 600";
         }
       }
     }
     leaf flow-inactive-timeout {
       description "Period of inactivity that marks a flow inactive";
       default "60";
       type union {
         type string {
           pattern "<.*>|$.*";
         }
         type uint32 {
           range "10 .. 600";
         }
       }
     }
     leaf template-id {
       description "Template id";
       type union {
         type string {
           pattern "<.*>|$.*";
         }
         type uint32 {
           range "1024 .. 65535";
         }
       }
     }
     leaf option-template-id {
       description "Options template id";
       type union {
         type string {
           pattern "<.*>|$.*";
         }
         type uint32 {
           range "1024 .. 65535";
         }
       }
     }
     leaf observation-domain-id {
       description "Observation Domain Id";
       default "0";
       type union {
         type string {
           pattern "<.*>|$.*";
         }
         type uint32 {
           range "0 .. 255";
         }
       }
     }
     container nexthop-learning {
       presence "enable nexthop-learning";
       description "Nexthop learning parameter. Valid ONLY for INLINE-JFLOW";
       uses apply-advanced;
       choice enable-disable {
         case case_1 {
           leaf enable {
             description "Enable nexthop learning";
             type empty;
           }
         }
         case case_2 {
           leaf disable {
             description "Disable nexthop learning";
             type empty;
           }
         }
       }
     }
     container template-refresh-rate {
       presence "enable template-refresh-rate";
       description "Template refresh rate";
       uses apply-advanced;
       leaf packets {
         description "In number of packets";
         default "4800";
         type union {
           type string {
             pattern "<.*>|$.*";
           }
           type uint32 {
             range "1 .. 480000";
           }
         }
       }
       leaf seconds {
         description "In number of seconds";
         type union {
           type string {
             pattern "<.*>|$.*";
           }
           type uint32 {
             range "10 .. 600";
           }
         }
       }
     }
     container option-refresh-rate {
       presence "enable option-refresh-rate";
       description "Option template refresh rate";
       uses apply-advanced;
       leaf packets {
         description "In number of packets";
         default "4800";
         type union {
           type string {
             pattern "<.*>|$.*";
           }
           type uint32 {
             range "1 .. 480000";
           }
         }
       }
       leaf seconds {
         description "In number of seconds";
         type union {
           type string {
             pattern "<.*>|$.*";
           }
           type uint32 {
             range "10 .. 600";
           }
         }
       }
     }
     choice template-types {
       case case_1 {
         container ipv4-template {
           presence "enable ipv4-template";
           description "IPv4 template configuration";
         }
       }
       case case_2 {
         container ipv6-template {
           presence "enable ipv6-template";
           description "IPv6 template configuration";
         }
       }
       case case_3 {
         container vpls-template {
           presence "enable vpls-template";
           junos:must "(!((\".. flow-key flow-direction\" || \".. flow-key vlan-id\")))";
           junos:must-message "Flow key flow-direction/flow-key must not be configured with vpls template";
           description "VPLS template configuration";
           status deprecated;
         }
       }
       case case_4 {
         container bridge-template {
           presence "enable bridge-template";
           junos:must "(!((\".. flow-key flow-direction\" || \".. flow-key vlan-id\")))";
           junos:must-message "Flow key flow-direction/flow-key must not be configured with bridge template";
           description "BRIDGE template configuration";
         }
       }
       case case_5 {
         container mpls-template {
           presence "enable mpls-template";
           junos:must "((!(\".. flow-key\") || \".. tunnel-observation\"))";
           junos:must-message "Flow key must not be configured for mpls template without tunnel observation";
           description "MPLS template configuration";
           uses apply-advanced;
           leaf-list label-position {
             ordered-by user;
             description "One or more MPLS label positions";
             type union {
               type string {
                 pattern "<.*>|$.*";
               }
               type uint8 {
                 range "1 .. 8";
               }
             }
             max-elements 3;
           }
         }
       }
       case case_6 {
         container mpls-ipv4-template {
           presence "enable mpls-ipv4-template";
           description "MPLS IPV4 template configuration";
           status deprecated;
           uses apply-advanced;
           leaf-list label-position {
             ordered-by user;
             description "One or more MPLS label positions";
             type union {
               type string {
                 pattern "<.*>|$.*";
               }
               type uint8 {
                 range "1 .. 8";
               }
             }
             max-elements 3;
           }
         }
       }
     }
     container tunnel-observation {
       junos:must "((\".. ipv4-template\" || (\".. mpls-ipvx-template\" || \".. mpls-template\")))";
       junos:must-message "Tunnel observation must be configured only for ipv4,mpls and mpls-ipvx templates";
       description "Tunnel observation";
       uses apply-advanced;
       leaf mpls-over-udp {
         description "Mpls-over-udp";
         type empty;
       }
       leaf ipv4 {
         description "IPv4";
         junos:must "(\".. .. mpls-template\")";
         junos:must-message "Tunnel observation must be set to ipv4 only for mpls template";
         type empty;
       }
       leaf ipv6 {
         description "IPv6";
         junos:must "(\".. .. mpls-template\")";
         junos:must-message "Tunnel observation must be set to ipv6 only for mpls template";
         type empty;
       }
     }
     container flow-key {
       description "Flow key for the template. Valid ONLY for INLINE-JFLOW";
       uses apply-advanced;
       leaf flow-direction {
         description "Include flow direction";
         type empty;
       }
       leaf vlan-id {
         description "Include vlan ID";
         type empty;
       }
       leaf output-interface {
         description "Include output interface";
         junos:must "((\".. .. vpls-template\" || \".. .. bridge-template\"))";
         junos:must-message "Flow-key output interafce must be configured for bridge/vpls template";
         type empty;
       }
     }
   }
   grouping version9-template {
     description "One or more version 9 templates for flow monitoring";
     leaf name {
       description "Name of template";
       type string;
     }
     uses apply-advanced;
     leaf flow-active-timeout {
       description "Interval after which active flow is exported";
       default "60";
       type union {
         type string {
           pattern "<.*>|$.*";
         }
         type uint32 {
           range "10 .. 600";
         }
       }
     }
     leaf flow-inactive-timeout {
       description "Period of inactivity that marks a flow inactive";
       default "60";
       type union {
         type string {
           pattern "<.*>|$.*";
         }
         type uint32 {
           range "10 .. 600";
         }
       }
     }
     leaf template-id {
       description "Template id";
       type union {
         type string {
           pattern "<.*>|$.*";
         }
         type uint32 {
           range "1024 .. 65535";
         }
       }
     }
     leaf option-template-id {
       description "Options template id";
       type union {
         type string {
           pattern "<.*>|$.*";
         }
         type uint32 {
           range "1024 .. 65535";
         }
       }
     }
     leaf source-id {
       description "Source Id";
       default "0";
       type union {
         type string {
           pattern "<.*>|$.*";
         }
         type uint32 {
           range "0 .. 255";
         }
       }
     }
     container nexthop-learning {
       description "Nexthop learning parameter. Valid ONLY for INLINE-JFLOW";
       uses apply-advanced;
       choice enable-disable {
         case case_1 {
           leaf enable {
             description "Enable nexthop learning";
             type empty;
           }
         }
         case case_2 {
           leaf disable {
             description "Disable nexthop learning";
             type empty;
           }
         }
       }
     }
     container template-refresh-rate {
       presence "enable template-refresh-rate";
       description "Template refresh rate";
       uses apply-advanced;
       leaf packets {
         description "In number of packets";
         default "4800";
         type union {
           type string {
             pattern "<.*>|$.*";
           }
           type uint32 {
             range "1 .. 480000";
           }
         }
       }
       leaf seconds {
         description "In number of seconds";
         type union {
           type string {
             pattern "<.*>|$.*";
           }
           type uint32 {
             range "10 .. 600";
           }
         }
       }
     }
     container option-refresh-rate {
       presence "enable option-refresh-rate";
       description "Option template refresh rate";
       uses apply-advanced;
       leaf packets {
         description "In number of packets";
         default "4800";
         type union {
           type string {
             pattern "<.*>|$.*";
           }
           type uint32 {
             range "1 .. 480000";
           }
         }
       }
       leaf seconds {
         description "In number of seconds";
         type union {
           type string {
             pattern "<.*>|$.*";
           }
           type uint32 {
             range "10 .. 600";
           }
         }
       }
     }
     choice template-types {
       case case_1 {
         container mpls-ipv4-template {
           presence "enable mpls-ipv4-template";
           description "MPLS-IPv4 template configuration";
           status deprecated;
           uses apply-advanced;
           leaf-list label-position {
             ordered-by user;
             description "One or more MPLS label positions";
             type union {
               type string {
                 pattern "<.*>|$.*";
               }
               type uint8 {
                 range "1 .. 8";
               }
             }
             max-elements 3;
           }
         }
       }
       case case_2 {
         container mpls-template {
           presence "enable mpls-template";
           junos:must "((!(\".. flow-key\") || \".. tunnel-observation\"))";
           junos:must-message "Flow key must not be configured for mpls template without tunnel observation";
           description "MPLS template configuration";
           uses apply-advanced;
           leaf-list label-position {
             ordered-by user;
             description "One or more MPLS label positions";
             type union {
               type string {
                 pattern "<.*>|$.*";
               }
               type uint8 {
                 range "1 .. 8";
               }
             }
             max-elements 3;
           }
         }
       }
       case case_3 {
         container ipv6-template {
           presence "enable ipv6-template";
           description "IPv6 template configuration";
           uses apply-advanced;
           list export-extension {
             key name;
             ordered-by user;
             description "IPv6 template configuration with extra fields added to the template";
             leaf name {
               type enumeration {
                 enum "flow-dir" {
                   description "Applicationid field type";
                 }
                 enum "app-id" {
                   description "Applicationid field type";
                 }
               }
             }
             uses apply-advanced;
           }
           container nexthop-options {
             presence "enable nexthop-options";
             description "Additional information retrieved from nexthop";
             uses apply-advanced;
             choice nexthop-types {
               case case_1 {
                 container mpls {
                   presence "enable mpls";
                   description "MPLS information retrieved from nexthop";
                   uses apply-advanced;
                   leaf-list label-position {
                     ordered-by user;
                     description "One or more MPLS label positions";
                     type union {
                       type string {
                         pattern "<.*>|$.*";
                       }
                       type uint8 {
                         range "1 .. 3";
                       }
                     }
                     max-elements 3;
                   }
                 }
               }
             }
           }
         }
       }
       case case_4 {
         container peer-as-billing-template {
           presence "enable peer-as-billing-template";
           description "Peer AS billing template configuration";
         }
       }
       case case_5 {
         container ipv4-template {
           presence "enable ipv4-template";
           description "IPv4 template configuration";
           uses apply-advanced;
           list export-extension {
             key name;
             ordered-by user;
             description "IPv4 template configuration with extra fields added to the template";
             leaf name {
               type enumeration {
                 enum "flow-dir" {
                   description "Applicationid field type";
                 }
                 enum "app-id" {
                   description "Applicationid field type";
                 }
               }
             }
             uses apply-advanced;
           }
           container nexthop-options {
             presence "enable nexthop-options";
             description "Additional information retrieved from nexthop";
             uses apply-advanced;
             choice nexthop-types {
               case case_1 {
                 container mpls {
                   presence "enable mpls";
                   description "MPLS information retrieved from nexthop";
                   uses apply-advanced;
                   leaf-list label-position {
                     ordered-by user;
                     description "One or more MPLS label positions";
                     type union {
                       type string {
                         pattern "<.*>|$.*";
                       }
                       type uint8 {
                         range "1 .. 3";
                       }
                     }
                     max-elements 3;
                   }
                 }
               }
             }
           }
         }
       }
       case case_6 {
         container vpls-template {
           presence "enable vpls-template";
           junos:must "(!((\".. flow-key flow-direction\" || \".. flow-key vlan-id\")))";
           junos:must-message "Flow key flow-direction/flow-key must not be configured with vpls template";
           description "VPLS template configuration";
           status deprecated;
         }
       }
       case case_7 {
         container bridge-template {
           presence "enable bridge-template";
           junos:must "(!((\".. flow-key flow-direction\" || \".. flow-key vlan-id\")))";
           junos:must-message "Flow key flow-direction/flow-key must not be configured with bridge template";
           description "BRIDGE template configuration";
         }
       }
     }
     container tunnel-observation {
       junos:must "((\".. ipv4-template\" || (\".. mpls-ipvx-template\" || \".. mpls-template\")))";
       junos:must-message "Tunnel observation must be configured only for ipv4,mpls and mpls-ipvx templates";
       description "Tunnel observation";
       uses apply-advanced;
       leaf mpls-over-udp {
         description "Mpls-over-udp";
         type empty;
       }
       leaf ipv4 {
         description "IPv4";
         junos:must "(\".. .. mpls-template\")";
         junos:must-message "Tunnel observation must be set to ipv4 only for mpls template";
         type empty;
       }
       leaf ipv6 {
         description "IPv6";
         junos:must "(\".. .. mpls-template\")";
         junos:must-message "Tunnel observation must be set to ipv6 only for mpls template";
         type empty;
       }
     }
     container flow-key {
       description "Flow key for the template. Valid ONLY for INLINE-JFLOW";
       uses apply-advanced;
       leaf flow-direction {
         description "Include flow direction";
         type empty;
       }
       leaf vlan-id {
         description "Include vlan ID";
         type empty;
       }
       leaf output-interface {
         description "Include output interface";
         junos:must "((\".. .. vpls-template\" || \".. .. bridge-template\"))";
         junos:must-message "Flow-key output interafce must be configured for bridge/vpls template";
         type empty;
       }
     }
   }
   grouping virtual-interface-indications-object {
     description "Virtual interface indications";
     uses apply-advanced;
     container virtual-interface-up {
       uses pgcp-virtual-interface-up-object;
     }
     container virtual-interface-down {
       uses pgcp-virtual-interface-down-object;
     }
   }
   grouping pgcp-virtual-interface-down-object {
     description "Virtual interface down";
     uses apply-advanced;
     leaf graceful {
       description "Configure graceful service change";
       type enumeration {
         enum "none" {
           description "Suppress graceful-905 service change";
         }
         enum "graceful-905" {
           description "Termination taken out of service";
         }
       }
     }
     leaf administrative {
       description "Configure administrative service change";
       type enumeration {
         enum "forced-905" {
           description "Termination taken out of service";
         }
         enum "forced-906" {
           description "Loss of lower layer connectivity";
         }
         enum "none" {
           description "Suppress service change";
         }
       }
     }
     leaf failure {
       description "Configure failure service change";
       status deprecated;
       type enumeration {
         enum "forced-904" {
           description "Termination malfunctioning";
           status deprecated;
         }
         enum "forced-906" {
           description "Loss of lower layer connectivity";
           status deprecated;
         }
         enum "none" {
           description "Suppress service change";
           status deprecated;
         }
       }
     }
     leaf link-loss {
       description "Configure link-loss service change";
       status deprecated;
       type enumeration {
         enum "forced-906" {
           description "Loss of lower layer connectivity";
           status deprecated;
         }
         enum "none" {
           description "Suppress forced-906 service change";
           status deprecated;
         }
       }
     }
   }
   grouping pgcp-virtual-interface-up-object {
     description "Virtual interface up";
     uses apply-advanced;
     leaf warm {
       description "Configure warm-boot service change";
       type enumeration {
         enum "restart-900" {
           description "Service restored";
         }
         enum "none" {
           description "Suppress restart-900 service change";
         }
       }
     }
     leaf cancel-graceful {
       description "Configure cancel-graceful service change";
       type enumeration {
         enum "none" {
           description "Suppress restart-918 service change";
         }
         enum "restart-918" {
           description "Cancel graceful";
         }
       }
     }
   }
   grouping wildcard-address-type {
     description "Wildcard address and mask";
     leaf name {
       description "Numeric IPv4 wildcard address with in the form of a.d.d.r/netmask";
       type string {
         length "1 .. 63";
       }
     }
     uses apply-advanced;
   }
 }
