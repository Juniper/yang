/*
 * Copyright (c) 2019 Juniper Networks, Inc.
 * All rights reserved.
 */
 module junos-nfx-rpc-event-options {
   namespace "http://yang.juniper.net/junos-nfx/rpc/event-options";

   prefix event-options;

   import junos-common-ddl-extensions {
     prefix junos;
   }

   import junos-common-odl-extensions {
     prefix junos-odl;
   }

   import junos-common-types {
     prefix jt;
   }

   organization "Juniper Networks, Inc.";

   contact "yang-support@juniper.net";

   description "Junos RPC YANG module for event-options command(s)";

   revision 2019-01-01 {
     description "Junos: 18.4R2.7";
   }

   rpc get-event-scripts-policies {
     description "Show event policies configured through event-scripts";
     output {
       choice output_c {
         case output-tag {
           leaf output {
             type string;
           }
         }
         case multichassis-tag {
           anyxml multi-routing-engine-results;
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice vc-selector {
       case case_1 {
         leaf local {
           description "Local virtual chassis member";
           type empty;
         }
       }
     }
     choice tenant-selector {
       case case_1 {
         leaf tenant {
           description "Name of tenant, or 'all'";
           type string;
         }
       }
     }
     leaf all-members {
       description "All virtual chassis members";
       type empty;
     }
     leaf member {
       description "Specific virtual chassis member";
       type union {
         type string {
           pattern "<.*>|$.*";
         }
         type uint32;
       }
     }
   }
 }
