/*
 * Copyright (c) 2019 Juniper Networks, Inc.
 * All rights reserved.
 */
 module junos-qfx-rpc-dhcp {
   namespace "http://yang.juniper.net/junos-qfx/rpc/dhcp";

   prefix dhcp;

   import junos-common-types {
     prefix jt;
   }

   organization "Juniper Networks, Inc.";

   contact "yang-support@juniper.net";

   description "Junos RPC YANG module for dhcp command(s)";

   revision 2019-01-01 {
     description "Junos: 18.4R2.7";
   }

   rpc get-dhcp-service-statistics-information {
     description "Show DHCP service statistics";
     input {
       leaf level {
         default "summary";
         type enumeration {
           enum "summary" {
             description "Display summary information";
           }
         }
       }
       leaf interface {
         description "Name of interface";
         type union {
           type jt:interface-name;
           type string {
             pattern "<.*>|$.*";
           }
         }
       }
     }
     output {
       choice output_c {
         case output-tag {
           leaf output {
             type string;
           }
         }
         case actual-tag {
           anyxml dhcp-service-statistics-information;
         }
         case multichassis-tag {
           anyxml multi-routing-engine-results;
         }
       }
     }
   }
   rpc get-dhcp-relay-binding-information {
     description "Show DHCP relay client binding information";
     input {
       leaf level {
         default "brief";
         type enumeration {
           enum "brief" {
             description "Display brief information";
           }
           enum "detail" {
             description "Display detailed information";
           }
           enum "summary" {
             description "Display summary information";
           }
         }
       }
       choice show-choice {
         case address {
           leaf address {
             description "IP address/MAC address/Session Id of DHCP client binding";
             type string;
           }
         }
         case interfaces-wildcard {
           leaf interfaces-wildcard {
             description "Interfaces to show bindings on (can be '*' wildcard)";
             type string {
             }
           }
         }
         case interfaces-vlan {
           leaf interfaces-vlan {
             description "Interface VLAN-ID/SVLAN-ID on which to show bindings";
             type string {
             }
           }
         }
       }
       leaf routing-instance {
         description "Name of routing instance";
         type string;
       }
       leaf bridge-domain {
         description "Name of bridge domain";
         type string;
       }
       choice lsys-tenant {
         case logical-system {
           leaf logical-system {
             description "Name of logical system";
             type string {
             }
           }
         }
         case tenant {
           leaf tenant {
             description "Name of tenant";
             type string {
             }
           }
         }
       }
     }
     output {
       choice output_c {
         case output-tag {
           leaf output {
             type string;
           }
         }
         case actual-tag {
           anyxml dhcp-relay-binding-information;
         }
         case multichassis-tag {
           anyxml multi-routing-engine-results;
         }
       }
     }
   }
   rpc get-dhcp-relay-binding-ltv-information {
     description "Display lease time violated client bindings";
     input {
       leaf level {
         default "brief";
         type enumeration {
           enum "brief" {
             description "Display brief information";
           }
           enum "detail" {
             description "Display detailed information";
           }
           enum "summary" {
             description "Display summary information";
           }
         }
       }
       leaf routing-instance {
         description "Name of routing instance";
         type string;
       }
       leaf logical-system {
         description "Name of logical system";
         type string {
         }
       }
     }
     output {
       choice output_c {
         case output-tag {
           leaf output {
             type string;
           }
         }
         case actual-tag {
           anyxml dhcp-relay-binding-information;
         }
         case multichassis-tag {
           anyxml multi-routing-engine-results;
         }
       }
     }
   }
   rpc get-dhcp-relay-interface-bindings {
     description "Name of interface on which to show bindings";
     input {
       leaf interface-name {
         description "Name of interface";
         type string;
         mandatory true;
       }
       leaf level {
         default "brief";
         type enumeration {
           enum "brief" {
             description "Display brief information";
           }
           enum "detail" {
             description "Display detailed information";
           }
           enum "summary" {
             description "Display summary information";
           }
         }
       }
     }
     output {
       choice output_c {
         case output-tag {
           leaf output {
             type string;
           }
         }
         case actual-tag {
           anyxml dhcp-relay-binding-information;
         }
         case multichassis-tag {
           anyxml multi-routing-engine-results;
         }
       }
     }
   }
   rpc get-dhcp-relay-statistics-information {
     description "Show DHCP statistics";
     input {
       leaf level {
         default "summary";
         type enumeration {
           enum "summary" {
             description "Display summary information";
           }
         }
       }
       leaf routing-instance {
         description "Name of routing instance";
         type string;
       }
       leaf bridge-domain {
         description "Name of bridge domain";
         type string;
       }
       choice lsys-tenant {
         case logical-system {
           leaf logical-system {
             description "Name of logical system";
             type string {
             }
           }
         }
         case tenant {
           leaf tenant {
             description "Name of tenant";
             type string {
             }
           }
         }
       }
     }
     output {
       choice output_c {
         case output-tag {
           leaf output {
             type string;
           }
         }
         case actual-tag {
           anyxml dhcp-relay-statistics-information;
         }
         case multichassis-tag {
           anyxml multi-routing-engine-results;
         }
       }
     }
   }
   rpc get-dhcp-relay-leasequery-statistics {
     description "Show DHCP relay leasequery statistics";
     input {
       leaf level {
         default "summary";
         type enumeration {
           enum "summary" {
             description "Display summary information";
           }
         }
       }
       leaf routing-instance {
         description "Name of routing instance";
         type string;
       }
       leaf logical-system {
         description "Name of logical system";
         type string {
         }
       }
     }
     output {
       choice output_c {
         case output-tag {
           leaf output {
             type string;
           }
         }
         case actual-tag {
           anyxml dhcp-relay-leasequery-statistics;
         }
         case multichassis-tag {
           anyxml multi-routing-engine-results;
         }
       }
     }
   }
   rpc get-dhcp-relay-bulk-leasequery-conn-statistics {
     description "Show DHCP relay bulk leasequery statistics";
     input {
       leaf level {
         default "summary";
         type enumeration {
           enum "summary" {
             description "Display summary information";
           }
         }
       }
       leaf routing-instance {
         description "Name of routing instance";
         type string;
       }
       leaf logical-system {
         description "Name of logical system";
         type string {
         }
       }
     }
     output {
       choice output_c {
         case output-tag {
           leaf output {
             type string;
           }
         }
         case actual-tag {
           anyxml dhcp-relay-bulk-leasequery-conn-statistics;
         }
         case multichassis-tag {
           anyxml multi-routing-engine-results;
         }
       }
     }
   }
   rpc get-dhcp-relay-lockout-entries-information {
     description "Show DHCP lockout entries";
     input {
       leaf level {
         default "all";
         type enumeration {
           enum "all" {
             description "Display all the lockout entries";
           }
         }
       }
       leaf index {
         description "Display lockout information per index";
         type union {
           type uint32;
           type string {
             pattern "<.*>|$.*";
           }
         }
       }
       leaf routing-instance {
         description "Name of routing instance";
         type string;
       }
       leaf logical-system {
         description "Name of logical system";
         type string {
         }
       }
     }
     output {
       choice output_c {
         case output-tag {
           leaf output {
             type string;
           }
         }
         case actual-tag {
           anyxml dhcp-relay-lockout-entries-information;
         }
         case multichassis-tag {
           anyxml multi-routing-engine-results;
         }
       }
     }
   }
   rpc get-dhcp-server-binding-information {
     description "Show DHCP server client binding information";
     input {
       leaf level {
         default "brief";
         type enumeration {
           enum "brief" {
             description "Display brief information";
           }
           enum "detail" {
             description "Display detailed information";
           }
           enum "summary" {
             description "Display summary information";
           }
         }
       }
       choice show-choice {
         case address {
           leaf address {
             description "IP address/MAC address/Session Id of DHCP client binding";
             type string;
           }
         }
         case interfaces-wildcard {
           leaf interfaces-wildcard {
             description "Interfaces to show bindings on (can be '*' wildcard)";
             type string {
             }
           }
         }
         case interfaces-vlan {
           leaf interfaces-vlan {
             description "Interface VLAN-ID/SVLAN-ID on which to show bindings";
             type string {
             }
           }
         }
       }
       leaf routing-instance {
         description "Name of routing instance";
         type string;
       }
       choice lsys-tenant {
         case logical-system {
           leaf logical-system {
             description "Name of logical system";
             type string {
             }
           }
         }
         case tenant {
           leaf tenant {
             description "Name of tenant";
             type string {
             }
           }
         }
       }
     }
     output {
       choice output_c {
         case output-tag {
           leaf output {
             type string;
           }
         }
         case actual-tag {
           anyxml dhcp-server-binding-information;
         }
         case multichassis-tag {
           anyxml multi-routing-engine-results;
         }
       }
     }
   }
   rpc get-dhcp-server-binding-ltv-information {
     description "Display lease time violated client bindings";
     input {
       leaf level {
         default "brief";
         type enumeration {
           enum "brief" {
             description "Display brief information";
           }
           enum "detail" {
             description "Display detailed information";
           }
           enum "summary" {
             description "Display summary information";
           }
         }
       }
       leaf routing-instance {
         description "Name of routing instance";
         type string;
       }
       leaf logical-system {
         description "Name of logical system";
         type string {
         }
       }
     }
     output {
       choice output_c {
         case output-tag {
           leaf output {
             type string;
           }
         }
         case actual-tag {
           anyxml dhcp-server-binding-information;
         }
         case multichassis-tag {
           anyxml multi-routing-engine-results;
         }
       }
     }
   }
   rpc get-dhcp-relay-binding-interface {
     description "Name of interface on which to show bindings";
     input {
       leaf interface-name {
         description "Name of interface";
         type string;
         mandatory true;
       }
       leaf level {
         default "brief";
         type enumeration {
           enum "brief" {
             description "Display brief information";
           }
           enum "detail" {
             description "Display detailed information";
           }
           enum "summary" {
             description "Display summary information";
           }
         }
       }
     }
     output {
       choice output_c {
         case output-tag {
           leaf output {
             type string;
           }
         }
         case actual-tag {
           anyxml dhcp-relay-binding-information;
         }
         case multichassis-tag {
           anyxml multi-routing-engine-results;
         }
       }
     }
   }
   rpc get-dhcp-server-statistics-information {
     description "Show DHCP server statistics";
     input {
       leaf level {
         default "summary";
         type enumeration {
           enum "summary" {
             description "Display summary information";
           }
         }
       }
       leaf routing-instance {
         description "Name of routing instance";
         type string;
       }
       choice lsys-tenant {
         case logical-system {
           leaf logical-system {
             description "Name of logical system";
             type string {
             }
           }
         }
         case tenant {
           leaf tenant {
             description "Name of tenant";
             type string {
             }
           }
         }
       }
     }
     output {
       choice output_c {
         case output-tag {
           leaf output {
             type string;
           }
         }
         case actual-tag {
           anyxml dhcp-server-statistics-information;
         }
         case multichassis-tag {
           anyxml multi-routing-engine-results;
         }
       }
     }
   }
   rpc get-dhcp-server-bulk-leasequery-conn-statistics {
     description "Show DHCP server bulk leasequeery conn statistics";
     input {
       leaf routing-instance {
         description "Name of routing instance";
         type string;
       }
       leaf logical-system {
         description "Name of logical system";
         type string {
         }
       }
     }
     output {
       choice output_c {
         case output-tag {
           leaf output {
             type string;
           }
         }
         case actual-tag {
           anyxml dhcp-server-bulk-leasequery-conn-statistics;
         }
         case multichassis-tag {
           anyxml multi-routing-engine-results;
         }
       }
     }
   }
   rpc get-dhcp-server-lockout-entries-information {
     description "Show DHCP lockout entries";
     input {
       leaf level {
         default "all";
         type enumeration {
           enum "all" {
             description "Display all the lockout entries";
           }
         }
       }
       leaf index {
         description "Display lockout information per index";
         type union {
           type uint32;
           type string {
             pattern "<.*>|$.*";
           }
         }
       }
       leaf routing-instance {
         description "Name of routing instance";
         type string;
       }
       leaf logical-system {
         description "Name of logical system";
         type string {
         }
       }
     }
     output {
       choice output_c {
         case output-tag {
           leaf output {
             type string;
           }
         }
         case actual-tag {
           anyxml dhcp-server-lockout-entries-information;
         }
         case multichassis-tag {
           anyxml multi-routing-engine-results;
         }
       }
     }
   }
   rpc get-dhcp-client-binding-information {
     description "Show DHCP client binding information";
     input {
       leaf level {
         default "brief";
         type enumeration {
           enum "brief" {
             description "Display brief information";
           }
           enum "detail" {
             description "Display detailed information";
           }
           enum "summary" {
             description "Display summary information";
           }
         }
       }
       leaf routing-instance {
         description "Name of routing instance";
         type string;
       }
       choice lsys-tenant {
         case logical-system {
           leaf logical-system {
             description "Name of logical system";
             type string {
             }
           }
         }
         case tenant {
           leaf tenant {
             description "Name of tenant";
             type string {
             }
           }
         }
       }
     }
     output {
       choice output_c {
         case output-tag {
           leaf output {
             type string;
           }
         }
         case actual-tag {
           anyxml dhcp-client-binding-information;
         }
         case multichassis-tag {
           anyxml multi-routing-engine-results;
         }
       }
     }
   }
   rpc get-dhcp-client-binding-information-by-interface {
     description "Name of interface on which to show bindings";
     input {
       leaf interface-name {
         description "Name of interface";
         type string;
         mandatory true;
       }
       leaf level {
         default "brief";
         type enumeration {
           enum "brief" {
             description "Display brief information";
           }
           enum "detail" {
             description "Display detailed information";
           }
         }
       }
     }
     output {
       choice output_c {
         case output-tag {
           leaf output {
             type string;
           }
         }
         case actual-tag {
           anyxml dhcp-client-binding-information;
         }
         case multichassis-tag {
           anyxml multi-routing-engine-results;
         }
       }
     }
   }
   rpc get-dhcp-client-statistics-information {
     description "Show DHCP client statistics";
     input {
       leaf routing-instance {
         description "Name of routing instance";
         type string;
       }
       choice lsys-tenant {
         case logical-system {
           leaf logical-system {
             description "Name of logical system";
             type string {
             }
           }
         }
         case tenant {
           leaf tenant {
             description "Name of tenant";
             type string {
             }
           }
         }
       }
     }
     output {
       choice output_c {
         case output-tag {
           leaf output {
             type string;
           }
         }
         case actual-tag {
           anyxml dhcp-client-statistics-information;
         }
         case multichassis-tag {
           anyxml multi-routing-engine-results;
         }
       }
     }
   }
   rpc get-dhcp-proxy-client-binding-information {
     description "Show DHCP proxy-client binding information";
     input {
       leaf level {
         default "brief";
         type enumeration {
           enum "brief" {
             description "Display brief information";
           }
           enum "detail" {
             description "Display detailed information";
           }
           enum "summary" {
             description "Display summary information";
           }
         }
       }
       leaf routing-instance {
         description "Name of routing instance";
         type string;
       }
       leaf logical-system {
         description "Name of logical system";
         type string {
         }
       }
     }
     output {
       choice output_c {
         case output-tag {
           leaf output {
             type string;
           }
         }
         case actual-tag {
           anyxml dhcp-client-binding-information;
         }
         case multichassis-tag {
           anyxml multi-routing-engine-results;
         }
       }
     }
   }
   rpc get-proxy-dhcp-client-statistics-information {
     description "Show DHCP proxy-client statistics";
     input {
       leaf routing-instance {
         description "Name of routing instance";
         type string;
       }
       leaf logical-system {
         description "Name of logical system";
         type string {
         }
       }
     }
     output {
       choice output_c {
         case output-tag {
           leaf output {
             type string;
           }
         }
         case actual-tag {
           anyxml dhcp-proxy-client-statistics-information;
         }
         case multichassis-tag {
           anyxml multi-routing-engine-results;
         }
       }
     }
   }
   rpc get-dhcp-proxy-client-profile-servers-info {
     description "Show DHCP-Proxy server list of profile";
     input {
       leaf logical-system {
         description "Name of logical system";
         type string;
         mandatory true;
       }
       leaf routing-instance {
         description "Name of routing instance";
         type string;
         mandatory true;
       }
       leaf profile-name {
         description "Name of profile name";
         type string;
         mandatory true;
       }
     }
     output {
       choice output_c {
         case output-tag {
           leaf output {
             type string;
           }
         }
         case actual-tag {
           anyxml dhcp-proxy-client-profile-servers-information;
         }
         case multichassis-tag {
           anyxml multi-routing-engine-results;
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member";
           type union {
             type string {
               pattern "<.*>|$.*";
             }
             type uint32;
           }
         }
       }
     }
   }
 }
