/*
 * Copyright (c) 2022 Juniper Networks, Inc.
 * All rights reserved.
 */
 module junos-es-conf-smtp {
   namespace "http://yang.juniper.net/junos-es/conf/smtp";

   prefix jc-smtp;

   import junos-common-ddl-extensions {
     prefix junos;
     revision-date 2022-01-01;
   }

   import junos-common-types {
     prefix jt;
     revision-date 2022-01-01;
   }

   import junos-es-conf-root {
     prefix jc;
     revision-date 2022-01-01;
   }

   organization "Juniper Networks, Inc.";

   contact "yang-support@juniper.net";

   description "Junos smtp configuration module";

   revision 2022-01-01 {
     description "Junos: 22.2R1.12";
   }

   augment /jc:configuration {
     uses smtp-group;
   }
   augment /jc:configuration/jc:groups {
     uses smtp-group;
   }
   grouping smtp-group {
     container smtp {
       description "Simple Mail Transfer Protocol service configuration";
       uses apply-advanced;
       container primary-server {
         description "SMTP primary server configuration";
         uses apply-advanced;
         leaf address {
           description "SMTP server's IPv4 address";
           type jt:ipv4addr;
         }
         choice authentication {
           case case_1 {
             list login {
               key name;
               ordered-by user;
               description "Configure a mail sender account to the server";
               uses login-object;
             }
           }
         }
       }
       container secondary-server {
         description "SMTP secondary server configuration";
         uses apply-advanced;
         leaf address {
           description "SMTP server's IPv4 address";
           type jt:ipv4addr;
         }
         choice authentication {
           case case_1 {
             list login {
               key name;
               ordered-by user;
               description "Configure a mail sender account to the server";
               uses login-object;
             }
           }
         }
       }
       container traceoptions {
         description "Trace options for SMTP client service";
         uses apply-advanced;
         list flag {
           key name;
           ordered-by user;
           description "Tracing parameters";
           leaf name {
             type enumeration {
               enum "IPC" {
                 description "Trace inter-processs communication";
               }
               enum "protocol-exchange" {
                 description "Trace SMTP protocol exchanges";
               }
               enum "configuration" {
                 description "Trace configuration event";
               }
               enum "send-request" {
                 description "Trace send mail request event";
               }
               enum "all" {
                 description "Trace everything";
               }
             }
           }
         }
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping login-object {
     description "Mail login parameters";
     leaf name {
       description "Default sender email address in user@foo.com format";
       type string {
         junos:posix-pattern "^[A-Za-z.0-9_@-]{1,40}$";
         junos:pattern-message "Must be in the form user@foo.com consisting up to 40 letters, numbers, periods underscores and dashes";
       }
     }
     uses apply-advanced;
     leaf password {
       description "Default sender password for user authentication";
       type jt:unreadable;
     }
   }
   grouping macro-data-type {
     leaf name {
       description "Keyword part of the keyword-value pair";
       type string;
     }
     leaf value {
       description "Value part of the keyword-value pair";
       type string;
     }
   }
 }
