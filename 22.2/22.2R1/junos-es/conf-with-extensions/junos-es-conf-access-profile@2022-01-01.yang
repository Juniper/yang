/*
 * Copyright (c) 2022 Juniper Networks, Inc.
 * All rights reserved.
 */
 module junos-es-conf-access-profile {
   namespace "http://yang.juniper.net/junos-es/conf/access-profile";

   prefix jc-access-profile;

   import junos-common-ddl-extensions {
     prefix junos;
     revision-date 2022-01-01;
   }

   import junos-common-types {
     prefix jt;
     revision-date 2022-01-01;
   }

   import junos-es-conf-root {
     prefix jc;
     revision-date 2022-01-01;
   }

   organization "Juniper Networks, Inc.";

   contact "yang-support@juniper.net";

   description "Junos access-profile configuration module";

   revision 2022-01-01 {
     description "Junos: 22.2R1.12";
   }

   augment /jc:configuration {
     uses access-profile-group;
   }
   augment /jc:configuration/jc:groups {
     uses access-profile-group;
   }
   grouping access-profile-group {
     container access-profile {
       description "Access profile for this instance";
       leaf access-profile-name {
         description "Profile name";
         junos:must "(\"access profile $$\")";
         junos:must-message "Access-profile must be defined in the [edit access profile] hierarchy";
         type string;
       }
     }
   }
 }
