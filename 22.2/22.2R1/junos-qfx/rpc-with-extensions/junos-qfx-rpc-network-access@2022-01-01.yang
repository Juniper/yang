/*
 * Copyright (c) 2022 Juniper Networks, Inc.
 * All rights reserved.
 */
 module junos-qfx-rpc-network-access {
   namespace "http://yang.juniper.net/junos-qfx/rpc/network-access";

   prefix network-access;

   import junos-common-ddl-extensions {
     prefix junos;
     revision-date 2022-01-01;
   }

   import junos-common-odl-extensions {
     prefix junos-odl;
     revision-date 2022-01-01;
   }

   import junos-common-types {
     prefix jt;
     revision-date 2022-01-01;
   }

   organization "Juniper Networks, Inc.";

   contact "yang-support@juniper.net";

   description "Junos RPC YANG module for network-access command(s)";

   revision 2022-01-01 {
     description "Junos: 22.2R1.12";
   }

   rpc get-authentication-pending-table {
     description "Show pending authentication requests";
     input {
       uses command-forwarding;
       choice filter {
         case detail {
           leaf get-authentication-pending-table-detailed {
             description "Show the detailed information";
             type empty;
           }
         }
         case index {
           leaf get-authentication-pending-table-specific {
             description "Show detail information for a specific request";
             type union {
               type string {
                 pattern "<.*>|$.*";
               }
               type uint64 {
                 range "1 .. 18446744073709551615";
               }
             }
           }
         }
       }
     }
     output {
       choice output_c {
         case output-tag {
           leaf output {
             type string;
           }
         }
         case actual-tag {
           anyxml auth-pending-table;
         }
         case multichassis-tag {
           anyxml multi-routing-engine-results;
         }
       }
     }
   }
   rpc get-authentication-statistics {
     description "Show authentication statistics";
     output {
       choice output_c {
         case output-tag {
           leaf output {
             type string;
           }
         }
         case actual-tag {
           anyxml auth-statistics;
         }
         case multichassis-tag {
           anyxml multi-routing-engine-results;
         }
       }
     }
   }
   rpc get-domain-map-statistics {
     description "Domain-map module statistics";
     output {
       choice output_c {
         case output-tag {
           leaf output {
             type string;
           }
         }
         case actual-tag {
           anyxml domain-map-statistics;
         }
         case multichassis-tag {
           anyxml multi-routing-engine-results;
         }
       }
     }
   }
   rpc get-aaa-subscriber-table {
     description "List subscriber specific command options";
     input {
       uses command-forwarding;
       leaf username {
         description "Show details for this subscriber's session entry";
         type string;
       }
       leaf routing-instance {
         description "Name of routing instance";
         type string;
       }
       choice lsys-tenant {
       }
       choice daemon-select {
         case logical-system {
         }
       }
     }
     output {
       choice output_c {
         case output-tag {
           leaf output {
             type string;
           }
         }
         case actual-tag {
           anyxml aaa-subscriber-table;
         }
         case multichassis-tag {
           anyxml multi-routing-engine-results;
         }
       }
     }
   }
   rpc get-aaa-subscriber-by-session-id {
     description "Session id";
     input {
       leaf id {
         description "Session id";
         type union {
           type string {
             pattern "<.*>|$.*";
           }
           type uint64 {
             range "1 .. 18446744073709551615";
           }
         }
         mandatory true;
       }
       leaf level {
         default "brief";
         type enumeration {
           enum "brief" {
             description "Show brief output";
           }
           enum "detail" {
             description "Show detailed output";
           }
         }
       }
       choice lsys-tenant {
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc get-aaa-subscriber-statistics {
     description "Statistics on subscriber events";
     input {
       uses command-forwarding;
       leaf username {
         description "Show statistics for this subscriber's session entry";
         type string;
         mandatory true;
       }
       choice lsys-tenant {
       }
       choice daemon-select {
         case logical-system {
         }
       }
     }
     output {
       choice output_c {
         case output-tag {
           leaf output {
             type string;
           }
         }
         case actual-tag {
           anyxml aaa-subscriber-statistics;
         }
         case multichassis-tag {
           anyxml multi-routing-engine-results;
         }
       }
     }
   }
   rpc get-aaa-module-statistics {
     description "(Re)authentication, authorization and accounting (AAA) module statistics";
     input {
       uses command-forwarding;
       leaf statistics-type {
         type enumeration {
           enum "authentication" {
             description "Authentication statistics";
           }
           enum "accounting" {
             description "Accounting statistics";
           }
           enum "dynamic-requests" {
             description "Dynamic requests statistics";
           }
           enum "re-authentication" {
             description "Re-authentication statistics";
           }
           enum "preauthentication" {
             description "Preauthentication statistics";
           }
           enum "subscribers" {
             description "Subscriber statistics";
           }
           enum "radius" {
             description "RADIUS statistics";
           }
           enum "pending-accounting-stops" {
             description "Pending Accounting stop statistics";
           }
         }
         mandatory true;
       }
       leaf detail {
         description "Display detailed output";
         type empty;
       }
     }
     output {
       choice output_c {
         case output-tag {
           leaf output {
             type string;
           }
         }
         case actual-tag {
           anyxml aaa-module-statistics;
         }
         case multichassis-tag {
           anyxml multi-routing-engine-results;
         }
       }
     }
   }
   rpc get-session-limit-per-username {
     description "Show session limit per username related information";
     input {
       leaf level {
         default "summary";
         type enumeration {
           enum "summary" {
             description "Show summary output";
           }
           enum "brief" {
             description "Show brief output";
           }
           enum "detail" {
             description "Show detailed output";
           }
         }
       }
     }
     output {
       choice output_c {
         case output-tag {
           leaf output {
             type string;
           }
         }
         case actual-tag {
           anyxml aaa-session-limit-per-username-info;
         }
         case multichassis-tag {
           anyxml multi-routing-engine-results;
         }
       }
     }
   }
   rpc get-address-assignment-pool-statistics {
     description "Show pool information based on pool name";
     input {
       leaf get-address-assignment-pool-table-specific {
         description "Show information for a specific pool";
         type string;
         mandatory true;
       }
       leaf routing-instance {
         description "Name of routing instance";
         type string;
       }
       choice lsys-tenant {
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case actual-tag {
           anyxml aaa-module-statistics;
         }
         case multichassis-tag {
           anyxml multi-routing-engine-results;
         }
       }
     }
   }
   rpc get-address-assignment-client-statistics {
     description "Show pool information based on client";
     input {
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case actual-tag {
           anyxml aaa-module-statistics;
         }
         case multichassis-tag {
           anyxml multi-routing-engine-results;
         }
       }
     }
   }
   rpc get-reconciliation-statistics {
     description "Reconciliation statistics";
     output {
       choice output_c {
         case output-tag {
           leaf output {
             type string;
           }
         }
         case actual-tag {
           anyxml aaa-module-reconciliation;
         }
         case multichassis-tag {
           anyxml multi-routing-engine-results;
         }
       }
     }
   }
   rpc get-aaa-terminate-code {
     description "Show terminate-code information";
     input {
       uses command-forwarding;
       leaf verbosity_level {
         default "summary";
         type enumeration {
           enum "summary" {
             description "Display summary output(default)";
           }
           enum "brief" {
             description "Display brief output";
           }
           enum "detail" {
             description "Display detailed output";
           }
         }
       }
     }
     output {
       choice output_c {
         case output-tag {
           leaf output {
             type string;
           }
         }
         case actual-tag {
           anyxml aaa-terminate-code;
         }
         case multichassis-tag {
           anyxml multi-routing-engine-results;
         }
       }
     }
   }
   rpc get-aaa-terminate-code-aaa {
     description "Limit display to AAA terminate codes";
     input {
       uses command-forwarding;
       leaf verbosity_level {
         default "summary";
         type enumeration {
           enum "summary" {
             description "Display summary output(default)";
           }
           enum "brief" {
             description "Display brief output";
           }
           enum "detail" {
             description "Display detailed output";
           }
         }
       }
     }
     output {
       choice output_c {
         case output-tag {
           leaf output {
             type string;
           }
         }
         case actual-tag {
           anyxml aaa-terminate-code-aaa;
         }
         case multichassis-tag {
           anyxml multi-routing-engine-results;
         }
       }
     }
   }
   rpc get-aaa-terminate-code-dhcp {
     description "Limit display to DHCP terminate codes";
     input {
       uses command-forwarding;
       leaf verbosity_level {
         default "summary";
         type enumeration {
           enum "summary" {
             description "Display summary output(default)";
           }
           enum "brief" {
             description "Display brief output";
           }
           enum "detail" {
             description "Display detailed output";
           }
         }
       }
     }
     output {
       choice output_c {
         case output-tag {
           leaf output {
             type string;
           }
         }
         case actual-tag {
           anyxml aaa-terminate-code-dhcp;
         }
         case multichassis-tag {
           anyxml multi-routing-engine-results;
         }
       }
     }
   }
   rpc get-aaa-terminate-code-reverse {
     description "Show reverse terminate-code information";
     input {
       uses command-forwarding;
       leaf verbosity_level {
         default "summary";
         type enumeration {
           enum "summary" {
             description "Display summary output(default)";
           }
           enum "brief" {
             description "Display brief output";
           }
           enum "detail" {
             description "Display detailed output";
           }
         }
       }
     }
     output {
       choice output_c {
         case output-tag {
           leaf output {
             type string;
           }
         }
         case actual-tag {
           anyxml aaa-terminate-code-reverss;
         }
         case multichassis-tag {
           anyxml multi-routing-engine-results;
         }
       }
     }
   }
   rpc get-aaa-terminate-code-reverse-aaa {
     description "Limit display to AAA terminate codes";
     input {
       uses command-forwarding;
       leaf verbosity_level {
         default "summary";
         type enumeration {
           enum "summary" {
             description "Display summary output(default)";
           }
           enum "brief" {
             description "Display brief output";
           }
           enum "detail" {
             description "Display detailed output";
           }
         }
       }
     }
     output {
       choice output_c {
         case output-tag {
           leaf output {
             type string;
           }
         }
         case actual-tag {
           anyxml aaa-terminate-code-reverse-aaa;
         }
         case multichassis-tag {
           anyxml multi-routing-engine-results;
         }
       }
     }
   }
   rpc get-aaa-terminate-code-reverse-dhcp {
     description "Limit display to DHCP terminate codes";
     input {
       uses command-forwarding;
       leaf verbosity_level {
         default "summary";
         type enumeration {
           enum "summary" {
             description "Display summary output(default)";
           }
           enum "brief" {
             description "Display brief output";
           }
           enum "detail" {
             description "Display detailed output";
           }
         }
       }
     }
     output {
       choice output_c {
         case output-tag {
           leaf output {
             type string;
           }
         }
         case actual-tag {
           anyxml aaa-terminate-code-reverse-dhcp;
         }
         case multichassis-tag {
           anyxml multi-routing-engine-results;
         }
       }
     }
   }
   rpc get-aaa-accounting-status {
     description "Statistics of RADIUS servers";
     output {
       choice output_c {
         case output-tag {
           leaf output {
             type string;
           }
         }
         case actual-tag {
           anyxml aaa-accounting-status;
         }
         case multichassis-tag {
           anyxml multi-routing-engine-results;
         }
       }
     }
   }
   rpc get-radius-servers-table {
     description "Show RADIUS servers information";
     input {
       uses command-forwarding;
       leaf verbosity_level {
         default "brief";
         type enumeration {
           enum "brief" {
             description "Display brief output";
           }
           enum "detail" {
             description "Display detailed output";
           }
         }
       }
     }
     output {
       choice output_c {
         case output-tag {
           leaf output {
             type string;
           }
         }
         case actual-tag {
           anyxml aaa-module-radius-servers-information;
         }
         case multichassis-tag {
           anyxml multi-routing-engine-results;
         }
       }
     }
   }
   rpc get-address-assignment-pool-table {
     description "Show pool information";
     input {
       uses command-forwarding;
       leaf get-address-assignment-pool-table-specific {
         description "Show information for a specific pool";
         type string;
         mandatory true;
       }
       leaf routing-instance {
         description "Name of routing instance";
         type string;
       }
       choice lsys-tenant {
       }
       choice daemon-select {
         case logical-system {
         }
       }
     }
     output {
       choice output_c {
         case output-tag {
           leaf output {
             type string;
           }
         }
         case actual-tag {
           anyxml address-assignment-pool-table;
         }
         case multichassis-tag {
           anyxml multi-routing-engine-results;
         }
       }
     }
   }
   rpc get-address-assignment-preserved-table {
     description "Show preserved addresses";
     output {
       choice output_c {
         case output-tag {
           leaf output {
             type string;
           }
         }
         case actual-tag {
           anyxml address-assignment-preserved-table;
         }
         case multichassis-tag {
           anyxml multi-routing-engine-results;
         }
       }
     }
   }
   rpc get-authd-apm-status {
     description "Show APM connection/alarm status information";
     output {
       choice output_c {
         case output-tag {
           leaf output {
             type string;
           }
         }
         case actual-tag {
           anyxml authd-apm-status;
         }
         case multichassis-tag {
           anyxml multi-routing-engine-results;
         }
       }
     }
   }
   rpc get-authd-apm-domain-information {
     description "Show address-pool-manager domain status";
     input {
       leaf get-authd-apm-domain-name {
         description "Show detailed APM domain statistics";
         type string;
       }
       leaf get-authd-apm-domain-routing-instance {
         description "Name of routing instance";
         type string;
       }
     }
     output {
       choice output_c {
         case output-tag {
           leaf output {
             type string;
           }
         }
         case actual-tag {
           anyxml authd-apm-domain-information;
         }
         case multichassis-tag {
           anyxml multi-routing-engine-results;
         }
       }
     }
   }
   rpc get-authd-apm-domain-state {
     description "Show address-pool-manager domain state";
     input {
       leaf get-apm-domain-state-routing-instance {
         description "Name of routing instance";
         type string;
       }
     }
     output {
       choice output_c {
         case output-tag {
           leaf output {
             type string;
           }
         }
         case actual-tag {
           anyxml authd-apm-domain-state;
         }
         case multichassis-tag {
           anyxml multi-routing-engine-results;
         }
       }
     }
   }
   rpc node-secret-file-table {
     description "Show SecurID server's node secret file path";
     output {
       choice output_c {
         case output-tag {
           leaf output {
             type string;
           }
         }
         case actual-tag {
           anyxml node-secret-file-table;
         }
         case multichassis-tag {
           anyxml multi-routing-engine-results;
         }
       }
     }
   }
   rpc get-jsrc-counters {
     description "Jsrc module statistics";
     output {
       choice output_c {
         case output-tag {
           leaf output {
             type string;
           }
         }
         case actual-tag {
           anyxml jsrc-counters;
         }
         case multichassis-tag {
           anyxml multi-routing-engine-results;
         }
       }
     }
   }
   rpc get-gx-plus-state-information {
     description "Show gx-plus state information";
     output {
       choice output_c {
         case output-tag {
           leaf output {
             type string;
           }
         }
         case actual-tag {
           anyxml gx-plus-state-information;
         }
         case multichassis-tag {
           anyxml multi-routing-engine-results;
         }
       }
     }
   }
   rpc get-gx-plus-sync-state-information {
     description "Show gx-plus sync-state information";
     output {
       choice output_c {
         case output-tag {
           leaf output {
             type string;
           }
         }
         case actual-tag {
           anyxml gx-plus-sync-state-information;
         }
         case multichassis-tag {
           anyxml multi-routing-engine-results;
         }
       }
     }
   }
   rpc get-gx-plus-statistics-information {
     description "Show gx-plus statistics information";
     input {
       uses command-forwarding;
       leaf verbosity_level {
         default "brief";
         type enumeration {
           enum "brief" {
             description "Show brief output (deafault)";
           }
           enum "detail" {
             description "Show detailed output";
           }
           enum "extensive" {
             description "Show extensive output";
           }
         }
       }
     }
     output {
       choice output_c {
         case output-tag {
           leaf output {
             type string;
           }
         }
         case actual-tag {
           anyxml gx-plus-statistics-information;
         }
         case multichassis-tag {
           anyxml multi-routing-engine-results;
         }
       }
     }
   }
   rpc get-nasreq-counters {
     description "Nasreq module statistics";
     output {
       choice output_c {
         case output-tag {
           leaf output {
             type string;
           }
         }
         case actual-tag {
           anyxml nasreq-counters;
         }
         case multichassis-tag {
           anyxml multi-routing-engine-results;
         }
       }
     }
   }
   rpc get-pcrf-state-information {
     description "Show pcrf state information";
     output {
       choice output_c {
         case output-tag {
           leaf output {
             type string;
           }
         }
         case actual-tag {
           anyxml pcrf-state-information;
         }
         case multichassis-tag {
           anyxml multi-routing-engine-results;
         }
       }
     }
   }
   rpc get-pcrf-statistics-information {
     description "Show pcrf statistics information";
     input {
       uses command-forwarding;
       leaf verbosity_level {
         default "brief";
         type enumeration {
           enum "brief" {
             description "Show brief output (deafault)";
           }
           enum "detail" {
             description "Show detailed output";
           }
           enum "extensive" {
             description "Show extensive output";
           }
         }
       }
     }
     output {
       choice output_c {
         case output-tag {
           leaf output {
             type string;
           }
         }
         case actual-tag {
           anyxml pcrf-statistics-information;
         }
         case multichassis-tag {
           anyxml multi-routing-engine-results;
         }
       }
     }
   }
   rpc get-ocs-state-information {
     description "Show ocs state information";
     output {
       choice output_c {
         case output-tag {
           leaf output {
             type string;
           }
         }
         case actual-tag {
           anyxml ocs-state-information;
         }
         case multichassis-tag {
           anyxml multi-routing-engine-results;
         }
       }
     }
   }
   rpc get-ocs-statistics-information {
     description "Show ocs statistics information";
     input {
       uses command-forwarding;
       leaf verbosity_level {
         default "brief";
         type enumeration {
           enum "brief" {
             description "Show brief output (deafault)";
           }
           enum "detail" {
             description "Show detailed output";
           }
           enum "extensive" {
             description "Show extensive output";
           }
         }
       }
     }
     output {
       choice output_c {
         case output-tag {
           leaf output {
             type string;
           }
         }
         case actual-tag {
           anyxml ocs-statistics-information;
         }
         case multichassis-tag {
           anyxml multi-routing-engine-results;
         }
       }
     }
   }
   rpc get-radsec-state-information {
     description "Show radsec state information";
     input {
       uses command-forwarding;
       leaf radsec-state-destination {
         description "Destination to show";
         type union {
           type uint32;
           type string {
             pattern "<.*>|$.*";
           }
         }
       }
     }
     output {
       choice output_c {
         case output-tag {
           leaf output {
             type string;
           }
         }
         case actual-tag {
           anyxml radsec-state-information;
         }
         case multichassis-tag {
           anyxml multi-routing-engine-results;
         }
       }
     }
   }
   rpc get-radsec-statistics-information {
     description "Show radsec statistics information";
     input {
       uses command-forwarding;
       leaf verbosity_level {
         default "brief";
         type enumeration {
           enum "brief" {
             description "Show brief output (deafault)";
           }
           enum "detail" {
             description "Show detailed output";
           }
           enum "extensive" {
             description "Show extensive output";
           }
         }
       }
       leaf radsec-statistics-destination {
         description "Destination to show";
         type union {
           type uint32;
           type string {
             pattern "<.*>|$.*";
           }
         }
       }
     }
     output {
       choice output_c {
         case output-tag {
           leaf output {
             type string;
           }
         }
         case actual-tag {
           anyxml rasec-statistics-information;
         }
         case multichassis-tag {
           anyxml multi-routing-engine-results;
         }
       }
     }
   }
   rpc get-local-cert-state-information {
     description "Show local certificate state information";
     output {
       choice output_c {
         case output-tag {
           leaf output {
             type string;
           }
         }
         case actual-tag {
           anyxml local-cert-state-information;
         }
         case multichassis-tag {
           anyxml multi-routing-engine-results;
         }
       }
     }
   }
   rpc get-local-cert-statistics-information {
     description "Show local certificate statistics information";
     input {
       uses command-forwarding;
       leaf verbosity_level {
         default "brief";
         type enumeration {
           enum "brief" {
             description "Show brief output (deafault)";
           }
           enum "detail" {
             description "Show detailed output";
           }
           enum "extensive" {
             description "Show extensive output";
           }
         }
       }
     }
     output {
       choice output_c {
         case output-tag {
           leaf output {
             type string;
           }
         }
         case actual-tag {
           anyxml local-cert-statistics-information;
         }
         case multichassis-tag {
           anyxml multi-routing-engine-results;
         }
       }
     }
   }
   rpc get-s6a-state-information {
     description "Show s6a state information";
     output {
       choice output_c {
         case output-tag {
           leaf output {
             type string;
           }
         }
         case actual-tag {
           anyxml s6a-state-information;
         }
         case multichassis-tag {
           anyxml multi-routing-engine-results;
         }
       }
     }
   }
   rpc get-s6a-statistics-information {
     description "Show s6a statistics information";
     input {
       uses command-forwarding;
       leaf verbosity_level {
         default "brief";
         type enumeration {
           enum "brief" {
             description "Show brief output (deafault)";
           }
           enum "detail" {
             description "Show detailed output";
           }
           enum "extensive" {
             description "Show extensive output";
           }
         }
       }
     }
     output {
       choice output_c {
         case output-tag {
           leaf output {
             type string;
           }
         }
         case actual-tag {
           anyxml s6a-statistics-information;
         }
         case multichassis-tag {
           anyxml multi-routing-engine-results;
         }
       }
     }
   }
   rpc get-nas-5g-state-information {
     description "Show nas-5g state information";
     output {
       choice output_c {
         case output-tag {
           leaf output {
             type string;
           }
         }
         case actual-tag {
           anyxml nas-5g-state-information;
         }
         case multichassis-tag {
           anyxml multi-routing-engine-results;
         }
       }
     }
   }
   rpc get-nas-5g-counters {
     description "Show nas-5g statistics information";
     output {
       choice output_c {
         case output-tag {
           leaf output {
             type string;
           }
         }
         case actual-tag {
           anyxml nas-5g-counters;
         }
         case multichassis-tag {
           anyxml multi-routing-engine-results;
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member";
           type union {
             type string {
               pattern "<.*>|$.*";
             }
             type uint32;
           }
         }
       }
     }
   }
 }
