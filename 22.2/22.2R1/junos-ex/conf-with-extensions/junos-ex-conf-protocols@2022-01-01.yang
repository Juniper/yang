/*
 * Copyright (c) 2022 Juniper Networks, Inc.
 * All rights reserved.
 */
 module junos-ex-conf-protocols {
   namespace "http://yang.juniper.net/junos-ex/conf/protocols";

   prefix jc-protocols;

   import junos-common-ddl-extensions {
     prefix junos;
     revision-date 2022-01-01;
   }

   import junos-common-types {
     prefix jt;
     revision-date 2022-01-01;
   }

   import junos-ex-conf-root {
     prefix jc;
     revision-date 2022-01-01;
   }

   organization "Juniper Networks, Inc.";

   contact "yang-support@juniper.net";

   description "Junos protocols configuration module";

   revision 2022-01-01 {
     description "Junos: 22.2R1.12";
   }

   augment /jc:configuration {
     uses protocols-group;
   }
   augment /jc:configuration/jc:groups {
     uses protocols-group;
   }
   grouping protocols-group {
     container protocols {
       description "Routing protocol configuration";
       uses juniper-protocols;
     }
   }
   grouping juniper-protocols {
     uses apply-advanced;
     container router-advertisement {
       description "IPv6 router advertisement options";
       uses apply-advanced;
       container traceoptions {
         description "Trace options for router advertisement";
         uses apply-advanced;
         container file {
           description "Trace file options";
           leaf filename {
             description "Name of file in which to write trace information";
             type string {
               length "1 .. 1024";
               junos:posix-pattern "![/ %]";
               junos:pattern-message "Must not contain '/', % or a space";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
         }
       }
       list interface {
         key name;
         ordered-by user;
         description "Interfaces on which to configure router advertisement";
         leaf name {
           type string;
         }
         uses apply-advanced;
         leaf preference {
           description "Set the Preference for Router Selection";
           type enumeration {
             enum "medium" {
               description "Medium / (Default)";
             }
             enum "high" {
               description "High";
             }
             enum "low" {
               description "Low";
             }
           }
         }
         leaf max-advertisement-interval {
           description "Maximum advertisement interval";
           units "seconds";
           type union {
             type string {
               pattern "<.*>|$.*";
             }
             type uint32 {
               range "4 .. 1800";
             }
           }
         }
         leaf min-advertisement-interval {
           description "Minimum advertisement interval";
           units "seconds";
           type union {
             type string {
               pattern "<.*>|$.*";
             }
             type uint32 {
               range "3 .. 1350";
             }
           }
         }
         choice managed-configuration-choice {
           leaf managed-configuration {
             description "Set managed address configuration";
             type empty;
           }
           leaf no-managed-configuration {
             description "Don't set managed address configuration";
             type empty;
           }
         }
         choice other-stateful-configuration-choice {
           leaf other-stateful-configuration {
             description "Set other stateful configuration";
             type empty;
           }
           leaf no-other-stateful-configuration {
             description "Don't set other stateful configuration";
             type empty;
           }
         }
         choice link-mtu-choice {
           leaf link-mtu {
             description "Link MTU";
             type empty;
           }
           leaf no-link-mtu {
             description "Don't link MTU";
             type empty;
           }
         }
         leaf solicit-router-advertisement-unicast {
           description "Enbale solicited router advertisement as unicast";
           type empty;
         }
         leaf reachable-time {
           description "Reachable time";
           units "milliseconds";
           type union {
             type string {
               pattern "<.*>|$.*";
             }
             type uint32 {
               range "0 .. 3600000";
             }
           }
         }
         leaf retransmit-timer {
           description "Retransmit timer";
           units "milliseconds";
           type union {
             type string {
               pattern "<.*>|$.*";
             }
             type uint32 {
               range "0 .. 4294967295";
             }
           }
         }
         leaf virtual-router-only {
           description "Send advertisemnets only for vrrp-inet6-group";
           type empty;
         }
         leaf current-hop-limit {
           description "Current hop limit";
           type union {
             type string {
               pattern "<.*>|$.*";
             }
             type uint32 {
               range "0 .. 255";
             }
           }
         }
         leaf default-lifetime {
           description "Router lifetime";
           units "seconds";
           type union {
             type string {
               pattern "<.*>|$.*";
             }
             type uint32 {
               range "0 .. 9000";
             }
           }
         }
         leaf passive-mode {
           description "RA receive only mode";
           type empty;
         }
         list dns-server-address {
           key name;
           ordered-by user;
           description "Recursive DNS address configuration";
           max-elements 3;
           leaf name {
             description "DNS address to be advertised";
             type string;
           }
           uses apply-advanced;
           leaf lifetime {
             description "DNS address lifetime";
             default "1800";
             units "seconds";
             type union {
               type string {
                 pattern "<.*>|$.*";
               }
               type uint32 {
                 range "0 .. 4294967295";
               }
             }
           }
         }
         list prefix {
           key name;
           ordered-by user;
           description "Prefix configuration";
           leaf name {
             description "Prefix to be advertised";
             type jt:ipv6prefix;
           }
           uses apply-advanced;
           leaf valid-lifetime {
             description "Valid lifetime (fixed)";
             units "seconds";
             type union {
               type string {
                 pattern "<.*>|$.*";
               }
               type uint32 {
                 range "0 .. 4294967295";
               }
             }
           }
           choice on-link-choice {
             leaf on-link {
               description "Set on-link flag";
               type empty;
             }
             leaf no-on-link {
               description "Don't set on-link flag";
               type empty;
             }
           }
           leaf preferred-lifetime {
             description "Preferred lifetime (fixed)";
             units "seconds";
             type union {
               type string {
                 pattern "<.*>|$.*";
               }
               type uint32 {
                 range "0 .. 4294967295";
               }
             }
           }
           choice autonomous-choice {
             leaf autonomous {
               description "Set autonomous flag";
               type empty;
             }
             leaf no-autonomous {
               description "Don't set autonomous flag";
               type empty;
             }
           }
         }
         list dns-search-list {
           key name;
           ordered-by user;
           description "DNS search list configuration";
           leaf name {
             description "DNS search list name";
             type string;
           }
           uses apply-advanced;
           leaf lifetime {
             description "DNS search list lifetime";
             default "5400";
             units "seconds";
             type union {
               type string {
                 pattern "<.*>|$.*";
               }
               type uint32 {
                 range "0 .. 4294967295";
               }
             }
           }
         }
         list rio-prefix {
           key name;
           ordered-by user;
           description "Route information option configuration";
           leaf name {
             description "Prefix to be advertised";
             type jt:ipv6prefix;
           }
           uses apply-advanced;
           leaf rio-lifetime {
             description "Route information lifetime";
             units "seconds";
             type union {
               type string {
                 pattern "<.*>|$.*";
               }
               type uint32 {
                 range "0 .. 4294967295";
               }
             }
           }
           leaf rio-preference {
             description "Set the preference for route information";
             type enumeration {
               enum "medium" {
                 description "Medium / Default";
               }
               enum "high" {
                 description "High";
               }
               enum "low" {
                 description "Low";
               }
             }
           }
         }
       }
       container ra-secure {
         description "Protect box against rogue incoming RA messages";
         uses apply-advanced;
         leaf accept-current-hop-limit-min {
           description "Current hop limit acceptable min for incoming RA";
           units "uint";
           type union {
             type string {
               pattern "<.*>|$.*";
             }
             type uint32 {
               range "1 .. 255";
             }
           }
         }
         leaf accept-current-hop-limit-max {
           description "Current hop acceptable min for incoming RA";
           units "uint";
           type union {
             type string {
               pattern "<.*>|$.*";
             }
             type uint32 {
               range "1 .. 255";
             }
           }
         }
         leaf accept-reachable-time-min {
           description "Reachable Time acceptable min for incoming RA";
           units "milliseconds";
           type union {
             type string {
               pattern "<.*>|$.*";
             }
             type uint32 {
               range "1000 .. 3600000";
             }
           }
         }
         leaf accept-reachable-time-max {
           description "Reachable Time acceptable max for incoming RA";
           units "milliseconds";
           type union {
             type string {
               pattern "<.*>|$.*";
             }
             type uint32 {
               range "1000 .. 3600000";
             }
           }
         }
         leaf accept-retransmit-time-min {
           description "Retransmit Time acceptable min for incoming RA";
           units "milliseconds";
           type union {
             type string {
               pattern "<.*>|$.*";
             }
             type uint32 {
               range "1000 .. 3600000";
             }
           }
         }
         leaf accept-retransmit-time-max {
           description "Retransmit Time acceptable min for incoming RA";
           units "milliseconds";
           type union {
             type string {
               pattern "<.*>|$.*";
             }
             type uint32 {
               range "1000 .. 3600000";
             }
           }
         }
       }
     }
     container neighbor-discovery {
       presence "enable neighbor-discovery";
       description "IPv6 neighbor discovery";
       uses apply-advanced;
       leaf onlink-subnet-only {
         description "Onlink subnet only knob";
         type empty;
       }
       leaf no-dad-on-state-change {
         description "Disable DAD on interface state change";
         type empty;
       }
       container ndp-proxy {
         description "Configure NDP PROXY behaviour";
         uses apply-advanced;
         leaf no-proxy-on-resolve {
           description "Disable proxy on unresolved address";
           type empty;
         }
         leaf proxy-force-resolve {
           description "Enable Neighbor Solicitation for already learned address";
           type empty;
         }
       }
       container dad-proxy {
         description "Configure DAD PROXY behaviour";
         uses apply-advanced;
         leaf no-proxy-on-resolve {
           description "Disable proxy on unresolved address";
           type empty;
         }
       }
     }
     container iccp {
       description "ICCP options";
       uses apply-advanced;
       leaf local-ip-addr {
         description "Local IP address to use by default for all peers";
         type jt:ipv4addr;
       }
       leaf session-establishment-hold-time {
         description "Time within which connection must succeed with peers";
         default "300";
         units "seconds";
         type union {
           type string {
             pattern "<.*>|$.*";
           }
           type uint32 {
             range "45 .. 600";
           }
         }
       }
       leaf authentication-key {
         description "MD5 authentication key for all peers";
         type string {
           length "1 .. 126";
         }
       }
       list peer {
         key name;
         description "Redundancy Group Configuration";
         max-elements 1;
         uses peer-group;
       }
       container traceoptions {
         description "Trace options for ICCP";
         uses apply-advanced;
         leaf no-remote-trace {
           description "Disable remote tracing";
           junos:must "(\"system tracing\")";
           junos:must-message "'no-remote-trace' is valid only when [system tracing] is configured";
           type empty;
         }
         container file {
           description "Trace file information";
           leaf filename {
             description "Name of file in which to write trace information";
             type string {
               length "1 .. 1024";
               junos:posix-pattern "![/ %]";
               junos:pattern-message "Must not contain '/', % or a space";
             }
           }
           leaf size {
             description "Maximum trace file size";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           ordered-by user;
           description "Trace flag information";
           leaf name {
             type enumeration {
               enum "error" {
                 description "Trace all errors";
               }
               enum "event" {
                 description "Trace all events";
               }
               enum "packet" {
                 description "Trace all packets";
               }
               enum "pipe" {
                 description "Trace pipe messages";
               }
               enum "pipe-detail" {
                 description "Trace pipe messages in detail";
               }
               enum "all" {
                 description "Trace everything";
               }
             }
           }
         }
       }
     }
     container ilmi {
       description "Interim Local Management Interface Protocol configuration";
       uses apply-advanced;
       container traceoptions {
         description "ILMI trace options";
         uses apply-advanced;
         leaf no-remote-trace {
           description "Disable remote tracing";
           junos:must "(\"system tracing\")";
           junos:must-message "'no-remote-trace' is valid only when [system tracing] is configured";
           type empty;
         }
         container file {
           description "Trace file information";
           leaf filename {
             description "Name of file in which to write trace information";
             type string {
               length "1 .. 1024";
               junos:posix-pattern "![/ %]";
               junos:pattern-message "Must not contain '/', % or a space";
             }
           }
           leaf size {
             description "Maximum trace file size";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           ordered-by user;
           description "Tracing parameters";
           leaf name {
             type enumeration {
               enum "database" {
                 description "Trace database events";
               }
               enum "routing-socket" {
                 description "Trace Routing socket events";
               }
               enum "state" {
                 description "Trace state change events";
               }
               enum "debug" {
                 description "Trace debug messages";
               }
               enum "event" {
                 description "Trace event handler events";
               }
               enum "packet" {
                 description "Trace packet events";
               }
               enum "all" {
                 description "Trace all areas of code";
               }
             }
           }
         }
       }
     }
     container lacp {
       description "Link Aggregation Control Protocol configuration";
       uses apply-advanced;
       container traceoptions {
         description "LACP trace options";
         uses apply-advanced;
         leaf no-remote-trace {
           description "Disable remote tracing";
           junos:must "(\"system tracing\")";
           junos:must-message "'no-remote-trace' is valid only when [system tracing] is configured";
           type empty;
         }
         container file {
           description "Trace file information";
           leaf filename {
             description "Name of file in which to write trace information";
             type string {
               length "1 .. 1024";
               junos:posix-pattern "![/ %]";
               junos:pattern-message "Must not contain '/', % or a space";
             }
           }
           leaf size {
             description "Maximum trace file size";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           ordered-by user;
           description "Events and packet types to include in the trace";
           leaf name {
             type enumeration {
               enum "configuration" {
                 description "Configuration events";
               }
               enum "routing-socket" {
                 description "Routing socket events";
               }
               enum "process" {
                 description "Process events";
               }
               enum "startup" {
                 description "Process startup events";
               }
               enum "protocol" {
                 description "Protocol events";
               }
               enum "packet" {
                 description "LACP packets";
               }
               enum "ppm" {
                 description "LACP PPM messages";
               }
               enum "bfd" {
                 description "LACP BFD events";
               }
               enum "mc-ae" {
                 description "Multi-chassis AE messages";
               }
               enum "all" {
                 description "All events and packets";
               }
             }
           }
         }
       }
       leaf ppm {
         description "Force PPM processing";
         type enumeration {
           enum "centralized" {
             description "Centralized PPM processing";
           }
           enum "inline" {
             description "Distributed inline PPM processing";
           }
         }
       }
     }
     container oam {
       description "Operation, Administration, and Management configuration";
       uses apply-advanced;
       container ethernet {
         description "OAM configuration for Ethernet";
         uses apply-advanced;
         container link-fault-management {
           description "802.3ah Ethernet OAM configuration";
           uses apply-advanced;
           container traceoptions {
             description "Trace options for link-fault management";
             uses apply-advanced;
             leaf no-remote-trace {
               description "Disable remote tracing";
               junos:must "(\"system tracing\")";
               junos:must-message "'no-remote-trace' is valid only when [system tracing] is configured";
               type empty;
             }
             container file {
               description "Trace file information";
               leaf filename {
                 description "Name of file in which to write trace information";
                 type string {
                   length "1 .. 1024";
                   junos:posix-pattern "![/ %]";
                   junos:pattern-message "Must not contain '/', % or a space";
                 }
               }
               leaf size {
                 description "Maximum trace file size";
                 type string;
               }
               leaf files {
                 description "Maximum number of trace files";
                 default "3";
                 type union {
                   type string {
                     pattern "<.*>|$.*";
                   }
                   type uint32 {
                     range "2 .. 1000";
                   }
                 }
               }
               choice world-readable-choice {
                 leaf world-readable {
                   description "Allow any user to read the log file";
                   type empty;
                 }
                 leaf no-world-readable {
                   description "Don't allow any user to read the log file";
                   type empty;
                 }
               }
               leaf match {
                 description "Regular expression for lines to be logged";
                 type jt:regular-expression;
               }
             }
             list flag {
               key name;
               ordered-by user;
               description "Tracing parameters";
               leaf name {
                 type enumeration {
                   enum "configuration" {
                     description "Trace configuration events";
                   }
                   enum "routing-socket" {
                     description "Trace routing socket events";
                   }
                   enum "protocol" {
                     description "Trace protocol processing events";
                   }
                   enum "action-profile" {
                     description "Trace action profile invocation events";
                   }
                   enum "all" {
                     description "Trace everything";
                   }
                 }
               }
             }
           }
           list action-profile {
             key name;
             ordered-by user;
             description "Define an action profile";
             leaf name {
               description "Name of action profile";
               type string {
                 length "1 .. 32";
               }
             }
             uses apply-advanced;
             container event {
               description "Events this action profile will check";
               uses apply-advanced;
               leaf link-adjacency-loss {
                 description "Loss of adjacency with OAM peer";
                 type empty;
               }
               leaf protocol-down {
                 description "Upper layer indication on protocol down";
                 type empty;
               }
               container link-event-rate {
                 uses apply-advanced;
                 leaf symbol-period {
                   description "Rate of receiving symbol period events";
                   units "error(s) per 100 symbol";
                   type union {
                     type string {
                       pattern "<.*>|$.*";
                     }
                     type int32 {
                       range "1 .. 100";
                     }
                   }
                 }
                 leaf frame-error {
                   description "Rate of receiving frame error events";
                   units "error(s) per 100 milli-second";
                   type union {
                     type string {
                       pattern "<.*>|$.*";
                     }
                     type int32 {
                       range "1 .. 1000";
                     }
                   }
                 }
                 leaf frame-period {
                   description "Rate of receiving frame period events";
                   units "error(s) per 100 frames";
                   type union {
                     type string {
                       pattern "<.*>|$.*";
                     }
                     type int32 {
                       range "1 .. 100";
                     }
                   }
                 }
                 leaf frame-period-summary {
                   description "Rate of receiving frame period summary events";
                   units "error(s) per second";
                   type union {
                     type string {
                       pattern "<.*>|$.*";
                     }
                     type int32 {
                       range "1 .. 1000";
                     }
                   }
                 }
               }
             }
             container action {
               description "Action to take on specified events";
               uses apply-advanced;
               leaf syslog {
                 description "Generate syslog message";
                 type empty;
               }
               leaf link-down {
                 description "Mark the interface down for transit traffic";
                 type empty;
               }
               leaf send-critical-event {
                 description "Start sending OAM PDUs with critical event bit set";
                 junos:must "(\".. .. event protocol-down\")";
                 junos:must-message "send-critical-event action can be configured only with protocol-down event";
                 type empty;
               }
             }
           }
           list interface {
             key name;
             ordered-by user;
             description "Interface on which to set Ethernet OAM parameters";
             leaf name {
               description "Interface name";
               type union {
                 type jt:interface-device;
                 type string {
                   pattern "<.*>|$.*";
                 }
               }
             }
             uses apply-advanced;
             leaf-list apply-action-profile {
               ordered-by user;
               description "Apply the specified action profile on the interface";
               type string;
             }
             leaf pdu-interval {
               description "Periodic OAM protocol data unit interval";
               default "1000";
               units "milliseconds";
               type union {
                 type string {
                   pattern "<.*>|$.*";
                 }
                 type int32 {
                   range "100 .. 1000";
                 }
               }
             }
             leaf loopback-tracking {
               description "Enable link down on loopback detection";
               type empty;
             }
             leaf detect-loc {
               description "Detects initial lack of adjacency formation";
               type empty;
             }
             leaf link-discovery {
               description "Mode of discovery";
               default "active";
               type enumeration {
                 enum "active" {
                 }
                 enum "passive" {
                 }
               }
             }
             leaf pdu-threshold {
               description "Number of PDUs missed before declaring peer lost";
               default "3";
               type union {
                 type string {
                   pattern "<.*>|$.*";
                 }
                 type int32;
               }
             }
             leaf remote-loopback {
               description "Put remote DTE into remote-loopback mode";
               junos:must "(!(\".. link-discovery passive\"))";
               junos:must-message "remote-loopback request not allowed in passive mode";
               type empty;
             }
             container negotiation-options {
               description "802.3ah features supported on the interface";
               uses apply-advanced;
               leaf no-allow-link-events {
                 description "Do not emit periodic PDUs detailing framing and symbol errors";
                 type empty;
               }
               leaf allow-remote-loopback {
                 description "Allow local port to be put into loopback mode";
                 type empty;
               }
             }
             container event-thresholds {
               junos:must "(!(\".. negotiation-options no-allow-link-events\"))";
               junos:must-message "'event-thresholds' statement cannot be included along with 'no-allow-link-events' statement";
               description "Thresholds for sending 802.3ah events";
               uses apply-advanced;
               leaf symbol-period {
                 description "Threshold for sending symbol period events";
                 default "1";
                 type union {
                   type string {
                     pattern "<.*>|$.*";
                   }
                   type int32 {
                     range "0 .. 100";
                   }
                 }
               }
               leaf frame-error {
                 description "Threshold for sending frame error events";
                 default "1";
                 type union {
                   type string {
                     pattern "<.*>|$.*";
                   }
                   type int32 {
                     range "0 .. 100";
                   }
                 }
               }
               leaf frame-period {
                 description "Threshold for sending frame period error events";
                 default "1";
                 type union {
                   type string {
                     pattern "<.*>|$.*";
                   }
                   type int32 {
                     range "0 .. 100";
                   }
                 }
               }
               leaf frame-period-summary {
                 description "Threshold for sending frame period summary error events";
                 default "1";
                 type union {
                   type string {
                     pattern "<.*>|$.*";
                   }
                   type int32 {
                     range "0 .. 100";
                   }
                 }
               }
             }
           }
         }
         container connectivity-fault-management {
           description "Configurations related to 802.1ag ethernet oam";
           uses apply-advanced;
           container performance-monitoring {
             description "Configurations related to ethernet performance monitoring";
             uses apply-advanced;
             leaf hardware-assisted-timestamping {
               description "Enable timestamping feature in hardware";
               type empty;
             }
             leaf delegate-server-processing {
               description "Delegate performance measurement request handling to PFE";
               type empty;
             }
             leaf hardware-assisted-keepalives {
               description "Enable/Disable delegating keepalives to hardware";
               type enumeration {
                 enum "enable" {
                   description "Enable delegate keepalives handling to Hardware";
                 }
                 enum "disable" {
                   description "Disable delegate keepalives handling to Hardware (default)";
                 }
               }
             }
             leaf hardware-assisted-pm {
               description "Enable inline support for performance monitoring";
               junos:must "(\"protocols oam ethernet connectivity-fault-management enhanced-cfm-mode\")";
               junos:must-message "enhanced-cfm-mode needs to be configured for inline pm support";
               type empty;
             }
             leaf enhanced-sla-iterator {
               description "Enable Enhanced SLA Iterator Cycle-time";
               type empty;
             }
             leaf measurement-interval {
               description "Enables measurement-interval based PM (MEF 36 mode). Default 15 min in enhanced-cfm-mode";
               units "minutes";
               junos:must "(\".. enhanced-sla-iterator\")";
               junos:must-message "enhanced-sla-iterator needs to be configured for MEF36 mode";
               type enumeration {
                 enum "2" {
                   description "2 minutes measurement interval";
                 }
                 enum "5" {
                   description "5 minutes measurement interval";
                 }
                 enum "15" {
                   description "15 minutes measurement interval";
                 }
                 enum "30" {
                   description "30 minutes measurement interval";
                 }
                 enum "60" {
                   description "1 hour measurement interval";
                 }
               }
             }
             leaf legacy-pm-display {
               description "Display Legacy PM output (for DM) in MEF mode.";
               junos:must "((\".. measurement-interval\" || \".. .. enhanced-cfm-mode\"))";
               junos:must-message "measurement-interval or enhanced-cfm-mode needs to be configured for legacy PM output in MEF mode.";
               type empty;
             }
             list sla-iterator-profiles {
               key name;
               ordered-by user;
               description "Configuration related to an sla monitoring iterator";
               leaf name {
                 type string;
               }
               uses apply-advanced;
               leaf disable {
                 description "Disable the iterator profile";
                 type empty;
               }
               leaf measurement-type {
                 description "Choice of the type of Y.1731(SLA measurement) frame to be sent";
                 type enumeration {
                   enum "two-way-delay" {
                     description "Y.1731 2-way DM frames are sent for this profile";
                     junos:must "(!(\"routing-options ppm no-delegate-processing\"))";
                     junos:must-message "Iterator two-way-delay measurement is not supported with ppm no-delegate-processing";
                   }
                   enum "loss" {
                     description "Y.1731 LM frames are sent for this profile";
                   }
                   enum "slm" {
                     description "Y.1731 SLM frames are sent for this profile";
                   }
                   enum "statistical-frame-loss" {
                     description "Y.1731 2-way DM frames for statistical frame loss are sent for this profile";
                     junos:must "(!(\"routing-options ppm no-delegate-processing\"))";
                     junos:must-message "Iterator statistical-frame-loss measurement is not supported with ppm no-delegate-processing";
                   }
                 }
               }
               leaf flap-trap-monitor {
                 description "Configurable timer value 1-360";
                 units "seconds";
                 type union {
                   type string {
                     pattern "<.*>|$.*";
                   }
                   type uint32 {
                     range "1 .. 360";
                   }
                 }
               }
               leaf cycle-time {
                 description "Time period of an iterator profile";
                 default "1000";
                 units "milliseconds";
                 type union {
                   type string {
                     pattern "<.*>|$.*";
                   }
                   type uint32;
                 }
               }
               leaf iteration-period {
                 description "Maximum services under this iterator profile";
                 default "2000";
                 units "connections";
                 type union {
                   type string {
                     pattern "<.*>|$.*";
                   }
                   type uint32 {
                     range "1 .. 2000";
                   }
                 }
               }
               container calculation-weight {
                 presence "enable calculation-weight";
                 junos:must "(\".. measurement-type two-way-delay\")";
                 junos:must-message "The measurement type must be two-way-delay";
                 description "Configure delay and delay variation calculation weight";
                 uses apply-advanced;
                 leaf delay {
                   description "Weight used in delay calculation";
                   default "1";
                   type union {
                     type string {
                       pattern "<.*>|$.*";
                     }
                     type uint32 {
                       range "1 .. 65535";
                     }
                   }
                 }
                 leaf delay-variation {
                   description "Weight used in delay-variation calculation";
                   default "1";
                   type union {
                     type string {
                       pattern "<.*>|$.*";
                     }
                     type uint32 {
                       range "1 .. 65535";
                     }
                   }
                 }
               }
               container avg-flr-forward-threshold {
                 presence "enable avg-flr-forward-threshold";
                 junos:must "((\".. measurement-type loss\" || \" .. measurement-type slm\"))";
                 junos:must-message " The measurement type must be either loss or slm";
                 description "Avg forward flr threshold";
                 uses apply-advanced;
                 leaf avg-flr-forward {
                   description "Avg forward flr threshold value in mili-percent";
                   type union {
                     type string {
                       pattern "<.*>|$.*";
                     }
                     type uint32 {
                       range "1 .. 100000";
                     }
                   }
                 }
                 leaf flap-trap-monitor {
                   description "Configurable timer value 1-360";
                   units "seconds";
                   type union {
                     type string {
                       pattern "<.*>|$.*";
                     }
                     type uint32 {
                       range "1 .. 360";
                     }
                   }
                 }
               }
               container avg-flr-backward-threshold {
                 presence "enable avg-flr-backward-threshold";
                 junos:must "((\".. measurement-type loss\" || \" .. measurement-type slm\"))";
                 junos:must-message " The measurement type must be either loss or slm";
                 description "Avg backward flr threshold";
                 uses apply-advanced;
                 leaf avg-flr-backward {
                   description "Avg backward flr threshold value in mili-percent";
                   type union {
                     type string {
                       pattern "<.*>|$.*";
                     }
                     type uint32 {
                       range "1 .. 100000";
                     }
                   }
                 }
                 leaf flap-trap-monitor {
                   description "Configurable timer value 1-360";
                   units "seconds";
                   type union {
                     type string {
                       pattern "<.*>|$.*";
                     }
                     type uint32 {
                       range "1 .. 360";
                     }
                   }
                 }
               }
               container avg-fd-twoway-threshold {
                 presence "enable avg-fd-twoway-threshold";
                 junos:must "(\".. measurement-type two-way-delay\")";
                 junos:must-message " The measurement type must be two-way-delay";
                 description "Avg frame delay threshold value";
                 uses apply-advanced;
                 leaf avg-fd-twoway {
                   description "Avg frame delay threshold value in mili-percent";
                   units "microseconds";
                   type union {
                     type string {
                       pattern "<.*>|$.*";
                     }
                     type uint32 {
                       range "1 .. 4294967295";
                     }
                   }
                 }
                 leaf flap-trap-monitor {
                   description "Configurable timer value 1-360";
                   units "seconds";
                   type union {
                     type string {
                       pattern "<.*>|$.*";
                     }
                     type uint32 {
                       range "1 .. 360";
                     }
                   }
                 }
               }
               container avg-fdv-twoway-threshold {
                 presence "enable avg-fdv-twoway-threshold";
                 junos:must "(\".. measurement-type two-way-delay\")";
                 junos:must-message " The measurement type must be two-way-delay";
                 description "Avg frame delay variance threshold";
                 uses apply-advanced;
                 leaf avg-fdv-twoway {
                   description "Avg frame delay variance threshold value in mili-percent";
                   units "microseconds";
                   type union {
                     type string {
                       pattern "<.*>|$.*";
                     }
                     type uint32 {
                       range "1 .. 4294967295";
                     }
                   }
                 }
                 leaf flap-trap-monitor {
                   description "Configurable timer value 1-360";
                   units "seconds";
                   type union {
                     type string {
                       pattern "<.*>|$.*";
                     }
                     type uint32 {
                       range "1 .. 360";
                     }
                   }
                 }
               }
               container frame-delay {
                 description "Bin configuration for frame delay";
                 uses apply-advanced;
                 leaf num-bins {
                   description "Max number of bins";
                   type union {
                     type string {
                       pattern "<.*>|$.*";
                     }
                     type uint32 {
                       range "2 .. 5";
                     }
                   }
                 }
                 container two-way {
                   presence "enable two-way";
                   description "Bin configuration for 2way frame delay";
                   uses apply-advanced;
                   leaf-list lower-threshold-bin {
                     description "Lower threshold bin configuration in ascending order";
                     type union {
                       type string {
                         pattern "<.*>|$.*";
                       }
                       type uint32 {
                         range "1 .. 4294967294";
                       }
                     }
                   }
                 }
                 container forward {
                   presence "enable forward";
                   description "Bin configuration for forward frame delay";
                   uses apply-advanced;
                   leaf-list lower-threshold-bin {
                     description "Lower threshold bin configuration in ascending order";
                     type union {
                       type string {
                         pattern "<.*>|$.*";
                       }
                       type uint32 {
                         range "1 .. 4294967294";
                       }
                     }
                   }
                 }
                 container backward {
                   presence "enable backward";
                   description "Bin configuration for backward frame delay";
                   uses apply-advanced;
                   leaf-list lower-threshold-bin {
                     description "Lower threshold bin configuration in ascending order";
                     type union {
                       type string {
                         pattern "<.*>|$.*";
                       }
                       type uint32 {
                         range "1 .. 4294967294";
                       }
                     }
                   }
                 }
               }
               container frame-delay-range {
                 description "Bin configuration for frame delay range";
                 uses apply-advanced;
                 leaf num-bins {
                   description "Max number of bins";
                   type union {
                     type string {
                       pattern "<.*>|$.*";
                     }
                     type uint32 {
                       range "2 .. 5";
                     }
                   }
                 }
                 container two-way {
                   presence "enable two-way";
                   description "Bin configuration for 2way frame delay range";
                   uses apply-advanced;
                   leaf-list lower-threshold-bin {
                     description "Lower threshold bin configuration in ascending order";
                     type union {
                       type string {
                         pattern "<.*>|$.*";
                       }
                       type uint32 {
                         range "1 .. 4294967294";
                       }
                     }
                   }
                 }
                 container forward {
                   presence "enable forward";
                   description "Bin configuration for forward frame delay range";
                   uses apply-advanced;
                   leaf-list lower-threshold-bin {
                     description "Lower threshold bin configuration in ascending order";
                     type union {
                       type string {
                         pattern "<.*>|$.*";
                       }
                       type uint32 {
                         range "1 .. 4294967294";
                       }
                     }
                   }
                 }
                 container backward {
                   presence "enable backward";
                   description "Bin configuration for backward frame delay range";
                   uses apply-advanced;
                   leaf-list lower-threshold-bin {
                     description "Lower threshold bin configuration in ascending order";
                     type union {
                       type string {
                         pattern "<.*>|$.*";
                       }
                       type uint32 {
                         range "1 .. 4294967294";
                       }
                     }
                   }
                 }
               }
               container ifdv {
                 description "Bin configuration for IFDV";
                 uses apply-advanced;
                 leaf num-bins {
                   description "Max number of bins";
                   type union {
                     type string {
                       pattern "<.*>|$.*";
                     }
                     type uint32 {
                       range "2 .. 5";
                     }
                   }
                 }
                 container two-way {
                   presence "enable two-way";
                   description "Bin configuration for 2way IFDV";
                   uses apply-advanced;
                   leaf-list lower-threshold-bin {
                     description "Lower threshold bin configuration in ascending order";
                     type union {
                       type string {
                         pattern "<.*>|$.*";
                       }
                       type uint32 {
                         range "1 .. 4294967294";
                       }
                     }
                   }
                 }
                 container forward {
                   presence "enable forward";
                   description "Bin configuration for forward IFDV";
                   uses apply-advanced;
                   leaf-list lower-threshold-bin {
                     description "Lower threshold bin configuration in ascending order";
                     type union {
                       type string {
                         pattern "<.*>|$.*";
                       }
                       type uint32 {
                         range "1 .. 4294967294";
                       }
                     }
                   }
                 }
                 container backward {
                   presence "enable backward";
                   description "Bin configuration for backward IFDV";
                   uses apply-advanced;
                   leaf-list lower-threshold-bin {
                     description "Lower threshold bin configuration in ascending order";
                     type union {
                       type string {
                         pattern "<.*>|$.*";
                       }
                       type uint32 {
                         range "1 .. 4294967294";
                       }
                     }
                   }
                 }
               }
             }
             list interface {
               key name;
               ordered-by user;
               description "Name of interface for the performance monitoring";
               leaf name {
                 description "Interface name";
                 type union {
                   type jt:interface-unit;
                   type string {
                     pattern "<.*>|$.*";
                   }
                 }
               }
               leaf enable-multiclass-loss-measurement {
                 description "Disable multiclass loss measurement in hardware";
                 junos:must "((!(\".. code-point-based-lm-accounting\") && !(\".. priority-based-lm-accounting\")))";
                 junos:must-message "loss measurement modes are exclusive with each other";
                 type empty;
               }
               leaf code-point-based-lm-accounting {
                 description "Enable code point based loss measurement in hardware";
                 junos:must "((!(\".. enable-multiclass-loss-measurement\") && (!(\".. colorless-loss-measurement\") && !(\".. priority-based-lm-accounting\"))))";
                 junos:must-message "loss measurement modes are exclusive with each other";
                 type empty;
               }
               leaf priority-based-lm-accounting {
                 description "Enable priority based loss measurement in hardware";
                 junos:must "((!(\".. enable-multiclass-loss-measurement\") && (!(\".. colorless-loss-measurement\") && !(\".. code-point-based-lm-accounting\"))))";
                 junos:must-message "loss measurement modes are exclusive with each other";
                 type empty;
               }
             }
             leaf enable-multiclass-loss-measurement {
               description "Disable multiclass loss measurement in hardware";
               junos:must "((!(\".. code-point-based-lm-accounting\") && !(\".. priority-based-lm-accounting\")))";
               junos:must-message "loss measurement modes are exclusive with each other";
               type empty;
             }
             leaf code-point-based-lm-accounting {
               description "Enable code point based loss measurement in hardware";
               junos:must "((!(\".. enable-multiclass-loss-measurement\") && (!(\".. colorless-loss-measurement\") && !(\".. priority-based-lm-accounting\"))))";
               junos:must-message "loss measurement modes are exclusive with each other";
               type empty;
             }
             leaf priority-based-lm-accounting {
               description "Enable priority based loss measurement in hardware";
               junos:must "((!(\".. enable-multiclass-loss-measurement\") && (!(\".. colorless-loss-measurement\") && !(\".. code-point-based-lm-accounting\"))))";
               junos:must-message "loss measurement modes are exclusive with each other";
               type empty;
             }
             leaf colorless-loss-measurement {
               description "Enable colorless loss measurement in hardware";
               junos:must "((!(\".. code-point-based-lm-accounting\") && !(\".. priority-based-lm-accounting\")))";
               junos:must-message "loss measurement modes are exclusive with each other";
               type empty;
             }
           }
           leaf no-aggregate-delegate-processing {
             description "Do not distribute aggregate session to pfe";
             type empty;
           }
           leaf enhanced-cfm-mode {
             description "Enables Enhanced CFM Mode";
             type empty;
           }
           container traceoptions {
             description "Trace options for connectivity fault management";
             presence "enable traceoptions";
             uses cfm-traceoptions;
           }
           list action-profile {
             key name;
             ordered-by user;
             description "Action profiles to use when one or more remote maintenance association endpoints are down";
             leaf name {
               description "Name of action profile";
               type string;
             }
             uses apply-advanced;
             container event {
               junos:must "(\".. action\")";
               junos:must-message "Cannot configure event without action";
               description "Events that need to be monitored";
               uses apply-advanced;
               leaf-list interface-status-tlv {
                 ordered-by user;
                 description "Values that need to be monitored in interface status TLV";
                 type enumeration {
                   enum "down" {
                     description "Interface is administratively down";
                   }
                   enum "lower-layer-down" {
                     description "Interface is physically down";
                   }
                 }
               }
               leaf-list port-status-tlv {
                 ordered-by user;
                 description "Values that need to be monitored in port status TLV";
                 type enumeration {
                   enum "blocked" {
                     description "Port is blocked";
                   }
                 }
               }
               leaf adjacency-loss {
                 description "Connectivity is lost";
                 type empty;
               }
               leaf rdi {
                 description "RDI received from some MEP";
                 type empty;
               }
               leaf connection-protection-tlv {
                 description "Values that need to be monitored in connection protection TLV";
                 type enumeration {
                   enum "using-working-path" {
                     description "Service traffic is using working path";
                   }
                   enum "using-protection-path" {
                     description "Service traffic is using protection path";
                   }
                 }
               }
             }
             container action {
               junos:must "(\".. event\")";
               junos:must-message "Cannot configure action without event";
               uses apply-advanced;
               leaf interface-down {
                 description "Mark the interface as down";
                 type empty;
               }
               leaf revertive-interface-down {
                 description "Wait for CC loss-threshold to bring back the interface up";
                 junos:must "(!(\".. non-revertive-interface-down\"))";
                 junos:must-message "Cannot configure action along with revertive-interface-down";
                 type empty;
               }
               leaf non-revertive-interface-down {
                 description "Interface will not be brought up when CC is received";
                 junos:must "(!(\".. revertive-interface-down\"))";
                 junos:must-message "Cannot configure action along with non-revertive-interface-down";
                 type empty;
               }
               leaf propagate-remote-mac-flush {
                 description "Remote mac-flush";
                 type empty;
               }
               leaf interface-group-down {
                 description "Mark the interface group as down";
                 junos:must "((!(\".. .. event interface-status-tlv\") && (!(\".. .. event port-status-tlv\") && (!(\".. .. event connection-protection-tlv\") && (!(\".. .. event server-mep-defects\") && !(\".. .. event ais-trigger-condition\"))))))";
                 junos:must-message "Cannot configure events other that adjacency-loss or rdi with this action";
                 junos:must "((!(\".. interface-down\") && (!(\".. revertive-interface-down\") && !(\".. non-revertive-interface-down\"))))";
                 junos:must-message "Cannot configure action along with other interface down actions";
                 type empty;
               }
               leaf asynchronous-notification {
                 description "Generate asynchronous notification (Laser-off for optical phys)";
                 junos:must "((!(\".. .. event port-status-tlv\") && (!(\".. .. event rdi\") && (!(\".. .. event connection-protection-tlv\") && (!(\".. .. event server-mep-defects\") && !(\".. .. event ais-trigger-condition\"))))))";
                 junos:must-message "Cannot configure events other that adjacency-loss or interface-status-tlv with this action";
                 junos:must "((!(\".. interface-down\") && (!(\".. revertive-interface-down\") && (!(\".. non-revertive-interface-down\") && !(\".. interface-group-down\")))))";
                 junos:must-message "Cannot configure action along with other interface down actions";
                 type empty;
               }
               container log-and-generate-ais {
                 uses apply-advanced;
                 leaf-list level {
                   description "Server maintenance domain levels range";
                   type union {
                     type string {
                       pattern "<.*>|$.*";
                     }
                     type uint32 {
                       range "1 .. 7";
                     }
                   }
                 }
                 leaf interval {
                   description "Interval between AIS messages";
                   default "1s";
                   type enumeration {
                     enum "1s" {
                     }
                     enum "1m" {
                     }
                   }
                 }
                 leaf priority {
                   description "802.1p priority of AIS packet";
                   default "0";
                   type union {
                     type string {
                       pattern "<.*>|$.*";
                     }
                     type uint32 {
                       range "0 .. 7";
                     }
                   }
                 }
               }
             }
             container clear-action {
               junos:must "(\".. event\")";
               junos:must-message "Cannot configure action without event";
               uses apply-advanced;
               container interface-down {
                 description "Mark the interface as down";
                 leaf peer-interface {
                   description "Mark the interface as down";
                   type empty;
                 }
               }
               leaf propagate-remote-mac-flush {
                 description "Remote  mac flush";
                 type empty;
               }
             }
             container default-actions {
               junos:must "(!(\".. event\"))";
               junos:must-message "Cannot configure default-actions if event is set";
               description "Action that needs to be taken";
               uses apply-advanced;
               leaf interface-down {
                 description "Bring the interface down";
                 type empty;
               }
             }
           }
           container policer {
             description "Rate limit Ethernet OAM packets for all sessions";
             uses apply-advanced;
             leaf continuity-check {
               description "Policer to rate limit Continuity Check Ethernet OAM messages";
               junos:must "(\"firewall policer $$\")";
               junos:must-message "referenced policer must be defined";
               type string;
             }
             leaf other {
               description "Policer to rate limit non Continuity Check Ethernet OAM messages";
               junos:must "(\"firewall policer $$\")";
               junos:must-message "referenced policer must be defined";
               type string;
             }
             leaf all {
               description "Policer to rate limit all Ethernet OAM messages";
               junos:must "(\"firewall policer $$\")";
               junos:must-message "referenced policer must be defined";
               type string;
             }
           }
           container linktrace {
             presence "enable linktrace";
             description "Linktrace protocol global options";
             uses apply-advanced;
             leaf path-database-size {
               description "Number of linktrace reply entries to be stored per linktrace request";
               default "100";
               type union {
                 type string {
                   pattern "<.*>|$.*";
                 }
                 type uint32 {
                   range "1 .. 255";
                 }
               }
             }
             leaf age {
               description "Time after which a stale request-response entry is deleted";
               default "10m";
               type enumeration {
                 enum "10s" {
                 }
                 enum "30s" {
                 }
                 enum "1m" {
                 }
                 enum "10m" {
                 }
                 enum "30m" {
                 }
               }
             }
           }
           list maintenance-domain {
             key name;
             ordered-by user;
             description "Maintenance domain configuration";
             leaf name {
               type string;
             }
             uses apply-advanced;
             list bridge-domain {
               key name;
               ordered-by user;
               description "Bridge-domain information for the default maintenance domain";
               leaf name {
                 description "Bridge domain name";
                 type string;
               }
               leaf-list vlan-id {
                 ordered-by user;
                 description "VLAN id";
                 type string;
               }
             }
             list virtual-switch {
               key name;
               ordered-by user;
               description "Virtual switch Bridge-domain information for the default maintenance domain";
               leaf name {
                 description "Routing instance of type virtual switch";
                 type string;
               }
               uses apply-advanced;
               list bridge-domain {
                 key name;
                 ordered-by user;
                 leaf name {
                   description "Bridge domain name";
                   type string;
                 }
                 leaf-list vlan-id {
                   ordered-by user;
                   description "VLAN id";
                   type string;
                 }
               }
             }
             list instance {
               key name;
               ordered-by user;
               description "VPLS instance name for the default maintenance domain";
               leaf name {
                 description "VPLS routing instance name";
                 junos:must "(!(\"routing-instances $$ vlan-id inner-all\"))";
                 junos:must-message "MIPs are not allowed for VPLS with vlan-id inner-all";
                 junos:must "(!(\"routing-instances $$ vlan-id all\"))";
                 junos:must-message "MIPs are not allowed for VPLS with vlan-id all";
                 junos:must "((\"routing-instances $$ vlan-id\" || \"routing-instances $$ vlan-tags\"))";
                 junos:must-message "MIPs are allowed only for VPLS with vlan-id/vlan-tags";
                 junos:must "(\"routing-instances $$ instance-type vpls\")";
                 junos:must-message "Only VPLS routing-instances are allowed under default maintenance-domains";
                 type string;
               }
             }
             list interface {
               key name;
               ordered-by user;
               description "Name of interface for the default maintenance domain";
               leaf name {
                 description "Interface name";
                 junos:must "(!(\"protocols loop-detect enhanced interface $$\"))";
                 junos:must-message "Connectivtiy and loop-detect protocols cannot be enabled on same interface";
                 junos:must "(!(\"protocols oam ethernet link-fault-management interface $$\"))";
                 junos:must-message "Connectivtiy and link fault management protocols cannot be enabled on same interface";
                 junos:must "((!(any \"interfaces $$ unit <*> vlan-id 0\") && !(any \"logical-systems <*> interfaces $$ unit <*> vlan-id 0\")))";
                 junos:must-message "Default maintenance domain cannot be configured with a physical interface which has a logical interface configured with vlan-id 0";
                 type union {
                   type jt:interface-unit;
                   type string {
                     pattern "<.*>|$.*";
                   }
                 }
               }
             }
             leaf level {
               description "Level value for maintenance domain";
               type union {
                 type string {
                   pattern "<.*>|$.*";
                 }
                 type uint8 {
                   range "0 .. 7";
                 }
               }
             }
             leaf name-format {
               description "Format of maintenance domain name";
               type enumeration {
                 enum "none" {
                   description "No format specified";
                 }
                 enum "dns" {
                   description "Character string similar to Domain Name System name";
                 }
                 enum "mac+2oct" {
                   description "MAC address with 2 octet integer (xx:xx:xx:xx:xx:xx.Y format)";
                 }
                 enum "character-string" {
                   description "Character string";
                 }
               }
             }
             leaf mip-half-function {
               description "Half function to be implemented by MIP";
               default "none";
               type enumeration {
                 enum "none" {
                   description "No MHFs should be created";
                 }
                 enum "default" {
                   description "Create MHF as per IEEE 802.1ag specifications for defMHFDefault";
                 }
                 enum "explicit" {
                   description "Create MHF as per IEEE 802.1ag specifications for defMHFExplicit";
                 }
               }
             }
             list maintenance-association {
               key name;
               ordered-by user;
               description "Maintenance association configuration";
               leaf name {
                 description "Name of maintenance association in IEEE compliant format";
                 type string {
                   length "1 .. 45";
                 }
               }
               uses apply-advanced;
               leaf debug-session {
                 description "Debug the CFM session";
                 type empty;
               }
               leaf short-name-format {
                 description "Format of Maintenance Association Name";
                 type enumeration {
                   enum "2octet" {
                     description "An integer in the range 0..65535";
                   }
                   enum "rfc-2685-vpn-id" {
                     description "VPN identifier that complies with RFC 2685";
                   }
                   enum "vlan" {
                     description "Primary VLAN identifier";
                   }
                   enum "character-string" {
                     description "Character string";
                   }
                   enum "icc" {
                     description "ITU Carrier Code";
                   }
                 }
               }
               leaf primary-vid {
                 description "VLAN id";
                 type string;
               }
               container continuity-check {
                 presence "enable continuity-check";
                 description "Continuity check configuration";
                 uses apply-advanced;
                 leaf interval {
                   description "Interval between continuity-check messages";
                   default "1m";
                   type enumeration {
                     enum "10ms" {
                       junos:must "(!(\"routing-options ppm no-delegate-processing\"))";
                       junos:must-message "10ms interval for continuity-check is not supported with no-delegate-processing";
                     }
                     enum "100ms" {
                     }
                     enum "1s" {
                     }
                     enum "10s" {
                     }
                     enum "1m" {
                     }
                     enum "10m" {
                     }
                     enum "3.3ms" {
                       junos:must "(!(\"routing-options ppm no-delegate-processing\"))";
                       junos:must-message "3.3ms interval for continuity-check is not supported with no-delegate-processing";
                     }
                   }
                 }
                 leaf loss-threshold {
                   description "Number of continuity-check messages lost before marking endpoint as down";
                   default "3";
                   type union {
                     type string {
                       pattern "<.*>|$.*";
                     }
                     type uint32 {
                       range "3 .. 256";
                     }
                   }
                 }
                 leaf hold-interval {
                   description "Time before flushing MEP database if no updates occur";
                   default "10";
                   units "minutes";
                   type union {
                     type string {
                       pattern "<.*>|$.*";
                     }
                     type uint32 {
                       range "1 .. 30240";
                     }
                   }
                 }
                 leaf port-status-tlv {
                   description "Include port status TLV in CCM";
                   type empty;
                 }
                 leaf interface-status-tlv {
                   description "Include interface status TLV in CCM";
                   type empty;
                 }
                 leaf connection-protection-tlv {
                   description "Include connection protection OUI TLV in CCM";
                   type empty;
                 }
                 leaf convey-loss-threshold {
                   description "Include Loss Threshold OUI TLV in CCM";
                   type empty;
                 }
                 leaf interface-status-send-rdi {
                   description "Send RDI on interface operation status down in CCM";
                   type empty;
                 }
                 container sendid-tlv {
                   description "Include sendid-tlv in CCM/LBM/LTM";
                   uses apply-advanced;
                   leaf send-chassis-tlv {
                     description "Attach Chassis ID & Mgmt Addr to CCM/LBM/LTM";
                     type empty;
                   }
                 }
               }
               leaf mip-half-function {
                 description "Half function to be implemented by MIP";
                 default "defer";
                 type enumeration {
                   enum "none" {
                     description "No MHFs should be created";
                   }
                   enum "default" {
                     description "Create MHF as per IEEE 802.1ag specifications for defMHFDefault";
                   }
                   enum "explicit" {
                     description "Create MHF as per IEEE 802.1ag specifications for defMHFExplicit";
                   }
                   enum "defer" {
                     description "Create MHF as per IEEE 802.1ag specifications for defMHFDefer";
                   }
                 }
               }
               list mep {
                 key name;
                 ordered-by user;
                 description "Maintenance association endpoint configuration";
                 leaf name {
                   description "Identifier for maintenance association endpoint";
                   type union {
                     type string {
                       pattern "<.*>|$.*";
                     }
                     type uint16 {
                       range "1 .. 8191";
                     }
                   }
                 }
                 uses apply-advanced;
                 container interface {
                   presence "enable interface";
                   description "Name of interface";
                   leaf interface-name {
                     junos:must "(!(\"protocols oam ethernet link-fault-management interface $$\"))";
                     junos:must-message "Connectivtiy and link fault management protocols cannot be enabled on same interface";
                     junos:must "((!(any \"interfaces $$ unit <*> vlan-id 0\") && !(any \"logical-systems <*> interfaces $$ unit <*> vlan-id 0\")))";
                     junos:must-message "Cannot create a MEP on a physical interface which has a logical interface configured with vlan-id 0";
                     junos:must "(!(any \"interfaces $$ unit 0 family inet address <*>\"))";
                     junos:must-message "CFM interface cannot be configured with an INET address";
                     type union {
                       type jt:interface-unit;
                       type string {
                         pattern "<.*>|$.*";
                       }
                     }
                   }
                   leaf vlan {
                     description "Trunk port interface VLAN identifier";
                     type union {
                       type string {
                         pattern "<.*>|$.*";
                       }
                       type uint32 {
                         range "1 .. 4094";
                       }
                     }
                   }
                   choice connection-type {
                     case case_1 {
                       leaf working {
                         description "Monitory the primary path";
                         type empty;
                       }
                     }
                     case case_2 {
                       leaf protect {
                         description "Monitory the protect path";
                         type empty;
                       }
                     }
                   }
                 }
                 leaf direction {
                   description "Direction of maintenance endpoint";
                   default "down";
                   type enumeration {
                     enum "up" {
                     }
                     enum "down" {
                       junos:must "(!(\".. .. mip-half-function\"))";
                       junos:must-message "Cannot specify MA MHF with down MEP";
                       junos:must "(!(\".. .. .. mip-half-function\"))";
                       junos:must-message "Cannot specify MD MHF with down MEP";
                     }
                   }
                 }
                 leaf priority {
                   description "802.1p priority of continuity-check and link-trace packet";
                   default "0";
                   type union {
                     type string {
                       pattern "<.*>|$.*";
                     }
                     type uint32 {
                       range "0 .. 7";
                     }
                   }
                 }
                 leaf auto-discovery {
                   description "Accept continuity-check messages from all remote MEPs";
                   type empty;
                 }
                 leaf action-profile {
                   description "Name of the action profile";
                   junos:must "(!(\"protocols oam ethernet connectivity-fault-management action-profile $$ action asynchronous-notification\"))";
                   junos:must-message "Action asynchronous-notificaiton can not be configured at mep level";
                   junos:must "(\"protocols oam ethernet connectivity-fault-management action-profile $$\")";
                   junos:must-message "Action profile not configured";
                   type string;
                 }
                 list remote-mep {
                   key name;
                   ordered-by user;
                   description "Remote maintenance association endpoint configuration";
                   leaf name {
                     description "Identifier for remote maintenance association endpoint";
                     type union {
                       type string {
                         pattern "<.*>|$.*";
                       }
                       type uint16 {
                         range "1 .. 8191";
                       }
                     }
                   }
                   uses apply-advanced;
                   leaf action-profile {
                     description "Name of the action profile";
                     junos:must "(\"protocols oam ethernet connectivity-fault-management action-profile $$\")";
                     junos:must-message "Action profile not configured";
                     type string;
                   }
                   container interface-group {
                     presence "enable interface-group";
                     description "Mark this interface group down Profile configured with action interface-group-down";
                     uses apply-advanced;
                     leaf interface-device-name {
                       description "Interface device name";
                       type union {
                         type jt:interface-device;
                         type string {
                           pattern "<.*>|$.*";
                         }
                       }
                     }
                     leaf-list unit-list {
                       description "One or more logical interface unit numbers";
                       type jt:range;
                     }
                   }
                   list sla-iterator-profile {
                     key name;
                     ordered-by user;
                     description "Name of the iterator profile";
                     leaf name {
                       junos:must "((!(\".. .. .. no-delegate-processing\") || (\"protocols oam ethernet connectivity-fault-management performance-monitoring sla-iterator-profiles ${sla-iterator-profile} measurement-type loss\" || \"protocols oam ethernet connectivity-fault-management performance-monitoring sla-iterator-profiles ${sla-iterator-profile} measurement-type slm\")))";
                       junos:must-message "Iterator two-way-delay or statistical-frame-loss measurement is not supported with mep level no-delegate-processing";
                       junos:must "(\"protocols oam ethernet connectivity-fault-management performance-monitoring sla-iterator-profiles $$\")";
                       junos:must-message "The SLA iterator profile must be configured";
                       type string;
                     }
                     uses apply-advanced;
                     leaf iteration-count {
                       description "Iterations to partake for acquiring SLA measurements";
                       units "frames";
                       junos:must "(!(\"protocols oam ethernet connectivity-fault-management performance-monitoring measurement-interval\"))";
                       junos:must-message "Iteration-count not supported with measurement-interval";
                       type union {
                         type string {
                           pattern "<.*>|$.*";
                         }
                         type uint32 {
                           range "1 .. 65535";
                         }
                       }
                     }
                     leaf priority {
                       description "The vlan pcp value to be sent in the Y.1731 frame";
                       type union {
                         type string {
                           pattern "<.*>|$.*";
                         }
                         type uint32 {
                           range "0 .. 7";
                         }
                       }
                     }
                     leaf data-tlv-size {
                       description "Size of the data-tlv portion of Y.1731 frame";
                       units "bytes";
                       junos:must "((\"protocols oam ethernet connectivity-fault-management performance-monitoring sla-iterator-profiles ${sla-iterator-profile} measurement-type two-way-delay\" || (\"protocols oam ethernet connectivity-fault-management performance-monitoring sla-iterator-profiles ${sla-iterator-profile} measurement-type statistical-frame-loss\" || \"protocols oam ethernet connectivity-fault-management performance-monitoring sla-iterator-profiles ${sla-iterator-profile} measurement-type slm\")))";
                       junos:must-message "The measurement type must be two-way-delay or statistical-frame-loss or slm";
                       type union {
                         type string {
                           pattern "<.*>|$.*";
                         }
                         type uint32 {
                           range "1 .. 1400";
                         }
                       }
                     }
                   }
                   leaf detect-loc {
                     description "Detects initial loss of connectivity with remote mep";
                     type empty;
                   }
                 }
                 leaf lowest-priority-defect {
                   description "Lowest priority defect that is allowed to generate a fault alarm";
                   type enumeration {
                     enum "all-defects" {
                       description "Allows all defects";
                     }
                     enum "mac-rem-err-xcon" {
                       description "Allows only MAC, not receiving CCM, erroneous CCM and cross connect defects";
                     }
                     enum "rem-err-xcon" {
                       description "Allows only not receiving CCM, erroneous CCM and cross connect CCM defects";
                     }
                     enum "err-xcon" {
                       description "Allows only erroneous CCM and cross connect CCM defects";
                     }
                     enum "xcon" {
                       description "Allows only cross connect CCM defect";
                     }
                     enum "no-defect" {
                       description "Allows no defect";
                     }
                   }
                 }
               }
               container policer {
                 description "Rate limit Ethernet OAM packets for this session";
                 uses apply-advanced;
                 leaf continuity-check {
                   description "Policer to rate limit Continuity Check Ethernet OAM messages";
                   junos:must "(\"firewall policer $$\")";
                   junos:must-message "referenced policer must be defined";
                   type string;
                 }
                 leaf other {
                   description "Policer to rate limit non Continuity Check Ethernet OAM messages";
                   junos:must "(\"firewall policer $$\")";
                   junos:must-message "referenced policer must be defined";
                   type string;
                 }
                 leaf all {
                   description "Policer to rate limit all Ethernet OAM messages";
                   junos:must "(\"firewall policer $$\")";
                   junos:must-message "referenced policer must be defined";
                   type string;
                 }
               }
             }
           }
           container sendid-tlv {
             description "Include sendid-tlv in CCM/LBM/LTM";
             uses apply-advanced;
             leaf send-chassis-tlv {
               description "Attach Chassis ID & Mgmt Addr to CCM/LBM/LTM";
               type empty;
             }
           }
         }
         list evcs {
           key name;
           description "Ethernet virtual circuits configuration";
           leaf name {
             description "EVC id";
             type string {
               length "1 .. 100";
               junos:posix-pattern "!^((__.*__)|(.{100,})|(.*[+].*))$";
               junos:pattern-message "Must be a non-reserved string of 100 characters or less";
             }
           }
           uses apply-advanced;
           container evc-protocol {
             description "Signaling protocol to monitor EVC status";
             choice protocol {
               case case_1 {
                 container cfm {
                   presence "enable cfm";
                   description "Connectivity fault management";
                   leaf maintenance-domain {
                     description "Maintenance domain name";
                     junos:must "(\"protocols oam ethernet connectivity-fault-management maintenance-domain $$\")";
                     junos:must-message "referenced maintenance-domain must be defined";
                     type string;
                   }
                   leaf maintenance-association {
                     description "Maintenance association name";
                     junos:must "(any \"protocols oam ethernet connectivity-fault-management maintenance-domain <*> maintenance-association $$\")";
                     junos:must-message "referenced maintenance-association must be defined";
                     type string;
                   }
                   leaf mep {
                     description "Identifier for maintenance association endpoint";
                     junos:must "(any \"protocols oam ethernet connectivity-fault-management maintenance-domain <*> maintenance-association <*> mep $$\")";
                     junos:must-message "referenced maintenance association endpoint must be defined";
                     type union {
                       type string {
                         pattern "<.*>|$.*";
                       }
                       type uint16 {
                         range "1 .. 8191";
                       }
                     }
                   }
                 }
               }
               case case_2 {
                 container vpls {
                   presence "enable vpls";
                   description "Virtual private LAN service (BGP/LDP)";
                   leaf routing-instance {
                     description "Routing instance name";
                     junos:must "((\"routing-instances $$ instance-type vpls\" || (\"routing-instances $$ instance-type virtual-switch\" && \"routing-instances $$ protocols vpls\")))";
                     junos:must-message "referenced routing-instnace must be of instance-type vpls or instance-type virtual-swicth with protocols vpls configured";
                     junos:must "((\"routing-instances $$\" || any \"tenants <*> routing-instances $$\"))";
                     junos:must-message "referenced routing-instance must be defined";
                     type string;
                   }
                 }
               }
               case case_3 {
               }
               case case_4 {
               }
             }
           }
           leaf remote-uni-count {
             description "Number of remote UNIs in the EVC";
             default "1";
             type union {
               type string {
                 pattern "<.*>|$.*";
               }
               type uint8 {
                 range "1 .. 255";
               }
             }
           }
           leaf multipoint-to-multipoint {
             description "Multipoint to Multipoint EVC";
             type empty;
           }
         }
         container lmi {
           presence "enable lmi";
           description "Ethernet local management interface configuration";
           uses apply-advanced;
           container traceoptions {
             description "Trace options for ethernet local management interface";
             uses apply-advanced;
             leaf no-remote-trace {
               description "Disable remote tracing";
               junos:must "(\"system tracing\")";
               junos:must-message "'no-remote-trace' is valid only when [system tracing] is configured";
               type empty;
             }
             container file {
               description "Trace file information";
               leaf filename {
                 description "Name of file in which to write trace information";
                 type string {
                   length "1 .. 1024";
                   junos:posix-pattern "![/ %]";
                   junos:pattern-message "Must not contain '/', % or a space";
                 }
               }
               leaf size {
                 description "Maximum trace file size";
                 type string;
               }
               leaf files {
                 description "Maximum number of trace files";
                 default "3";
                 type union {
                   type string {
                     pattern "<.*>|$.*";
                   }
                   type uint32 {
                     range "2 .. 1000";
                   }
                 }
               }
               choice world-readable-choice {
                 leaf world-readable {
                   description "Allow any user to read the log file";
                   type empty;
                 }
                 leaf no-world-readable {
                   description "Don't allow any user to read the log file";
                   type empty;
                 }
               }
               leaf match {
                 description "Regular expression for lines to be logged";
                 type jt:regular-expression;
               }
             }
             list flag {
               key name;
               ordered-by user;
               description "Tracing parameters";
               leaf name {
                 type enumeration {
                   enum "configuration" {
                     description "Trace configuration events";
                   }
                   enum "routing-socket" {
                     description "Trace routing socket events";
                   }
                   enum "protocol" {
                     description "Trace protocol processing events";
                   }
                   enum "init" {
                     description "Trace events related to protocol daemon start-up";
                   }
                   enum "error" {
                     description "Trace events related to catestrophic errors in daemon";
                   }
                   enum "packet" {
                     description "Trace events related to packet flow";
                   }
                   enum "all" {
                     description "Trace everything";
                   }
                 }
               }
             }
           }
           leaf status-counter {
             description "E-LMI status counter (N393)";
             default "4";
             type union {
               type string {
                 pattern "<.*>|$.*";
               }
               type uint8 {
                 range "2 .. 10";
               }
             }
           }
           leaf polling-verification-timer {
             description "Polling verification timer (T392)";
             default "15";
             units "seconds";
             type union {
               type string {
                 pattern "<.*>|$.*";
               }
               type uint8 {
                 range "5 .. 30";
               }
             }
           }
           list interface {
             key name;
             description "Interface options";
             leaf name {
               type union {
                 type jt:interface-device;
                 type string {
                   pattern "<.*>|$.*";
                 }
               }
             }
             uses apply-advanced;
             leaf uni-id {
               description "UNI identifier";
               type string {
                 length "1 .. 64";
               }
             }
             leaf status-counter {
               description "E-LMI status counter (N393)";
               default "4";
               type union {
                 type string {
                   pattern "<.*>|$.*";
                 }
                 type uint8 {
                   range "2 .. 10";
                 }
               }
             }
             leaf polling-verification-timer {
               description "Polling verification timer (T392)";
               default "15";
               units "seconds";
               type union {
                 type string {
                   pattern "<.*>|$.*";
                 }
                 type uint8 {
                   range "5 .. 30";
                 }
               }
             }
             leaf evc-map-type {
               description "CE-VLAN ID/EVC map type";
               default "bundling";
               type enumeration {
                 enum "all-to-one-bundling" {
                   description "All to one bundling";
                 }
                 enum "service-multiplexing" {
                   description "Service multiplexing with no bundling";
                 }
                 enum "bundling" {
                   description "Bundling with service multiplexing";
                 }
               }
             }
             list evc {
               key name;
               description "EVC configuration";
               leaf name {
                 description "EVC identifier";
                 junos:must "(\"protocols oam ethernet evcs $$\")";
                 junos:must-message "referenced evc must be defined";
                 type string {
                   length "1 .. 100";
                 }
               }
               uses apply-advanced;
               leaf default-evc {
                 description "Default EVC";
                 type empty;
               }
               leaf-list vlan-list {
                 description "Vlans mapped to this EVC";
                 type jt:vlan-range;
               }
             }
           }
         }
         container fnp {
           presence "enable fnp";
           description "Failure notification protocol configuration";
           uses apply-advanced;
           container traceoptions {
             description "Tracing options for FNP";
             uses apply-advanced;
             container file {
               description "Trace file options";
               leaf filename {
                 description "Name of file in which to write trace information";
                 type string {
                   length "1 .. 1024";
                   junos:posix-pattern "![/ %]";
                   junos:pattern-message "Must not contain '/', % or a space";
                 }
               }
               leaf replace {
                 description "Replace trace file rather than appending to it";
                 status deprecated;
                 type empty;
               }
               leaf size {
                 description "Maximum trace file size";
                 type string;
               }
               leaf files {
                 description "Maximum number of trace files";
                 default "10";
                 type union {
                   type string {
                     pattern "<.*>|$.*";
                   }
                   type uint32 {
                     range "2 .. 1000";
                   }
                 }
               }
               leaf no-stamp {
                 description "Do not timestamp trace file";
                 status deprecated;
                 type empty;
               }
               choice world-readable-choice {
                 leaf world-readable {
                   description "Allow any user to read the log file";
                   type empty;
                 }
                 leaf no-world-readable {
                   description "Don't allow any user to read the log file";
                   type empty;
                 }
               }
             }
             list flag {
               key name;
               ordered-by user;
               description "Tracing parameters";
               leaf name {
                 type enumeration {
                   enum "events" {
                     description "Trace protocol events";
                   }
                   enum "pdu" {
                     description "Trace PDU reception and transmission";
                   }
                   enum "timers" {
                     description "Trace protocol timers";
                   }
                   enum "error" {
                     description "Trace all failure conditions";
                   }
                   enum "all" {
                     description "Trace all";
                   }
                 }
               }
             }
           }
           leaf interval {
             description "Interval between FNP messages";
             default "1s";
             type enumeration {
               enum "100ms" {
               }
               enum "1s" {
               }
               enum "10s" {
               }
               enum "1m" {
               }
               enum "10m" {
               }
             }
           }
           leaf loss-threshold {
             description "Number of FNP messages lost before clearing FNP state";
             default "4";
             type union {
               type string {
                 pattern "<.*>|$.*";
               }
               type uint8 {
                 range "3 .. 255";
               }
             }
           }
           list interface {
             key name;
             ordered-by user;
             description "Interface configuration";
             leaf name {
               junos:must "(\"interfaces $$ encapsulation vlan-vpls\")";
               junos:must-message "FNP is allowed on interfaces with vlan-vpls encapsulation only.";
               type union {
                 type jt:interface-name;
                 type string {
                   pattern "<.*>|$.*";
                 }
               }
             }
             uses apply-advanced;
             leaf domain-id {
               description "Ethernet domain identifier";
               default "0";
               type union {
                 type uint32;
                 type string {
                   pattern "<.*>|$.*";
                 }
               }
             }
           }
         }
       }
     }
     container ancp {
       description "Access Node Control Protocol options";
       uses juniper-protocols-ancp;
     }
     container bfd {
       description "Bidirectional Forwarding Detection (BFD) options";
       uses apply-advanced;
       container traceoptions {
         description "Trace options for BFD";
         uses apply-advanced;
         leaf no-remote-trace {
           description "Disable remote tracing";
           junos:must "(\"system tracing\")";
           junos:must-message "'no-remote-trace' is valid only when [system tracing] is configured";
           type empty;
         }
         container file {
           description "Trace file information";
           leaf filename {
             description "Name of file in which to write trace information";
             type string {
               length "1 .. 1024";
               junos:posix-pattern "![/ %]";
               junos:pattern-message "Must not contain '/', % or a space";
             }
           }
           leaf size {
             description "Maximum trace file size";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           ordered-by user;
           description "Trace flag information";
           leaf name {
             type enumeration {
               enum "adjacency" {
                 description "Trace adjacency messages";
               }
               enum "event" {
                 description "Trace all events";
               }
               enum "error" {
                 description "Trace all errors";
               }
               enum "rtsock" {
                 description "Trace all rtscok messages";
               }
               enum "packet" {
                 description "Trace all packets";
               }
               enum "ppm-packet" {
                 description "Trace packet activity by periodic packet management";
               }
               enum "pipe" {
                 description "Trace pipe messages";
               }
               enum "pipe-detail" {
                 description "Trace pipe messages in detail";
               }
               enum "state" {
                 description "Trace state transitions";
               }
               enum "timer" {
                 description "Trace timer processing";
               }
               enum "nsr-synchronization" {
                 description "Trace NSR synchronization events";
               }
               enum "nsr-packet" {
                 description "Trace packet activity of NSR";
               }
               enum "issu" {
                 description "Trace ISSU packet activity";
               }
               enum "slow-start" {
                 description "Trace slow-start activity";
               }
               enum "session" {
                 description "Per session activity";
               }
               enum "all" {
                 description "Trace everything";
               }
             }
           }
         }
       }
       leaf no-issu-timer-negotiation {
         description "Disable ISSU timer negotiation";
         type empty;
       }
       container sbfd {
         description "Seamless BFD parameters";
         uses apply-advanced;
         leaf-list pool {
           description "List of seamless BFD endpoints";
           type union {
             type uint32;
             type string {
               pattern "<.*>|$.*";
             }
           }
         }
         list local-discriminator {
           key name;
           ordered-by user;
           description "Local discriminator for seamless BFD responder";
           leaf name {
             description "Local discriminator for seamless BFD responder";
             type union {
               type string {
                 pattern "<.*>|$.*";
               }
               type uint32 {
                 range "1 .. 4294967295";
               }
             }
           }
           uses apply-advanced;
           leaf minimum-receive-interval {
             description "Minimum receive interval for seamless BFD responder";
             units "milliseconds";
             type union {
               type string {
                 pattern "<.*>|$.*";
               }
               type uint32 {
                 range "10 .. 255000";
               }
             }
           }
           leaf local-ip-address {
             description "IPv4 source address";
             type jt:ipv4addr;
           }
         }
       }
     }
     container ptp {
       description "Precision Time Protocol v2 options";
       uses apply-advanced;
       leaf clock-mode {
         description "Clock mode";
         type enumeration {
           enum "ordinary" {
             description "PTP Ordinary clock";
           }
           enum "boundary" {
             description "PTP Boundary clock";
           }
         }
       }
       leaf e2e-transparent {
         description "Enable end-to-end IEEE1588 transparent clock functionality";
         type empty;
       }
       leaf syntonized-e2e-transparent {
         description "Enable end-to-end Syntonized IEEE1588 transparent clock functionality";
         type empty;
       }
       leaf priority1 {
         description "Used in selecting best master clock";
         junos:must "(\"protocols ptp clock-mode\")";
         junos:must-message "Must configure 'protocols ptp clock-mode'";
         junos:must "(!((\"protocols ptp profile-type $$={g.8275.1}\" || (\"protocols ptp profile-type $$={g.8275.1.enh}\" || (\"protocols ptp profile-type $$={g.8275.2}\" || \"protocols ptp profile-type $$={g.8275.2.enh}\")))))";
         junos:must-message "Attribute not supported with profile-type
                          g.8275.1, g.8275.1 Enhanced, g.8275.2 or g.8275.2 Enhanced";
         type union {
           type string {
             pattern "<.*>|$.*";
           }
           type int32 {
             range "0 .. 255";
           }
         }
       }
       leaf priority2 {
         description "Tie-breaker in selecting best master clock";
         junos:must "(\"protocols ptp clock-mode\")";
         junos:must-message "Must configure 'protocols ptp clock-mode'";
         type union {
           type string {
             pattern "<.*>|$.*";
           }
           type int32 {
             range "0 .. 255";
           }
         }
       }
       leaf local-priority {
         description "Priority assigned to the local clock";
         junos:must "((\"protocols ptp profile-type\" && (\"protocols ptp profile-type $$={g.8275.1}\" || (\"protocols ptp profile-type $$={g.8275.1.enh}\" || \"protocols ptp profile-type $$={g.8275.2.enh}\"))))";
         junos:must-message "Attribute only supported with profile-type
                          g.8275.1, g.8275.1 Enhanced or g.8275.2 Enhanced";
         type union {
           type string {
             pattern "<.*>|$.*";
           }
           type uint32 {
             range "1 .. 255";
           }
         }
       }
       leaf domain {
         description "PTP domain number";
         junos:must "(\"protocols ptp clock-mode\")";
         junos:must-message "Must configure 'protocols ptp clock-mode'";
         type union {
           type string {
             pattern "<.*>|$.*";
           }
           type int32 {
             range "0 .. 127";
           }
         }
       }
       leaf path-trace {
         description "Enable path tracing";
         junos:must "(\"protocols ptp clock-mode\")";
         junos:must-message "Must configure 'protocols ptp clock-mode'";
         junos:must "(!((\"protocols ptp profile-type $$={g.8275.1}\" || \"protocols ptp profile-type $$={g.8275.1.enh}\")))";
         junos:must-message "Attribute not supported with profile-type
                          g.8275.1 or g.8275.1 Enhanced";
         type empty;
       }
       leaf unicast-negotiation {
         description "Enable unicast negotiation";
         junos:must "(\"protocols ptp clock-mode\")";
         junos:must-message "Must configure 'protocols ptp clock-mode'";
         junos:must "(!((\"protocols ptp profile-type $$={g.8275.1}\" || (\"protocols ptp profile-type $$={g.8275.1.enh}\" || \"protocols ptp profile-type $$={g.8275.2}\"))))";
         junos:must-message "Attribute not supported with profile-type
                          g.8275.1 or g.8275.1 Enhanced or g.8275.2 ";
         type empty;
       }
       container slave {
         junos:must "(\"protocols ptp clock-mode\")";
         junos:must-message "Must configure 'protocols ptp clock-mode'";
         description "PTP Slave parameters";
         uses apply-advanced;
         leaf frequency-only {
           description "Only for frequency syntonization";
           type empty;
         }
         leaf delay-request {
           description "Log mean interval between delay requests";
           junos:must "(!(\"protocols ptp profile-type $$={g.8275.1}\"))";
           junos:must-message "Attribute not supported with 'profile-type g.8275.1'";
           type union {
             type string {
               pattern "<.*>|$.*";
             }
             type int32 {
               range "-7 .. 7";
             }
           }
         }
         leaf announce-timeout {
           description "Timeout period for announce messages";
           junos:must "(!(\"protocols ptp profile-type $$={g.8275.1}\"))";
           junos:must-message "Attribute not supported with 'profile-type g.8275.1'";
           type union {
             type string {
               pattern "<.*>|$.*";
             }
             type uint32 {
               range "2 .. 10";
             }
           }
         }
         list interface {
           key name;
           description "Interface on which to respond to upstream PTP master";
           junos:must "(!(((\"protocols ptp profile-type $$={g.8275.1}\" || \"protocols ptp profile-type $$={g.8275.1.enh}\") && \"protocols ptp stateful interface\")))";
           junos:must-message "Attribute not supported with profile-type g.8275.1
                              or g.8275.1 Enhanced when stateful ifl is configured";
           leaf name {
             description "Interface name";
             junos:must "(!((\"interfaces $$-IFD gigether-options 802.3ad\" || \"interfaces $$-IFD ether-options 802.3ad\")))";
             junos:must-message "PTP not allowed on member links of AE interface";
             type union {
               type jt:interface-name;
               type string {
                 pattern "<.*>|$.*";
               }
             }
           }
           uses apply-advanced;
           container unicast-mode {
             junos:must "(!(\"protocols ptp profile-type $$={g.8275.1}\"))";
             junos:must-message "Attribute not supported with 'profile-type g.8275.1'";
             description "Configure upstream unicast PTP master clock sources";
             uses apply-advanced;
             leaf transport {
               description "Encapsulation for PTP packet transport";
               type enumeration {
                 enum "ipv4" {
                   description "Use IPv4 as transport";
                 }
                 enum "ipv6" {
                   description "Use IPv6 as transport";
                 }
               }
             }
             leaf local-priority {
               description "Priority assigned to the port";
               junos:must "((\"protocols ptp profile-type\" && (\"protocols ptp profile-type g.8275.1\" || (\"protocols ptp profile-type g.8275.1.enh\" || (\"protocols ptp profile-type g.8275.2\" || \"protocols ptp profile-type g.8275.2.enh\")))))";
               junos:must-message "Attribute only supported with profile-type g.8275.1,
                                     g.8275.1 Enhanced, g.8275.2 or g.8275.2 Enhanced";
               type union {
                 type string {
                   pattern "<.*>|$.*";
                 }
                 type uint32 {
                   range "1 .. 255";
                 }
               }
             }
             list clock-source {
               key "ip-address local-ip-address";
               description "Configure PTP master parameters";
               leaf ip-address {
                 description "IP address of PTP master";
                 type jt:ipaddr;
               }
               leaf local-ip-address {
                 description "Must be IP address on local interface";
                 type jt:ipaddr;
               }
               uses apply-advanced;
               leaf asymmetry {
                 description "Adjust the slave-to-master delay by value specified in nanoseconds";
                 type union {
                   type string {
                     pattern "<.*>|$.*";
                   }
                   type int32 {
                     range "-100000000 .. 100000000";
                   }
                 }
               }
             }
           }
         }
       }
       container master {
         junos:must "(\"protocols ptp clock-mode\")";
         junos:must-message "Must configure 'protocols ptp clock-mode'";
         description "PTP Master parameters";
         uses apply-advanced;
         leaf announce-interval {
           description "Log mean interval between announce messages";
           junos:must "(!(\"protocols ptp profile-type $$={g.8275.2}\"))";
           junos:must-message "Attribute not supported with 'profile-type g.8275.2'";
           junos:must "(!(\"protocols ptp profile-type $$={g.8275.1}\"))";
           junos:must-message "Attribute not supported with 'profile-type g.8275.1'";
           type union {
             type string {
               pattern "<.*>|$.*";
             }
             type int32 {
               range "-3 .. 4";
             }
           }
         }
         leaf sync-interval {
           description "Log mean interval between sync messages";
           junos:must "(!(\"protocols ptp profile-type $$={g.8275.2}\"))";
           junos:must-message "Attribute not supported with 'profile-type g.8275.2'";
           junos:must "(!(\"protocols ptp profile-type $$={g.8275.1}\"))";
           junos:must-message "Attribute not supported with 'profile-type g.8275.1'";
           type union {
             type string {
               pattern "<.*>|$.*";
             }
             type int32 {
               range "-7 .. 7";
             }
           }
         }
         list interface {
           key name;
           description "Interface on which to respond to downstream PTP slaves";
           leaf name {
             description "Interface name";
             junos:must "(!((\"interfaces $$-IFD gigether-options 802.3ad\" || \"interfaces $$-IFD ether-options 802.3ad\")))";
             junos:must-message "PTP not allowed on member links of AE interface";
             type union {
               type jt:interface-name;
               type string {
                 pattern "<.*>|$.*";
               }
             }
           }
           uses apply-advanced;
           container unicast-mode {
             junos:must "(!(\"protocols ptp profile-type $$={g.8275.1}\"))";
             junos:must-message "Attribute not supported with 'profile-type g.8275.1'";
             description "Configure downstream PTP clock slaves";
             uses apply-advanced;
             leaf transport {
               description "Encapsulation for PTP packet transport";
               type enumeration {
                 enum "ipv4" {
                   description "Use IPv4 as transport";
                 }
                 enum "ipv6" {
                   description "Use IPv6 as transport";
                 }
               }
             }
             list clock-client {
               key "ip-address local-ip-address";
               description "Configure PTP master parameters";
               leaf ip-address {
                 description "IP address or subnet of remote PTP slave";
                 type jt:ipprefix;
               }
               leaf local-ip-address {
                 description "IP address of local PTP master interface";
                 type jt:ipaddr;
               }
               uses apply-advanced;
               leaf manual {
                 description "This slave does not use unicast negotiation";
                 junos:must "(!((\"protocols ptp unicast-negotiation\" && \"protocols ptp profile-type $$={g.8275.2.enh}\")))";
                 junos:must-message "Attribute not supported when unicast-negotiation
                                          is configured with profile-type g.8275.2.enh";
                 type empty;
               }
               container l2-ifl {
                 uses apply-advanced;
               }
             }
           }
         }
       }
     }
     container dot1x {
       description "802.1X options";
       uses juniper-protocols-dot1x;
     }
     container ppp-service {
       description "Configure PPP service";
       uses apply-advanced;
       container traceoptions {
         description "Trace options for PPP service";
         uses apply-advanced;
         leaf no-remote-trace {
           description "Disable remote tracing";
           junos:must "(\"system tracing\")";
           junos:must-message "'no-remote-trace' is valid only when [system tracing] is configured";
           type empty;
         }
         container file {
           description "Trace file information";
           leaf filename {
             description "Name of file in which to write trace information";
             type string {
               length "1 .. 1024";
               junos:posix-pattern "![/ %]";
               junos:pattern-message "Must not contain '/', % or a space";
             }
           }
           leaf size {
             description "Maximum trace file size";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         leaf level {
           description "Level of debugging output";
           default "error";
           type enumeration {
             enum "error" {
               description "Match error conditions";
             }
             enum "warning" {
               description "Match warning messages";
             }
             enum "notice" {
               description "Match conditions that should be handled specially";
             }
             enum "info" {
               description "Match informational messages";
             }
             enum "verbose" {
               description "Match verbose messages";
             }
             enum "all" {
               description "Match all levels";
             }
           }
         }
         list flag {
           key name;
           ordered-by user;
           description "Area of PPP service to enable debugging output";
           leaf name {
             type enumeration {
               enum "accounting-statistics" {
                 description "Trace accounting statistics events";
               }
               enum "authentication" {
                 description "Trace authentication code";
               }
               enum "chap" {
                 description "Trace CHAP code";
               }
               enum "events" {
                 description "Trace interface events";
               }
               enum "gres" {
                 description "Trace GRES events";
               }
               enum "init" {
                 description "Trace daemon initialization";
               }
               enum "interface-db" {
                 description "Trace interface database code";
               }
               enum "lcp" {
                 description "Trace LCP state machine code";
               }
               enum "memory" {
                 description "Trace memory management code";
               }
               enum "ncp" {
                 description "Trace NCP state machine code";
               }
               enum "packet-error" {
                 description "Trace Packet error events";
               }
               enum "pap" {
                 description "Trace PAP code";
               }
               enum "parse" {
                 description "Trace parsing events";
               }
               enum "profile" {
                 description "Trace libdynamic-profile events";
               }
               enum "receive-packets" {
                 description "Trace received PPP packets";
               }
               enum "routing-process" {
                 description "Trace routing process interactions";
               }
               enum "rtp" {
                 description "Trace RealTimePriority code";
               }
               enum "rtsock" {
                 description "Trace routing socket code";
               }
               enum "session-db" {
                 description "Trace session database interactions";
               }
               enum "smi-services-sentry" {
                 description "Trace SMI services requests/retries";
               }
               enum "states" {
                 description "Trace state machine events";
               }
               enum "transmit-packets" {
                 description "Trace tranmitted PPP packets";
               }
               enum "tunnel" {
                 description "Trace l2tp tunneling";
               }
               enum "all" {
                 description "Trace all areas of code";
               }
             }
           }
         }
         container filter {
           presence "enable filter";
           description "Trace filtering";
           uses apply-advanced;
           leaf aci {
             description "Regular expression to match ACI";
             type string {
               length "1 .. 64";
               junos:posix-pattern "^[*]*.[^*]*[*]*$";
               junos:pattern-message "Must be a non-reserved string";
             }
           }
           leaf ari {
             description "Regular expression to match ARI";
             type string {
               length "1 .. 64";
               junos:posix-pattern "^[*]*.[^*]*[*]*$";
               junos:pattern-message "Must be a non-reserved string";
             }
           }
           leaf service-name {
             description "Service name";
             type string {
               length "1 .. 64";
               junos:posix-pattern "^([[:alnum:]][[:alnum:]_-]*)|([*][[:alnum:]_-]{1,})[*]?$";
               junos:pattern-message "Must be a non-reserved string";
             }
           }
           leaf underlying-interface {
             description "Underlying interface name";
             junos:must "((\"interfaces $$-IFL encapsulation ppp-over-ether\" || (\"interfaces $$-IFL encapsulation ppp-over-ether-over-atm-llc\" || \"interfaces $$-IFL family pppoe\")))";
             junos:must-message "Underlying interface must be configured";
             type string;
           }
         }
       }
       leaf max-failures {
         description "Max-Failures";
         type union {
           type string {
             pattern "<.*>|$.*";
           }
           type uint32 {
             range "1 .. 10";
           }
         }
       }
       leaf on-demand-ip-address {
         description "Enable On-Demand IPv4 address allocation and de-allocation";
         type empty;
       }
       leaf reject-unauthorized-ipv6cp {
         description "Reject IPv6 NCP if no appropriate IPv6 address or prefix is authorized";
         type empty;
       }
       container required-address {
         presence "enable required-address";
         description "Session address requirement";
         uses apply-advanced;
         leaf ip {
           description "Terminate session if no appropriate IP address is authorized";
           type empty;
         }
       }
       leaf pppoe-lcp-options-strict {
         description "Enforce RFC 2516 MUST requirements for FCS, ACFC and ACCM";
         type empty;
       }
       leaf source-interface-set-at-login {
         description "Generate interface-set name for use during login";
         type enumeration {
           enum "svlan" {
             description "Compose interface-set name from physical IFD and outer VLAN tag";
           }
         }
       }
     }
     container overlay {
       description "Overlay protocol";
       uses juniper-protocols-overlayd;
     }
     container vrrp {
       description "VRRP options";
       uses apply-advanced;
       container traceoptions {
         description "Trace options for VRRP";
         uses apply-advanced;
         leaf no-remote-trace {
           description "Disable remote tracing";
           junos:must "(\"system tracing\")";
           junos:must-message "'no-remote-trace' is valid only when [system tracing] is configured";
           type empty;
         }
         container file {
           description "Trace file information";
           leaf filename {
             description "Name of file in which to write trace information";
             type string {
               length "1 .. 1024";
               junos:posix-pattern "![/ %]";
               junos:pattern-message "Must not contain '/', % or a space";
             }
           }
           leaf size {
             description "Maximum trace file size";
             type string;
           }
           leaf files {
             description "Maximum number of trace files";
             default "3";
             type union {
               type string {
                 pattern "<.*>|$.*";
               }
               type uint32 {
                 range "0 .. 4294967295";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
           leaf microsecond-stamp {
             description "Timestamp with microsecond granularity";
             type empty;
           }
         }
         list flag {
           key name;
           ordered-by user;
           description "Tracing parameters";
           leaf name {
             type enumeration {
               enum "database" {
                 description "Trace database";
               }
               enum "general" {
                 description "Trace general events";
               }
               enum "interfaces" {
                 description "Trace interface messages";
               }
               enum "normal" {
                 description "Trace normal events";
               }
               enum "packets" {
                 description "Trace packets";
               }
               enum "state" {
                 description "Trace state transitions";
               }
               enum "timer" {
                 description "Trace timer events";
               }
               enum "ppm" {
                 description "VRRP PPM related messages";
               }
               enum "all" {
                 description "Trace all events";
               }
             }
           }
         }
       }
       leaf failover-delay {
         description "Additional failover delay timer";
         units "milliseconds";
         type union {
           type string {
             pattern "<.*>|$.*";
           }
           type uint32 {
             range "50 .. 100000";
           }
         }
       }
       leaf startup-silent-period {
         description "Period for ignoring master down timer at device startup";
         units "seconds";
         type union {
           type string {
             pattern "<.*>|$.*";
           }
           type uint32 {
             range "1 .. 2000";
           }
         }
       }
       leaf asymmetric-hold-time {
         description "Priority hold time asymmetric behaviour";
         type empty;
       }
       container delegate-processing {
         presence "enable delegate-processing";
         description "Switch to distributed PPMD";
         uses apply-advanced;
       }
       leaf skew-timer-disable {
         description "Disable the skew timer";
         type empty;
       }
       leaf global-advertisements-threshold {
         description "Number of vrrp advertisements missed before declaring master down";
         default "3";
         type union {
           type string {
             pattern "<.*>|$.*";
           }
           type uint32 {
             range "1 .. 15";
           }
         }
       }
       leaf inherit-advertisement-interval {
         description "Advertisement interval for inherit sessions";
         default "120";
         type union {
           type string {
             pattern "<.*>|$.*";
           }
           type uint32 {
             range "5 .. 120";
           }
         }
       }
       leaf version-3 {
         description "VRRPv3 conformance";
         type empty;
       }
     }
     container pgm {
       description "PGM options";
       presence "enable pgm";
       status deprecated;
       uses juniper-protocols-pgm;
     }
     container amt {
       description "AMT configuration";
       uses juniper-protocols-amt;
     }
     container bgp {
       description "BGP options";
       uses juniper-protocols-bgp;
     }
     container bgpmcast {
       description "BGP multicast options";
       presence "enable bgpmcast";
       uses juniper-protocols-bgpmcast;
     }
     container connections {
       description "Circuit cross-connect configuration";
       uses apply-advanced;
       list interface-switch {
         key name;
         ordered-by user;
         description "Bidirectional switch between interfaces";
         leaf name {
           description "Name of interface switch";
           type string {
             junos:posix-pattern "^.{1,128}$";
             junos:pattern-message "Must be a string of 128 characters or less";
           }
         }
         uses apply-advanced;
         list interface {
           key name;
           ordered-by user;
           description "Interface to be switched";
           leaf name {
             description "Interface name";
             junos:must "(!(any \"protocols l2circuit neighbor <*> interface $$\"))";
             junos:must-message "interface cannot be specified in another l2circuit";
             junos:must "(!(any \"routing-instances <*> interface $$\"))";
             junos:must-message "interface cannot be specified in another routing instance";
             type union {
               type jt:interface-name;
               type string {
                 pattern "<.*>|$.*";
               }
             }
           }
           uses apply-advanced;
         }
       }
       list remote-interface-switch {
         key name;
         ordered-by user;
         description "Bidirectional switch between a local and a remote interface";
         leaf name {
           description "Name of remote interface switch";
           type string {
             junos:posix-pattern "^.{1,128}$";
             junos:pattern-message "Must be a string of 128 characters or less";
           }
         }
         uses apply-advanced;
         leaf interface {
           description "Local interface name";
           junos:must "(!(any \"protocols l2circuit neighbor <*> interface $$\"))";
           junos:must-message "interface cannot be specified in another l2circuit";
           junos:must "(!(any \"routing-instances <*> interface $$\"))";
           junos:must-message "interface cannot be specified in another routing instance";
           type union {
             type jt:interface-name;
             type string {
               pattern "<.*>|$.*";
             }
           }
         }
         leaf transmit-lsp {
           description "Name of outgoing label-switched path";
           junos:must "(!(\".. .. .. mpls label-switched-path $$ ultimate-hop-popping\"))";
           junos:must-message "Circuit cross-connect cannot use referenced ultimate-hop-poping ingress LSP";
           junos:must "(!(\".. .. .. mpls ultimate-hop-popping\"))";
           junos:must-message "Circuit cross-connect cannot use any ultimate-hop-popping ingress LSP";
           type string;
         }
         leaf receive-lsp {
           description "Name of incoming label-switched path";
           type string;
         }
       }
       list lsp-switch {
         key name;
         ordered-by user;
         description "Unidirectional switch between two label-switched paths";
         leaf name {
           description "Name of label-switched path switch";
           type string {
             junos:posix-pattern "^.{1,128}$";
             junos:pattern-message "Must be a string of 128 characters or less";
           }
         }
         uses apply-advanced;
         leaf transmit-lsp {
           description "Name of outgoing label-switched path";
           junos:must "(!(\".. .. .. mpls label-switched-path $$ ultimate-hop-popping\"))";
           junos:must-message "Circuit cross-connect cannot use referenced ultimate-hop-poping ingress LSP";
           junos:must "(!(\".. .. .. mpls ultimate-hop-popping\"))";
           junos:must-message "Circuit cross-connect cannot use any ultimate-hop-popping ingress LSP";
           type string;
         }
         leaf receive-lsp {
           description "Name of incoming label-switched path";
           type string;
         }
       }
       list p2mp-transmit-switch {
         key name;
         ordered-by user;
         description "Local interface to point-to-multipoint LSP switch";
         leaf name {
           description "Point-to-multipoint switch name on which to transmit";
           type string {
             junos:posix-pattern "^.{1,128}$";
             junos:pattern-message "Must be a string of 128 characters or less";
           }
         }
         uses apply-advanced;
         leaf input-interface {
           description "Input interface name";
           junos:must "(!(any \"protocols l2circuit neighbor <*> interface $$\"))";
           junos:must-message "interface cannot be specified in another l2circuit";
           junos:must "(!(any \"routing-instances <*> interface $$\"))";
           junos:must-message "interface cannot be specified in another routing instance";
           type union {
             type jt:interface-name;
             type string {
               pattern "<.*>|$.*";
             }
           }
         }
         leaf transmit-p2mp-lsp {
           description "Point-to-multipoint LSP name on which to transmit";
           type string;
         }
         leaf-list output-interface {
           ordered-by user;
           description "Outgoing interface name";
           type union {
             type jt:interface-name;
             type string {
               pattern "<.*>|$.*";
             }
           }
           max-elements 16;
         }
       }
       list p2mp-receive-switch {
         key name;
         ordered-by user;
         description "Point-to-multipoint LSP to local interfaces switch";
         leaf name {
           description "Point-to-multipoint switch name on which to receive";
           type string {
             junos:posix-pattern "^.{1,128}$";
             junos:pattern-message "Must be a string of 128 characters or less";
           }
         }
         uses apply-advanced;
         leaf receive-p2mp-lsp {
           description "Point-to-multipoint LSP name on which to receive";
           type string;
         }
         leaf-list output-interface {
           ordered-by user;
           description "Next outgoing interface name";
           type union {
             type jt:interface-name;
             type string {
               pattern "<.*>|$.*";
             }
           }
         }
       }
     }
     container dvmrp {
       presence "enable dvmrp";
       description "DVMRP options";
       status deprecated;
       uses apply-advanced;
       choice enable-disable {
         case case_1 {
           leaf disable {
             description "Disable DVMRP";
             type empty;
           }
         }
       }
       container traceoptions {
         description "Trace options for DVMRP";
         uses apply-advanced;
         container file {
           description "Trace file options";
           leaf filename {
             description "Name of file in which to write trace information";
             type string {
               length "1 .. 1024";
               junos:posix-pattern "![/ %]";
               junos:pattern-message "Must not contain '/', % or a space";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "route" {
                 description "Trace routing information";
               }
               enum "poison" {
                 description "Trace poison-route-reverse packets";
               }
               enum "packets" {
                 description "Trace all DVMRP packets";
               }
               enum "probe" {
                 description "Trace probe packets";
               }
               enum "report" {
                 description "Trace DVMRP route report packets";
               }
               enum "neighbor" {
                 description "Trace neighbor probe packets";
               }
               enum "prune" {
                 description "Trace prune messages";
               }
               enum "graft" {
                 description "Trace graft messages";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       container rib-group {
         description "Routing table group";
         uses rib_group_inet_type;
       }
       leaf-list import {
         ordered-by user;
         description "Import policy";
         type jt:policy-algebra;
       }
       leaf-list export {
         ordered-by user;
         description "Export policy";
         type jt:policy-algebra;
       }
       list interface {
         key name;
         ordered-by user;
         description "DVMRP interface options";
         leaf name {
           description "Interface name";
           type union {
             type jt:interface-name;
             type string {
               pattern "<.*>|$.*";
             }
           }
         }
         uses apply-advanced;
         choice enable-disable {
           case case_1 {
             leaf disable {
               description "Disable DVMRP on this interface";
               type empty;
             }
           }
         }
         leaf mode {
           description "Mode of interface";
           type enumeration {
             enum "forwarding" {
               description "Use DVMRP for multicast forwarding";
               junos:must "((\"protocols pim interface ${interface} disable\" || (!((\"protocols pim interface ${interface}\" || (\"protocols pim interface ${interface} enable\" || (\"protocols pim interface all\" || \"protocols pim interface all enable\")))) || (\"protocols pim interface all disable\" && (!(\"protocols pim interface ${interface}\") && !(\"protocols pim interface ${interface} enable\"))))))";
               junos:must-message "Cannot enable PIM and DVMRP in forwarding mode at the same time";
             }
             enum "unicast-routing" {
               description "Use DVMRP for unicast routing only";
             }
           }
         }
         leaf metric {
           description "DVMRP metric value";
           type union {
             type string {
               pattern "<.*>|$.*";
             }
             type uint32 {
               range "1 .. 32";
             }
           }
         }
         leaf hold-time {
           description "When neighbors think the interface is down";
           units "seconds";
           type union {
             type string {
               pattern "<.*>|$.*";
             }
             type uint32 {
               range "1 .. 255";
             }
           }
         }
       }
     }
     container esis {
       description "End system-intermediate system options";
       uses juniper-protocols-esis;
     }
     container evpn {
       description "Configuration EVPN default routing instance";
       uses apply-advanced;
       container traceoptions {
         description "Trace options for Layer 2 VPNs";
         uses apply-advanced;
         container file {
           description "Trace file options";
           leaf filename {
             description "Name of file in which to write trace information";
             type string {
               length "1 .. 1024";
               junos:posix-pattern "![/ %]";
               junos:pattern-message "Must not contain '/', % or a space";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "error" {
                 description "Trace errors";
               }
               enum "topology" {
                 description "Trace Layer 2 VPN, VPLS and EVPN topology changes";
               }
               enum "nlri" {
                 description "Trace Layer 2 VPN, VPLS and EVPN remote site advertisements";
               }
               enum "connections" {
                 description "Trace Layer 2 VPN and VPLS connections";
               }
               enum "automatic-site" {
                 description "Trace VPLS automatic site state";
               }
               enum "oam" {
                 description "Trace OAM messages";
               }
               enum "mac-database" {
                 description "Trace MAC route database in a EVPN instance";
               }
               enum "nsr" {
                 description "Trace NSR in a EVPN instance";
               }
               enum "egress-protection" {
                 description "Trace Edge Protection messages";
               }
               enum "instance" {
                 description "Evpn instance related messages";
               }
               enum "interface" {
                 description "Interface related messages";
               }
               enum "l2aldsync" {
                 description "Messages related to EVPN-L2ALD communication";
               }
               enum "p2mp" {
                 description "P2MP messages";
               }
               enum "esi" {
                 description "Evpn ethernet segment related messages";
               }
               enum "mcsn" {
                 description "Evpn multicast snooping related messages";
               }
               enum "vpws" {
                 description "VPWS messages";
               }
               enum "irb" {
                 description "Integrated routing bridging messages";
               }
               enum "ar" {
                 description "Assisted-replication messages";
               }
               enum "etree" {
                 description "Evpn etree messages";
               }
               enum "kernel" {
                 description "Messages related to rpd-kernel communication";
               }
               enum "bd" {
                 description "Evpn bridge domain messages";
               }
               enum "pbb" {
                 description "Evpn provider backbone bridging messages";
               }
               enum "infra" {
                 description "Messages related to infrastructure in evpn";
               }
               enum "pfxdb" {
                 description "Type-5 related messages";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       leaf mac-history {
         description "Number of history entries to be maitained per mac";
         type union {
           type string {
             pattern "<.*>|$.*";
           }
           type uint16 {
             range "0 .. 255";
           }
         }
       }
       list mac-list {
         key name;
         description "Configure MAC lists";
         leaf name {
           description "List name";
           type string {
             length "1 .. 128";
           }
         }
         uses apply-advanced;
         leaf-list mac-address {
           description "MAC address";
           type jt:mac-addr;
         }
       }
       container mac-mobility {
         description "MAC mobility settings";
         uses apply-advanced;
         leaf no-sequence-numbers {
           description "Don't use sequence numbers for MAC mobility";
           type empty;
         }
       }
       leaf no-core-isolation {
         description "Disable EVPN Core isolation";
         type empty;
       }
       leaf leave-sync-route-oldstyle {
         description "Originate leave sync route oldstyle";
         type empty;
       }
       leaf-list interconnect-multihoming-peer-gateways {
         description "Configure multihoming peer gateway VTEP IPv4 addresses";
         type jt:ipaddr;
         max-elements 64;
       }
       leaf es-import-oldstyle {
         description "Enable noncompliant ES import route-target computation";
         type empty;
       }
       leaf es-label-oldstyle {
         description "Enable noncompliant ESI 24 bit label";
         type empty;
       }
       leaf encapsulation {
         description "Encapsulation type for EVPN";
         default "mpls";
         junos:must "((((\".. .. .. instance-type virtual-switch\" || (\".. .. ..  instance-type evpn\" || (\".. .. .. instance-type mac-vrf\" || \".. .. .. instance-type evpn-vpws\"))) && !(\".. .. .. switch-options route-distinguisher\")) || \".. .. .. switch-options route-distinguisher\"))";
         junos:must-message "Encapsulation can only be configured for an EVPN instance";
         type enumeration {
           enum "mpls" {
             description "MPLS encapsulation";
           }
           enum "vxlan" {
             description "VXLAN encapsulation";
           }
           enum "mpls-inet6" {
             description "MPLS over IPv6 encapsulation";
           }
         }
       }
       container assisted-replication {
         junos:must "(!(\"forwarding-options multicast-replication evpn irb local-only\"))";
         junos:must-message "Assisted Replication is not valid with forwarding-options multicast-replication evpn irb local-only";
         junos:must "(\".. encapsulation vxlan\")";
         junos:must-message "Assisted Replication is supported only with encapsulation vxlan option";
         description "Option to enable Assisted Replication";
         uses apply-advanced;
         choice AR {
           case case_1 {
             container leaf {
               presence "enable leaf";
               description "Assisted Replicator Leaf";
               uses apply-advanced;
               leaf replicator-activation-delay {
                 description "Dealy interval in starting replication";
                 default "10";
                 units "seconds";
                 type union {
                   type string {
                     pattern "<.*>|$.*";
                   }
                   type uint32 {
                     range "0 .. 180";
                   }
                 }
               }
             }
           }
           case case_2 {
           }
         }
       }
       leaf designated-forwarder-election-hold-time {
         description "Time to wait before electing a DF(seconds)";
         units "seconds";
         type union {
           type string {
             pattern "<.*>|$.*";
           }
           type uint32 {
             range "1 .. 1800";
           }
         }
       }
       leaf designated-forwarder-preference-least {
         description "Use least preference in DF election";
         type empty;
       }
       container remote-ip-host-routes {
         presence "enable remote-ip-host-routes";
         junos:must "(!(\".. .. .. instance-type vrf\"))";
         junos:must-message "remote-ip-host-routes knob is for virtual-switch, EVPN or default instance";
         description "Virtual machine traffic optimization(VMTO) for EVPN";
         uses apply-advanced;
         leaf-list import {
           ordered-by user;
           description "Policy to control the creation of remote IP host routes";
           type jt:policy-algebra;
         }
         leaf no-advertise-community {
           description "Don't advertise Type 2 route's community";
           type empty;
         }
       }
       leaf pmsi-tunnel-endpoint {
         description "IM IR PMSI tunnel Endpoint for remote PE";
         junos:must "(!(\".. pbb-evpn-core\"))";
         junos:must-message "Not Supported for PBB EVPN";
         junos:must "(!(\".. encapsulation vxlan\"))";
         junos:must-message "Not Supported for EVPN-VXLAN encapsulation";
         junos:must "(!(\".. .. .. provider-tunnel\"))";
         junos:must-message "Not Applicable for P2MP Tunnels";
         junos:must "(!(\".. .. .. instance-type evpn-vpws\"))";
         junos:must-message "Not Applicable for instance-type EVPN-VPWS";
         type jt:ipv4addr;
       }
       leaf label-allocation {
         description "Label allocation policy";
         type enumeration {
           enum "per-bridge-domain" {
             description "Allocate one label for each bridge-domain";
           }
         }
       }
       leaf esi-resolution-per-bridge-domain {
         description "Enable ESI Resolution Per BD";
         type empty;
       }
       leaf riot-loopback {
         description "Track loopback irb interface state on RIOT platform";
         type empty;
       }
       container interconnect {
         description "Interconnect";
         junos:must "((\".. .. .. switch-options vrf-target\" || \".. .. .. switch-options vrf-export\"))";
         junos:must-message "Switch-options vrf-target or vrf-export must be configured";
         junos:must "(\".. .. .. switch-options route-distinguisher\")";
         junos:must-message "Switch-options route-distinguisher must be configured";
         uses juniper-protocols-evpn-interconnect;
       }
       leaf multicast-mode {
         description "Multicast mode for EVPN";
         default "ingress-replication";
         junos:must "(\".. encapsulation vxlan\")";
         junos:must-message "multicast-mode can only be configured with encapsulation vxlan";
         junos:must "((((\".. .. .. instance-type virtual-switch\" || \".. .. .. instance-type mac-vrf\") && !(\".. .. .. switch-options route-distinguisher\")) || \".. .. .. switch-options route-distinguisher\"))";
         junos:must-message "multicast-mode can only be configured in a virtual switch instance";
         type enumeration {
           enum "ingress-replication" {
             description "Ingress Replication";
           }
         }
       }
       container vni-options {
         description "Vni options";
         junos:must "((\".. .. .. switch-options vrf-target\" || \".. .. .. switch-options vrf-export\"))";
         junos:must-message "Switch-options vrf-target or vrf-export must be configured";
         junos:must "(\".. .. .. switch-options route-distinguisher\")";
         junos:must-message "Switch-options route-distinguisher must be configured";
         junos:must "(\".. extended-vni-list\")";
         junos:must-message "Extended-vni-list must be configured";
         uses juniper-protocols-vni-options;
       }
     }
     container express-segments {
       description "Configuration for Express Segments";
       uses apply-advanced;
       list segment-template {
         key name;
         ordered-by user;
         description "Express Segments Template Definition";
         max-elements 64;
         leaf name {
           description "Express Segment Template Name";
           type string {
             junos:posix-pattern "^.{1,64}$";
             junos:pattern-message "Must be a string of 64 characters or less";
           }
         }
         uses apply-advanced;
         leaf-list admin-group {
           ordered-by user;
           description "Administrative groups";
           type string;
           max-elements 16;
         }
         leaf-list admin-group-extended {
           ordered-by user;
           description "Extended administrative groups";
           type string;
           max-elements 16;
         }
         leaf-list srlg {
           ordered-by user;
           description "SRLG Name";
           type string;
           max-elements 16;
         }
         container metric {
           description "Metric values for Express Segment Template";
           uses apply-advanced;
           leaf te {
             description "TE metric value";
             type union {
               type string {
                 pattern "<.*>|$.*";
               }
               type uint32 {
                 range "1 .. 4294967295";
               }
             }
           }
           leaf igp {
             description "IGP metric value";
             type union {
               type string {
                 pattern "<.*>|$.*";
               }
               type uint32 {
                 range "1 .. 16777215";
               }
             }
           }
           leaf delay {
             description "Delay metric value";
             units "microseconds";
             type union {
               type string {
                 pattern "<.*>|$.*";
               }
               type uint32 {
                 range "1 .. 16777215";
               }
             }
           }
         }
       }
       list segment-set {
         key name;
         ordered-by user;
         description "Express Segments Set Definition";
         max-elements 64;
         leaf name {
           description "Express Segment Set Name";
           type string {
             junos:posix-pattern "^.{1,64}$";
             junos:pattern-message "Must be a string of 64 characters or less";
           }
         }
         uses apply-advanced;
         leaf-list membership-policy {
           ordered-by user;
           description "Policy for matching specific LSPs to this express segment";
           type jt:policy-algebra;
         }
         container template {
           description "Template for Express Segment Attribute Selection";
           uses apply-advanced;
           leaf template-name {
             description "Name of Express Segment template";
             junos:must "(\"protocols express-segments segment-template  $$\")";
             junos:must-message "Referenced Express Segment template does not exist";
             type string {
               junos:posix-pattern "^.{1,64}$";
               junos:pattern-message "Must be a string of 64 characters or less";
             }
           }
         }
       }
       container traffic-engineering {
         presence "enable traffic-engineering";
         description "Enable Import of all Express Segments into TED";
         uses apply-advanced;
       }
       container traceoptions {
         description "Trace options for Express Segment";
         uses apply-advanced;
         container file {
           description "Trace file options";
           leaf filename {
             description "Name of file in which to write trace information";
             type string {
               length "1 .. 1024";
               junos:posix-pattern "![/ %]";
               junos:pattern-message "Must not contain '/', % or a space";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "all" {
                 description "Trace everything";
               }
               enum "error" {
                 description "Trace errors";
               }
               enum "route" {
                 description "Trace route-related changes";
               }
               enum "state" {
                 description "Trace state transitions";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
     }
     container igmp {
       presence "enable igmp";
       description "IGMP options";
       uses apply-advanced;
       container traceoptions {
         description "Trace options for IGMP";
         uses apply-advanced;
         container file {
           description "Trace file options";
           leaf filename {
             description "Name of file in which to write trace information";
             type string {
               length "1 .. 1024";
               junos:posix-pattern "![/ %]";
               junos:pattern-message "Must not contain '/', % or a space";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "packets" {
                 description "Trace all IGMP packets";
               }
               enum "query" {
                 description "Trace IGMP membership query messages";
               }
               enum "report" {
                 description "Trace membership report messages";
               }
               enum "leave" {
                 description "Trace leave group messages (IGMPv2 only)";
               }
               enum "mtrace" {
                 description "Trace mtrace packets";
               }
               enum "group" {
                 description "Trace group operations";
               }
               enum "client-notification" {
                 description "Trace notifications";
               }
               enum "host-notification" {
                 description "Trace host notifications";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       leaf query-interval {
         description "When to send host query messages";
         units "seconds";
         type union {
           type string {
             pattern "<.*>|$.*";
           }
           type uint32 {
             range "1 .. 1024";
           }
         }
       }
       leaf query-response-interval {
         description "How long to wait for a host query response";
         units "seconds";
         type string {
           junos:posix-pattern "^[0-9]{1,4}(.[0-9])?$";
           junos:pattern-message "Up to 1 digit to right of decimal point";
         }
       }
       leaf query-last-member-interval {
         description "When to send group query messages";
         units "seconds";
         type string {
           junos:posix-pattern "^[0-9]{1,4}(.[0-9])?$";
           junos:pattern-message "Up to 1 digit to right of decimal point";
         }
       }
       leaf robust-count {
         description "Expected packet loss on a subnet";
         type union {
           type string {
             pattern "<.*>|$.*";
           }
           type uint32 {
             range "2 .. 10";
           }
         }
       }
       leaf maximum-transmit-rate {
         description "Maximum transmission rate (packets per second)";
         type union {
           type string {
             pattern "<.*>|$.*";
           }
           type uint32 {
             range "1 .. 10000";
           }
         }
       }
       leaf accounting {
         description "Enable join and leave event notification";
         type empty;
       }
       list interface {
         key name;
         ordered-by user;
         description "Interface options for IGMP";
         leaf name {
           type string;
         }
         uses apply-advanced;
         choice enable-disable {
           case case_1 {
             leaf disable {
               description "Disable IGMP on this interface";
               type empty;
             }
           }
         }
         leaf version {
           description "Set IGMP version number on this interface";
           type union {
             type string {
               pattern "<.*>|$.*";
             }
             type uint8 {
               range "1 .. 3";
             }
           }
         }
         container static {
           description "Static group or source membership";
           uses apply-advanced;
           list group {
             key name;
             ordered-by user;
             description "IP multicast group address";
             leaf name {
               description "IP multicast group address";
               type jt:ipv4addr;
             }
             uses apply-advanced;
             leaf group-increment {
               description "Mask for the incrementing group IP address";
               type jt:ipv4addr;
             }
             leaf group-count {
               description "Number of groups";
               type union {
                 type string {
                   pattern "<.*>|$.*";
                 }
                 type uint32 {
                   range "1 .. 512";
                 }
               }
             }
             leaf exclude {
               description "Exclude sources";
               type empty;
             }
             list source {
               key name;
               ordered-by user;
               description "IP multicast source address";
               leaf name {
                 description "Source address of IP multicast data";
                 type jt:ipv4addr;
               }
               uses apply-advanced;
               leaf source-increment {
                 description "Mask for the incrementing source IP address";
                 type jt:ipv4addr;
               }
               leaf source-count {
                 description "Number of sources";
                 type union {
                   type string {
                     pattern "<.*>|$.*";
                   }
                   type uint32 {
                     range "1 .. 1024";
                   }
                 }
               }
             }
           }
         }
         leaf ssm-map {
           description "Map for SSM translation of IGMPv1 or IGMPv2 messages";
           type string;
         }
         leaf-list ssm-map-policy {
           ordered-by user;
           description "SSM map policy name";
           type jt:policy-algebra;
         }
         leaf immediate-leave {
           description "Group removed immediately, last membership query not sent";
           type empty;
         }
         leaf promiscuous-mode {
           description "Accept igmp messages coming from different subnet";
           type empty;
         }
         choice accounting-choice {
           leaf accounting {
             description "Enable join and leave event notification";
             type empty;
           }
           leaf no-accounting {
             description "Don't enable join and leave event notification";
             type empty;
           }
         }
         leaf-list group-policy {
           ordered-by user;
           description "Group filter applied to incoming IGMP report messages";
           type jt:policy-algebra;
         }
         leaf group-limit {
           description "Maximum number of (source,group) per interface";
           type union {
             type string {
               pattern "<.*>|$.*";
             }
             type uint16 {
               range "1 .. 32767";
             }
           }
         }
         leaf group-threshold {
           description "Percentage of limit at which to generate warnings";
           junos:must "(\" .. group-limit\")";
           junos:must-message "To configure group-threshold, group-limit must be set";
           type union {
             type string {
               pattern "<.*>|$.*";
             }
             type uint32 {
               range "1 .. 100";
             }
           }
         }
         leaf log-interval {
           description "Time between consecutive log messages";
           junos:must "(\" .. group-limit\")";
           junos:must-message "To configure log-interval, group-limit must be set";
           type union {
             type string {
               pattern "<.*>|$.*";
             }
             type uint32 {
               range "6 .. 32767";
             }
           }
         }
         container passive {
           presence "enable passive";
           description "Suppress sending and receiving IGMP messages";
           leaf allow-receive {
             description "Allow receiving IGMP messages";
             type empty;
           }
           leaf send-general-query {
             description "Send IGMP general query messages";
             type empty;
           }
           leaf send-group-query {
             description "Send IGMP group query messages";
             type empty;
           }
         }
         leaf-list oif-map {
           ordered-by user;
           description "Output interface map";
           type jt:policy-algebra;
         }
         leaf distributed {
           description "Distributed IGMP interface";
           junos:must "(\"chassis network-services enhanced-ip\")";
           junos:must-message "distributed is supported only in enhanced-ip mode";
           type empty;
         }
       }
       container amt {
         description "Automatic Multicast Tunnel options for IGMP";
         uses apply-advanced;
         container relay {
           description "AMT relay options for IGMP";
           uses apply-advanced;
           container defaults {
             presence "enable defaults";
             description "Default AMT relay options for IGMP";
             uses apply-advanced;
             leaf version {
               description "Set IGMP version number on AMT interfaces";
               type union {
                 type string {
                   pattern "<.*>|$.*";
                 }
                 type uint8 {
                   range "1 .. 3";
                 }
               }
             }
             leaf ssm-map {
               description "Map for SSM translation of IGMPv1 or IGMPv2 messages";
               type string;
             }
             leaf-list ssm-map-policy {
               ordered-by user;
               description "SSM map policy name";
               type jt:policy-algebra;
             }
             choice accounting-choice {
               leaf accounting {
                 description "Enable join and leave event notification";
                 type empty;
               }
               leaf no-accounting {
                 description "Don't enable join and leave event notification";
                 type empty;
               }
             }
             leaf-list group-policy {
               ordered-by user;
               description "Group filter applied to incoming IGMP report messages";
               type jt:policy-algebra;
             }
             leaf group-limit {
               description "Maximum number of (source,group) per interface";
               type union {
                 type string {
                   pattern "<.*>|$.*";
                 }
                 type uint16 {
                   range "1 .. 32767";
                 }
               }
             }
             leaf group-threshold {
               description "Percentage of limit at which to generate warnings";
               junos:must "(\" .. group-limit\")";
               junos:must-message "To configure group-threshold, group-limit must be set";
               type union {
                 type string {
                   pattern "<.*>|$.*";
                 }
                 type uint32 {
                   range "1 .. 100";
                 }
               }
             }
             leaf log-interval {
               description "Time between consecutive log messages";
               junos:must "(\" .. group-limit\")";
               junos:must-message "To configure log-interval, group-limit must be set";
               type union {
                 type string {
                   pattern "<.*>|$.*";
                 }
                 type uint32 {
                   range "6 .. 32767";
                 }
               }
             }
             leaf robust-count {
               description "Expected packet loss on a subnet";
               type union {
                 type string {
                   pattern "<.*>|$.*";
                 }
                 type uint32 {
                   range "2 .. 10";
                 }
               }
             }
             leaf query-interval {
               description "When to send host query messages";
               units "seconds";
               type union {
                 type string {
                   pattern "<.*>|$.*";
                 }
                 type uint32 {
                   range "1 .. 1024";
                 }
               }
             }
             leaf query-response-interval {
               description "How long to wait for a host query response";
               units "seconds";
               type string {
                 junos:posix-pattern "^[0-9]{1,4}(.[0-9])?$";
                 junos:pattern-message "Up to 1 digit to right of decimal point";
               }
             }
           }
         }
       }
     }
     container router-discovery {
       description "ICMP router discovery options";
       uses juniper-protocols-router-discovery;
     }
     container isis {
       description "IS-IS options";
       uses juniper-protocols-isis;
     }
     list isis-instance {
       key name;
       ordered-by user;
       description "Multi-instance IS-IS configuration";
       leaf name {
         description "IS-IS instance name";
         type string;
       }
       uses apply-advanced;
       list interface {
         key name;
         description "Interface configuration";
         leaf name {
           description "Interface name";
           type union {
             type jt:interface-name;
             type string {
               pattern "<.*>|$.*";
             }
           }
         }
         uses apply-advanced;
         container ldp-synchronization {
           description "Advertise maximum metric until LDP is operational";
           presence "enable ldp-synchronization";
           uses ldp-sync-obj;
         }
         list level {
           key name;
           ordered-by user;
           description "Configure levels on this interface";
           leaf name {
             description "IS-IS level number";
             type union {
               type string {
                 pattern "<.*>|$.*";
               }
               type uint32 {
                 range "1 .. 2";
               }
             }
           }
           uses apply-advanced;
           leaf te-metric {
             description "Traffic engineering metric";
             type union {
               type string {
                 pattern "<.*>|$.*";
               }
               type uint32 {
                 range "0 .. 16777215";
               }
             }
           }
           leaf no-advertise-adjacency-segment {
             description "Do not advertise an adjacency segment for this level";
             type empty;
           }
           container ipv4-adjacency-segment {
             junos:must "(!(\".. no-advertise-adjacency-segment\"))";
             junos:must-message "ipv4-adjacency-segment can't be configured if no-advertise-adjacency-segment is configured in the level";
             junos:must "(!(\".. .. no-advertise-adjacency-segment\"))";
             junos:must-message "ipv4-adjacency-segment can't be configured if no-advertise-adjacency-segment is configured in the same interface";
             description "Configure ipv4 adjacency segment";
             uses apply-advanced;
             container protected {
               description "Adjacency SID is eligible for protection";
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
             container unprotected {
               description "Adjacency SID uneligible for protection";
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
           }
           container ipv6-adjacency-segment {
             junos:must "(!(\".. no-advertise-adjacency-segment\"))";
             junos:must-message "ipv6-adjacency-segment can't be configured if no-advertise-adjacency-segment is configured in the same level";
             junos:must "(!(\".. .. no-advertise-adjacency-segment\"))";
             junos:must-message "ipv6-adjacency-segment can't be configured if no-advertise-adjacency-segment is configured in the same interface";
             description "Configure ipv6 adjacency segment";
             uses apply-advanced;
             container protected {
               description "Adjacency SID is eligible for protection";
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
             container unprotected {
               description "Adjacency SID uneligible for protection";
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
           }
           container srm6-adjacency-segment {
             description "Configure srm6 adjacency segment";
             uses apply-advanced;
             container unprotected {
               description "Adjacency SID uneligible for protection";
               leaf sid {
                 description "Set Adjacency SID Value";
                 type union {
                   type string {
                     pattern "<.*>|$.*";
                   }
                   type uint32 {
                     range "1 .. 65535";
                   }
                 }
               }
             }
           }
           container srv6-adjacency-segment {
             description "Configure srv6 adjacency segment";
             uses apply-advanced;
             container protected {
               presence "enable protected";
               description "SRv6 Adjacency segment is eligible for protection";
               uses apply-advanced;
               list locator {
                 key name;
                 ordered-by user;
                 description "Locator to bind SRv6 adjacency segment";
                 leaf name {
                   description "Locator name";
                   junos:must "(\"routing-options source-packet-routing srv6 locator $$\")";
                   junos:must-message "Referenced source-packet-routing srv6 must be defined";
                   type string;
                 }
                 uses apply-advanced;
                 list end-x-sid {
                   key name;
                   ordered-by user;
                   description "Endpoint 128 bit address";
                   leaf name {
                     type jt:ipv6addr;
                   }
                   uses apply-advanced;
                   container flavor {
                     presence "enable flavor";
                     uses apply-advanced;
                     leaf psp {
                       description "Penultimate segment pop of the SRH";
                       type empty;
                     }
                     leaf usp {
                       description "Ultimate segment pop of the SRH";
                       type empty;
                     }
                     leaf usd {
                       description "Ultimate segment decapsulation";
                       type empty;
                     }
                   }
                 }
               }
             }
             container unprotected {
               presence "enable unprotected";
               description "SRv6 Adjacency segment is uneligible for protection";
               uses apply-advanced;
               list locator {
                 key name;
                 ordered-by user;
                 description "Locator to bind SRv6 adjacency segment";
                 leaf name {
                   description "Locator name";
                   junos:must "(\"routing-options source-packet-routing srv6 locator $$\")";
                   junos:must-message "Referenced source-packet-routing srv6 must be defined";
                   type string;
                 }
                 uses apply-advanced;
                 list end-x-sid {
                   key name;
                   ordered-by user;
                   description "Endpoint 128 bit address";
                   leaf name {
                     type jt:ipv6addr;
                   }
                   uses apply-advanced;
                   container flavor {
                     presence "enable flavor";
                     uses apply-advanced;
                     leaf psp {
                       description "Penultimate segment pop of the SRH";
                       type empty;
                     }
                     leaf usp {
                       description "Ultimate segment pop of the SRH";
                       type empty;
                     }
                     leaf usd {
                       description "Ultimate segment decapsulation";
                       type empty;
                     }
                   }
                 }
               }
             }
           }
           list lan-neighbor {
             key name;
             ordered-by user;
             description "Configuration specific to a LAN neighbor";
             junos:must "(!(\".. ipv6-adjacency-segment\"))";
             junos:must-message "lan-neighbor can't be configured if ipv6-adjacency-segment is configured in the same interface";
             junos:must "(!(\".. ipv4-adjacency-segment\"))";
             junos:must-message "lan-neighbor can't be configured if ipv4-adjacency-segment is configured in the same interface";
             junos:must "(!(\".. no-advertise-adjacency-segment\"))";
             junos:must-message "lan-neighbor can't be configured if no-advertise-adjacency-segment is configured in the same level";
             junos:must "(!(\".. .. no-advertise-adjacency-segment\"))";
             junos:must-message "lan-neighbor can't be configured if  no-advertise-adjacency-segment is configured in the same interface";
             junos:must "(!(\".. .. point-to-point\"))";
             junos:must-message "lan-neighbor can't be configured for point-to-point interfaces";
             leaf name {
               description "Neighbor's sysid";
               type jt:sysid;
             }
             uses apply-advanced;
             container ipv4-adjacency-segment {
               junos:must "(!(\".. no-advertise-adjacency-segment\"))";
               junos:must-message "ipv4-adjacency-segment can't be configured if no-advertise-adjacency-segment is configured in the level";
               junos:must "(!(\".. .. no-advertise-adjacency-segment\"))";
               junos:must-message "ipv4-adjacency-segment can't be configured if no-advertise-adjacency-segment is configured in the same interface";
               description "Configure ipv4 adjacency segment";
               uses apply-advanced;
               container protected {
                 description "Adjacency SID is eligible for protection";
                 choice adjsid-type {
                   case case_1 {
                     container index {
                       description "Adjacency SID indexed from SRGB";
                       leaf index-number {
                         type union {
                           type string {
                             pattern "<.*>|$.*";
                           }
                           type uint32 {
                             range "0 .. 199999";
                           }
                         }
                       }
                     }
                   }
                   case case_2 {
                     leaf label {
                       description "Adjacency SID from static label pool";
                       type union {
                         type string {
                           pattern "<.*>|$.*";
                         }
                         type uint32 {
                           range "16 .. 1048575";
                         }
                       }
                     }
                   }
                   case case_3 {
                     leaf dynamic {
                       description "Dynamically allocate an adjacency segment";
                       type empty;
                     }
                   }
                 }
               }
               container unprotected {
                 description "Adjacency SID uneligible for protection";
                 choice adjsid-type {
                   case case_1 {
                     container index {
                       description "Adjacency SID indexed from SRGB";
                       leaf index-number {
                         type union {
                           type string {
                             pattern "<.*>|$.*";
                           }
                           type uint32 {
                             range "0 .. 199999";
                           }
                         }
                       }
                     }
                   }
                   case case_2 {
                     leaf label {
                       description "Adjacency SID from static label pool";
                       type union {
                         type string {
                           pattern "<.*>|$.*";
                         }
                         type uint32 {
                           range "16 .. 1048575";
                         }
                       }
                     }
                   }
                   case case_3 {
                     leaf dynamic {
                       description "Dynamically allocate an adjacency segment";
                       type empty;
                     }
                   }
                 }
               }
             }
             container ipv6-adjacency-segment {
               junos:must "(!(\".. no-advertise-adjacency-segment\"))";
               junos:must-message "ipv6-adjacency-segment can't be configured if no-advertise-adjacency-segment is configured in the same level";
               junos:must "(!(\".. .. no-advertise-adjacency-segment\"))";
               junos:must-message "ipv6-adjacency-segment can't be configured if no-advertise-adjacency-segment is configured in the same interface";
               description "Configure ipv6 adjacency segment";
               uses apply-advanced;
               container protected {
                 description "Adjacency SID is eligible for protection";
                 choice adjsid-type {
                   case case_1 {
                     container index {
                       description "Adjacency SID indexed from SRGB";
                       leaf index-number {
                         type union {
                           type string {
                             pattern "<.*>|$.*";
                           }
                           type uint32 {
                             range "0 .. 199999";
                           }
                         }
                       }
                     }
                   }
                   case case_2 {
                     leaf label {
                       description "Adjacency SID from static label pool";
                       type union {
                         type string {
                           pattern "<.*>|$.*";
                         }
                         type uint32 {
                           range "16 .. 1048575";
                         }
                       }
                     }
                   }
                   case case_3 {
                     leaf dynamic {
                       description "Dynamically allocate an adjacency segment";
                       type empty;
                     }
                   }
                 }
               }
               container unprotected {
                 description "Adjacency SID uneligible for protection";
                 choice adjsid-type {
                   case case_1 {
                     container index {
                       description "Adjacency SID indexed from SRGB";
                       leaf index-number {
                         type union {
                           type string {
                             pattern "<.*>|$.*";
                           }
                           type uint32 {
                             range "0 .. 199999";
                           }
                         }
                       }
                     }
                   }
                   case case_2 {
                     leaf label {
                       description "Adjacency SID from static label pool";
                       type union {
                         type string {
                           pattern "<.*>|$.*";
                         }
                         type uint32 {
                           range "16 .. 1048575";
                         }
                       }
                     }
                   }
                   case case_3 {
                     leaf dynamic {
                       description "Dynamically allocate an adjacency segment";
                       type empty;
                     }
                   }
                 }
               }
             }
             container srm6-adjacency-segment {
               description "Configure srm6 adjacency segment";
               uses apply-advanced;
               container unprotected {
                 description "Adjacency SID uneligible for protection";
                 leaf sid {
                   description "Set Adjacency SID Value";
                   type union {
                     type string {
                       pattern "<.*>|$.*";
                     }
                     type uint32 {
                       range "1 .. 65535";
                     }
                   }
                 }
               }
             }
             container srv6-adjacency-segment {
               description "Configure srv6 adjacency segment";
               uses apply-advanced;
               container protected {
                 presence "enable protected";
                 description "SRv6 Adjacency segment is eligible for protection";
                 uses apply-advanced;
                 list locator {
                   key name;
                   ordered-by user;
                   description "Locator to bind SRv6 adjacency segment";
                   leaf name {
                     description "Locator name";
                     junos:must "(\"routing-options source-packet-routing srv6 locator $$\")";
                     junos:must-message "Referenced source-packet-routing srv6 must be defined";
                     type string;
                   }
                   uses apply-advanced;
                   list end-x-sid {
                     key name;
                     ordered-by user;
                     description "Endpoint 128 bit address";
                     leaf name {
                       type jt:ipv6addr;
                     }
                     uses apply-advanced;
                     container flavor {
                       presence "enable flavor";
                       uses apply-advanced;
                       leaf psp {
                         description "Penultimate segment pop of the SRH";
                         type empty;
                       }
                       leaf usp {
                         description "Ultimate segment pop of the SRH";
                         type empty;
                       }
                       leaf usd {
                         description "Ultimate segment decapsulation";
                         type empty;
                       }
                     }
                   }
                 }
               }
               container unprotected {
                 presence "enable unprotected";
                 description "SRv6 Adjacency segment is uneligible for protection";
                 uses apply-advanced;
                 list locator {
                   key name;
                   ordered-by user;
                   description "Locator to bind SRv6 adjacency segment";
                   leaf name {
                     description "Locator name";
                     junos:must "(\"routing-options source-packet-routing srv6 locator $$\")";
                     junos:must-message "Referenced source-packet-routing srv6 must be defined";
                     type string;
                   }
                   uses apply-advanced;
                   list end-x-sid {
                     key name;
                     ordered-by user;
                     description "Endpoint 128 bit address";
                     leaf name {
                       type jt:ipv6addr;
                     }
                     uses apply-advanced;
                     container flavor {
                       presence "enable flavor";
                       uses apply-advanced;
                       leaf psp {
                         description "Penultimate segment pop of the SRH";
                         type empty;
                       }
                       leaf usp {
                         description "Ultimate segment pop of the SRH";
                         type empty;
                       }
                       leaf usd {
                         description "Ultimate segment decapsulation";
                         type empty;
                       }
                     }
                   }
                 }
               }
             }
           }
           container post-convergence-lfa {
             presence "enable post-convergence-lfa";
             junos:must "(\".. .. .. backup-spf-options use-post-convergence-lfa\")";
             junos:must-message "Not allowed without 'protocols isis backup-spf-options use-post-convergence-lfa'";
             description "Configure backup along post convergence on this interface";
             uses apply-advanced;
             container node-protection {
               presence "enable node-protection";
               description "Enable node protection";
               uses apply-advanced;
               leaf cost {
                 description "Cost for node protection";
                 type union {
                   type string {
                     pattern "<.*>|$.*";
                   }
                   type uint32 {
                     range "0 .. 16777215";
                   }
                 }
               }
             }
             leaf srlg-protection {
               description "Enable srlg protection";
               type empty;
             }
             leaf fate-sharing-protection {
               description "Enable fate-sharing protection";
               type empty;
             }
           }
           container application-specific {
             description "Advertise application-specific TE attributes";
             uses apply-advanced;
             list attribute-group {
               key name;
               ordered-by user;
               description "Link attribute group name";
               max-elements 1;
               leaf name {
                 description "Link attribute group name";
                 type string;
               }
               uses apply-advanced;
               leaf te-metric {
                 description "Traffic engineering metric for this attribute group";
                 junos:must "(\".. application\")";
                 junos:must-message "Atleast one application is must";
                 type union {
                   type string {
                     pattern "<.*>|$.*";
                   }
                   type uint32 {
                     range "0 .. 16777215";
                   }
                 }
               }
               leaf-list admin-group {
                 ordered-by user;
                 description "Administrative groups for this attribute-group";
                 type string;
                 max-elements 16;
               }
               container application {
                 junos:must "((\".. delay-metric\" || (\".. admin-group\" || (\".. te-metric\" || (\".. admin-groups\" || (\".. legacy\" || \".. advertise-delay-metric\"))))))";
                 junos:must-message "Atleast one attribute must be configured";
                 description "Standard Applications part of this attribute-group";
                 uses apply-advanced;
                 leaf flex-algorithm {
                   description "Set X flag in standard application bit mask";
                   type empty;
                 }
               }
             }
           }
           choice enable-disable {
             case case_1 {
               leaf disable {
                 description "Disable IS-IS for this level";
                 type empty;
               }
             }
           }
           leaf metric {
             description "Metric for this level";
             type union {
               type string {
                 pattern "<.*>|$.*";
               }
               type uint32 {
                 range "0 .. 16777215";
               }
             }
           }
           leaf ipv4-multicast-metric {
             description "IPv4 multicast metric for this level";
             type union {
               type string {
                 pattern "<.*>|$.*";
               }
               type uint32 {
                 range "0 .. 16777215";
               }
             }
           }
           leaf ipv6-unicast-metric {
             description "IPv6 unicast metric for this level";
             type union {
               type string {
                 pattern "<.*>|$.*";
               }
               type uint32 {
                 range "0 .. 16777215";
               }
             }
           }
           leaf ipv6-multicast-metric {
             description "IPv6 multicast metric for this level";
             type union {
               type string {
                 pattern "<.*>|$.*";
               }
               type uint32 {
                 range "0 .. 16777215";
               }
             }
           }
           list topology {
             key name;
             ordered-by user;
             description "Topology specific attributes";
             leaf name {
               description "Topology name";
               type enumeration {
                 enum "default" {
                   description "Default topology";
                 }
                 enum "ipv4-multicast" {
                   description "IPv4 multicast topology";
                 }
                 enum "ipv6-unicast" {
                   description "IPv6 unicast topology";
                 }
                 enum "ipv6-multicast" {
                   description "IPv6 multicast topology";
                 }
               }
             }
             uses apply-advanced;
             leaf metric {
               description "Topology metric";
               type union {
                 type string {
                   pattern "<.*>|$.*";
                 }
                 type uint32 {
                   range "0 .. 16777215";
                 }
               }
             }
             container bandwidth-based-metrics {
               junos:must "(\".. metric\")";
               junos:must-message "Metric must be configured";
               description "Configure bandwidth based metrics";
               uses apply-advanced;
               list bandwidth {
                 key name;
                 description "Bandwidth threshold";
                 leaf name {
                   type string;
                 }
                 leaf metric {
                   description "Metric associated with specified bandwidth";
                   type union {
                     type string {
                       pattern "<.*>|$.*";
                     }
                     type uint32 {
                       range "0 .. 16777215";
                     }
                   }
                 }
               }
             }
           }
           leaf authentication-key {
             description "Authentication key (password)";
             status deprecated;
             type jt:unreadable;
           }
           leaf authentication-type {
             description "Authentication type";
             status deprecated;
             type enumeration {
               enum "md5" {
                 description "MD5 authentication";
                 status deprecated;
               }
               enum "simple" {
                 description "Simple password authentication";
                 status deprecated;
               }
             }
           }
           leaf hello-authentication-key {
             description "Authentication key (password) for hello packets";
             type jt:unreadable;
           }
           leaf hello-authentication-type {
             description "Authentication type for hello packets";
             type enumeration {
               enum "md5" {
                 description "MD5 authentication";
               }
               enum "simple" {
                 description "Simple password authentication";
               }
             }
           }
           leaf hello-authentication-key-chain {
             description "Key chain name";
             junos:must "(!(\".. hello-authentication-type\"))";
             junos:must-message "May not be configured with hello-authentication-type";
             junos:must "(!(\".. hello-authentication-key\"))";
             junos:must-message "May not be configured with hello-authentication-key";
             junos:must "(!(\".. authentication-key\"))";
             junos:must-message "May not be configured with authentication-key";
             junos:must "(\"security authentication-key-chains key-chain $$\")";
             junos:must-message "Referenced key-chain must be defined";
             type string {
               length "1 .. 128";
               junos:posix-pattern "[A-za-z]$";
               junos:pattern-message "Keychain name must not end with number.";
             }
           }
           leaf hello-interval {
             description "Interval between hello packet transmissions";
             units "seconds";
             type union {
               type string {
                 pattern "<.*>|$.*";
               }
               type uint32 {
                 range "1 .. 21845";
               }
             }
           }
           leaf hold-time {
             description "Time after which neighbors think the interface is down";
             units "seconds";
             type union {
               type string {
                 pattern "<.*>|$.*";
               }
               type uint32 {
                 range "1 .. 65535";
               }
             }
           }
           leaf priority {
             description "Designated router election priority";
             type union {
               type string {
                 pattern "<.*>|$.*";
               }
               type uint32 {
                 range "0 .. 127";
               }
             }
           }
           container flood-reflector {
             presence "enable flood-reflector";
             junos:must "(\".. .. level 1 disable\")";
             junos:must-message "flood-reflector cannot be enabled on level 1 interface";
             junos:must "((\".. .. .. level 2 flood-reflector\" && !(\".. .. level 1 flood-reflector\")))";
             junos:must-message "flood-reflector is only supported on level 2 interfaces";
             description "Configure interface as flood-reflector";
             uses apply-advanced;
             leaf cluster-id {
               description "Cluster-ID";
               junos:must "(\".. .. .. .. level 2 flood-reflector client\")";
               junos:must-message "flood-reflector client is not configured at isis level";
               type union {
                 type string {
                   pattern "<.*>|$.*";
                 }
                 type uint32 {
                   range "1 .. 4294967295";
                 }
               }
             }
           }
           container passive {
             presence "enable passive";
             description "Do not run IS-IS at this level, but advertise it";
             uses apply-advanced;
             leaf remote-node-iso {
               description "ISO System-ID of the remote node";
               junos:must "(\".. remote-node-id\")";
               junos:must-message "remote-node-id must be configured";
               type jt:sysid;
             }
             leaf remote-node-id {
               description "Remote address of the link";
               junos:must "(\".. remote-node-iso\")";
               junos:must-message "remote-node-iso must be configured";
               type jt:ipv4addr;
             }
           }
         }
         leaf delay-metric {
           description "Delay metric";
           units "microseconds";
           type union {
             type string {
               pattern "<.*>|$.*";
             }
             type uint32 {
               range "0 .. 16777215";
             }
           }
         }
         container delay-measurement {
           presence "enable delay-measurement";
           description "Enable delay measurement";
           uses apply-advanced;
           leaf probe-interval {
             description "Probe interval";
             units "seconds";
             type union {
               type string {
                 pattern "<.*>|$.*";
               }
               type uint32 {
                 range "1 .. 255";
               }
             }
           }
           leaf probe-count {
             description "Probe count";
             units "seconds";
             type union {
               type string {
                 pattern "<.*>|$.*";
               }
               type uint32 {
                 range "1 .. 15";
               }
             }
           }
           container advertisement {
             description "Delay advertisement";
             uses apply-advanced;
             container periodic {
               description "Periodic advertisement parameters";
               uses apply-advanced;
               leaf threshold {
                 description "Threshold";
                 units "percentage";
                 type union {
                   type string {
                     pattern "<.*>|$.*";
                   }
                   type uint32 {
                     range "0 .. 100";
                   }
                 }
               }
               leaf interval {
                 description "Interval";
                 units "seconds";
                 type union {
                   type string {
                     pattern "<.*>|$.*";
                   }
                   type uint32 {
                     range "30 .. 3600";
                   }
                 }
               }
             }
             container accelerated {
               presence "enable accelerated";
               description "Accelerated advertisement parameters";
               uses apply-advanced;
               leaf threshold {
                 description "Threshold";
                 units "percentage";
                 type union {
                   type string {
                     pattern "<.*>|$.*";
                   }
                   type uint32 {
                     range "0 .. 100";
                   }
                 }
               }
             }
           }
         }
         leaf no-advertise-adjacency-segment {
           description "Do not advertise an adjacency segment for this interface";
           type empty;
         }
         container auto-bandwidth {
           description "Auto bandwidth configuration";
           uses apply-advanced;
           leaf template-name {
             description "Auto bandwidth template name";
             junos:must "(\"protocols isis source-packet-routing traffic-statistics statistics-granularity per-interface\")";
             junos:must-message "Config protocols isis source-packet-routing traffic-statistics statistics-granularity per-interface is must";
             junos:must "(\"routing-options auto-bandwidth template $$\")";
             junos:must-message "Referenced auto-bandwidth template must be defined";
             type string;
           }
           choice enable-disable {
             case case_1 {
               leaf disable {
                 description "Disable Auto bandwidth on this interface";
                 type empty;
               }
             }
           }
         }
         choice protection-type {
           case case_1 {
             leaf link-protection {
               description "Protect interface from link faults only";
               type empty;
             }
           }
           case case_2 {
             leaf node-link-protection {
               description "Protect interface from both link and node faults";
               type empty;
             }
           }
         }
         leaf no-eligible-backup {
           description "Not eligible for backup traffic from protected interfaces";
           type empty;
         }
         leaf no-eligible-remote-backup {
           description "Not eligible for Remote-LFA backup traffic from protected interfaces";
           type empty;
         }
         container link-degradation-threshold {
           presence "enable link-degradation-threshold";
           description "Link up and down thresholds (in %) for proactive link protection";
           leaf link-down {
             description "Signal degradation threshold above which link marked down";
             type union {
               type string {
                 pattern "<.*>|$.*";
               }
               type uint32 {
                 range "0 .. 100";
               }
             }
           }
           leaf link-up {
             description "Signal degradation threshold below which link is marked up.";
             type union {
               type string {
                 pattern "<.*>|$.*";
               }
               type uint32 {
                 range "0 .. 100";
               }
             }
           }
         }
         choice enable-disable {
           case case_1 {
             leaf disable {
               description "Disable IS-IS on this interface";
               type empty;
             }
           }
         }
         leaf authentication-key {
           description "Authentication key (password)";
           status deprecated;
           type jt:unreadable;
         }
         leaf authentication-type {
           description "Authentication type";
           status deprecated;
           type enumeration {
             enum "md5" {
               description "MD5 authentication";
               status deprecated;
             }
             enum "simple" {
               description "Simple password authentication";
               status deprecated;
             }
           }
         }
         leaf flood-group {
           description "ISO Area that this interface should send LSPs to";
           type string {
             junos:posix-pattern "^[[:xdigit:]]{2}.(([[:xdigit:]]){2}){1,2}((.(([[:xdigit:]]){2}){1,2}){0,1}){0,5}$";
             junos:pattern-message "At max 26 hexa decimal digits, standard ISO area ID format";
           }
         }
         leaf hello-authentication-key {
           description "Authentication key (password) for hello packets";
           status deprecated;
           type jt:unreadable;
         }
         leaf hello-authentication-type {
           description "Authentication type for hello packets";
           status deprecated;
           type enumeration {
             enum "md5" {
               description "MD5 authentication";
               status deprecated;
             }
             enum "simple" {
               description "Simple password authentication";
               status deprecated;
             }
           }
         }
         leaf hello-padding-type {
           description "Type of padding for hello packets";
           default "loose";
           type enumeration {
             enum "strict" {
               description "Padding for all adjacency states";
             }
             enum "adaptive" {
               description "Padding until state of neighbor adjacency is 'up'";
             }
             enum "loose" {
               description "Padding until state of adjacency is 'initializing'";
             }
             enum "disable" {
               description "Do not add any padding for hello packets";
             }
           }
         }
         leaf interface-group-holddown-delay {
           description "Time to wait before including in BBM calculation";
           units "seconds";
           type union {
             type string {
               pattern "<.*>|$.*";
             }
             type uint32 {
               range "0 .. 60";
             }
           }
         }
         choice layer2-map-choice {
           leaf layer2-map {
             description "Kernel ARP/ND creation for nexthops";
             type empty;
           }
           leaf no-layer2-map {
             description "Don't kernel ARP/ND creation for nexthops";
             type empty;
           }
         }
         leaf max-hello-size {
           description "Maximum size allowed for ISIS Hello PDUs";
           type union {
             type string {
               pattern "<.*>|$.*";
             }
             type uint32 {
               range "512 .. 16000";
             }
           }
         }
         leaf lsp-interval {
           description "Interval between LSP transmissions";
           default "100";
           units "milliseconds";
           type union {
             type string {
               pattern "<.*>|$.*";
             }
             type uint32 {
               range "1 .. 1000";
             }
           }
         }
         container csnp-interval {
           description "Rate of CSN packets (for LAN interfaces only)";
           choice csnp_interval_option {
             case case_1 {
               leaf csnp-interval-number {
                 description "Interval between CSN packets";
                 units "seconds";
                 type union {
                   type string {
                     pattern "<.*>|$.*";
                   }
                   type uint32 {
                     range "1 .. 65535";
                   }
                 }
               }
             }
             case case_2 {
               leaf disable {
                 description "Do not send CSN packets on this interface";
                 type empty;
               }
             }
           }
         }
         container strict-dual-isis {
           presence "enable strict-dual-isis";
           junos:must "(!(\".. .. topologies\"))";
           junos:must-message "strict-dual-isis is not allowed with multi-topologies";
           description "Enable dual isis if spf computation is required for both ipv4 and ipv6 family";
           uses apply-advanced;
           leaf holdown {
             description "Time to wait for ipv4 and ipv6 connectivity";
             status deprecated;
             default "12";
             type union {
               type string {
                 pattern "<.*>|$.*";
               }
               type uint32 {
                 range "1 .. 65535";
               }
             }
           }
           leaf holddown {
             description "Time to wait for ipv4 and ipv6 connectivity";
             default "12";
             type union {
               type string {
                 pattern "<.*>|$.*";
               }
               type uint32 {
                 range "1 .. 65535";
               }
             }
           }
         }
         container mesh-group {
           description "Add the interface to a mesh group";
           choice mesh_group_option {
             case case_1 {
               leaf mesh-group-number {
                 description "Mesh group number for this interface";
                 type union {
                   type uint32;
                   type string {
                     pattern "<.*>|$.*";
                   }
                 }
               }
             }
             case case_2 {
               leaf blocked {
                 description "Do not flood new LSPs on this interface";
                 type empty;
               }
             }
           }
         }
         leaf point-to-point {
           description "Treat interface as point to point";
           type empty;
         }
         container passive {
           presence "enable passive";
           description "Do not run IS-IS, but advertise it";
           uses apply-advanced;
           leaf remote-node-iso {
             description "ISO System-ID of the remote node";
             junos:must "(\".. remote-node-id\")";
             junos:must-message "remote-node-id must be configured";
             type jt:sysid;
           }
           leaf remote-node-id {
             description "Remote address of the link";
             junos:must "(\".. remote-node-iso\")";
             junos:must-message "remote-node-iso must be configured";
             type jt:ipv4addr;
           }
         }
         leaf checksum {
           description "Enable checksum for packets on this interface";
           type empty;
         }
         leaf no-unicast-topology {
           description "Do not include this interface in the unicast topology";
           type empty;
         }
         leaf no-ipv4-multicast {
           description "Do not include this interface in the IPv4 multicast topology";
           type empty;
         }
         leaf no-ipv6-unicast {
           description "Do not include this interface in the IPv6 unicast topology";
           type empty;
         }
         leaf no-ipv6-multicast {
           description "Do not include this interface in the IPv6 multicast topology";
           type empty;
         }
         leaf no-adjacency-down-notification {
           description "Do not inform other protocols about adjacency down events";
           type empty;
         }
         container bfd-liveness-detection {
           junos:must "(!(\".. family inet bfd-liveness-detection\"))";
           junos:must-message "To configure bfd-liveness-detection, 'family inet bfd-liveness-detection' must not be configured";
           description "Bidirectional Forwarding Detection options";
           status deprecated;
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
           container authentication {
             description "Authentication options";
             uses apply-advanced;
             leaf key-chain {
               description "Key chain name";
               junos:must "(\".. algorithm\")";
               junos:must-message "May not be configured without algorithm";
               junos:must "(\"security authentication-key-chains key-chain $$\")";
               junos:must-message "Referenced key-chain must be defined";
               type string;
             }
             leaf algorithm {
               description "Algorithm name";
               junos:must "(\".. key-chain\")";
               junos:must-message "May not be configured without key-chain";
               type enumeration {
                 enum "simple-password" {
                   description "Simple password";
                 }
                 enum "keyed-md5" {
                   description "Keyed message Digest 5";
                 }
                 enum "meticulous-keyed-md5" {
                   description "Meticulous keyed message Digest 5";
                 }
                 enum "keyed-sha-1" {
                   description "Keyed secure hash algorithm (SHA1) ";
                 }
                 enum "meticulous-keyed-sha-1" {
                   description "Meticulous keyed secure hash algorithm (SHA1) ";
                 }
               }
             }
             leaf loose-check {
               description "Verify authentication only if authentication is negotiated";
               type empty;
             }
           }
         }
         list family {
           key name;
           ordered-by user;
           description "Address family specific interface attributes";
           leaf name {
             type enumeration {
               enum "inet" {
                 description "IPv4 family";
               }
               enum "inet6" {
                 description "IPv6 family";
               }
             }
           }
           uses apply-advanced;
           container bfd-liveness-detection {
             junos:must "(!((\".. .. bfd-liveness-detection\" && \".. .. family inet bfd-liveness-detection\")))";
             junos:must-message "bfd-liveness-detection and 'family inet bfd-liveness-detection' cannot be configured at the same time";
             description "Bidirectional Forwarding Detection options";
             uses apply-advanced;
             leaf version {
               description "BFD protocol version number";
               default "automatic";
               type enumeration {
                 enum "0" {
                   description "BFD version 0 (deprecated)";
                 }
                 enum "1" {
                   description "BFD version 1";
                 }
                 enum "automatic" {
                   description "Choose BFD version automatically";
                 }
               }
             }
             leaf minimum-interval {
               description "Minimum transmit and receive interval";
               units "milliseconds";
               type union {
                 type string {
                   pattern "<.*>|$.*";
                 }
                 type uint32 {
                   range "1 .. 255000";
                 }
               }
             }
             leaf minimum-transmit-interval {
               description "Minimum transmit interval";
               status deprecated;
               units "milliseconds";
               type union {
                 type string {
                   pattern "<.*>|$.*";
                 }
                 type uint32 {
                   range "1 .. 255000";
                 }
               }
             }
             leaf minimum-receive-interval {
               description "Minimum receive interval";
               units "milliseconds";
               type union {
                 type string {
                   pattern "<.*>|$.*";
                 }
                 type uint32 {
                   range "1 .. 255000";
                 }
               }
             }
             leaf multiplier {
               description "Detection time multiplier";
               default "3";
               type union {
                 type string {
                   pattern "<.*>|$.*";
                 }
                 type uint32 {
                   range "1 .. 255";
                 }
               }
             }
             choice adaptation-choice {
               case case_1 {
                 leaf no-adaptation {
                   description "Disable adaptation";
                   type empty;
                 }
               }
             }
             container transmit-interval {
               description "Transmit-interval options";
               uses apply-advanced;
               leaf minimum-interval {
                 description "Minimum transmit interval";
                 units "milliseconds";
                 type union {
                   type string {
                     pattern "<.*>|$.*";
                   }
                   type uint32 {
                     range "1 .. 255000";
                   }
                 }
               }
               leaf threshold {
                 description "High transmit interval triggering a trap";
                 units "milliseconds";
                 type union {
                   type uint32;
                   type string {
                     pattern "<.*>|$.*";
                   }
                 }
               }
             }
             container detection-time {
               description "Detection-time options";
               uses apply-advanced;
               leaf threshold {
                 description "High detection-time triggering a trap";
                 units "milliseconds";
                 type union {
                   type uint32;
                   type string {
                     pattern "<.*>|$.*";
                   }
                 }
               }
             }
             container authentication {
               description "Authentication options";
               uses apply-advanced;
               leaf key-chain {
                 description "Key chain name";
                 junos:must "(\".. algorithm\")";
                 junos:must-message "May not be configured without algorithm";
                 junos:must "(\"security authentication-key-chains key-chain $$\")";
                 junos:must-message "Referenced key-chain must be defined";
                 type string;
               }
               leaf algorithm {
                 description "Algorithm name";
                 junos:must "(\".. key-chain\")";
                 junos:must-message "May not be configured without key-chain";
                 type enumeration {
                   enum "simple-password" {
                     description "Simple password";
                   }
                   enum "keyed-md5" {
                     description "Keyed message Digest 5";
                   }
                   enum "meticulous-keyed-md5" {
                     description "Meticulous keyed message Digest 5";
                   }
                   enum "keyed-sha-1" {
                     description "Keyed secure hash algorithm (SHA1) ";
                   }
                   enum "meticulous-keyed-sha-1" {
                     description "Meticulous keyed secure hash algorithm (SHA1) ";
                   }
                 }
               }
               leaf loose-check {
                 description "Verify authentication only if authentication is negotiated";
                 type empty;
               }
             }
           }
         }
       }
       container source-packet-routing {
         presence "enable source-packet-routing";
         junos:must "(!(\".. srm6\"))";
         junos:must-message "must not have 'protocols isis srm6' configured";
         description "Enable Source Packet Routing (SPRING)";
         uses apply-advanced;
         container adjacency-segment {
           junos:must "(!(\".. .. .. .. protocols mpls disable\"))";
           junos:must-message "SPRING configuration is not allowed with 'protocols mpls disable'";
           description "Configure attributes for Adjacency Segments in SPRING";
           uses apply-advanced;
           leaf hold-time {
             description "Duration(ms) for which adjacency segments will be retained after isolating from an interface";
             type union {
               type string {
                 pattern "<.*>|$.*";
               }
               type uint32 {
                 range "180000 .. 900000";
               }
             }
           }
         }
         container udp-tunneling {
           junos:must "(!(\".. .. .. .. protocols mpls disable\"))";
           junos:must-message "SPRING configuration is not allowed with 'protocols mpls disable'";
           description "Enable SR over UDP feature";
           uses apply-advanced;
           leaf encapsulation {
             description "Enable UDP Tunnel Encapsulation";
             type empty;
           }
           leaf decapsulation {
             description "Enable UDP Tunnel decapsulation";
             type empty;
           }
         }
         container srgb {
           junos:must "(!(\".. node-segment index-range\"))";
           junos:must-message "May not be confiugred with node-segment index-range";
           junos:must "(!(\".. .. .. .. protocols mpls disable\"))";
           junos:must-message "SPRING configuration is not allowed with 'protocols mpls disable'";
           description "Set the SRGB global block in SPRING";
           leaf start-label {
             description "Start range for SRGB label block";
             type union {
               type string {
                 pattern "<.*>|$.*";
               }
               type uint32;
             }
           }
           leaf index-range {
             description "Index to the SRGB start label block";
             type union {
               type string {
                 pattern "<.*>|$.*";
               }
               type uint32;
             }
           }
         }
         container node-segment {
           junos:must "(!(\".. .. .. .. protocols mpls disable\"))";
           junos:must-message "SPRING configuration is not allowed with 'protocols mpls disable'";
           description "Enable support for Node segments in SPRING";
           uses apply-advanced;
           leaf ipv4-index {
             description "Set IPv4 Node Segment index";
             type union {
               type string {
                 pattern "<.*>|$.*";
               }
               type uint32 {
                 range "0 .. 199999";
               }
             }
           }
           leaf ipv6-index {
             description "Set IPv6 Node Segment index";
             type union {
               type string {
                 pattern "<.*>|$.*";
               }
               type uint32 {
                 range "0 .. 199999";
               }
             }
           }
           leaf index-range {
             description "Set Range of Node Segment indices allowed";
             type union {
               type string {
                 pattern "<.*>|$.*";
               }
               type uint32 {
                 range "32 .. 16385";
               }
             }
           }
         }
         leaf-list flex-algorithm {
           description "Flex-algorithms we would like to participate in";
           type union {
             type string {
               pattern "<.*>|$.*";
             }
             type uint32 {
               range "128 .. 255";
             }
           }
           max-elements 16;
         }
         leaf use-flex-algorithm-metric-always {
           description "Use flex-algo prefix metric whenever available";
           type empty;
         }
         leaf strict-asla-based-flex-algorithm {
           description "Flex-Algorithm to ignore links not having ASLA sub-TLVs";
           type empty;
         }
         leaf new-capability-subtlv {
           description "Advertise all ranges in single spring capability subtlv";
           junos:must "(!(\".. .. .. .. protocols mpls disable\"))";
           junos:must-message "SPRING configuration is not allowed with 'protocols mpls disable'";
           type empty;
         }
         leaf explicit-null {
           description "Set E and P bits in all Prefix SID advertisements";
           junos:must "(!(\".. .. .. .. protocols mpls disable\"))";
           junos:must-message "SPRING configuration is not allowed with 'protocols mpls disable'";
           type empty;
         }
         leaf mapping-server {
           description "Mapping server name";
           junos:must "(!(\".. .. .. .. protocols mpls disable\"))";
           junos:must-message "SPRING configuration is not allowed with 'protocols mpls disable'";
           junos:must "(\"routing-options source-packet-routing mapping-server-entry $$\")";
           junos:must-message "Referenced source-packet-routing mapping-server-entry must be defined";
           type string;
         }
         leaf no-strict-spf {
           description " Disable strict spf algo 1 advertisement";
           type empty;
         }
         leaf no-binding-sid-leaking {
           description " Disable SRMS binding sid leaking";
           type empty;
         }
         leaf ldp-stitching {
           description "Enable SR to LDP stitching";
           junos:must "(!(\".. .. .. .. protocols mpls disable\"))";
           junos:must-message "SPRING configuration is not allowed with 'protocols mpls disable'";
           type empty;
         }
         container srv6 {
           presence "enable srv6";
           description "Enable IPv6 Segment Routing (SRv6)";
           uses apply-advanced;
           list locator {
             key name;
             ordered-by user;
             description "SRv6 Locator";
             leaf name {
               description "Locator name";
               junos:must "(\"routing-options source-packet-routing srv6 locator $$\")";
               junos:must-message "Referenced source-packet-routing srv6 must be defined";
               type string;
             }
             uses apply-advanced;
             leaf anycast {
               description "Set A flag in the Prefix-Attribute sub-TLV";
               type empty;
             }
             list end-sid {
               key name;
               ordered-by user;
               leaf name {
                 type jt:ipv6addr;
               }
               uses apply-advanced;
               container flavor {
                 presence "enable flavor";
                 uses apply-advanced;
                 leaf psp {
                   description "Penultimate segment pop of the SRH";
                   type empty;
                 }
                 leaf usp {
                   description "Ultimate segment pop of the SRH";
                   type empty;
                 }
                 leaf usd {
                   description "Ultimate segment decapsulation";
                   type empty;
                 }
               }
             }
           }
         }
         container sensor-based-stats {
           junos:must "(!(\".. .. .. .. protocols mpls disable\"))";
           junos:must-message "SPRING configuration is not allowed with 'protocols mpls disable'";
           description "Configure sensor based stats in SPRING";
           uses apply-advanced;
           container per-interface-per-member-link {
             description "Configure sensor based stats per nexthop";
             leaf ingress {
               description "Enable sensor based stats on ingress interface";
               type empty;
             }
             leaf egress {
               description "Enable sensor based stats on egress interface";
               type empty;
             }
           }
           container per-sid {
             description "Configure sensor based stats per spring route";
             leaf ingress {
               description "Enable sensor based stats for per-sid ingress accounting";
               type empty;
             }
             leaf egress {
               description "Enable sensor based stats for IP-MPLS egress accounting";
               type empty;
             }
           }
         }
         container traffic-statistics {
           junos:must "(!(\".. .. .. .. protocols mpls disable\"))";
           junos:must-message "SPRING configuration is not allowed with 'protocols mpls disable'";
           description "Enable support for traffic statistics in SPRING";
           uses apply-advanced;
           container statistics-granularity {
             description "Granularity for traffic statistics in SPRING";
             uses apply-advanced;
             leaf per-interface {
               description "Interface Based traffic statistics in SPRING";
               type empty;
             }
           }
           leaf auto-bandwidth {
             description "Auto bandwidth name";
             junos:must "(\"protocols isis source-packet-routing traffic-statistics statistics-granularity per-interface\")";
             junos:must-message "Config protocols isis source-packet-routing traffic-statistics statistics-granularity per-interface is must";
             junos:must "(\"routing-options auto-bandwidth template $$\")";
             junos:must-message "Referenced auto-bandwidth template must be defined";
             type string;
           }
         }
       }
       container srm6 {
         presence "enable srm6";
         junos:must "(!(\".. source-packet-routing\"))";
         junos:must-message "must not have 'protocols isis source-packet-routing' configured";
         description "Enable SRm6";
         uses apply-advanced;
         container sid {
           description "Configure attributes for SID in srm6";
           uses apply-advanced;
           leaf node-sid {
             description "Set Node SID Value";
             type union {
               type string {
                 pattern "<.*>|$.*";
               }
               type uint32 {
                 range "1 .. 65535";
               }
             }
           }
           leaf address {
             description "IPv6 address corresponding to SID";
             type jt:ipv6addr;
           }
         }
       }
       list level {
         key name;
         ordered-by user;
         description "Configure global level attributes";
         leaf name {
           description "IS-IS level number";
           type union {
             type string {
               pattern "<.*>|$.*";
             }
             type uint32 {
               range "1 .. 2";
             }
           }
         }
         uses apply-advanced;
         leaf labeled-preference {
           description "Preference of labeled IS-IS routes";
           junos:must "(\".. .. source-packet-routing\")";
           junos:must-message "labeled-preference cannot be specified without 'protocols isis source-packet-routing'";
           type union {
             type uint32;
             type string {
               pattern "<.*>|$.*";
             }
           }
         }
         leaf srv6-preference {
           description "Preference of SRV6 IS-IS routes";
           junos:must "(\".. .. source-packet-routing\")";
           junos:must-message "srv6-preference cannot be specified without 'protocols isis source-packet-routing'";
           type union {
             type uint32;
             type string {
               pattern "<.*>|$.*";
             }
           }
         }
         leaf flex-algorithm-preference {
           description "Preference of flex-algorithm L-ISIS routes";
           junos:must "(\".. .. source-packet-routing\")";
           junos:must-message "flex-algorithm-preference cannot be specified without 'protocols isis source-packet-routing'";
           type union {
             type uint32;
             type string {
               pattern "<.*>|$.*";
             }
           }
         }
         container source-packet-routing {
           presence "enable source-packet-routing";
           description "Enable Source Packet Routing (SPRING)";
           uses apply-advanced;
           choice enable-disable {
             case case_1 {
               leaf disable {
                 description "Disable Source Packet Routing on this level";
                 type empty;
               }
             }
           }
           leaf srms-preference {
             description "Set SRMS preference value";
             type union {
               type string {
                 pattern "<.*>|$.*";
               }
               type uint32 {
                 range "0 .. 255";
               }
             }
           }
         }
         choice enable-disable {
           case case_1 {
             leaf disable {
               description "Disable IS-IS on this level";
               type empty;
             }
           }
         }
         leaf authentication-key {
           description "Authentication key (password)";
           type jt:unreadable;
         }
         leaf authentication-type {
           description "Authentication type";
           type enumeration {
             enum "md5" {
               description "MD5 authentication";
             }
             enum "simple" {
               description "Simple password authentication";
             }
           }
         }
         leaf purge-originator {
           description "Add Purge Originator information";
           type enumeration {
             enum "self" {
               description "Add POI only for self-originated purge LSPs";
             }
             enum "empty" {
               description "Add POI for purge LSPs who do not have POI information";
             }
           }
         }
         leaf no-hello-authentication {
           description "Disable authentication for hello packets";
           type empty;
         }
         leaf no-csnp-authentication {
           description "Disable authentication for CSN packets";
           type empty;
         }
         leaf no-psnp-authentication {
           description "Disable authentication for PSN packets";
           type empty;
         }
         leaf authentication-key-chain {
           description "Key chain name";
           junos:must "(!(\".. authentication-type\"))";
           junos:must-message "May not be configured with authentication-type";
           junos:must "(!(\".. authentication-key\"))";
           junos:must-message "May not be configured with authentication-key";
           junos:must "(\"security authentication-key-chains key-chain $$\")";
           junos:must-message "Referenced key-chain must be defined";
           type string {
             length "1 .. 128";
             junos:posix-pattern "[A-za-z]$";
             junos:pattern-message "Keychain name must not end with number.";
           }
         }
         leaf wide-metrics-only {
           description "Generate wide metrics only";
           junos:must "(!(\".. .. clns-routing\"))";
           junos:must-message "wide-metrics-only cannot be specified with clns-routing";
           type empty;
         }
         leaf preference {
           description "Preference of internal routes";
           type union {
             type uint32;
             type string {
               pattern "<.*>|$.*";
             }
           }
         }
         leaf external-preference {
           description "Preference of external routes";
           type union {
             type uint32;
             type string {
               pattern "<.*>|$.*";
             }
           }
         }
         leaf prefix-export-limit {
           description "Maximum number of external prefixes that can be exported";
           type union {
             type string {
               pattern "<.*>|$.*";
             }
             type uint32 {
               range "0 .. 4294967295";
             }
           }
         }
         container flood-reflector {
           junos:must "(!(\".. .. level 1 flood-reflector\"))";
           junos:must-message "Flood-reflector is supported only in level 2";
           description "Enable flood-reflector";
           uses apply-advanced;
           choice flood-reflector-choice {
             case case_1 {
               container reflector {
                 junos:must "(!(\".. client\"))";
                 junos:must-message "flood-reflector and client can't be configured together";
                 description "Configure this as a flood-reflector";
                 uses apply-advanced;
                 leaf cluster-id {
                   description "Cluster-ID";
                   type union {
                     type string {
                       pattern "<.*>|$.*";
                     }
                     type uint32 {
                       range "1 .. 4294967295";
                     }
                   }
                 }
               }
             }
             case case_2 {
               leaf client {
                 description "Configure interface as flood-reflector client";
                 type empty;
               }
             }
           }
         }
       }
       list interface-group {
         key name;
         description "Interface grouping configuration";
         leaf name {
           description "Interface group name";
           type string;
         }
         uses apply-advanced;
         list level {
           key name;
           ordered-by user;
           description "Configure levels on this interface-group";
           leaf name {
             description "IS-IS level number";
             type union {
               type string {
                 pattern "<.*>|$.*";
               }
               type uint32 {
                 range "1 .. 2";
               }
             }
           }
           uses apply-advanced;
           container ipv4-adjacency-segment {
             junos:must "(!(\".. no-advertise-adjacency-segment\"))";
             junos:must-message "ipv4-adjacency-segment can't be configured if no-advertise-adjacency-segment is configured in the level";
             junos:must "(!(\".. .. no-advertise-adjacency-segment\"))";
             junos:must-message "ipv4-adjacency-segment can't be configured if no-advertise-adjacency-segment is configured in the same interface";
             description "Configure ipv4 adjacency segment";
             uses apply-advanced;
             container protected {
               description "Adjacency SID is eligible for protection";
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
             container unprotected {
               description "Adjacency SID uneligible for protection";
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
           }
           container ipv6-adjacency-segment {
             junos:must "(!(\".. no-advertise-adjacency-segment\"))";
             junos:must-message "ipv6-adjacency-segment can't be configured if no-advertise-adjacency-segment is configured in the same level";
             junos:must "(!(\".. .. no-advertise-adjacency-segment\"))";
             junos:must-message "ipv6-adjacency-segment can't be configured if no-advertise-adjacency-segment is configured in the same interface";
             description "Configure ipv6 adjacency segment";
             uses apply-advanced;
             container protected {
               description "Adjacency SID is eligible for protection";
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
             container unprotected {
               description "Adjacency SID uneligible for protection";
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
           }
           container srm6-adjacency-segment {
             description "Configure srm6 adjacency segment";
             uses apply-advanced;
             container unprotected {
               description "Adjacency SID uneligible for protection";
               leaf sid {
                 description "Set Adjacency SID Value";
                 type union {
                   type string {
                     pattern "<.*>|$.*";
                   }
                   type uint32 {
                     range "1 .. 65535";
                   }
                 }
               }
             }
           }
           list topology {
             key name;
             ordered-by user;
             description "Topology specific attributes";
             leaf name {
               description "Topology name";
               type enumeration {
                 enum "default" {
                   description "Default topology";
                 }
                 enum "ipv4-multicast" {
                   description "IPv4 multicast topology";
                 }
                 enum "ipv6-unicast" {
                   description "IPv6 unicast topology";
                 }
                 enum "ipv6-multicast" {
                   description "IPv6 multicast topology";
                 }
               }
             }
             uses apply-advanced;
             leaf metric {
               description "Topology metric";
               type union {
                 type string {
                   pattern "<.*>|$.*";
                 }
                 type uint32 {
                   range "0 .. 16777215";
                 }
               }
             }
             container bandwidth-based-metrics {
               junos:must "(\".. metric\")";
               junos:must-message "Metric must be configured";
               description "Configure bandwidth based metrics";
               uses apply-advanced;
               list bandwidth {
                 key name;
                 description "Bandwidth threshold";
                 leaf name {
                   type string;
                 }
                 leaf metric {
                   description "Metric associated with specified bandwidth";
                   type union {
                     type string {
                       pattern "<.*>|$.*";
                     }
                     type uint32 {
                       range "0 .. 16777215";
                     }
                   }
                 }
               }
             }
           }
         }
         container link-group-protection {
           junos:must "(!(\".. .. backup-spf-options\"))";
           junos:must-message "Backup SPF options can't be configured";
           description "Configure link group protection";
           uses apply-advanced;
           leaf minimum-bandwidth {
             description "Minimum bandwidth to carry traffic";
             type string;
           }
           leaf revert-bandwidth {
             description "Revert bandwidth to carry traffic";
             type string;
           }
         }
         list interface {
           key name;
           description "List interfaces for this group";
           leaf name {
             description "Interface name";
             type union {
               type jt:interface-name;
               type string {
                 pattern "<.*>|$.*";
               }
             }
           }
           uses apply-advanced;
           leaf weight {
             description "Interface weight for adjacency set";
             type union {
               type string {
                 pattern "<.*>|$.*";
               }
               type uint32 {
                 range "1 .. 255";
               }
             }
           }
         }
       }
       container spf-options {
         description "Configure SPF attributes";
         uses apply-advanced;
         container microloop-avoidance {
           description "Configure microloop avoidance mechanisms";
           uses apply-advanced;
           container post-convergence-path {
             presence "enable post-convergence-path";
             junos:must "(\".. .. .. source-packet-routing\")";
             junos:must-message "Please configure source-packet-routing under isis/isis-instance";
             junos:must "(!(\".. use-route-convergence-delay\"))";
             junos:must-message "use-route-convergence-delay is not allowed with post-convergence-path";
             description "Temporarily install post-convergence path for routes potentially affected by microloops";
             uses apply-advanced;
             leaf delay {
               description "Time after which temporary post-convergence paths are removed";
               units "milliseconds";
               type union {
                 type string {
                   pattern "<.*>|$.*";
                 }
                 type uint32 {
                   range "500 .. 60000";
                 }
               }
             }
             leaf maximum-labels {
               description "Set maximum number of label supported for Micro-Loop-Avoidance calculations";
               type union {
                 type string {
                   pattern "<.*>|$.*";
                 }
                 type uint32 {
                   range "2 .. 8";
                 }
               }
             }
             leaf maximum-srv6-sids {
               description "Set maximum number of SRV6 SIDs supported for Micro-Loop-Avoidance calculations";
               type union {
                 type string {
                   pattern "<.*>|$.*";
                 }
                 type uint32 {
                   range "2 .. 6";
                 }
               }
             }
           }
         }
         leaf delay {
           description "Time to wait before running an SPF";
           units "milliseconds";
           type union {
             type string {
               pattern "<.*>|$.*";
             }
             type uint32 {
               range "50 .. 1000";
             }
           }
         }
         leaf holddown {
           description "Time to hold down before running an SPF";
           units "milliseconds";
           type union {
             type string {
               pattern "<.*>|$.*";
             }
             type uint32 {
               range "2000 .. 10000";
             }
           }
         }
         leaf rapid-runs {
           description "Number of rapid SPF runs before SPF holddown";
           type union {
             type string {
               pattern "<.*>|$.*";
             }
             type uint32 {
               range "1 .. 5";
             }
           }
         }
         container multipath {
           description "Configure multipath options";
           uses apply-advanced;
           container weighted {
             description "Weighted multipath options";
             uses apply-advanced;
             leaf one-hop {
               description "Enable load balancing on onehop multipath based on interface bandwidth";
               type empty;
             }
           }
         }
       }
       container traceoptions {
         description "Trace options for IS-IS";
         uses apply-advanced;
         list flag {
           key name;
           ordered-by user;
           description "Tracing parameters";
           leaf name {
             type enumeration {
               enum "traffic-statistics" {
                 description "Trace traffic-statistics related events";
               }
               enum "post-convergence-lfa" {
                 description "Trace post-convergence-lfa related events";
               }
               enum "error" {
                 description "Trace errored packets";
               }
               enum "spf" {
                 description "Trace SPF events";
               }
               enum "packets" {
                 description "Trace IS-IS packets";
               }
               enum "hello" {
                 description "Trace hello packets";
               }
               enum "lsp" {
                 description "Trace link-state packets";
               }
               enum "psn" {
                 description "Trace partial sequence number (PSN) packets";
               }
               enum "csn" {
                 description "Trace complete sequence number (CSN) packets";
               }
               enum "layer2-map" {
                 description "Trace ARP/ND kernel state manipulation";
               }
               enum "lsp-generation" {
                 description "Trace LSP generation";
               }
               enum "graceful-restart" {
                 description "Trace graceful restart events";
               }
               enum "ldp-synchronization" {
                 description "Trace synchronization between IS-IS and LDP";
               }
               enum "nsr-synchronization" {
                 description "Trace NSR synchronization events";
               }
               enum "spring" {
                 description "Trace source packet routing";
               }
               enum "prefix-sid" {
                 description "Trace source packet routing, prefix-sids";
               }
               enum "flex-algorithm" {
                 description "Trace flex-algorithm related events";
               }
               enum "adj-sid" {
                 description "Trace adj-sid related events";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "srv6" {
                 description "Trace srv6 related events";
               }
               enum "rmopd" {
                 description "Trace rmopd interactions";
               }
               enum "mapping-server" {
                 description "Trace mapping server related events";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
         container file {
           description "Trace file options";
           leaf filename {
             description "Name of file in which to write trace information";
             type string {
               length "1 .. 1024";
               junos:posix-pattern "![/ %]";
               junos:pattern-message "Must not contain '/', % or a space";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
       }
       container backup-spf-options {
         description "Configure backup SPF attributes";
         uses apply-advanced;
         container remote-backup-calculation {
           presence "enable remote-backup-calculation";
           junos:must "(!(\".. .. backup-spf-options use-post-convergence-lfa\"))";
           junos:must-message "Not allowed with 'protocols isis backup-spf-options use-post-convergence-lfa'";
           description "Calculate Remote LFA backup nexthops";
           uses apply-advanced;
         }
         container use-post-convergence-lfa {
           presence "enable use-post-convergence-lfa";
           junos:must "(\".. .. source-packet-routing\")";
           junos:must-message "Configuration of 'protocols isis source-packet-routing' is must";
           description "Calculate Post Convergence Backup Nexthops";
           uses apply-advanced;
           leaf maximum-labels {
             description "Set maximum number of label supported for post convergence path calculations";
             type union {
               type string {
                 pattern "<.*>|$.*";
               }
               type uint32 {
                 range "2 .. 8";
               }
             }
           }
           leaf maximum-srv6-sids {
             description "Set maximum number of SRV6 SIDs for post convergence path calculations";
             type union {
               type string {
                 pattern "<.*>|$.*";
               }
               type uint32 {
                 range "2 .. 6";
               }
             }
           }
           leaf maximum-backup-paths {
             description "Set maximum equal cost backup post convergence paths";
             type union {
               type string {
                 pattern "<.*>|$.*";
               }
               type uint32 {
                 range "1 .. 8";
               }
             }
           }
         }
         container use-source-packet-routing {
           presence "enable use-source-packet-routing";
           junos:must "(\".. .. source-packet-routing\")";
           junos:must-message "Use of SPRING paths as backup can't be configured without configuring 'protocols isis source-packet-routing'";
           description "Use SPRING routed paths for protection";
           uses apply-advanced;
         }
         leaf per-prefix-calculation {
           description "Calculate backup nexthops for non-best prefix originators";
           type empty;
         }
         leaf node-link-degradation {
           description "Degrade to link protection when nodelink protection not available";
           junos:must "(!(\".. .. backup-spf-options use-post-convergence-lfa\"))";
           junos:must-message "Not allowed with 'protocols isis backup-spf-options use-post-convergence-lfa'";
           type empty;
         }
       }
       list context-identifier {
         key name;
         ordered-by user;
         description "Configuration for advertisement of a context-identifier ";
         leaf name {
           description "Context identifier range";
           type jt:ipprefix;
         }
         uses apply-advanced;
         list level {
           key name;
           ordered-by user;
           description "Configure global level attributes";
           leaf name {
             description "IS-IS level number";
             type union {
               type string {
                 pattern "<.*>|$.*";
               }
               type uint32 {
                 range "1 .. 2";
               }
             }
           }
           uses apply-advanced;
           choice enable-disable {
             case case_1 {
               leaf disable {
                 description "Disable advertisements to this level";
                 type empty;
               }
             }
           }
         }
       }
       container traffic-engineering {
         description "Configure traffic engineering attributes";
         uses apply-advanced;
         choice enable-disable {
           case case_1 {
             leaf disable {
               description "Disable traffic engineering";
               type empty;
             }
           }
         }
         leaf l3-unicast-topology {
           description "Download IGP topology into TED";
           type empty;
         }
         leaf ipv6 {
           description "Enable TEDv6";
           type empty;
         }
         leaf credibility-protocol-preference {
           description "Follow IGP protocol preference for TED protocol credibility";
           type empty;
         }
         leaf ipv4-multicast-rpf-routes {
           description "Install IPv4 routes for multicast RPF checks into inet.2";
           status deprecated;
           junos:must "(!(\".. .. topologies ipv4-multicast\"))";
           junos:must-message "ipv4-multicast-rpf-routes cannot be used with the ipv4-multicast topology";
           junos:must "(!(\".. .. multicast-topology\"))";
           junos:must-message "ipv4-multicast-rpf-routes cannot be used with multicast-topology";
           junos:must "(\".. shortcuts\")";
           junos:must-message "ipv4-multicast-rpf-routes cannot be used without shortcuts";
           type empty;
         }
         leaf ignore-lsp-metrics {
           description "Ignore label-switched path metrics when doing shortcuts";
           type empty;
         }
         container tunnel-source-protocol {
           description "Protocols from which to pick label-switched paths";
           uses apply-advanced;
           container rsvp {
             presence "enable rsvp";
             description "Pick label-switched paths from rsvp";
             uses apply-advanced;
             leaf preference {
               description "Preference for label-switched paths from this protocol";
               type union {
                 type string {
                   pattern "<.*>|$.*";
                 }
                 type uint32 {
                   range "1 .. 255";
                 }
               }
             }
           }
           container spring-te {
             presence "enable spring-te";
             description "Pick label-switched paths from spring-te";
             uses apply-advanced;
             leaf preference {
               description "Preference for label-switched paths from this protocol";
               type union {
                 type string {
                   pattern "<.*>|$.*";
                 }
                 type uint32 {
                   range "1 .. 255";
                 }
               }
             }
           }
         }
         list family {
           key name;
           ordered-by user;
           description "Address family specific traffic-engineering attributes";
           leaf name {
             type enumeration {
               enum "inet" {
                 description "IPv4 family";
               }
               enum "inet6" {
                 description "IPv6 family";
               }
               enum "inet-mpls" {
                 description "IPv4-MPLS family";
               }
               enum "inet6-mpls" {
                 description "IPv6-MPLS family";
               }
             }
           }
           uses apply-advanced;
           container shortcuts {
             presence "enable shortcuts";
             junos:must "(!(\".. .. no-ldp-shortcuts\"))";
             junos:must-message "Shortcuts configuration cannot be used with no-ldp-shortcuts";
             junos:must "(!(\".. .. shortcuts\"))";
             junos:must-message "per-family shortcuts configuration cannot be used with global shortcuts enabled";
             junos:must "(!(\".. .. disable\"))";
             junos:must-message "shortcuts cannot be used without traffic-engineering enabled";
             description "Use label-switched paths as next hops, if possible";
             uses apply-advanced;
             leaf multicast-rpf-routes {
               description "Install routes for multicast RPF checks into multicast RIB";
               junos:must "(!(\".. .. .. .. multicast-topology\"))";
               junos:must-message "ipv4 multicast-rpf-routes cannot be used with the multicast-topology";
               junos:must "(!(\".. .. .. .. topologies ipv4-multicast\"))";
               junos:must-message "ipv4 multicast-rpf-routes cannot be used with the ipv4-multicast topology";
               type empty;
             }
             leaf-list import {
               ordered-by user;
               description "Import policy for shortcut";
               type jt:policy-algebra;
             }
           }
         }
         container shortcuts {
           presence "enable shortcuts";
           description "Use label-switched paths as next hops, if possible";
           status deprecated;
           uses apply-advanced;
           leaf ignore-lsp-metrics {
             description "Ignore label-switched path metrics when doing shortcuts";
             status deprecated;
             type empty;
           }
         }
         container multipath {
           description "Configure label-switched-path multipath behavior";
           uses apply-advanced;
           leaf lsp-equal-cost {
             description "Include equal cost label-switched-paths";
             junos:must "((\".. .. shortcuts\" || (\".. .. family $$={inet} shortcuts\" || (\".. .. family $$={inet6} shortcuts\" || \".. .. family $$={iso} shortcuts\"))))";
             junos:must-message "Traffic engineering shortcuts for inet, inet6 or iso family must be configured.";
             type empty;
           }
         }
         container advertisement {
           description "Configure traffic engineering attribute advertisements";
           uses apply-advanced;
           leaf always {
             description "Advertise applicable legacy TE attributes always";
             type empty;
           }
           container application-specific {
             description "Advertise application-specific TE attributes";
             uses apply-advanced;
             container all-applications {
               presence "enable all-applications";
               description "Advertise common application-specific link attributes";
               uses apply-advanced;
               leaf legacy {
                 description "Use legacy TE attributes for this application";
                 type empty;
               }
             }
           }
         }
       }
       list label-switched-path {
         key name;
         ordered-by user;
         description "Configuration for advertisement of a label-switched path";
         junos:must "(!(\".. traffic-engineering ipv4-multicast-rpf-routes\"))";
         junos:must-message "cannot advertise LSPs when using ipv4-multicast-rpf-routes";
         leaf name {
           description "Name of label-switched path to be advertised";
           type string {
             length "1 .. 64";
           }
         }
         uses apply-advanced;
         list level {
           key name;
           ordered-by user;
           description "Configure global level attributes";
           leaf name {
             description "IS-IS level number";
             type union {
               type string {
                 pattern "<.*>|$.*";
               }
               type uint32 {
                 range "1 .. 2";
               }
             }
           }
           uses apply-advanced;
           choice enable-disable {
             case case_1 {
               leaf disable {
                 description "Disable advertisements to this level";
                 type empty;
               }
             }
           }
           leaf metric {
             description "SPF metric for this level";
             type union {
               type string {
                 pattern "<.*>|$.*";
               }
               type uint32 {
                 range "0 .. 16777215";
               }
             }
           }
         }
       }
       choice enable-disable {
         case case_1 {
           leaf disable {
             description "Disable IS-IS";
             type empty;
           }
         }
       }
       leaf-list export {
         ordered-by user;
         description "Export policy";
         type jt:policy-algebra;
       }
       leaf-list import {
         ordered-by user;
         description "Import policy";
         type jt:policy-algebra;
       }
       leaf reference-bandwidth {
         description "Bandwidth for calculating metric defaults";
         type string;
       }
       choice layer2-map-choice {
         leaf layer2-map {
           description "Kernel ARP/ND creation for nexthops";
           type empty;
         }
         leaf no-layer2-map {
           description "Don't kernel ARP/ND creation for nexthops";
           type empty;
         }
       }
       leaf job-stats {
         description "Collect job statistics";
         type empty;
       }
       leaf lsp-lifetime {
         description "Lifetime of LSPs";
         units "seconds";
         type union {
           type string {
             pattern "<.*>|$.*";
           }
           type uint32 {
             range "350 .. 65535";
           }
         }
       }
       leaf max-lsp-size {
         description "Maximum size allowed for LSPs";
         default "1492";
         type union {
           type string {
             pattern "<.*>|$.*";
           }
           type uint32 {
             range "512 .. 1492";
           }
         }
       }
       leaf max-hello-size {
         description "Maximum size allowed for ISIS Hello PDUs";
         default "1492";
         type union {
           type string {
             pattern "<.*>|$.*";
           }
           type uint32 {
             range "512 .. 16000";
           }
         }
       }
       leaf max-snp-size {
         description "Maximum size allowed for Sequence Number (Complete/Partial) PDUs";
         default "1400";
         type union {
           type string {
             pattern "<.*>|$.*";
           }
           type uint32 {
             range "512 .. 1400";
           }
         }
       }
       leaf spf-delay {
         description "Time to wait before running an SPF";
         status deprecated;
         units "milliseconds";
         junos:must "(!(\".. spf-options delay\"))";
         junos:must-message "You can only configure either spf-delay or delay under spf-options";
         type union {
           type string {
             pattern "<.*>|$.*";
           }
           type uint32 {
             range "50 .. 120000";
           }
         }
       }
       leaf authentication-key {
         description "Authentication key (password)";
         status deprecated;
         type jt:unreadable;
       }
       leaf authentication-type {
         description "Authentication type";
         status deprecated;
         type enumeration {
           enum "md5" {
             description "MD5 authentication";
             status deprecated;
           }
           enum "simple" {
             description "Simple password authentication";
             status deprecated;
           }
         }
       }
       leaf loose-authentication-check {
         description "Verify authentication only if PDU has authentication TLV";
         type empty;
       }
       leaf max-areas {
         description "Maximum number of advertised Areas";
         default "3";
         type union {
           type string {
             pattern "<.*>|$.*";
           }
           type uint32 {
             range "3 .. 64";
           }
         }
       }
       leaf no-authentication-check {
         description "Disable authentication checking";
         type empty;
       }
       leaf no-ipv4-routing {
         description "Disable IPv4 routing";
         type empty;
       }
       leaf no-ipv6-routing {
         description "Disable IPv6 routing";
         type empty;
       }
       leaf no-adjacency-holddown {
         description "Disable adjacency hold down";
         type empty;
       }
       leaf multicast-topology {
         description "Enable multicast topology";
         status deprecated;
         type empty;
       }
       leaf ignore-attached-bit {
         description "Ignore the attached bit in Level 1 LSPs";
         type empty;
       }
       container rib-group {
         description "Routing table group for importing IS-IS routes";
         uses rib_group_type;
       }
       container strict-dual-isis {
         presence "enable strict-dual-isis";
         junos:must "(!(\".. topologies\"))";
         junos:must-message "strict-dual-isis is not allowed with multi-topologies";
         description "Enable dual isis if spf computation is required for both ipv4 and ipv6 family";
         uses apply-advanced;
         leaf holdown {
           description "Time to wait for ipv4 and ipv6 connectivity";
           status deprecated;
           default "12";
           type union {
             type string {
               pattern "<.*>|$.*";
             }
             type uint32 {
               range "1 .. 65535";
             }
           }
         }
         leaf holddown {
           description "Time to wait for ipv4 and ipv6 connectivity";
           default "12";
           type union {
             type string {
               pattern "<.*>|$.*";
             }
             type uint32 {
               range "1 .. 65535";
             }
           }
         }
       }
       container topologies {
         description "Enable topologies";
         uses apply-advanced;
         leaf ipv4-multicast {
           description "Enable IPv4-multicast topology";
           type empty;
         }
         leaf ipv6-unicast {
           description "Enable IPv6-unicast topology";
           type empty;
         }
         leaf ipv6-multicast {
           description "Enable IPv6-multicast topology";
           type empty;
         }
       }
       container overload {
         presence "enable overload";
         description "Set the overload bit (no transit traffic)";
         uses apply-advanced;
         leaf timeout {
           description "Time after which overload bit is reset";
           units "seconds";
           type union {
             type string {
               pattern "<.*>|$.*";
             }
             type uint32 {
               range "60 .. 3600";
             }
           }
         }
         leaf advertise-high-metrics {
           description "Advertise high metrics instead of setting the overload bit";
           type empty;
         }
         leaf allow-route-leaking {
           description "Allow routes to be leaked when overload is configured";
           type empty;
         }
         leaf internal-prefixes {
           description "Allow internal prefixes to be advertised with high metric";
           type empty;
         }
         leaf external-prefixes {
           description "Allow external prefixes to be advertised with high metric";
           type empty;
         }
       }
       container graceful-restart {
         description "IS-IS graceful restart options";
         choice enable-disable {
           case case_1 {
             leaf disable {
               description "Disable graceful restart";
               type empty;
             }
           }
         }
         leaf helper-disable {
           description "Disable graceful restart helper capability";
           type empty;
         }
         leaf restart-duration {
           description "Maximum time for graceful restart to finish";
           units "seconds";
           type union {
             type string {
               pattern "<.*>|$.*";
             }
             type uint32 {
               range "30 .. 300";
             }
           }
         }
       }
     }
     container l2iw {
       presence "enable l2iw";
       description "Configuration for Layer 2 interworking";
       uses apply-advanced;
       container traceoptions {
         description "Trace options for Layer 2 circuits";
         uses apply-advanced;
         container file {
           description "Trace file options";
           leaf filename {
             description "Name of file in which to write trace information";
             type string {
               length "1 .. 1024";
               junos:posix-pattern "![/ %]";
               junos:pattern-message "Must not contain '/', % or a space";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "error" {
                 description "Trace errors";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
     }
     container l2circuit {
       description "Configuration for Layer 2 circuits over MPLS";
       uses apply-advanced;
       container traceoptions {
         description "Trace options for Layer 2 circuits";
         uses apply-advanced;
         container file {
           description "Trace file options";
           leaf filename {
             description "Name of file in which to write trace information";
             type string {
               length "1 .. 1024";
               junos:posix-pattern "![/ %]";
               junos:pattern-message "Must not contain '/', % or a space";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "error" {
                 description "Trace errors";
               }
               enum "topology" {
                 description "Trace Layer 2 circuit topology changes";
               }
               enum "fec" {
                 description "Trace Layer 2 circuit VC FEC advertisements";
               }
               enum "connections" {
                 description "Trace Layer 2 circuit connections";
               }
               enum "oam" {
                 description "Trace Layer 2 circuit OAM messages";
               }
               enum "egress-protection" {
                 description "Trace Layer 2 circuit egress protection messages";
               }
               enum "auto-sensing" {
                 description "Trace Layer 2 circuit PW auto-sensing";
               }
               enum "sdb" {
                 description "Trace SDB";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       list neighbor {
         key name;
         ordered-by user;
         description "List of Layer 2 circuits to this neighbor";
         leaf name {
           description "Neighbor ID";
           type jt:ipv4addr;
         }
         uses apply-advanced;
         list interface {
           key name;
           ordered-by user;
           description "Interface forming the Layer 2 circuit";
           leaf name {
             description "Interface name";
             type union {
               type jt:interface-name;
               type string {
                 pattern "<.*>|$.*";
               }
             }
           }
           uses apply-advanced;
           container static {
             presence "enable static";
             junos:must "((!(\".. backup-neighbor\") || all \".. backup-neighbor <*> static\"))";
             junos:must-message "Backup neighbor should be static";
             description "Configuration of static Pseudowire";
             uses apply-advanced;
             leaf incoming-label {
               description "Layer 2 circuit incoming static label";
               type union {
                 type string {
                   pattern "<.*>|$.*";
                 }
                 type uint32 {
                   range "16 .. 1048575";
                 }
               }
             }
             leaf outgoing-label {
               description "Layer 2 circuit outgoing static label";
               type union {
                 type string {
                   pattern "<.*>|$.*";
                 }
                 type uint32 {
                   range "16 .. 1048575";
                 }
               }
             }
             leaf send-oam {
               description "Turn on sending of l2ckt ping";
               type empty;
             }
           }
           leaf psn-tunnel-endpoint {
             description "Endpoint of the transport tunnel on the remote PE";
             type jt:ipv4addr;
           }
           leaf protect-interface {
             description "Name of protect interface";
             type union {
               type jt:interface-name;
               type string {
                 pattern "<.*>|$.*";
               }
             }
           }
           leaf virtual-circuit-id {
             description "Identifier for this Layer 2 circuit";
             type union {
               type string {
                 pattern "<.*>|$.*";
               }
               type uint32 {
                 range "1 .. 4294967295";
               }
             }
           }
           leaf description {
             description "Text description of Layer 2 circuit";
             type string;
           }
           choice control-word-choice {
             leaf control-word {
               description "Add control word to the Layer 2 encapsulation";
               type empty;
             }
             leaf no-control-word {
               description "Don't add control word to the Layer 2 encapsulation";
               type empty;
             }
           }
           leaf flow-label-transmit {
             description "Advertise capability to push Flow Label in transmit direction to remote PE";
             junos:must "(!(\".. egress-protection\"))";
             junos:must-message "Can't configure flow-label with egress-protection";
             junos:must "(!(\".. connection-protection\"))";
             junos:must-message "Can't configure flow-label with connection-protection";
             type empty;
           }
           leaf flow-label-transmit-static {
             description "Push Flow Label on PW packets sent to remote PE";
             junos:must "(!(\".. static\"))";
             junos:must-message "Can't configure flow-label for static pseudowire";
             junos:must "(!(\".. egress-protection\"))";
             junos:must-message "Can't configure flow-label with egress-protection";
             junos:must "(!(\".. connection-protection\"))";
             junos:must-message "Can't configure flow-label with connection-protection";
             junos:must "(!(\".. backup-neighbor\"))";
             junos:must-message "Can't configure flow-label with backup-neighbor";
             junos:must "(!(\".. flow-label-transmit\"))";
             junos:must-message "Can't have flow-label-transmit-static along with flow-label-transmit";
             type empty;
           }
           leaf flow-label-receive {
             description "Advertise capability to pop Flow Label in receive direction to remote PE";
             junos:must "(!(\".. egress-protection\"))";
             junos:must-message "Can't configure flow-label with egress-protection";
             junos:must "(!(\".. connection-protection\"))";
             junos:must-message "Can't configure flow-label with connection-protection";
             type empty;
           }
           leaf flow-label-receive-static {
             description "Pop Flow Label from PW packets received from remote PE";
             junos:must "(!(\".. static\"))";
             junos:must-message "Can't configure flow-label for static pseudowire";
             junos:must "(!(\".. egress-protection\"))";
             junos:must-message "Can't configure flow-label with egress-protection";
             junos:must "(!(\".. connection-protection\"))";
             junos:must-message "Can't configure flow-label with connection-protection";
             junos:must "(!(\".. backup-neighbor\"))";
             junos:must-message "Can't configure flow-label with backup-neighbor";
             junos:must "(!(\".. flow-label-receive\"))";
             junos:must-message "Can't have flow-label-receive-static along with flow-label-receive";
             type empty;
           }
           leaf community {
             description "Community associated with this Layer 2 circuit";
             type string;
           }
           leaf mtu {
             description "MTU to be advertised for this Layer 2 circuit";
             type union {
               type string {
                 pattern "<.*>|$.*";
               }
               type uint32 {
                 range "512 .. 65535";
               }
             }
           }
           leaf encapsulation-type {
             description "Encapsulation type for VPN";
             type enumeration {
               enum "atm-aal5" {
                 description "ATM AAL/5 encapsulation";
               }
               enum "atm-cell" {
                 description "ATM port promiscuous mode cell encapsulation";
               }
               enum "atm-cell-port-mode" {
                 description "ATM port promiscuous mode cell encapsulation";
               }
               enum "atm-cell-vp-mode" {
                 description "ATM VP promiscuous mode cell encapsulation";
               }
               enum "atm-cell-vc-mode" {
                 description "ATM non-promiscuous cell encapsulation";
               }
               enum "frame-relay" {
                 description "Frame Relay encapsulation";
               }
               enum "ppp" {
                 description "PPP encapsulation";
               }
               enum "cisco-hdlc" {
                 description "Cisco-compatible HDLC encapsulation";
               }
               enum "ethernet-vlan" {
                 description "Ethernet VLAN encapsulation";
               }
               enum "ethernet" {
                 description "Ethernet encapsulation";
               }
               enum "interworking" {
                 description "Layer 2.5 interworking VPN";
               }
               enum "frame-relay-port-mode" {
                 description "Frame Relay port mode encapsulation";
               }
               enum "satop-t1" {
                 description "SATOP-T1 based Layer 2 VPN";
               }
               enum "satop-e1" {
                 description "SATOP-E1 based Layer 2 VPN";
               }
               enum "satop-t3" {
                 description "SATOP-T3 based Layer 2 VPN";
               }
               enum "satop-e3" {
                 description "SATOP-E3 based Layer 2 VPN";
               }
               enum "cesop" {
                 description "CESOP based Layer 2 VPN";
               }
             }
           }
           leaf ignore-encapsulation-mismatch {
             description "Allow different encapsulation types on local and remote end";
             junos:must "(!(\".. static\"))";
             junos:must-message "not supported for static pseudowires";
             type empty;
           }
           leaf ignore-mtu-mismatch {
             description "Allow different MTUs on interfaces";
             junos:must "(!(\".. static\"))";
             junos:must-message "not supported for static pseudowires";
             type empty;
           }
           leaf no-revert {
             description "Don't revert to primary-interface";
             junos:must "(\".. protect-interface\")";
             junos:must-message "no-revert cannot be configured without protect-interface";
             type empty;
           }
           container bandwidth {
             description "Bandwidth to reserve (bps)";
             uses bandwidth-type;
           }
           leaf send-ip-addr-list-tlv {
             description "Send IP ADDR LIST TLV to remote side";
             type empty;
           }
           container pseudowire-status-tlv {
             presence "enable pseudowire-status-tlv";
             description "Send pseudowire status TLV";
             uses apply-advanced;
             leaf hot-standby-vc-on {
               description "Activate pseudowire upon arrival of 'hot-standby' status TLV message";
               junos:must "(!(\".. .. static\"))";
               junos:must-message "not supported for static pseudowires";
               type empty;
             }
           }
           leaf switchover-delay {
             description "Layer 2 circuit switchover delay";
             default "10000";
             units "milliseconds";
             type union {
               type string {
                 pattern "<.*>|$.*";
               }
               type uint32 {
                 range "0 .. 180000";
               }
             }
           }
           container revert-time {
             presence "enable revert-time";
             description "Enable pseudowire redundancy reversion";
             leaf delay {
               description "Reversion timer (seconds)";
               units "seconds";
               type union {
                 type string {
                   pattern "<.*>|$.*";
                 }
                 type uint32 {
                   range "0 .. 600";
                 }
               }
             }
             leaf maximum {
               description "Maximum reversion interval to add over revert-time delay";
               units "seconds";
               type union {
                 type string {
                   pattern "<.*>|$.*";
                 }
                 type uint32 {
                   range "0 .. 1200";
                 }
               }
             }
           }
           leaf connection-protection {
             description "End-2-end protection via OAM failure detection";
             junos:must "((!(\".. backup-neighbor\") || all \".. backup-neighbor <*> standby\"))";
             junos:must-message "For connection-protection services, backup neighbor must be standby";
             junos:must "(!(\".. switchover-delay\"))";
             junos:must-message "connection-protection cannot be configured with switchover-delay";
             junos:must "(!(\".. revert-time\"))";
             junos:must-message "connection-protection cannot be configured with revert-time";
             type empty;
           }
           list backup-neighbor {
             key name;
             ordered-by user;
             description "Configuration of redundant l2circuit";
             leaf name {
               description "Neighbor ID";
               type jt:ipv4addr;
             }
             uses apply-advanced;
             container static {
               presence "enable static";
               junos:must "(\".. .. static\")";
               junos:must-message "Primary Pseudo wire has to be static";
               description "Configuration of static Pseudowire";
               uses apply-advanced;
               leaf incoming-label {
                 description "Layer 2 circuit incoming static label";
                 type union {
                   type string {
                     pattern "<.*>|$.*";
                   }
                   type uint32 {
                     range "16 .. 1048575";
                   }
                 }
               }
               leaf outgoing-label {
                 description "Layer 2 circuit outgoing static label";
                 type union {
                   type string {
                     pattern "<.*>|$.*";
                   }
                   type uint32 {
                     range "16 .. 1048575";
                   }
                 }
               }
             }
             leaf virtual-circuit-id {
               description "Identifier for this Layer 2 circuit";
               type union {
                 type string {
                   pattern "<.*>|$.*";
                 }
                 type uint32 {
                   range "1 .. 4294967295";
                 }
               }
             }
             leaf community {
               description "Community associated with this Layer 2 circuit";
               junos:must "(!(\".. .. connection-protection\"))";
               junos:must-message "The backup neighbor cannot be configured with community alongwith connection-protection";
               type string;
             }
             leaf psn-tunnel-endpoint {
               description "Endpoint of the transport tunnel on the remote PE";
               type jt:ipv4addr;
             }
             leaf standby {
               description "Keep backup pseudowire in continuous standby";
               type empty;
             }
             leaf hot-standby {
               description "Keep backup pseudowire in continuous standby mode and ready for traffic forwarding";
               junos:must "(\".. .. pseudowire-status-tlv\")";
               junos:must-message "Pseudowire-status-tlv must be configured in order to have hot-standby enabled";
               junos:must "(!(\".. .. connection-protection\"))";
               junos:must-message "Hot-standby cannot be configured while having connection-protection enabled";
               junos:must "(!(\".. standby\"))";
               junos:must-message "The backup neighbor cannot be configured with standby and hot-standby features simultaneously";
               type empty;
             }
           }
           container oam {
             description "OAM Configuration for Layer 2 circuit";
             uses apply-advanced;
             leaf ping-interval {
               description "Time interval between ping messages";
               default "60";
               units "seconds";
               type union {
                 type string {
                   pattern "<.*>|$.*";
                 }
                 type uint16 {
                   range "30 .. 3600";
                 }
               }
             }
             leaf ping-multiplier {
               description "Number of ping reply missed before declaring BFD down";
               type union {
                 type string {
                   pattern "<.*>|$.*";
                 }
                 type uint8 {
                   range "1 .. 5";
                 }
               }
             }
             container bfd-liveness-detection {
               description "Bidirectional Forwarding Detection (BFD) options";
               uses apply-advanced;
               leaf version {
                 description "BFD protocol version number";
                 default "automatic";
                 type enumeration {
                   enum "0" {
                     description "BFD version 0 (deprecated)";
                   }
                   enum "1" {
                     description "BFD version 1";
                   }
                   enum "automatic" {
                     description "Choose BFD version automatically";
                   }
                 }
               }
               leaf minimum-interval {
                 description "Minimum transmit and receive interval";
                 units "milliseconds";
                 type union {
                   type string {
                     pattern "<.*>|$.*";
                   }
                   type uint32 {
                     range "1 .. 255000";
                   }
                 }
               }
               leaf minimum-transmit-interval {
                 description "Minimum transmit interval";
                 status deprecated;
                 units "milliseconds";
                 type union {
                   type string {
                     pattern "<.*>|$.*";
                   }
                   type uint32 {
                     range "1 .. 255000";
                   }
                 }
               }
               leaf minimum-receive-interval {
                 description "Minimum receive interval";
                 units "milliseconds";
                 type union {
                   type string {
                     pattern "<.*>|$.*";
                   }
                   type uint32 {
                     range "1 .. 255000";
                   }
                 }
               }
               leaf multiplier {
                 description "Detection time multiplier";
                 default "3";
                 type union {
                   type string {
                     pattern "<.*>|$.*";
                   }
                   type uint32 {
                     range "1 .. 255";
                   }
                 }
               }
               choice adaptation-choice {
                 case case_1 {
                   leaf no-adaptation {
                     description "Disable adaptation";
                     type empty;
                   }
                 }
               }
               container transmit-interval {
                 description "Transmit-interval options";
                 uses apply-advanced;
                 leaf minimum-interval {
                   description "Minimum transmit interval";
                   units "milliseconds";
                   type union {
                     type string {
                       pattern "<.*>|$.*";
                     }
                     type uint32 {
                       range "1 .. 255000";
                     }
                   }
                 }
                 leaf threshold {
                   description "High transmit interval triggering a trap";
                   units "milliseconds";
                   type union {
                     type uint32;
                     type string {
                       pattern "<.*>|$.*";
                     }
                   }
                 }
               }
               container detection-time {
                 description "Detection-time options";
                 uses apply-advanced;
                 leaf threshold {
                   description "High detection-time triggering a trap";
                   units "milliseconds";
                   type union {
                     type uint32;
                     type string {
                       pattern "<.*>|$.*";
                     }
                   }
                 }
               }
             }
           }
           container egress-protection {
             junos:must "(!(\".. backup-neighbor\"))";
             junos:must-message "Can't configure both backup-neighbor and egress-protection";
             junos:must "(!(\".. protect-interface\"))";
             junos:must-message "Can't configure both protect-interface and egress-protection";
             description "Egress protection for Layer 2 circuit";
             uses apply-advanced;
             choice protection-type {
               case case_1 {
                 leaf protector-interface {
                   description "Name of the protector interface for local protection";
                   junos:must "(!(\".. protected-l2circuit\"))";
                   junos:must-message "Can't configure both protector-interface and protected-l2circuit";
                   type union {
                     type jt:interface-name;
                     type string {
                       pattern "<.*>|$.*";
                     }
                   }
                 }
               }
               case case_2 {
                 container protector-pe {
                   junos:must "(\".. .. .. .. .. ldp upstream-label-assignment\")";
                   junos:must-message "LDP upstream-label-assignment capability must be enabled";
                   description "Address of the protector PE";
                   leaf address {
                     description "Address of the protector PE";
                     type jt:ipv4addr;
                   }
                   leaf context-identifier {
                     description "Identifier of the context used for this protection";
                     type jt:ipv4addr;
                   }
                   leaf lsp {
                     description "Name of the label-switched path used for the protection";
                     type string {
                       junos:posix-pattern "^.{1,64}$";
                       junos:pattern-message "Must be a string of 64 characters or less";
                     }
                   }
                 }
               }
             }
             container protected-l2circuit {
               junos:must "(\".. .. .. .. .. ldp upstream-label-assignment\")";
               junos:must-message "LDP upstream-label-assignment capability must be enabled";
               description "Primary Layer 2 circuit to be protected";
               leaf l2circuit-name {
                 description "Name of the protected Layer 2 circuit";
                 type string {
                   junos:posix-pattern "^.{1,64}$";
                   junos:pattern-message "Must be a string of 64 characters or less";
                 }
               }
               leaf ingress-pe {
                 description "Ingress PE address of the protected Layer 2 circuit";
                 type jt:ipv4addr;
               }
               leaf egress-pe {
                 description "Egress PE address of the protected Layer 2 circuit";
                 type jt:ipv4addr;
               }
               leaf virtual-circuit-id {
                 description "Identifier of the protected Layer 2 circuit";
                 type union {
                   type string {
                     pattern "<.*>|$.*";
                   }
                   type uint32 {
                     range "1 .. 4294967295";
                   }
                 }
               }
             }
           }
         }
       }
       container local-switching {
         description "Configuration of Layer 2 circuits local switching";
         uses apply-advanced;
         list interface {
           key name;
           ordered-by user;
           description "Interface forming the local Layer 2 circuit";
           leaf name {
             description "Interface name";
             type union {
               type jt:interface-name;
               type string {
                 pattern "<.*>|$.*";
               }
             }
           }
           uses apply-advanced;
           leaf no-revert {
             description "Do not revert to primary-interface";
             junos:must "(\".. protect-interface\")";
             junos:must-message "no-revert cannot be configured without protect-interface";
             type empty;
           }
           leaf protect-interface {
             description "Name of protect interface";
             type union {
               type jt:interface-name;
               type string {
                 pattern "<.*>|$.*";
               }
             }
           }
           leaf connection-protection {
             description "End-2-end protection via OAM failure detection";
             junos:must "((\".. neighbor\" || (\".. backup-neighbor\" || \".. end-interface backup-interface\")))";
             junos:must-message "Connection-protection can be configured only when neighbor/backup-neighbor/backup-interface is present";
             type empty;
           }
           list neighbor {
             key name;
             ordered-by user;
             description "Configuration of Layer 2 circuit";
             junos:must "(\".. end-interface backup-interface\")";
             junos:must-message "Backup-interface must be configured when neighbor is present";
             junos:must "(\".. connection-protection\")";
             junos:must-message "Connection-protection must be configured when neighbor is present";
             junos:must "(!(\".. end-interface interface\"))";
             junos:must-message "Neighbor cannot be configured along with end-interface interface";
             junos:must "(!(\".. backup-neighbor\"))";
             junos:must-message "Neighbor cannot be configured along with backup-neighbor";
             leaf name {
               description "Neighbor ID";
               type jt:ipv4addr;
             }
             uses apply-advanced;
             leaf virtual-circuit-id {
               description "Identifier for this Layer 2 circuit";
               type union {
                 type string {
                   pattern "<.*>|$.*";
                 }
                 type uint32 {
                   range "1 .. 4294967295";
                 }
               }
             }
             leaf community {
               description "Community associated with this Layer 2 circuit";
               type string;
             }
             leaf psn-tunnel-endpoint {
               description "Endpoint of the transport tunnel on the neighbor PE";
               type jt:ipv4addr;
             }
             leaf mtu {
               description "MTU to be advertised for this Layer 2 circuit";
               type union {
                 type string {
                   pattern "<.*>|$.*";
                 }
                 type uint32 {
                   range "512 .. 65535";
                 }
               }
             }
           }
           list backup-neighbor {
             key name;
             ordered-by user;
             description "Configuration of redundant l2circuit";
             junos:must "(\".. end-interface interface\")";
             junos:must-message "End-interface interface must be configured when backup-neighbor is present";
             junos:must "(\".. connection-protection\")";
             junos:must-message "Connection-protection must be configured when backup-neighbor is present";
             junos:must "(!(\".. end-interface backup-interface\"))";
             junos:must-message "Backup-neighbor cannot be configured along with backup-interface";
             junos:must "(!(\".. neighbor\"))";
             junos:must-message "Backup-neighbor cannot be configured along with neighbor";
             leaf name {
               description "Backup Neighbor ID";
               type jt:ipv4addr;
             }
             uses apply-advanced;
             leaf virtual-circuit-id {
               description "Identifier for this Layer 2 circuit";
               type union {
                 type string {
                   pattern "<.*>|$.*";
                 }
                 type uint32 {
                   range "1 .. 4294967295";
                 }
               }
             }
             leaf psn-tunnel-endpoint {
               description "Endpoint of the transport tunnel on the backup neighbor PE";
               type jt:ipv4addr;
             }
             leaf community {
               description "Community associated with this Layer 2 circuit";
               type string;
             }
             leaf mtu {
               description "MTU to be advertised for this Layer 2 circuit";
               type union {
                 type string {
                   pattern "<.*>|$.*";
                 }
                 type uint32 {
                   range "512 .. 65535";
                 }
               }
             }
           }
           container end-interface {
             description "Interface name of the other end point";
             uses apply-advanced;
             leaf interface {
               description "Interface name";
               junos:must "(!(\".. .. neighbor\"))";
               junos:must-message "end-interface interface cannot be configured along with neighbor";
               type union {
                 type jt:interface-name;
                 type string {
                   pattern "<.*>|$.*";
                 }
               }
             }
             leaf no-revert {
               description "Do not revert to primary-interface";
               junos:must "(\".. protect-interface\")";
               junos:must-message "no-revert cannot be configured without protect-interface";
               type empty;
             }
             leaf protect-interface {
               description "Name of protect interface";
               junos:must "(\".. interface\")";
               junos:must-message "Protect-interface can be configured only when end-interface interface is present";
               type union {
                 type jt:interface-name;
                 type string {
                   pattern "<.*>|$.*";
                 }
               }
             }
             leaf backup-interface {
               description "Name of backup interface";
               junos:must "((\".. interface\" || \".. .. neighbor\"))";
               junos:must-message "Backup-interface can be configured only when neighbor/end-interface interface is present";
               junos:must "(\".. .. connection-protection\")";
               junos:must-message "Connection-protection must be configured when backup-interface is present";
               junos:must "(!(\".. .. backup-neighbor\"))";
               junos:must-message "Backup-interface cannot be configured along with backup-neighbor";
               junos:must "(!(\".. protect-interface\"))";
               junos:must-message "Backup-interface cannot be configured along with protect-interface";
               type union {
                 type jt:interface-name;
                 type string {
                   pattern "<.*>|$.*";
                 }
               }
             }
           }
           leaf description {
             description "Text description of Layer 2 circuit";
             type string;
           }
           leaf encapsulation-type {
             description "Encapsulation type for VPN";
             type enumeration {
               enum "atm-aal5" {
                 description "ATM AAL/5 encapsulation";
               }
               enum "atm-cell" {
                 description "ATM port promiscuous mode cell encapsulation";
               }
               enum "atm-cell-port-mode" {
                 description "ATM port promiscuous mode cell encapsulation";
               }
               enum "atm-cell-vp-mode" {
                 description "ATM VP promiscuous mode cell encapsulation";
               }
               enum "atm-cell-vc-mode" {
                 description "ATM non-promiscuous cell encapsulation";
               }
               enum "frame-relay" {
                 description "Frame Relay encapsulation";
               }
               enum "ppp" {
                 description "PPP encapsulation";
               }
               enum "cisco-hdlc" {
                 description "Cisco-compatible HDLC encapsulation";
               }
               enum "ethernet-vlan" {
                 description "Ethernet VLAN encapsulation";
               }
               enum "ethernet" {
                 description "Ethernet encapsulation";
               }
               enum "interworking" {
                 description "Layer 2.5 interworking VPN";
               }
               enum "frame-relay-port-mode" {
                 description "Frame Relay port mode encapsulation";
               }
               enum "satop-t1" {
                 description "SATOP-T1 based Layer 2 VPN";
               }
               enum "satop-e1" {
                 description "SATOP-E1 based Layer 2 VPN";
               }
               enum "satop-t3" {
                 description "SATOP-T3 based Layer 2 VPN";
               }
               enum "satop-e3" {
                 description "SATOP-E3 based Layer 2 VPN";
               }
               enum "cesop" {
                 description "CESOP based Layer 2 VPN";
               }
             }
           }
           leaf ignore-encapsulation-mismatch {
             description "Allow different encapsulation types on local and remote end";
             type empty;
           }
           leaf ignore-mtu-mismatch {
             description "Allow different MTUs on interfaces";
             type empty;
           }
         }
       }
       container auto-sensing {
         presence "enable auto-sensing";
         description "Configuration of PW auto-sensing";
         uses apply-advanced;
         leaf password {
           description "Password for authentication with Radius server; 1 to 15 characters long";
           type jt:unreadable;
         }
       }
       container resolution {
         description "Configuration of PW nexthop resolution";
         uses apply-advanced;
         leaf preserve-nexthop-heirarchy {
           description "Install expanded heirarchy";
           type empty;
         }
       }
     }
     container l2vpn {
       description "Configuration for Layer 2 VPN circuits over MPLS";
       uses apply-advanced;
       container resolution {
         description "Configuration of PW nexthop resolution";
         uses apply-advanced;
         leaf preserve-nexthop-heirarchy {
           description "Install expanded heirarchy";
           type empty;
         }
       }
     }
     container ldp {
       description "LDP options";
       uses juniper-protocols-ldp;
     }
     container link-management {
       description "LMP options";
       uses juniper-protocols-lmp;
     }
     container mld {
       presence "enable mld";
       description "MLD options";
       uses apply-advanced;
       container traceoptions {
         description "Trace options for MLD";
         uses apply-advanced;
         container file {
           description "Trace file options";
           leaf filename {
             description "Name of file in which to write trace information";
             type string {
               length "1 .. 1024";
               junos:posix-pattern "![/ %]";
               junos:pattern-message "Must not contain '/', % or a space";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "packets" {
                 description "Trace all MLD packets";
               }
               enum "query" {
                 description "Trace MLD membership query messages";
               }
               enum "report" {
                 description "Trace membership report messages";
               }
               enum "leave" {
                 description "Trace leave group messages (MLDv2 only)";
               }
               enum "mtrace" {
                 description "Trace mtrace packets";
               }
               enum "group" {
                 description "Trace group operations";
               }
               enum "client-notification" {
                 description "Trace notifications";
               }
               enum "host-notification" {
                 description "Trace host notifications";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       leaf query-interval {
         description "When to send host query messages";
         units "seconds";
         type union {
           type string {
             pattern "<.*>|$.*";
           }
           type uint32 {
             range "1 .. 1024";
           }
         }
       }
       leaf query-response-interval {
         description "How long to wait for a host query response";
         units "seconds";
         type string {
           junos:posix-pattern "^[0-9]{1,4}(.[0-9])?$";
           junos:pattern-message "Up to 1 digit to right of decimal point";
         }
       }
       leaf query-last-member-interval {
         description "When to send group query messages";
         units "seconds";
         type string {
           junos:posix-pattern "^[0-9]{1,4}(.[0-9])?$";
           junos:pattern-message "Up to 1 digit to right of decimal point";
         }
       }
       leaf robust-count {
         description "Expected packet loss on a subnet";
         type union {
           type string {
             pattern "<.*>|$.*";
           }
           type uint32 {
             range "2 .. 10";
           }
         }
       }
       leaf maximum-transmit-rate {
         description "Maximum transmission rate (packets per second)";
         type union {
           type string {
             pattern "<.*>|$.*";
           }
           type uint32 {
             range "1 .. 10000";
           }
         }
       }
       leaf accounting {
         description "Enable join and leave event notification";
         type empty;
       }
       list interface {
         key name;
         ordered-by user;
         description "Interface options for MLD";
         leaf name {
           type string;
         }
         uses apply-advanced;
         choice enable-disable {
           case case_1 {
             leaf disable {
               description "Disable MLD on this interface";
               type empty;
             }
           }
         }
         leaf version {
           description "Set mld version number on this interface";
           type union {
             type string {
               pattern "<.*>|$.*";
             }
             type uint8 {
               range "1 .. 2";
             }
           }
         }
         container static {
           description "Static group or source membership";
           uses apply-advanced;
           list group {
             key name;
             ordered-by user;
             description "IP multicast group address";
             leaf name {
               description "IP multicast group address";
               type jt:ipv6addr;
             }
             uses apply-advanced;
             leaf group-increment {
               description "Mask for the incrementing group IP address";
               type jt:ipv6addr;
             }
             leaf group-count {
               description "Number of groups";
               type union {
                 type string {
                   pattern "<.*>|$.*";
                 }
                 type uint32 {
                   range "1 .. 512";
                 }
               }
             }
             leaf exclude {
               description "Exclude sources";
               type empty;
             }
             list source {
               key name;
               ordered-by user;
               description "IP multicast source address";
               leaf name {
                 description "Source address of IP multicast data";
                 type jt:ipv6addr;
               }
               uses apply-advanced;
               leaf source-increment {
                 description "Mask for the incrementing source IP address";
                 type jt:ipv6addr;
               }
               leaf source-count {
                 description "Number of sources";
                 type union {
                   type string {
                     pattern "<.*>|$.*";
                   }
                   type uint32 {
                     range "1 .. 1024";
                   }
                 }
               }
             }
           }
         }
         leaf ssm-map {
           description "Map for ssm translation of mld v1 messages";
           type string;
         }
         leaf-list ssm-map-policy {
           ordered-by user;
           description "SSM map policy name";
           type jt:policy-algebra;
         }
         leaf immediate-leave {
           description "Group removed immediately, last membership query not sent";
           type empty;
         }
         leaf-list group-policy {
           ordered-by user;
           description "Group filter applied to incoming mld report messages";
           type jt:policy-algebra;
         }
         leaf group-limit {
           description "Maximum number of (source,group) per interface";
           type union {
             type string {
               pattern "<.*>|$.*";
             }
             type uint16 {
               range "1 .. 32767";
             }
           }
         }
         leaf group-threshold {
           description "Percentage of group-limit at which to start generating warnings";
           junos:must "(\".. group-limit\")";
           junos:must-message "To configure group-threshold, group-limit must be configured";
           type union {
             type string {
               pattern "<.*>|$.*";
             }
             type uint16 {
               range "1 .. 100";
             }
           }
         }
         leaf log-interval {
           description "Time between consecutive log messages";
           junos:must "(\".. group-limit\")";
           junos:must-message "To configure log-interval, group-limit must be configured";
           type union {
             type string {
               pattern "<.*>|$.*";
             }
             type uint32 {
               range "6 .. 32767";
             }
           }
         }
         choice accounting-choice {
           leaf accounting {
             description "Enable join and leave event notification";
             type empty;
           }
           leaf no-accounting {
             description "Don't enable join and leave event notification";
             type empty;
           }
         }
         container passive {
           presence "enable passive";
           description "Suppress sending and receiving mld messages";
           leaf allow-receive {
             description "Allow receiving mld messages";
             type empty;
           }
           leaf send-general-query {
             description "Send mld general query messages";
             type empty;
           }
           leaf send-group-query {
             description "Send mld group query messages";
             type empty;
           }
         }
         leaf-list oif-map {
           ordered-by user;
           description "Output interface map";
           type jt:policy-algebra;
         }
         leaf distributed {
           description "Distributed MLD interface";
           junos:must "(\"chassis network-services enhanced-ip\")";
           junos:must-message "distributed is supported only in enhanced-ip mode";
           type empty;
         }
       }
     }
     container mpls {
       description "Multiprotocol Label Switching options";
       uses juniper-protocols-mpls;
     }
     container msdp {
       description "MSDP configuration";
       uses juniper-protocols-msdp;
     }
     container mvpn {
       description "BGP-MVPN configuration";
       uses juniper-protocols-mvpn;
     }
     container ospf {
       description "OSPF configuration";
       uses juniper-protocols-ospf;
     }
     container ospf3 {
       description "OSPFv3 configuration";
       uses juniper-protocols-ospf3;
     }
     container pim {
       description "PIM configuration";
       uses juniper-protocols-pim;
     }
     container ripng {
       description "RIPng options";
       uses juniper-protocols-ripng;
     }
     container rip {
       description "RIP options";
       uses juniper-protocols-rip;
     }
     container rsvp {
       description "RSVP options";
       uses juniper-protocols-rsvp;
     }
     container sap {
       presence "enable sap";
       description "Session Advertisement Protocol options";
       uses apply-advanced;
       choice enable-disable {
         case case_1 {
           leaf disable {
             description "Disable SAP";
             type empty;
           }
         }
       }
       list listen {
         key name;
         ordered-by user;
         description "Address for SAP and SDP to listen on";
         leaf name {
           description "IP address";
           type jt:ipv4addr;
         }
         leaf port {
           description "Port to listen for session advertisements";
           type union {
             type uint16;
             type string {
               pattern "<.*>|$.*";
             }
           }
         }
       }
     }
     container source-packet-routing {
       presence "enable source-packet-routing";
       description "Enable source packet routing (SPRING)";
       uses apply-advanced;
       container traceoptions {
         description "Trace options for soure-packet-routing";
         uses apply-advanced;
         container file {
           description "Trace file options";
           leaf filename {
             description "Name of file in which to write trace information";
             type string {
               length "1 .. 1024";
               junos:posix-pattern "![/ %]";
               junos:pattern-message "Must not contain '/', % or a space";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "controller" {
                 description "Trace controller-related activity";
               }
               enum "state" {
                 description "Trace LSP state-related activity";
               }
               enum "route" {
                 description "Trace route-related activity";
               }
               enum "general" {
                 description "Trace general activity";
               }
               enum "interface" {
                 description "Trace interface-related activity";
               }
               enum "dtm" {
                 description "Trace dtm-related activity";
               }
               enum "bfd" {
                 description "Trace bfd-related activity";
               }
               enum "translation" {
                 description "Trace translation-related activity";
               }
               enum "srv6-te" {
                 description "Trace srv6-te activity";
               }
               enum "telemetry-statistics" {
                 description "Trace telemetry statistics related activity";
               }
               enum "compute" {
                 description "Trace compute profile and computed lsp related activity";
               }
               enum "nsr-replication" {
                 description "Trace NSR replication activity";
               }
               enum "all" {
                 description "Trace everything";
               }
             }
           }
           leaf detail {
             description "Trace detailed information";
             type empty;
           }
         }
       }
       list lsp-external-controller {
         key name;
         ordered-by user;
         description "External path computing entity";
         junos:must "(\".. .. mpls lsp-external-controller\")";
         junos:must-message "To enable spring, mpls lsp-external-controller must be configure";
         leaf name {
           description "Name of the external path computing entity";
           type string {
             length "1 .. 64";
           }
         }
         uses apply-advanced;
       }
       leaf preference {
         description "Route preference for SPRING-TE routes";
         type union {
           type uint32;
           type string {
             pattern "<.*>|$.*";
           }
         }
       }
       leaf sr-preference-override {
         description "SR-preference override for static SR-policies.Higher value is more preferred";
         type union {
           type string {
             pattern "<.*>|$.*";
           }
           type uint32 {
             range "0 .. 4294967295";
           }
         }
       }
       leaf sr-preference {
         description "SR-preference for static SR-policies.Higher value is more preferred";
         type union {
           type string {
             pattern "<.*>|$.*";
           }
           type uint32 {
             range "0 .. 4294967295";
           }
         }
       }
       leaf maximum-segment-list-depth {
         description "Maximum segment list depth for SR-TE policies";
         type union {
           type string {
             pattern "<.*>|$.*";
           }
           type uint32 {
             range "1 .. 16";
           }
         }
       }
       leaf maximum-srv6-te-segment-list-depth {
         description "Maximum segment list depth for SRv6-TE policies";
         type union {
           type string {
             pattern "<.*>|$.*";
           }
           type uint32 {
             range "1 .. 6";
           }
         }
       }
       leaf no-chained-composite-next-hop {
         description "Do not use chained composite next hops for SRTE routes";
         type empty;
       }
       leaf tunnel-tracking {
         description "Track route status for first hop label based tunnels";
         type empty;
       }
       list segment-list {
         key name;
         ordered-by user;
         description "Explicit path for SR-TE segments";
         leaf name {
           description "Name of SR-TE segment-list";
           type string {
             length "1 .. 64";
           }
         }
         uses apply-advanced;
         leaf inherit-label-nexthops {
           description "Inherit label nexthops for first hop in this segment list";
           junos:must "(!(\".. srv6\"))";
           junos:must-message "Inherit label nexthops functionality can't be used with a segment-list for SRv6";
           junos:must "(!(\".. compute\"))";
           junos:must-message "Inherit label nexthops functionality can't be used with a segment-list for compute";
           type empty;
         }
         choice translation-type {
           case case_1 {
             container auto-translate {
               presence "enable auto-translate";
               junos:must "(!(\".. srv6\"))";
               junos:must-message "Please use non SRv6 segment lists for auto-translate";
               junos:must "(!(\".. compute\"))";
               junos:must-message "Please use different segment lists for compute and auto-translate";
               description "Enable auto translation from IP address to labels";
               uses apply-advanced;
               choice protection-choice {
                 case case_1 {
                   container protected {
                     presence "enable protected";
                     description "Choose protected labels if available";
                     uses apply-advanced;
                     leaf mandatory {
                       description "Mandatorily choose protected labels";
                       type empty;
                     }
                   }
                 }
                 case case_2 {
                   container unprotected {
                     presence "enable unprotected";
                     description "Choose unprotected labels if available";
                     uses apply-advanced;
                     leaf mandatory {
                       description "Mandatorily choose unprotected labels";
                       type empty;
                     }
                   }
                 }
               }
             }
           }
           case case_2 {
             container dynamic {
               presence "enable dynamic";
               junos:must "(!(\".. srv6\"))";
               junos:must-message "Please use non SRv6 segment lists for dynamic";
               junos:must "(!(\".. compute\"))";
               junos:must-message "Please use different segment lists for compute and dynamic template";
               description "Enable dynamic last hop computation";
               uses apply-advanced;
               choice protection-choice {
                 case case_1 {
                   container protected {
                     presence "enable protected";
                     description "Choose protected labels if available";
                     uses apply-advanced;
                     leaf mandatory {
                       description "Mandatorily choose protected labels";
                       type empty;
                     }
                   }
                 }
                 case case_2 {
                   container unprotected {
                     presence "enable unprotected";
                     description "Choose unprotected labels if available";
                     uses apply-advanced;
                     leaf mandatory {
                       description "Mandatorily choose unprotected labels";
                       type empty;
                     }
                   }
                 }
               }
             }
           }
         }
         leaf compute {
           description "Segment list used for specifying explicit path for computed paths";
           junos:must "(!(\".. srv6\"))";
           junos:must-message "Please use non SRv6 segment lists for compute";
           type empty;
         }
         leaf srm6 {
           description "Segment list used for SRm6";
           junos:must "((!(\".. compute\") && (!(\".. dynamic\") && (!(\".. inherit-label-nexthops\") && (!(\".. auto-translate\") && !(\".. srv6\"))))))";
           junos:must-message "SRm6 segment-list cannot be configured with SR-TE combination";
           type empty;
         }
         leaf srv6 {
           description "Segment list used for SRv6";
           junos:must "(\".. .. srv6\")";
           junos:must-message "Please enable srv6 under protocols source-packet-routing";
           junos:must "(!(\".. srm6\"))";
           junos:must-message "SRv6 segment-list cannot be configured with srm6";
           junos:must "(!(\".. auto-translate\"))";
           junos:must-message "SRv6 segment-list cannot be configured with auto-translate";
           junos:must "(!(\".. inherit-label-nexthops\"))";
           junos:must-message "SRv6 segment-list cannot be configured with inherit-label-nexthops";
           junos:must "(!(\".. dynamic\"))";
           junos:must-message "SRv6 segment-list cannot be configured with dynamic";
           junos:must "(!(\".. compute\"))";
           junos:must-message "SRv6 segment-list cannot be configured with compute";
           type empty;
         }
         list hop-list {
           key name;
           ordered-by user;
           max-elements 16;
           leaf name {
             description "Next hop in segment-list";
             type string {
               length "1 .. 64";
             }
           }
           uses apply-advanced;
           leaf label {
             description "Next label in SR-TE segment-list";
             junos:must "(!(\".. .. srv6\"))";
             junos:must-message "label hop can't be used with a segment-list for srv6";
             junos:must "(!(\".. .. srm6\"))";
             junos:must-message "label hop can't be used with a segment-list for srm6";
             junos:must "(!(\".. .. compute\"))";
             junos:must-message "label hops can't be used with a segment-list for compute";
             type union {
               type string {
                 pattern "<.*>|$.*";
               }
               type uint32 {
                 range "0 .. 1048575";
               }
             }
           }
           leaf ip-address {
             description "IP address of the hop";
             junos:must "(!(\".. .. srv6\"))";
             junos:must-message "ip address hop can't be used with a segment-list for srv6";
             junos:must "(!(\".. .. srm6\"))";
             junos:must-message "ip address hop can't be used with a segment-list for srm6";
             type jt:ipaddr;
           }
           leaf sid {
             description "Next sid in SRm6 segment-list";
             junos:must "(!(\".. .. srv6\"))";
             junos:must-message "sid can't be used with a segment-list for srv6";
             junos:must "(\".. .. srm6\")";
             junos:must-message "srm6 must be configured";
             type union {
               type string {
                 pattern "<.*>|$.*";
               }
               type uint32 {
                 range "1 .. 65535";
               }
             }
           }
           leaf srv6-sid {
             description "Sid for SRv6 segment-list in form of ipv6 address";
             junos:must "(\".. .. srv6\")";
             junos:must-message "srv6 must be configured";
             junos:must "(!(\".. .. srm6\"))";
             junos:must-message "srm6 can't be used with a segment-list for srv6";
             type jt:ipaddr;
           }
           choice hop-choice {
             case case_1 {
               leaf strict {
                 description "Strict hop";
                 junos:must "(!(\".. .. srv6\"))";
                 junos:must-message "Hop choice only for compute-type segment-list not for srv6";
                 junos:must "(!(\".. .. srm6\"))";
                 junos:must-message "Hop choice only for compute-type segment-list not for srm6";
                 junos:must "(\".. .. compute\")";
                 junos:must-message "Hop choice only for compute-type segment-list";
                 type empty;
               }
             }
             case case_2 {
               leaf loose {
                 description "Loose hop";
                 junos:must "(!(\".. .. srv6\"))";
                 junos:must-message "Hop choice only for compute-type segment-list not for srv6";
                 junos:must "(!(\".. .. srm6\"))";
                 junos:must-message "Hop choice only for compute-type segment-list not for srm6";
                 junos:must "(\".. .. compute\")";
                 junos:must-message "Hop choice only for compute-type segment-list";
                 type empty;
               }
             }
           }
           container label-type {
             junos:must "(!(\".. .. srv6\"))";
             junos:must-message "label-type functionality can't be used with a segment-list for srv6";
             junos:must "(!(\".. .. srm6\"))";
             junos:must-message "label-type functionality can't be used with a segment-list for srm6";
             junos:must "(!(\".. .. compute\"))";
             junos:must-message "label-type functionality can't be used with a segment-list for compute";
             description "Type of label for the hop";
             uses apply-advanced;
             leaf node {
               description "Hop represents a node";
               type empty;
             }
           }
         }
       }
       list compute-profile {
         key name;
         ordered-by user;
         description "Compute profile for dynamically computed paths";
         leaf name {
           description "Name of the computation-profile";
           type string {
             length "1 .. 64";
           }
         }
         uses apply-advanced;
         container admin-group {
           description "Administrative group policy";
           uses admin_group_include_exclude;
         }
         leaf maximum-segment-list-depth {
           description "Maximum depth of computed path";
           type union {
             type string {
               pattern "<.*>|$.*";
             }
             type uint32 {
               range "1 .. 16";
             }
           }
         }
         leaf algorithm {
           description "Algorithm to constrain the path into";
           junos:must "(!(\".. no-label-stack-compression\"))";
           junos:must-message "Algorithm functionality can't be used with a no-label-stack-compression for compute";
           type union {
             type string {
               pattern "<.*>|$.*";
             }
             type uint32 {
               range "1 .. 255";
             }
           }
         }
         leaf no-label-stack-compression {
           description "Provide fully expanded path, using adjacency segment identifiers";
           junos:must "(!(\".. algorithm\"))";
           junos:must-message "no-label-stack-compression functionality can't be enabled with algorithm for compute";
           type empty;
         }
         choice protection-choice {
           case case_1 {
             container protected {
               presence "enable protected";
               description "Choose protected labels if available";
               uses apply-advanced;
               leaf mandatory {
                 description "Mandatorily choose protected labels";
                 type empty;
               }
             }
           }
           case case_2 {
             container unprotected {
               presence "enable unprotected";
               description "Choose unprotected labels if available";
               uses apply-advanced;
               leaf mandatory {
                 description "Mandatorily choose unprotected labels";
                 type empty;
               }
             }
           }
         }
         leaf compute-segment-list {
           description "Name of the compute type segmentlist";
           junos:must "(\".. .. segment-list $$ compute\")";
           junos:must-message "Compute segment list can only be referenced by this compute profile";
           type string {
             length "1 .. 64";
           }
         }
         leaf maximum-computed-segment-lists {
           description "Maximum number of segment-lists(ECMP paths) to be computed";
           type union {
             type string {
               pattern "<.*>|$.*";
             }
             type uint32 {
               range "1 .. 128";
             }
           }
         }
         container metric-type {
           description "Metric type used for computaion";
           uses apply-advanced;
           choice metric-choice {
             case case_1 {
               leaf te {
                 description "TE metric";
                 type empty;
               }
             }
             case case_2 {
               leaf igp {
                 description "IGP metric";
                 type empty;
               }
             }
             case case_3 {
               container delay {
                 presence "enable delay";
                 description "Delay metric";
                 uses apply-advanced;
                 choice metric-choice {
                   case case_1 {
                     leaf minimum {
                       description "Minimum delay metric type";
                       type empty;
                     }
                   }
                   case case_2 {
                     leaf maximum {
                       description "Maximum delay metric type";
                       type empty;
                     }
                   }
                   case case_3 {
                     leaf average {
                       description "Average delay metric type";
                       type empty;
                     }
                   }
                 }
                 leaf delay-variation-threshold {
                   description "Link delay variation threshold";
                   type union {
                     type string {
                       pattern "<.*>|$.*";
                     }
                     type uint32 {
                       range "1 .. 16777215";
                     }
                   }
                 }
               }
             }
           }
         }
       }
       leaf srv6 {
         description "Enable srv6 support for source-packet-routing";
         junos:must "(\"routing-options forwarding-table srv6-chain-merge\")";
         junos:must-message "SRv6 can only be enabled with srv6-chain-merge";
         junos:must "((\"routing-options resolution preserve-nexthop-hierarchy\" || (\"protocols source-packet-routing preserve-nexthop-hierarchy\" && !(\"protocols source-packet-routing preserve-nexthop-hierarchy srv6 disable\"))))";
         junos:must-message "SRv6 can only be enabled with preserve-nexthop-hierarchy";
         type empty;
       }
       container preserve-nexthop-hierarchy {
         presence "enable preserve-nexthop-hierarchy";
         description "Enable preserve-nexthop-hierarchy for source-packet-routing";
         uses apply-advanced;
         container sr-mpls {
           description "Disable preserve-nexthop-hierarchy for sr-mpls";
           uses apply-advanced;
           choice enable-disable {
             case case_1 {
               leaf disable {
                 description "Disable preserve-nexthop-hierarchy for sr-mpls";
                 type empty;
               }
             }
           }
         }
         container srv6 {
           description "Disable preserve-nexthop-hierarchy for srv6";
           uses apply-advanced;
           choice enable-disable {
             case case_1 {
               leaf disable {
                 description "Disable preserve-nexthop-hierarchy for srv6";
                 type empty;
               }
             }
           }
         }
       }
       list source-routing-path {
         key name;
         ordered-by user;
         description "Configure a source-routing-path";
         leaf name {
           description "Name of the source routing path";
           type string {
             length "1 .. 64";
           }
         }
         uses apply-advanced;
         leaf srm6 {
           description "Tunnel type SRm6";
           junos:must "(\".. from\")";
           junos:must-message "From address mandatory for srm6 tunnel";
           junos:must "((!(\".. ldp-tunneling\") && (!(\".. color\") && (!(\".. no-ingress\") && (!(\".. binding-sid\") && (!(\".. preference\") && (!(\".. metric\") && (!(\".. sr-preference\") && (!(\".. lsp-external-controller\") && (!(\".. install\") && (!(\".. secondary\") && (!(\".. srv6\") && !(\".. use-for-shortcut\")))))))))))))";
           junos:must-message "SRm6 tunnel cannot be configured with SR-TE combination";
           type empty;
         }
         leaf srv6 {
           description "Tunnel type SRv6";
           junos:must "(!(\".. use-for-shortcut\"))";
           junos:must-message "SRv6 tunnel cannot be configured with use-for-shortcut";
           junos:must "(\".. .. srv6\")";
           junos:must-message "Srv6 knob under source-packet-routing mandatory for SRv6 tunnel";
           junos:must "(!(\".. srm6\"))";
           junos:must-message "SRv6 tunnel cannot be configured with srm6";
           junos:must "(!(\".. binding-sid\"))";
           junos:must-message "SRv6 tunnel cannot be configured with binding-sid";
           junos:must "(!(\".. no-ingress\"))";
           junos:must-message "SRv6 tunnel cannot be configured with no-ingress";
           junos:must "(!(\".. ldp-tunneling\"))";
           junos:must-message "SRv6 tunnel cannot be configured with ldp-tunneling";
           type empty;
         }
         leaf ldp-tunneling {
           description "Allow LDP to use this LSP for tunneling";
           junos:must "(!(\".. color\"))";
           junos:must-message "LDP tunneling is not supported for colored source-routing paths";
           type empty;
         }
         leaf use-for-shortcut {
           description "Allow this LSP to be used as a shortcut tunnel";
           junos:must "(!(\".. srv6\"))";
           junos:must-message "Shortcut usage is not supported with SRv6 tunnel";
           junos:must "(!(\".. srm6\"))";
           junos:must-message "Shortcut usage is not supported with SRm6 tunnel";
           junos:must "(!(\".. color\"))";
           junos:must-message "Shortcut usage is not supported for colored source-routing paths";
           type empty;
         }
         leaf to {
           description "Ip-address of the tunnel end-point";
           type jt:ipaddr;
         }
         leaf from {
           description "Ip-address of the tunnel start-point";
           junos:must "((\".. srm6\" || \".. srv6\"))";
           junos:must-message "Tunnel must be of type srm6 or srv6";
           type jt:ipaddr;
         }
         leaf color {
           description "Color identifier for the tunnel end-point";
           type union {
             type uint32;
             type string {
               pattern "<.*>|$.*";
             }
           }
         }
         leaf no-ingress {
           description "Disable ingress functionality for this tunnel";
           junos:must "(!(\".. color\"))";
           junos:must-message "Ingress functionlity is required for colored source-routing paths";
           junos:must "((\".. binding-sid\" || \".. install\"))";
           junos:must-message "Please configure the binding-label or install prefixes if ingress functinality is not required";
           type empty;
         }
         leaf binding-sid {
           description "Specify the binding-label to enable transit functionality for this tunnel";
           type union {
             type string {
               pattern "<.*>|$.*";
             }
             type uint32 {
               range "16 .. 1048575";
             }
           }
         }
         list install {
           key name;
           ordered-by user;
           description "Install prefix";
           leaf name {
             description "Destination prefix";
             junos:must "(!(\".. .. to $$\"))";
             junos:must-message "Install and to address must be different";
             type jt:ipaddr;
           }
         }
         leaf preference {
           description "Preference for routes downloaded for this tunnel";
           status deprecated;
           type union {
             type uint32;
             type string {
               pattern "<.*>|$.*";
             }
           }
         }
         leaf metric {
           description "Metric for routes downloaded for this tunnel";
           type union {
             type string {
               pattern "<.*>|$.*";
             }
             type uint32 {
               range "1 .. 16777215";
             }
           }
         }
         leaf te-group-id {
           description "Te group id";
           junos:must "(!(\".. color\"))";
           junos:must-message "Te grp id is not required for colored source-routing paths";
           type union {
             type string {
               pattern "<.*>|$.*";
             }
             type uint32 {
               range "1 .. 128";
             }
           }
         }
         leaf sr-preference {
           description "SR-preference for SPRING-TE routes. Higher value is more preferred";
           type union {
             type string {
               pattern "<.*>|$.*";
             }
             type uint32 {
               range "0 .. 4294967295";
             }
           }
         }
         leaf lsp-external-controller {
           description "Name of the external path computing entity";
           junos:must "(\"protocols source-packet-routing lsp-external-controller $$\")";
           junos:must-message "Please define the lsp-external-controller under 'protocols source-packet-routing' hierarchy";
           type string {
             length "1 .. 64";
           }
         }
         list primary {
           key name;
           ordered-by user;
           description "Configure a primary segment list for this source-routing-path";
           max-elements 128;
           leaf name {
             description "Name of SR-TE segment-list";
             junos:must "(!(\".. .. .. segment-list $$ dynamic\"))";
             junos:must-message "Dynamic segment list cannot be referenced by this static policy";
             junos:must "(!(\".. .. .. segment-list $$ compute\"))";
             junos:must-message "compute segment list cannot be referenced by this static policy";
             junos:must "(((\".. .. .. segment-list $$\" && !(\".. compute\")) || (!(\".. .. .. segment-list $$\") && \".. compute\")))";
             junos:must-message "Please either use defined segment list without compute or undefined segment list with compute";
             type string {
               length "1 .. 64";
             }
           }
           uses apply-advanced;
           leaf weight {
             description "Specify the balance factor for this segment list in SR-TE tunnel";
             junos:must "(!(\".. .. srm6\"))";
             junos:must-message "Balance factor cannot be configured with SRm6 tunnel";
             type union {
               type uint32;
               type string {
                 pattern "<.*>|$.*";
               }
             }
           }
           container bfd-liveness-detection {
             junos:must "(!(\".. .. srv6\"))";
             junos:must-message "Bidirectional forwarding detection cannot be configured with SRv6 tunnel";
             junos:must "(!(\".. .. srm6\"))";
             junos:must-message "Bidirectional forwarding detection cannot be configured with SRm6 tunnel";
             description "Bidirectional forwarding detection options";
             uses apply-advanced;
             container sbfd {
               presence "enable sbfd";
               description "Seamless BFD parameters";
               uses apply-advanced;
               leaf remote-discriminator {
                 description "Remote discriminator of reflector";
                 type union {
                   type string {
                     pattern "<.*>|$.*";
                   }
                   type uint32 {
                     range "1 .. 4294967295";
                   }
                 }
               }
             }
             leaf minimum-interval {
               description "Minimum transmit and receive interval";
               units "milliseconds";
               type union {
                 type string {
                   pattern "<.*>|$.*";
                 }
                 type uint32 {
                   range "1 .. 255000";
                 }
               }
             }
             leaf multiplier {
               description "Detection time multiplier";
               default "3";
               type union {
                 type string {
                   pattern "<.*>|$.*";
                 }
                 type uint32 {
                   range "1 .. 255";
                 }
               }
             }
             leaf no-router-alert-option {
               description "Do not set the router alert option in IP header";
               type empty;
             }
           }
           container compute {
             presence "enable compute";
             junos:must "(!(\".. .. srv6\"))";
             junos:must-message "Computation cannot be configured with SRv6 tunnel";
             junos:must "(!(\".. .. srm6\"))";
             junos:must-message "Computation cannot be configured with SRm6 tunnel";
             description "Enable computation";
             uses apply-advanced;
             leaf compute-profile-name {
               description "Name of compute-profile";
               junos:must "(\".. .. .. .. compute-profile $$\")";
               junos:must-message "Please define the compute-profile referenced by this policy";
               type string {
                 length "1 .. 64";
               }
             }
           }
           leaf lsp-external-controller {
             description "Name of the external path computing entity";
             junos:must "(\"protocols source-packet-routing lsp-external-controller $$\")";
             junos:must-message "Please define the lsp-external-controller under 'protocols source-packet-routing' hierarchy";
             type string {
               length "1 .. 64";
             }
           }
         }
         list secondary {
           key name;
           ordered-by user;
           description "Configure a secondary segment list for this source-routing-path";
           max-elements 1;
           leaf name {
             description "Name of SR-TE segment-list";
             junos:must "(!(\".. .. .. segment-list $$ dynamic\"))";
             junos:must-message "Dynamic segment list cannot be referenced by this static policy";
             junos:must "(!(\".. .. .. segment-list $$ compute\"))";
             junos:must-message "compute segment list cannot be referenced by this static policy";
             junos:must "(((\".. .. .. segment-list $$\" && !(\".. compute\")) || (!(\".. .. .. segment-list $$\") && \".. compute\")))";
             junos:must-message "Please either use defined segment list without compute or undefined segment list with compute";
             type string {
               length "1 .. 64";
             }
           }
           uses apply-advanced;
           container bfd-liveness-detection {
             junos:must "(!(\".. .. srv6\"))";
             junos:must-message "Bidirectional forwarding detection cannot be configured with SRv6 tunnel";
             junos:must "(!(\".. .. srm6\"))";
             junos:must-message "Bidirectional forwarding detection cannot be configured with SRm6 tunnel";
             description "Bidirectional forwarding detection options";
             uses apply-advanced;
             container sbfd {
               presence "enable sbfd";
               description "Seamless BFD parameters";
               uses apply-advanced;
               leaf remote-discriminator {
                 description "Remote discriminator of reflector";
                 type union {
                   type string {
                     pattern "<.*>|$.*";
                   }
                   type uint32 {
                     range "1 .. 4294967295";
                   }
                 }
               }
             }
             leaf minimum-interval {
               description "Minimum transmit and receive interval";
               units "milliseconds";
               type union {
                 type string {
                   pattern "<.*>|$.*";
                 }
                 type uint32 {
                   range "1 .. 255000";
                 }
               }
             }
             leaf multiplier {
               description "Detection time multiplier";
               default "3";
               type union {
                 type string {
                   pattern "<.*>|$.*";
                 }
                 type uint32 {
                   range "1 .. 255";
                 }
               }
             }
             leaf no-router-alert-option {
               description "Do not set the router alert option in IP header";
               type empty;
             }
           }
           container compute {
             presence "enable compute";
             junos:must "(!(\".. .. srv6\"))";
             junos:must-message "Computation cannot be configured with SRv6 tunnel";
             junos:must "(!(\".. .. srm6\"))";
             junos:must-message "Computation cannot be configured with SRm6 tunnel";
             description "Enable computation";
             uses apply-advanced;
             leaf compute-profile-name {
               description "Name of compute-profile";
               junos:must "(\".. .. .. .. compute-profile $$\")";
               junos:must-message "Please define the compute-profile referenced by this policy";
               type string {
                 length "1 .. 64";
               }
             }
           }
         }
       }
       list source-routing-path-template {
         key name;
         ordered-by user;
         description "Configure a source-routing-path-template";
         leaf name {
           description "Name of the source routing path";
           type string {
             length "1 .. 64";
           }
         }
         uses apply-advanced;
         leaf no-ingress {
           description "Disable ingress functionality for this tunnel";
           type empty;
         }
         leaf use-for-shortcut {
           description "Allow this LSP to be used as a shortcut tunnel";
           junos:must "(!(\".. srv6\"))";
           junos:must-message "Shortcut usage is not supported with SRv6 tunnel";
           junos:must "(!(\".. srm6\"))";
           junos:must-message "Shortcut usage is not supported with SRm6 tunnel";
           junos:must "(!(\".. color\"))";
           junos:must-message "Shortcut usage is not supported for colored source-routing paths";
           type empty;
         }
         leaf metric {
           description "Metric for routes downloaded for this tunnel";
           type union {
             type string {
               pattern "<.*>|$.*";
             }
             type uint32 {
               range "1 .. 16777215";
             }
           }
         }
         leaf sr-preference {
           description "SR-preference for SPRING-TE routes. Higher value is more preferred";
           type union {
             type string {
               pattern "<.*>|$.*";
             }
             type uint32 {
               range "0 .. 4294967295";
             }
           }
         }
         leaf ldp-tunneling {
           description "Allow LDP to use this LSP for tunneling";
           type empty;
         }
         leaf lsp-external-controller {
           description "Name of the external path computing entity";
           junos:must "(\"protocols source-packet-routing lsp-external-controller $$\")";
           junos:must-message "Please define the lsp-external-controller under 'protocols source-packet-routing' hierarchy";
           type string {
             length "1 .. 64";
           }
         }
         list primary {
           key name;
           ordered-by user;
           description "Configure a primary segment list for this source-routing-path";
           max-elements 128;
           leaf name {
             description "Name of SR-TE segment-list";
             junos:must "(!(\".. .. .. segment-list $$ compute\"))";
             junos:must-message "compute segment list cannot be referenced by this static policy";
             junos:must "(((\".. .. .. segment-list $$ dynamic\" && !(\".. compute\")) || (!(\".. .. .. segment-list $$\") && \".. compute\")))";
             junos:must-message "Please either define dynamic type segment list without compute or undefined segment list with compute";
             type string {
               length "1 .. 64";
             }
           }
           uses apply-advanced;
           leaf weight {
             description "Specify the balance factor for this segment list in SR-TE tunnel";
             type union {
               type uint32;
               type string {
                 pattern "<.*>|$.*";
               }
             }
           }
           container compute {
             presence "enable compute";
             junos:must "(!(\".. .. srv6\"))";
             junos:must-message "Computation cannot be configured with SRv6 tunnel";
             junos:must "(!(\".. .. srm6\"))";
             junos:must-message "Computation cannot be configured with SRm6 tunnel";
             description "Enable computation";
             uses apply-advanced;
             leaf compute-profile-name {
               description "Name of compute-profile";
               junos:must "(\".. .. .. .. compute-profile $$\")";
               junos:must-message "Please define the compute-profile referenced by this policy";
               type string {
                 length "1 .. 64";
               }
             }
           }
           leaf lsp-external-controller {
             description "Name of the external path computing entity";
             junos:must "(\"protocols source-packet-routing lsp-external-controller $$\")";
             junos:must-message "Please define the lsp-external-controller under 'protocols source-packet-routing' hierarchy";
             type string {
               length "1 .. 64";
             }
           }
         }
         list secondary {
           key name;
           ordered-by user;
           description "Configure a secondary segment list for this source-routing-path";
           max-elements 1;
           leaf name {
             description "Name of SR-TE segment-list";
             junos:must "(!(\".. .. .. segment-list $$ compute\"))";
             junos:must-message "compute segment list cannot be referenced by this static policy";
             junos:must "(((\".. .. .. segment-list $$ dynamic\" && !(\".. compute\")) || (!(\".. .. .. segment-list $$\") && \".. compute\")))";
             junos:must-message "Please either define dynamic type segment list without compute or undefined segment list with compute";
             type string {
               length "1 .. 64";
             }
           }
           uses apply-advanced;
           container compute {
             presence "enable compute";
             junos:must "(!(\".. .. srv6\"))";
             junos:must-message "Computation cannot be configured with SRv6 tunnel";
             junos:must "(!(\".. .. srm6\"))";
             junos:must-message "Computation cannot be configured with SRm6 tunnel";
             description "Enable computation";
             uses apply-advanced;
             leaf compute-profile-name {
               description "Name of compute-profile";
               junos:must "(\".. .. .. .. compute-profile $$\")";
               junos:must-message "Please define the compute-profile referenced by this policy";
               type string {
                 length "1 .. 64";
               }
             }
           }
         }
         container bfd-liveness-detection {
           junos:must "(!(\".. srv6\"))";
           junos:must-message "Bidirectional forwarding detection cannot be configured with SRv6 tunnel";
           junos:must "(!(\".. srm6\"))";
           junos:must-message "Bidirectional forwarding detection cannot be configured with SRm6 tunnel";
           description "Bidirectional forwarding detection options";
           uses apply-advanced;
           container sbfd {
             presence "enable sbfd";
             description "Seamless BFD parameters";
             uses apply-advanced;
             leaf remote-discriminator {
               description "Remote discriminator of reflector";
               type union {
                 type string {
                   pattern "<.*>|$.*";
                 }
                 type uint32 {
                   range "1 .. 4294967295";
                 }
               }
             }
           }
           leaf minimum-interval {
             description "Minimum transmit and receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           leaf no-router-alert-option {
             description "Do not set the router alert option in IP header";
             type empty;
           }
         }
         leaf srv6 {
           description "Template type SRv6";
           junos:must "(!(\".. bfd-liveness-detection\"))";
           junos:must-message "SRv6 template cannot be configured with bfd-liveness-detection";
           junos:must "(!(\".. use-for-shortcut\"))";
           junos:must-message "SRv6 template cannot be configured with use-for-shortcut";
           junos:must "(\".. .. srv6\")";
           junos:must-message "Srv6 knob under source-packet-routing mandatory for SRv6 template";
           junos:must "(!(\".. secondary\"))";
           junos:must-message "SRv6 template cannot be configured with secondary";
           junos:must "(!(\".. primary\"))";
           junos:must-message "SRv6 template cannot be configured with primary";
           junos:must "(!(\".. lsp-external-controller\"))";
           junos:must-message "SRv6 template cannot be configured with lsp-external-controller";
           junos:must "(!(\".. no-ingress\"))";
           junos:must-message "SRv6 template cannot be configured with no-ingress";
           junos:must "(!(\".. ldp-tunneling\"))";
           junos:must-message "SRv6 template cannot be configured with ldp-tunneling";
           type empty;
         }
       }
       leaf inherit-label-nexthops {
         description "Inherit label nexthops for first hop in segment lists";
         type empty;
       }
       container rib-group {
         description "Enable rib-group import  poilicies on SR-TE";
         uses apply-advanced;
         container ipv4 {
           presence "enable ipv4";
           description "Import  policy to be applied on ipv4 uncolored route";
           uses apply-advanced;
           leaf rib-group-name {
             description "Rib-group import policy";
             type string {
               length "1 .. 64";
             }
           }
         }
         container ipv6 {
           presence "enable ipv6";
           description "Import  policy to be applied on ipv6 uncolored route";
           uses apply-advanced;
           leaf rib-group-name {
             description "Rib-group import policy";
             type string {
               length "1 .. 64";
             }
           }
         }
         container ipv4-color {
           presence "enable ipv4-color";
           description "Import  policy to be applied on ipv4 colored route";
           uses apply-advanced;
           leaf rib-group-name {
             description "Rib-group import policy";
             type string {
               length "1 .. 64";
             }
           }
         }
         container ipv6-color {
           presence "enable ipv6-color";
           description "Import  policy to be applied on ipv6 colored route";
           uses apply-advanced;
           leaf rib-group-name {
             description "Rib-group import policy";
             type string {
               length "1 .. 64";
             }
           }
         }
         container tag {
           presence "enable tag";
           description "Import  policy to be applied on mpls route";
           uses apply-advanced;
           leaf rib-group-name {
             description "Rib-group import policy";
             type string {
               length "1 .. 64";
             }
           }
         }
       }
       container telemetry {
         description "Enable telemetry on SR-TE policies";
         uses apply-advanced;
         container statistics {
           presence "enable statistics";
           description "Enable traffic-statistics collection on SR-TE policies";
           uses apply-advanced;
           leaf no-transit {
             description "Disable statistics collection on binding sid route";
             junos:must "(!(\".. no-ingress\"))";
             junos:must-message "Please enable ingress statistics if no transit statistics is required";
             type empty;
           }
           leaf no-ingress {
             description "Disable statistics collection on destination route";
             junos:must "(!(\".. no-transit\"))";
             junos:must-message "Please enable transit statistics if no ingress statistics is required";
             type empty;
           }
           container per-source {
             description "Enable traffic-statistics collection per source";
             uses apply-advanced;
             leaf per-segment-list {
               description "Enable per path level traffic-statistics collection";
               type empty;
             }
           }
         }
       }
       container use-transport-class {
         presence "enable use-transport-class";
         junos:must "(!((\".. rib-group ipv4-color\" || \".. rib-group ipv6-color\")))";
         junos:must-message "Transport Class and color based rib-groups cannot be configured at the same time";
         junos:must "(\"routing-options transport-class\")";
         junos:must-message "Please enable required Transport Class configs under routing-options transport-class hierarchy";
         description "Enable transport class on SR-TE colored policies";
         uses apply-advanced;
         leaf fib-install {
           description "Install SRTE routes in FIB";
           type empty;
         }
         leaf inet3-install {
           description "Install SRTE routes in inet{6}.3 table";
           type empty;
         }
       }
       leaf inet-color-append-explicit-null {
         description "Enable appending explicit NULL for inet SRTE policy";
         type empty;
       }
       leaf retry-timer {
         description "Time before retrying auto-translation failed paths";
         units "seconds";
         type union {
           type string {
             pattern "<.*>|$.*";
           }
           type int32 {
             range "1 .. 600";
           }
         }
       }
       leaf import-color-only-cross-af {
         description "Enable importing of Null Endpoint color route for cross address family";
         type empty;
       }
       leaf inet6-color-append-explicit-null {
         description "Enable appending explicit NULL for inet6 SRTE policy";
         type empty;
       }
       leaf ipv6-tunneling-append-explicit-null {
         description "Enable appending explicit NULL for v4ov6 SRTE routes ";
         type empty;
       }
       container source-routing-path-template-map {
         description "Configure a source routing path template map";
         uses apply-advanced;
         leaf-list policy {
           ordered-by user;
           description "Configure policy";
           type jt:policy-algebra;
         }
       }
     }
     container l2-learning {
       description "Layer 2 forwarding configuration";
       uses juniper-protocols-bridge;
     }
     container network-isolation {
       description "Network isolation configuration";
       uses apply-advanced;
       list group {
         key name;
         description "Network isolation group";
         leaf name {
           description "Group name";
           type string {
             length "1 .. 254";
           }
         }
         uses apply-advanced;
         container detection {
           presence "enable detection";
           description "Network isolation detection";
           uses apply-advanced;
           container hold-time {
             description "Hold time for network core isolation ";
             leaf up {
               description "Hold time in milliseconds for declaring network reachable";
               units "milliseconds";
               type union {
                 type uint32;
                 type string {
                   pattern "<.*>|$.*";
                 }
               }
             }
             leaf down {
               description "Hold time in milliseconds for declaring network not reachable";
               units "milliseconds";
               type union {
                 type uint32;
                 type string {
                   pattern "<.*>|$.*";
                 }
               }
             }
           }
           container link-tracking {
             presence "enable link-tracking";
             description "Network isolation detection via link tracking";
             uses apply-advanced;
             leaf minimum-links {
               description "Minimum link count in up state to consider network not isolated";
               type union {
                 type string {
                   pattern "<.*>|$.*";
                 }
                 type uint32 {
                   range "0 .. 10";
                 }
               }
             }
             leaf failure-type {
               description "Type of Failure";
               default "link";
               type enumeration {
                 enum "link" {
                   description "Failure type link";
                 }
               }
             }
             list interface {
               key name;
               description "Interface or list of interfaces ";
               leaf name {
                 description "Interface name";
                 type union {
                   type jt:interface-name;
                   type string {
                     pattern "<.*>|$.*";
                   }
                 }
               }
               uses apply-advanced;
             }
           }
         }
       }
     }
     container dcbx {
       presence "enable dcbx";
     }
     container lldp {
       description "Link Layer Detection Protocol";
       uses apply-advanced;
       choice enable-disable {
         case case_1 {
           leaf disable {
             description "Disable LLDP";
             type empty;
           }
         }
       }
       container traceoptions {
         description "Trace options for LLDP";
         uses apply-advanced;
         container file {
           description "Trace file options";
           leaf filename {
             description "Name of file in which to write trace information";
             type string {
               length "1 .. 1024";
               junos:posix-pattern "![/ %]";
               junos:pattern-message "Must not contain '/', % or a space";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           description "Tracing parameters";
           leaf name {
             type enumeration {
               enum "all" {
                 description "Trace configuration events";
               }
               enum "configuration" {
                 description "Log configuration events";
               }
               enum "rtsock" {
                 description "Trace rtsock message events";
               }
               enum "packet" {
                 description "Trace packet information";
               }
               enum "protocol" {
                 description "Trace protocol information";
               }
               enum "interface" {
                 description "Trace interface update events";
               }
               enum "vlan" {
                 description "Trace VLAN update events";
               }
               enum "snmp" {
                 description "Trace SNMP events";
               }
               enum "jvision" {
                 description "Trace Jvision events";
               }
             }
           }
           leaf disable {
             description "Disable this trace flag";
             type empty;
           }
         }
       }
       leaf management-address {
         description "LLDP management address";
         type jt:ipaddr;
       }
       leaf advertisement-interval {
         description "Transmit interval for LLDP messages";
         default "30";
         units "seconds";
         type union {
           type string {
             pattern "<.*>|$.*";
           }
           type uint32 {
             range "5 .. 32768";
           }
         }
       }
       leaf transmit-delay {
         description "Transmit delay time interval for LLDP messages";
         units "seconds";
         type union {
           type string {
             pattern "<.*>|$.*";
           }
           type uint32 {
             range "1 .. 8192";
           }
         }
       }
       leaf hold-multiplier {
         description "Hold timer interval for LLDP messages";
         default "4";
         type union {
           type string {
             pattern "<.*>|$.*";
           }
           type uint32 {
             range "2 .. 10";
           }
         }
       }
       leaf ptopo-configuration-trap-interval {
         description "Interval for physical topology configuration change trap";
         default "0";
         units "seconds";
         type union {
           type string {
             pattern "<.*>|$.*";
           }
           type uint32 {
             range "0 .. 3600";
           }
         }
       }
       leaf ptopo-configuration-maximum-hold-time {
         description "Hold time for physical topology connection entries";
         default "300";
         units "seconds";
         type union {
           type string {
             pattern "<.*>|$.*";
           }
           type uint32 {
             range "1 .. 2147483647";
           }
         }
       }
       leaf lldp-configuration-notification-interval {
         description "Time interval for LLDP notification";
         default "5";
         units "seconds";
         type union {
           type string {
             pattern "<.*>|$.*";
           }
           type uint32 {
             range "5 .. 3600";
           }
         }
       }
       leaf port-id-subtype {
         description "Sub-type to be used for Port ID TLV generation";
         default "locally-assigned";
         type enumeration {
           enum "locally-assigned" {
             description "Locally assigned value (SNMP index of the interface)";
           }
           enum "interface-name" {
             description "Interface name on which LLDPDU is sent";
           }
         }
       }
       leaf port-description-type {
         description "The Interfaces Group MIB object to be used for Port Description TLV generation";
         default "interface-alias";
         type enumeration {
           enum "interface-alias" {
             description "Use object ifAlias value for TLV generation";
           }
           enum "interface-description" {
             description "Use object ifDescr value for TLV generation";
           }
         }
       }
       leaf neighbour-port-info-display {
         description "Show lldp neighbors to display port-id or port-description ";
         type enumeration {
           enum "port-id" {
             description "Display port-id information of neighbor in port info";
           }
           enum "port-description" {
             description "Display port description of neighbor in port info";
           }
         }
       }
       leaf mau-type {
         description "Populate mau-type in lldp PDU";
         type empty;
       }
       leaf vlan-name-tlv-option {
         description "Vlan tlv options to transmit vlan name or vlan-id";
         default "vlan-id";
         type enumeration {
           enum "vlan-id" {
             description "Use vlan-id for tlv";
           }
           enum "name" {
             description "Use vlan-name for tlv";
           }
         }
       }
       leaf lldp-tx-fast-init {
         description "Transmission count in fast transmission mode";
         type union {
           type string {
             pattern "<.*>|$.*";
           }
           type uint32 {
             range "1 .. 8";
           }
         }
       }
       leaf fast-rx-processing {
         description "Start optimised processing of received pdu";
         type empty;
       }
       leaf-list tlv-select {
         ordered-by user;
         description "Select TLVs to be sent";
         type enumeration {
           enum "port-description" {
             description "Port Description";
           }
           enum "system-name" {
             description "System Name";
           }
           enum "system-description" {
             description "System Description";
           }
           enum "system-capabilities" {
             description "System Capabilities";
           }
           enum "management-address" {
             description "Management Address";
           }
           enum "mac-phy-config-status" {
             description "OUI IEEE 802.3 mac-phy-config-status";
           }
           enum "power-vi-mdi" {
             description "OUI IEEE 802.3 power-vi-mdi";
           }
           enum "link-aggregation" {
             description "OUI IEEE 802.3 link-aggregation";
           }
           enum "maximum-frame-size" {
             description "OUI IEEE 802.3 maximum-frame-size";
           }
           enum "jnpr-chassis-serial" {
             description "OUI Juniper chassis-serial";
           }
           enum "jnpr-vcp" {
             description "OUI Juniper vcp";
           }
           enum "jnpr-mode-change" {
             description "OUI Juniper mode-change";
           }
           enum "jnpr-mode-change-error" {
             description "OUI Juniper mode-change-error";
           }
           enum "jnpr-mode-change-ip-address" {
             description "OUI Juniper mode-change-ip-address";
           }
           enum "jnpr-mode-change-image-name" {
             description "OUI Juniper mode-change-image-name";
           }
           enum "jnpr-mode-change-ftp-login" {
             description "OUI Juniper mode-change-ftp-login";
           }
           enum "jnpr-mode-change-image-md5" {
             description "OUI Juniper mode-change-image-md5";
           }
           enum "jnpr-mode-change-ftp-server" {
             description "OUI Juniper mode-change-ftp-server";
           }
           enum "port-vid" {
             description "OUI IEEE 802.1 port-vid";
           }
           enum "port-protocol-vid" {
             description "OUI IEEE 802.1 port-procol-vid";
           }
           enum "vlan-name" {
             description "OUI IEEE 802.1 vlan-name";
           }
           enum "protocol-id" {
             description "OUI IEEE 802.1 protocol-id";
           }
           enum "link-aggregation-8021" {
             description "OUI IEEE 802.1 link-aggregation";
           }
           enum "dcbx-ets-configuration" {
             description "OUI IEEE 802.1 dcbx ets configuration";
           }
           enum "dcbx-ets-recommendation" {
             description "OUI IEEE 802.1 dcbx ets recommendation";
           }
           enum "dcbx-priority-flow-control" {
             description "OUI IEEE 802.1 dcbx pfc";
           }
           enum "dcbx-version-101" {
             description "OUI IEEE 802.1 dcbx version 1.01";
           }
           enum "evb" {
             description "OUI IEEE 82.1QBG evb";
           }
           enum "power-via-mdi-measurements" {
             description "OUI IEEE 802.3 power-via-mdi-measurements";
           }
           enum "cloud-reach-event" {
             description "Cloud reachability event";
           }
           enum "phone-home-active" {
             description "Phone-home active configuration";
           }
         }
       }
       leaf-list tlv-filter {
         ordered-by user;
         description "Filter TLVs to be sent";
         junos:must "(!(\".. tlv-select\"))";
         junos:must-message "tlv-select or tlv-filter is allowed, not both.";
         type enumeration {
           enum "all" {
             description "Filter all non mandatory TLVs";
           }
           enum "port-description" {
             description "Port Description";
           }
           enum "system-name" {
             description "System Name";
           }
           enum "system-description" {
             description "System Description";
           }
           enum "system-capabilities" {
             description "System Capabilities";
           }
           enum "management-address" {
             description "Management Address";
           }
           enum "mac-phy-config-status" {
             description "OUI IEEE 802.3 mac-phy-config-status";
           }
           enum "power-vi-mdi" {
             description "OUI IEEE 802.3 power-vi-mdi";
           }
           enum "link-aggregation" {
             description "OUI IEEE 802.3 link-aggregation";
           }
           enum "maximum-frame-size" {
             description "OUI IEEE 802.3 maximum-frame-size";
           }
           enum "jnpr-chassis-serial" {
             description "OUI Juniper chassis-serial";
           }
           enum "jnpr-vcp" {
             description "OUI Juniper vcp";
           }
           enum "jnpr-mode-change" {
             description "OUI Juniper mode-change";
           }
           enum "jnpr-mode-change-error" {
             description "OUI Juniper mode-change-error";
           }
           enum "jnpr-mode-change-ip-address" {
             description "OUI Juniper mode-change-ip-address";
           }
           enum "jnpr-mode-change-image-name" {
             description "OUI Juniper mode-change-image-name";
           }
           enum "jnpr-mode-change-ftp-login" {
             description "OUI Juniper mode-change-ftp-login";
           }
           enum "jnpr-mode-change-image-md5" {
             description "OUI Juniper mode-change-image-md5";
           }
           enum "jnpr-mode-change-ftp-server" {
             description "OUI Juniper mode-change-ftp-server";
           }
           enum "port-vid" {
             description "OUI IEEE 802.1 port-vid";
           }
           enum "port-protocol-vid" {
             description "OUI IEEE 802.1 port-procol-vid";
           }
           enum "vlan-name" {
             description "OUI IEEE 802.1 vlan-name";
           }
           enum "protocol-id" {
             description "OUI IEEE 802.1 protocol-id";
           }
           enum "link-aggregation-8021" {
             description "OUI IEEE 802.1 Link Aggregation";
           }
           enum "dcbx-priority-flow-control" {
             description "OUI IEEE 802.1 dcbx pfc";
           }
           enum "dcbx-ets-configuration" {
             description "OUI IEEE 802.1 dcbx ets configuration";
           }
           enum "dcbx-ets-recommendation" {
             description "OUI IEEE 802.1 dcbx ets recommendation";
           }
           enum "dcbx-version-101" {
             description "OUI IEEE 802.1 dcbx version 1.01";
           }
           enum "evb" {
             description "OUI IEEE 802.1QBG evb";
           }
           enum "power-via-mdi-measurements" {
             description "OUI IEEE 802.3 power-via-mdi-measurements";
           }
           enum "cloud-reach-event" {
             description "Cloud reachability event";
           }
           enum "phone-home-active" {
             description "Phone-home active configuration";
           }
         }
       }
       leaf dest-mac-type {
         description "Destination address to be used";
         junos:must "(!(\".. interface all dest-mac-type\"))";
         junos:must-message "User defined LLDP destination address can be configured either at global level or under interface all.";
         type enumeration {
           enum "nearest-bridge" {
             description "To set destination mac as 01:80:C2:00:00:0E";
           }
           enum "nearest-non-tpmr-bridge" {
             description "To set destination mac as 01:80:C2:00:00:03";
           }
           enum "nearest-customer-bridge" {
             description "To set destination mac as 01:80:C2:00:00:00";
           }
         }
       }
       leaf management-interface {
         description "Management interface to be used in LLDP PDUs";
         junos:must "(!(\".. management-address\"))";
         junos:must-message "Both LLDP management-address and management-interface can not be configured together.";
         type union {
           type jt:interface-name;
           type string {
             pattern "<.*>|$.*";
           }
         }
       }
       list interface {
         key name;
         ordered-by user;
         description "Interface configuration";
         leaf name {
           type string;
         }
         uses apply-advanced;
         choice enable-disable {
           case case_1 {
             leaf disable {
               description "Disable LLDP";
               type empty;
             }
           }
         }
         container power-negotiation {
           presence "enable power-negotiation";
           description "LLDP power negotiation";
           uses apply-advanced;
           choice enable-disable {
             case case_1 {
               leaf disable {
                 description "Disable power negotiation";
                 type empty;
               }
             }
           }
         }
         leaf-list tlv-select {
           ordered-by user;
           description "Select TLV(s) to be sent";
           type enumeration {
             enum "port-description" {
               description "Port Description";
             }
             enum "system-name" {
               description "System Name";
             }
             enum "system-description" {
               description "System Description";
             }
             enum "system-capabilities" {
               description "System Capabilities";
             }
             enum "management-address" {
               description "Management Address";
             }
             enum "mac-phy-config-status" {
               description "OUI IEEE 802.3 mac-phy-config-status";
             }
             enum "power-vi-mdi" {
               description "OUI IEEE 802.3 power-vi-mdi";
             }
             enum "link-aggregation" {
               description "OUI IEEE 802.3 link-aggregation";
             }
             enum "maximum-frame-size" {
               description "OUI IEEE 802.3 maximum-frame-size";
             }
             enum "jnpr-chassis-serial" {
               description "OUI Juniper chassis-serial";
             }
             enum "jnpr-vcp" {
               description "OUI Juniper vcp";
             }
             enum "jnpr-mode-change" {
               description "OUI Juniper mode-change";
             }
             enum "jnpr-mode-change-error" {
               description "OUI Juniper mode-change-error";
             }
             enum "jnpr-mode-change-ip-address" {
               description "OUI Juniper mode-change-ip-address";
             }
             enum "jnpr-mode-change-image-name" {
               description "OUI Juniper mode-change-image-name";
             }
             enum "jnpr-mode-change-ftp-login" {
               description "OUI Juniper mode-change-ftp-login";
             }
             enum "jnpr-mode-change-image-md5" {
               description "OUI Juniper mode-change-image-md5";
             }
             enum "jnpr-mode-change-ftp-server" {
               description "OUI Juniper mode-change-ftp-server";
             }
             enum "port-vid" {
               description "OUI IEEE 802.1 port-vid";
             }
             enum "port-protocol-vid" {
               description "OUI IEEE 802.1 port-procol-vid";
             }
             enum "vlan-name" {
               description "OUI IEEE 802.1 vlan-name";
             }
             enum "protocol-id" {
               description "OUI IEEE 802.1 protocol-id";
             }
             enum "link-aggregation-8021" {
               description "OUI IEEE 802.1 link-aggregation";
             }
             enum "dcbx-ets-configuration" {
               description "OUI IEEE 802.1 dcbx ets configuration";
             }
             enum "dcbx-ets-recommendation" {
               description "OUI IEEE 802.1 dcbx ets recommendation";
             }
             enum "dcbx-priority-flow-control" {
               description "OUI IEEE 802.1 dcbx pfc";
             }
             enum "dcbx-version-101" {
               description "OUI IEEE 802.1 dcbx version 1.01";
             }
             enum "evb" {
               description "OUI IEEE 82.1QBG evb";
             }
             enum "power-via-mdi-measurements" {
               description "OUI IEEE 802.3 power-via-mdi-measurements";
             }
             enum "cloud-reach-event" {
               description "Cloud reachability event";
             }
             enum "phone-home-active" {
               description "Phone-home active configuration";
             }
           }
         }
         leaf-list tlv-filter {
           ordered-by user;
           description "Filter TLV(s) to be sent";
           junos:must "(!(\".. tlv-select\"))";
           junos:must-message "tlv-select or tlv-filter is allowed, not both.";
           type enumeration {
             enum "all" {
               description "Filter all non mandatory TLVs";
             }
             enum "port-description" {
               description "Port Description";
             }
             enum "system-name" {
               description "System Name";
             }
             enum "system-description" {
               description "System Description";
             }
             enum "system-capabilities" {
               description "System Capabilities";
             }
             enum "management-address" {
               description "Management Address";
             }
             enum "mac-phy-config-status" {
               description "OUI IEEE 802.3 mac-phy-config-status";
             }
             enum "power-vi-mdi" {
               description "OUI IEEE 802.3 power-vi-mdi";
             }
             enum "link-aggregation" {
               description "OUI IEEE 802.3 link-aggregation";
             }
             enum "maximum-frame-size" {
               description "OUI IEEE 802.3 maximum-frame-size";
             }
             enum "jnpr-chassis-serial" {
               description "OUI Juniper chassis-serial";
             }
             enum "jnpr-vcp" {
               description "OUI Juniper vcp";
             }
             enum "jnpr-mode-change" {
               description "OUI Juniper mode-change";
             }
             enum "jnpr-mode-change-error" {
               description "OUI Juniper mode-change-error";
             }
             enum "jnpr-mode-change-ip-address" {
               description "OUI Juniper mode-change-ip-address";
             }
             enum "jnpr-mode-change-image-name" {
               description "OUI Juniper mode-change-image-name";
             }
             enum "jnpr-mode-change-ftp-login" {
               description "OUI Juniper mode-change-ftp-login";
             }
             enum "jnpr-mode-change-image-md5" {
               description "OUI Juniper mode-change-image-md5";
             }
             enum "jnpr-mode-change-ftp-server" {
               description "OUI Juniper mode-change-ftp-server";
             }
             enum "port-vid" {
               description "OUI IEEE 802.1 port-vid";
             }
             enum "port-protocol-vid" {
               description "OUI IEEE 802.1 port-procol-vid";
             }
             enum "vlan-name" {
               description "OUI IEEE 802.1 vlan-name";
             }
             enum "protocol-id" {
               description "OUI IEEE 802.1 protocol-id";
             }
             enum "link-aggregation-8021" {
               description "OUI IEEE 802.1 Link Aggregation";
             }
             enum "dcbx-priority-flow-control" {
               description "OUI IEEE 802.1 dcbx pfc";
             }
             enum "dcbx-ets-configuration" {
               description "OUI IEEE 802.1 dcbx ets configuration";
             }
             enum "dcbx-ets-recommendation" {
               description "OUI IEEE 802.1 dcbx ets recommendation";
             }
             enum "dcbx-version-101" {
               description "OUI IEEE 802.1 dcbx version 1.01";
             }
             enum "evb" {
               description "OUI IEEE 802.1QBG evb";
             }
             enum "power-via-mdi-measurements" {
               description "OUI IEEE 802.3 power-via-mdi-measurements";
             }
             enum "cloud-reach-event" {
               description "Cloud reachability event";
             }
             enum "phone-home-active" {
               description "Phone-home active configuration";
             }
           }
         }
         leaf trap-notification {
           description "To enable or disable for lldp-trap notification";
           default "enable";
           type enumeration {
             enum "enable" {
               description "Enable trap notification";
             }
             enum "disable" {
               description "Disable trap notification";
             }
           }
         }
         leaf dest-mac-type {
           description "Destination address to be used";
           type enumeration {
             enum "nearest-bridge" {
               description "To set destination mac as 01:80:C2:00:00:0E";
             }
             enum "nearest-non-tpmr-bridge" {
               description "To set destination mac as 01:80:C2:00:00:03";
             }
             enum "nearest-customer-bridge" {
               description "To set destination mac as 01:80:C2:00:00:00";
             }
           }
         }
       }
     }
     container lldp-med {
       presence "enable lldp-med";
       description "LLDP Media Endpoint Discovery";
       uses apply-advanced;
       leaf fast-start {
         description "Discovery count for MED";
         type union {
           type string {
             pattern "<.*>|$.*";
           }
           type uint32 {
             range "1 .. 10";
           }
         }
       }
       list interface {
         key name;
         ordered-by user;
         description "Interface configuration";
         leaf name {
           type string;
         }
         uses apply-advanced;
         choice enable-disable {
           case case_1 {
             leaf disable {
               description "Disable LLDP";
               type empty;
             }
           }
         }
         container location {
           presence "enable location";
           uses apply-advanced;
           choice location-type {
             case case_1 {
               container civic-based {
                 description "Postal address";
                 presence "enable civic-based";
                 uses civic-address-elements;
               }
             }
             case case_2 {
               leaf elin {
                 description "Emergency line identification (ELIN) string";
                 type string;
               }
             }
             case case_3 {
             }
           }
         }
         leaf-list tlv-select {
           ordered-by user;
           description "Select TLV(s) to be sent";
           type enumeration {
             enum "med-capabilities" {
               description "OUI TIA med-capabilities";
             }
             enum "network-policy" {
               description "OUI TIA network-policy";
             }
             enum "location-id" {
               description "OUI TIA location-id";
             }
             enum "ext-power-via-mdi" {
               description "OUI TIA ext-power-via-mdi";
             }
           }
         }
         leaf-list tlv-filter {
           ordered-by user;
           description "Filter TLV(s) to be sent";
           junos:must "(!(\".. tlv-select\"))";
           junos:must-message "tlv-select or tlv-filter is allowed, not both.";
           type enumeration {
             enum "all" {
               description "Filter all non mandatory TLVs";
             }
             enum "med-capabilities" {
               description "OUI TIA med-capabilities";
             }
             enum "network-policy" {
               description "OUI TIA network-policy";
             }
             enum "location-id" {
               description "OUI TIA location-id";
             }
             enum "ext-power-via-mdi" {
               description "OUI TIA ext-power-via-mdi";
             }
           }
         }
       }
       leaf-list tlv-select {
         ordered-by user;
         description "Select MED TLVs to be sent";
         type enumeration {
           enum "med-capabilities" {
             description "OUI TIA med-capabilities";
           }
           enum "network-policy" {
             description "OUI TIA network-policy";
           }
           enum "location-id" {
             description "OUI TIA location-id";
           }
           enum "ext-power-via-mdi" {
             description "OUI TIA ext-power-via-mdi";
           }
         }
       }
       leaf-list tlv-filter {
         ordered-by user;
         description "Filter MED TLVs to be sent";
         junos:must "(!(\".. tlv-select\"))";
         junos:must-message "tlv-select or tlv-filter is allowed, not both.";
         type enumeration {
           enum "all" {
             description "Filter all non mandatory TLVs";
           }
           enum "med-capabilities" {
             description "OUI TIA med-capabilities";
           }
           enum "network-policy" {
             description "OUI TIA network-policy";
           }
           enum "location-id" {
             description "OUI TIA location-id";
           }
           enum "ext-power-via-mdi" {
             description "OUI TIA ext-power-via-mdi";
           }
         }
       }
     }
     container igmp-snooping {
       description "IGMP snooping configuration";
       uses juniper-default-ri-protocols-igmp-snooping;
     }
     container mld-snooping {
       description "MLD snooping configuration";
       uses juniper-default-ri-protocols-mld-snooping;
     }
     container openflow {
       description "OpenFlow protocol";
       uses juniper-protocols-openflow;
     }
     container ppp {
       description "Configure PPP process";
       uses apply-advanced;
       container traceoptions {
         description "PPP trace options";
         uses ppp-traceoptions-type;
       }
       list monitor-session {
         key session-name;
         description "Monitor packet exchange for PPP session";
         leaf session-name {
           description "PPP session name";
           type string;
         }
         uses apply-advanced;
       }
     }
     container pppoe {
       junos:must "(!(\"forwarding-options hyper-mode\"))";
       junos:must-message "To configure pppoe, 'forwarding-options hyper-mode' should not be configured";
       description "Configure PPPoE process";
       uses apply-advanced;
       container traceoptions {
         description "PPPoE trace options";
         uses pppoe-traceoptions-type;
       }
       leaf pado-advertise {
         description "Enable PADO advertising of PPPoE Service-Names";
         type empty;
       }
     }
     container sflow {
       presence "enable sflow";
       description "SFLOW protocol";
       uses apply-advanced;
       container traceoptions {
         description "Trace options for SFLOW";
         uses apply-advanced;
         container file {
           description "Trace file options";
           leaf filename {
             description "Name of file in which to write trace information";
             type string {
               length "1 .. 1024";
               junos:posix-pattern "![/ %]";
               junos:pattern-message "Must not contain '/', % or a space";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "configuration" {
                 description "Trace sflow configuration";
               }
               enum "rtsock" {
                 description "Trace rtsock events";
               }
               enum "interface" {
                 description "Trace interface events";
               }
               enum "client-server" {
                 description "Trace sflow client-server events";
               }
               enum "all" {
                 description "Trace all sflow events";
               }
             }
           }
           leaf disable {
             description "Disable this trace flag";
             type empty;
           }
         }
       }
       container agent-id {
         description "Sflow agent id configuration";
         leaf inet {
           description "Sflow agent ipv4 address";
           type jt:ipv4addr;
         }
       }
       leaf polling-interval {
         description "Interval between port statistics";
         default "20";
         units "seconds";
         type union {
           type string {
             pattern "<.*>|$.*";
           }
           type uint32 {
             range "0 .. 3600";
           }
         }
       }
       container adaptive-sample-rate {
         description "Trigger adaptive sampling";
         leaf sample-rate {
           description "Sflow adaptive sampling rate configuration";
           type union {
             type string {
               pattern "<.*>|$.*";
             }
             type uint32;
           }
         }
         leaf fallback {
           description "Enable fallback to previous adapted sample rates";
           type empty;
         }
         leaf sample-limit-threshold {
           description "Per FPC Sample limits in pps ";
           junos:must "(\".. fallback\")";
           junos:must-message "Adaptive sample rate fallback must be configured";
           type union {
             type string {
               pattern "<.*>|$.*";
             }
             type uint32;
           }
         }
       }
       leaf inline-sampling {
         description "Enable inline sampling of packets";
         type empty;
       }
       container sample-rate {
         description "Sampling rate";
         uses apply-advanced;
         leaf ingress {
           description "Ingress direction";
           type union {
             type string {
               pattern "<.*>|$.*";
             }
             type uint32;
           }
         }
         leaf egress {
           description "Egress direction";
           type union {
             type string {
               pattern "<.*>|$.*";
             }
             type uint32;
           }
         }
       }
       container source-ip {
         description "Sflow agent id configuration";
         leaf inet {
           description "Sflow datagram source ipv4 address";
           type jt:ipv4addr;
         }
       }
       list collector {
         key name;
         ordered-by user;
         description "SFLOW collector configuration";
         max-elements 4;
         leaf name {
           description "Collector IP v4/v6 address";
           junos:must "(!((\"protocols sflow source-ip $$\" || \"protocols sflow source-ip inet6 $$\")))";
           junos:must-message "sFlow collector address and source ip cannot be same";
           type jt:ipaddr;
         }
         uses apply-advanced;
         leaf udp-port {
           description "Collector UDP port";
           default "6343";
           type union {
             type uint16;
             type string {
               pattern "<.*>|$.*";
             }
           }
         }
       }
       list interfaces {
         key name;
         description "Enable SFLOW on this interface";
         leaf name {
           description "Interface name";
           type union {
             type jt:interface-name;
             type string {
               pattern "<.*>|$.*";
             }
           }
         }
         uses apply-advanced;
         leaf polling-interval {
           description "Interval between port statistics";
           units "seconds";
           type union {
             type string {
               pattern "<.*>|$.*";
             }
             type uint32 {
               range "0 .. 3600";
             }
           }
         }
         container sample-rate {
           description "Sampling rate";
           uses apply-advanced;
           leaf ingress {
             description "Ingress direction";
             type union {
               type string {
                 pattern "<.*>|$.*";
               }
               type uint32;
             }
           }
           leaf egress {
             description "Egress direction";
             type union {
               type string {
                 pattern "<.*>|$.*";
               }
               type uint32;
             }
           }
         }
       }
       leaf disable-sw-rate-limiter {
         description "Disable sw rate limiter";
         type empty;
       }
     }
     container protection-group {
       description "Protection group";
       presence "enable protection-group";
       uses juniper-protocols-protection-group;
     }
     container mvrp {
       description "MVRP configuration";
       junos:must "((!(\".. vstp\") || \".. vstp disable\"))";
       junos:must-message "vstp enabled, mvrp is not supported";
       junos:must "(((\".. mstp\" && !(\".. mstp disable\")) || (\".. rstp\" && !(\".. rstp disable\"))))";
       junos:must-message "RSTP/MSTP is not enabled, MVRP not allowed";
       uses juniper-protocols-mvrp;
     }
     container layer2-control {
       description "Global options for layer 2 protocols";
       uses juniper-protocols-l2control;
     }
     container rstp {
       description "Rapid Spanning Tree Protocol options";
       uses juniper-protocols-stp;
     }
     container mstp {
       description "Multiple Spanning Tree Protocol options";
       uses juniper-protocols-mstp;
     }
     container vstp {
       description "VLAN Spanning Tree Protocol options";
       junos:must "((\".. vstp disable\" || (!(\".. mstp\") || \".. mstp disable\")))";
       junos:must-message "MSTP is enabled in the same routing instance, VSTP not allowed";
       uses juniper-protocols-vstp;
     }
     container loop-detect {
       presence "enable loop-detect";
       description "Layer2 Loop Detect on interface with non-IP L2 Multicast mac as destination mac";
       uses apply-advanced;
       list interface {
         key name;
         ordered-by user;
         description "Interface name to block Loop Detect PDUs on";
         junos:must "(any \".. destination-mac <*>\")";
         junos:must-message "destination-mac is mandatory for enabling loop-detect";
         leaf name {
           type string;
         }
         uses apply-advanced;
         leaf disable {
           description "Disable loop detect feature on a port";
           type empty;
         }
       }
       container enhanced {
         description "Enhanced loop detect configuration";
         uses apply-advanced;
         list interface {
           key name;
           ordered-by user;
           description "Name of interface";
           leaf name {
             type string;
           }
           uses apply-advanced;
           leaf vlan-id {
             description "VLAN identifier for trunk interface";
             type union {
               type string {
                 pattern "<.*>|$.*";
               }
               type uint32 {
                 range "1 .. 4094";
               }
             }
           }
           leaf loop-detect-action {
             description "Action that needs to be taken";
             default "interface-down";
             type enumeration {
               enum "interface-down" {
                 description "Interface down action";
               }
               enum "laser-off" {
                 description "Laser off action";
               }
             }
           }
           leaf transmit-interval {
             description "Interval between loop-detect messages";
             default "1s";
             type enumeration {
               enum "1s" {
               }
               enum "10s" {
               }
               enum "1m" {
               }
               enum "10m" {
               }
             }
           }
           leaf revert-interval {
             description "Interval after which action will be reverted";
             default "0";
             units "seconds";
             type union {
               type string {
                 pattern "<.*>|$.*";
               }
               type uint32 {
                 range "0 .. 300";
               }
             }
           }
         }
       }
       leaf destination-mac {
         description "Destination non-IP L2 multicast mac to be used for transmitting Loop Detect PDUs";
         type jt:mac-multicast;
       }
       leaf transmit-interval {
         description "Loop Detect PDU TX interval in sec --default 30s";
         units "seconds";
         type union {
           type string {
             pattern "<.*>|$.*";
           }
           type uint16 {
             range "5 .. 3600";
           }
         }
       }
     }
     container uplink-failure-detection {
       description "Uplink failure detection configuration";
       uses apply-advanced;
       container group {
         description "Uplink failure detection group";
         uses apply-advanced;
         list ufd-group-name {
           key name;
           description "Uplink failure detection group name";
           uses ufd-group-type;
         }
       }
       container traceoptions {
         description "Trace options for uplink failure detection";
         uses apply-advanced;
         container file {
           description "Trace file options";
           leaf filename {
             description "Name of file in which to write trace information";
             type string {
               length "1 .. 1024";
               junos:posix-pattern "![/ %]";
               junos:pattern-message "Must not contain '/', % or a space";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "parse" {
                 description "Trace configuration parsing";
               }
               enum "interface" {
                 description "Trace interface notifcation handlers of ufd";
               }
               enum "dcd" {
                 description "Trace ufdd interaction with dcd";
               }
               enum "groups" {
                 description "Trace uplink failure detection group handling";
               }
               enum "all" {
                 description "Trace everything";
               }
             }
           }
         }
       }
       container action {
         description "Define action on ufd group state change";
         uses apply-advanced;
         leaf log {
           description "Log a message";
           type empty;
         }
       }
     }
   }
   grouping admin_group_include_exclude {
     uses apply-advanced;
     choice include-any-choice {
       case case_1 {
         leaf-list include-any {
           ordered-by user;
           description "Groups, one or more of which must be present";
           type string;
         }
       }
     }
     choice include-all-choice {
       case case_1 {
         leaf-list include-all {
           ordered-by user;
           description "Groups, all of which must be present";
           type string;
         }
       }
     }
     choice exclude-choice {
       case case_1 {
         leaf-list exclude {
           ordered-by user;
           description "Groups, all of which must be absent";
           type string;
         }
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping bandwidth-type {
     uses apply-advanced;
     leaf per-traffic-class-bandwidth {
       description "Bandwidth to reserve";
       units "bps";
       type string;
     }
     leaf ct0 {
       description "Bandwidth from traffic class 0";
       units "bps";
       type string;
     }
     leaf ct1 {
       description "Bandwidth from traffic class 1";
       units "bps";
       type string;
     }
     leaf ct2 {
       description "Bandwidth from traffic class 2";
       units "bps";
       type string;
     }
     leaf ct3 {
       description "Bandwidth from traffic class 3";
       units "bps";
       type string;
     }
   }
   grouping cfm-traceoptions {
     description "Trace options for connectivity fault management";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Tracing parameters";
       leaf name {
         type enumeration {
           enum "configuration" {
             description "Trace configuration events";
           }
           enum "routing-socket" {
             description "Trace routing socket events";
           }
           enum "protocol" {
             description "Trace protocol processing events";
           }
           enum "init" {
             description "Trace events related to protocol daemon start-up";
           }
           enum "error" {
             description "Trace events related to catestrophic errors in daemon";
           }
           enum "issu" {
             description "Trace ISSU related events";
           }
           enum "all" {
             description "Trace everything";
           }
         }
       }
     }
   }
   grouping civic-address-elements {
     uses apply-advanced;
     leaf what {
       description "Type of address";
       default "1";
       type union {
         type string {
           pattern "<.*>|$.*";
         }
         type uint16 {
           range "0 .. 2";
         }
       }
     }
     leaf country-code {
       description "Two-letter country code";
       type string {
         length 2;
       }
     }
     list ca-type {
       key name;
       ordered-by user;
       leaf name {
         description "Address element type";
         type union {
           type string {
             pattern "<.*>|$.*";
           }
           type uint16 {
             range "0 .. 255";
           }
         }
       }
       uses apply-advanced;
       leaf ca-value {
         description "Address element value";
         type string;
       }
     }
   }
   grouping juniper-default-ri-protocols-igmp-snooping {
     description "IGMP snooping options";
     uses apply-advanced;
     list vlan {
       key name;
       ordered-by user;
       description "VLAN options";
       leaf name {
         description "VLAN name";
         junos:must "(!(\".. .. .. .. vlans ${vlan} private-vlan\"))";
         junos:must-message "Snooping cannot be enabled on secondary vlan";
         junos:must "((!(\".. .. .. .. vlans ${vlan} vlan-id-list\") && (!(\".. .. .. .. vlans ${vlan} vxlan\") || \".. .. .. .. protocols evpn\")))";
         junos:must-message "Snooping must be configured on specific vlans which is not vxlan enabled (not on vlan list)";
         type string;
       }
       uses apply-advanced;
       container traceoptions {
         description "Trace options for IGMP Snooping";
         uses apply-advanced;
         container file {
           description "Trace file options";
           leaf filename {
             description "Name of file in which to write trace information";
             type string {
               length "1 .. 1024";
               junos:posix-pattern "![/ %]";
               junos:pattern-message "Must not contain '/', % or a space";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "packets" {
                 description "Trace all IGMP packets";
               }
               enum "query" {
                 description "Trace IGMP membership query messages";
               }
               enum "report" {
                 description "Trace membership report messages";
               }
               enum "leave" {
                 description "Trace leave group messages (IGMPv2 only)";
               }
               enum "group" {
                 description "Trace group operations";
               }
               enum "client-notification" {
                 description "Trace notifications";
               }
               enum "route" {
                 description "Trace routing information";
               }
               enum "normal" {
                 description "Trace normal events";
               }
               enum "general" {
                 description "Trace general events";
               }
               enum "state" {
                 description "Trace state transitions";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       leaf query-interval {
         description "When to send host query messages";
         default "125";
         units "seconds";
         type union {
           type string {
             pattern "<.*>|$.*";
           }
           type uint32 {
             range "1 .. 1024";
           }
         }
       }
       container l2-querier {
         description "Enable L2 querier mode";
         uses apply-advanced;
         leaf source-address {
           description "Source IP address to use for L2 querier";
           type jt:ipv4addr;
         }
       }
       leaf query-response-interval {
         description "How long to wait for a host query response";
         default "10";
         units "seconds";
         type string {
           junos:posix-pattern "^[0-9]{1,4}(.[0-9])?$";
           junos:pattern-message "Up to 1 digit to right of decimal point";
         }
       }
       leaf query-last-member-interval {
         description "When to send group query messages";
         default "1";
         units "seconds";
         type string {
           junos:posix-pattern "^[0-9]{1,4}(.[0-9])?$";
           junos:pattern-message "Up to 1 digit to right of decimal point";
         }
       }
       leaf robust-count {
         description "Expected packet loss on a subnet";
         default "2";
         type union {
           type string {
             pattern "<.*>|$.*";
           }
           type uint32 {
             range "2 .. 10";
           }
         }
       }
       leaf immediate-leave {
         description "Enable immediate group leave on interfaces";
         type empty;
       }
       container proxy {
         presence "enable proxy";
         description "Enable proxy mode";
         uses apply-advanced;
         leaf source-address {
           description "Source IP address to use for proxy";
           junos:must "(!(\".. .. .. .. .. vlans ${vlan} vlan-id all\"))";
           junos:must-message "With qualified-learning source-address should be configured under qualified vlan options";
           type jt:ipv4addr;
         }
       }
       leaf evpn-ssm-reports-only {
         description "Accept and process only <s,g> reports of SSM groups";
         type empty;
       }
       list interface {
         key name;
         ordered-by user;
         description "Interface options for IGMP";
         leaf name {
           description "Interface name";
           junos:must "(!(\"interfaces $$-IFL vlan-tags inner-range\"))";
           junos:must-message "interface with vlan-tags inner-range should be specified in a learning-domain only";
           junos:must "(!(\"interfaces $$-IFL vlan-id-range\"))";
           junos:must-message "interface with vlan-id-range should be specified in a learning-domain only";
           junos:must "(!(\".. .. .. .. .. vlans ${vlan} vlan-id all\"))";
           junos:must-message "When 'vlan-id all' is configured, interface should be configured only under vlan";
           type union {
             type jt:interface-name;
             type string {
               pattern "<.*>|$.*";
             }
           }
         }
         uses apply-advanced;
         leaf multicast-router-interface {
           description "Enabling multicast-router-interface on the interface";
           type empty;
         }
         leaf immediate-leave {
           description "Enable immediate group leave on interface";
           type empty;
         }
         leaf host-only-interface {
           description "Enable interface to be treated as host-side interface";
           junos:must "(!(\".. multicast-router-interface\"))";
           junos:must-message "interface cannot be both host-only and multicast-router";
           type empty;
         }
         leaf group-limit {
           description "Maximum number of groups an interface can join";
           type union {
             type uint16;
             type string {
               pattern "<.*>|$.*";
             }
           }
         }
         container static {
           description "Static group or source membership";
           uses apply-advanced;
           list group {
             key name;
             ordered-by user;
             description "IP multicast group address";
             leaf name {
               description "IP multicast group address";
               type jt:ipv4addr;
             }
             uses apply-advanced;
             list source {
               key name;
               ordered-by user;
               description "IP multicast source address";
               leaf name {
                 description "Source address of IP multicast data";
                 type jt:ipv4addr;
               }
               uses apply-advanced;
             }
           }
         }
       }
       list qualified-vlan {
         key name;
         ordered-by user;
         description "VLAN options for qualified-learning";
         leaf name {
           description "VLAN ID of the learning-domain";
           junos:must "(\".. .. .. .. .. vlans ${vlan} vlan-id all\")";
           junos:must-message "vlan specific configuration is allowed with qualified-learning only";
           type union {
             type string {
               pattern "<.*>|$.*";
             }
             type uint32 {
               range "0 .. 1023";
             }
           }
         }
         uses apply-advanced;
         leaf query-interval {
           description "When to send host query messages";
           units "seconds";
           type union {
             type string {
               pattern "<.*>|$.*";
             }
             type uint32 {
               range "1 .. 1024";
             }
           }
         }
         container l2-querier {
           description "Enable L2 querier mode";
           uses apply-advanced;
           leaf source-address {
             description "Source IP address to use for L2 querier";
             type jt:ipv4addr;
           }
         }
         leaf query-response-interval {
           description "How long to wait for a host query response";
           units "seconds";
           type string {
             junos:posix-pattern "^[0-9]{1,4}(.[0-9])?$";
             junos:pattern-message "Up to 1 digit to right of decimal point";
           }
         }
         leaf query-last-member-interval {
           description "When to send group query messages";
           units "seconds";
           type string {
             junos:posix-pattern "^[0-9]{1,4}(.[0-9])?$";
             junos:pattern-message "Up to 1 digit to right of decimal point";
           }
         }
         leaf robust-count {
           description "Expected packet loss on a subnet";
           type union {
             type string {
               pattern "<.*>|$.*";
             }
             type uint32 {
               range "2 .. 10";
             }
           }
         }
         leaf immediate-leave {
           description "Enable immediate group leave on interfaces";
           type empty;
         }
         container proxy {
           presence "enable proxy";
           description "Enable proxy mode";
           uses apply-advanced;
           leaf source-address {
             description "Source IP address to use for proxy";
             type jt:ipv4addr;
           }
         }
         leaf evpn-ssm-reports-only {
           description "Accept and process only <s,g> reports of SSM groups";
           type empty;
         }
         list interface {
           key name;
           ordered-by user;
           description "Interface options for IGMP";
           leaf name {
             description "Interface name";
             junos:must "(\".. .. .. .. .. .. vlans ${vlan} interface $$\")";
             junos:must-message "interface options can be specified for the interfaces in the routing-instance";
             type union {
               type jt:interface-name;
               type string {
                 pattern "<.*>|$.*";
               }
             }
           }
           uses apply-advanced;
           leaf multicast-router-interface {
             description "Enabling multicast-router-interface on the interface";
             type empty;
           }
           leaf immediate-leave {
             description "Enable immediate group leave on interface";
             type empty;
           }
           leaf host-only-interface {
             description "Enable interface to be treated as host-side interface";
             junos:must "(!(\".. multicast-router-interface\"))";
             junos:must-message "interface cannot be both host-only and multicast-router";
             type empty;
           }
           leaf group-limit {
             description "Maximum number of groups an interface can join";
             type union {
               type uint16;
               type string {
                 pattern "<.*>|$.*";
               }
             }
           }
           container static {
             description "Static group or source membership";
             uses apply-advanced;
             list group {
               key name;
               ordered-by user;
               description "IP multicast group address";
               leaf name {
                 description "IP multicast group address";
                 type jt:ipv4addr;
               }
               uses apply-advanced;
               list source {
                 key name;
                 ordered-by user;
                 description "IP multicast source address";
                 leaf name {
                   description "Source address of IP multicast data";
                   type jt:ipv4addr;
                 }
                 uses apply-advanced;
               }
             }
           }
         }
       }
     }
     container traceoptions {
       description "Trace options for IGMP Snooping";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "packets" {
               description "Trace all IGMP packets";
             }
             enum "query" {
               description "Trace IGMP membership query messages";
             }
             enum "report" {
               description "Trace membership report messages";
             }
             enum "leave" {
               description "Trace leave group messages (IGMPv2 only)";
             }
             enum "group" {
               description "Trace group operations";
             }
             enum "client-notification" {
               description "Trace notifications";
             }
             enum "host-notification" {
               description "Trace host notifications";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     leaf query-interval {
       description "When to send host query messages";
       default "125";
       units "seconds";
       type union {
         type string {
           pattern "<.*>|$.*";
         }
         type uint32 {
           range "1 .. 1024";
         }
       }
     }
     leaf query-response-interval {
       description "How long to wait for a host query response";
       default "10";
       units "seconds";
       type string {
         junos:posix-pattern "^[0-9]{1,4}(.[0-9])?$";
         junos:pattern-message "Up to 1 digit to right of decimal point";
       }
     }
     leaf query-last-member-interval {
       description "When to send group query messages";
       default "1";
       units "seconds";
       type string {
         junos:posix-pattern "^[0-9]{1,4}(.[0-9])?$";
         junos:pattern-message "Up to 1 digit to right of decimal point";
       }
     }
     leaf robust-count {
       description "Expected packet loss on a subnet";
       default "2";
       type union {
         type string {
           pattern "<.*>|$.*";
         }
         type uint32 {
           range "2 .. 10";
         }
       }
     }
     leaf immediate-leave {
       description "Enable immediate group leave on interfaces";
       type empty;
     }
     leaf evpn-ssm-reports-only {
       description "Accept and process only <s,g> reports of SSM groups";
       type empty;
     }
     container proxy {
       presence "enable proxy";
       description "Enable proxy mode";
       uses apply-advanced;
       leaf source-address {
         description "Source IP address to use for proxy";
         type jt:ipv4addr;
       }
       leaf irb {
         description "Proxy IGMP reports to IRB";
         type empty;
       }
     }
     list interface {
       key name;
       ordered-by user;
       description "Interface options for IGMP";
       leaf name {
         description "Interface name";
         junos:must "((\"interfaces $$-IFL family bridge interface-mode\" && !(any \"routing-instances <*> interface $$\")))";
         junos:must-message "interface options can be specified for access/trunk interfaces in this routing instance only";
         type union {
           type jt:interface-name;
           type string {
             pattern "<.*>|$.*";
           }
         }
       }
       uses apply-advanced;
       leaf multicast-router-interface {
         description "Enabling multicast-router-interface on the interface";
         type empty;
       }
       leaf immediate-leave {
         description "Enable immediate group leave on interfaces";
         type empty;
       }
       leaf host-only-interface {
         description "Enable interfaces to be treated as host-side interfaces";
         junos:must "(!(\".. multicast-router-interface\"))";
         junos:must-message "interface cannot be both host-only and multicast-router";
         type empty;
       }
       leaf group-limit {
         description "Maximum number of (source,group) per interface";
         type union {
           type string {
             pattern "<.*>|$.*";
           }
           type uint16 {
             range "1 .. 65535";
           }
         }
       }
       container static {
         description "Static group or source membership";
         uses apply-advanced;
         list group {
           key name;
           ordered-by user;
           description "IP multicast group address";
           leaf name {
             description "IP multicast group address";
             type jt:ipv4addr;
           }
           uses apply-advanced;
           list source {
             key name;
             ordered-by user;
             description "IP multicast source address";
             leaf name {
               description "Source address of IP multicast data";
               type jt:ipv4addr;
             }
             uses apply-advanced;
           }
         }
       }
     }
   }
   grouping juniper-default-ri-protocols-mld-snooping {
     description "MLD snooping options";
     uses apply-advanced;
     list vlan {
       key name;
       ordered-by user;
       description "VLAN options";
       leaf name {
         description "VLAN name";
         junos:must "(!(\".. .. .. .. vlans ${vlan} private-vlan\"))";
         junos:must-message "Snooping cannot be enabled on secondary vlan";
         junos:must "((!(\".. .. .. .. vlans ${vlan} vlan-id-list\") && (!(\".. .. .. .. vlans ${vlan} vxlan\") || \".. .. .. .. protocols evpn\")))";
         junos:must-message "Snooping must be configured on specific vlans which is not vxlan enabled(not on vlan list)";
         type string;
       }
       uses apply-advanced;
       container traceoptions {
         description "Trace options for MLD Snooping";
         uses apply-advanced;
         container file {
           description "Trace file options";
           leaf filename {
             description "Name of file in which to write trace information";
             type string {
               length "1 .. 1024";
               junos:posix-pattern "![/ %]";
               junos:pattern-message "Must not contain '/', % or a space";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "packets" {
                 description "Trace all MLD packets";
               }
               enum "query" {
                 description "Trace MLD membership query messages";
               }
               enum "report" {
                 description "Trace membership report messages";
               }
               enum "leave" {
                 description "Trace leave group messages (MLDv1 only)";
               }
               enum "group" {
                 description "Trace group operations";
               }
               enum "client-notification" {
                 description "Trace notifications";
               }
               enum "host-notification" {
                 description "Trace host notifications";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       leaf query-interval {
         description "When to send host query messages";
         default "125";
         units "seconds";
         type union {
           type string {
             pattern "<.*>|$.*";
           }
           type uint32 {
             range "1 .. 1024";
           }
         }
       }
       container l2-querier {
         description "Enable L2 querier mode";
         uses apply-advanced;
         leaf source-address {
           description "Source IP address to use for L2 querier";
           type jt:ipv6addr;
         }
       }
       leaf query-response-interval {
         description "How long to wait for a host query response";
         default "10";
         units "seconds";
         type string {
           junos:posix-pattern "^[0-9]{1,4}(.[0-9])?$";
           junos:pattern-message "Up to 1 digit to right of decimal point";
         }
       }
       leaf query-last-member-interval {
         description "When to send group query messages";
         default "1";
         units "seconds";
         type string {
           junos:posix-pattern "^[0-9]{1,4}(.[0-9])?$";
           junos:pattern-message "Up to 1 digit to right of decimal point";
         }
       }
       leaf robust-count {
         description "Expected packet loss on a subnet";
         default "2";
         type union {
           type string {
             pattern "<.*>|$.*";
           }
           type uint32 {
             range "2 .. 10";
           }
         }
       }
       leaf immediate-leave {
         description "Enable immediate group leave on interfaces";
         type empty;
       }
       container proxy {
         presence "enable proxy";
         description "Enable proxy mode";
         uses apply-advanced;
         leaf source-address {
           description "Source IP address to use for proxy";
           junos:must "(!(\".. .. .. .. .. vlans ${vlan} vlan-id all\"))";
           junos:must-message "With qualified-learning source-address should be configured under Vlan options";
           type jt:ipv6addr;
         }
       }
       leaf evpn-ssm-reports-only {
         description "Accept and process only <s,g> reports of SSM groups";
         type empty;
       }
       list interface {
         key name;
         ordered-by user;
         description "Interface options for MLD";
         leaf name {
           description "Interface name";
           junos:must "(!(\"interfaces $$-IFL vlan-tags inner-range\"))";
           junos:must-message "interface with vlan-tags inner-range should be specified in a learning-domain only";
           junos:must "(!(\"interfaces $$-IFL vlan-id-range\"))";
           junos:must-message "interface with vlan-id-range should be specified in a learning-domain only";
           junos:must "(!(\".. .. .. .. .. vlans ${vlan} vlan-id all\"))";
           junos:must-message "When 'vlan-id all' is configured, interface should be configured only under vlan";
           type union {
             type jt:interface-name;
             type string {
               pattern "<.*>|$.*";
             }
           }
         }
         uses apply-advanced;
         leaf multicast-router-interface {
           description "Enabling multicast-router-interface on the interface";
           type empty;
         }
         leaf immediate-leave {
           description "Enable immediate group leave on interfaces";
           type empty;
         }
         leaf host-only-interface {
           description "Enable interfaces to be treated as host-side interfaces";
           type empty;
         }
         leaf group-limit {
           description "Maximum number of groups an interface can join";
           type union {
             type uint16;
             type string {
               pattern "<.*>|$.*";
             }
           }
         }
         container static {
           description "Static group or source membership";
           uses apply-advanced;
           list group {
             key name;
             ordered-by user;
             description "IP multicast group address";
             leaf name {
               description "IP multicast group address";
               type jt:ipv6addr;
             }
             uses apply-advanced;
             list source {
               key name;
               ordered-by user;
               description "IP multicast source address";
               leaf name {
                 description "Source address of IP multicast data";
                 type jt:ipv6addr;
               }
               uses apply-advanced;
             }
           }
         }
       }
       list qualified-vlan {
         key name;
         ordered-by user;
         description "VLAN options for qualified-learning";
         leaf name {
           description "VLAN ID of the learning-domain";
           junos:must "(\".. .. .. .. .. vlans ${vlan} vlan-id all\")";
           junos:must-message "vlan specific configuration is allowed with qualified-learning only";
           type union {
             type string {
               pattern "<.*>|$.*";
             }
             type uint32 {
               range "0 .. 1023";
             }
           }
         }
         uses apply-advanced;
         leaf query-interval {
           description "When to send host query messages";
           units "seconds";
           type union {
             type string {
               pattern "<.*>|$.*";
             }
             type uint32 {
               range "1 .. 1024";
             }
           }
         }
         container l2-querier {
           uses apply-advanced;
           leaf source-address {
             description "Source IP address to use for L2 querier";
             type jt:ipv6addr;
           }
         }
         leaf query-response-interval {
           description "How long to wait for a host query response";
           units "seconds";
           type string {
             junos:posix-pattern "^[0-9]{1,4}(.[0-9])?$";
             junos:pattern-message "Up to 1 digit to right of decimal point";
           }
         }
         leaf query-last-member-interval {
           description "When to send group query messages";
           units "seconds";
           type string {
             junos:posix-pattern "^[0-9]{1,4}(.[0-9])?$";
             junos:pattern-message "Up to 1 digit to right of decimal point";
           }
         }
         leaf robust-count {
           description "Expected packet loss on a subnet";
           type union {
             type string {
               pattern "<.*>|$.*";
             }
             type uint32 {
               range "2 .. 10";
             }
           }
         }
         leaf immediate-leave {
           description "Enable immediate group leave on interfaces";
           type empty;
         }
         container proxy {
           presence "enable proxy";
           description "Enable proxy mode";
           uses apply-advanced;
           leaf source-address {
             description "Source IP address to use for proxy";
             type jt:ipv6addr;
           }
         }
         leaf evpn-ssm-reports-only {
           description "Accept and process only <s,g> reports of SSM groups";
           type empty;
         }
         list interface {
           key name;
           ordered-by user;
           description "Interface options for MLD";
           leaf name {
             description "Interface name";
             junos:must "(\".. .. .. .. .. .. vlans ${vlan} interface $$\")";
             junos:must-message "interface options can be specified for the interfaces in the routing-instance";
             type union {
               type jt:interface-name;
               type string {
                 pattern "<.*>|$.*";
               }
             }
           }
           uses apply-advanced;
           leaf multicast-router-interface {
             description "Enabling multicast-router-interface on the interface";
             type empty;
           }
           leaf immediate-leave {
             description "Enable immediate group leave on interfaces";
             type empty;
           }
           leaf host-only-interface {
             description "Enable interfaces to be treated as host-side interfaces";
             type empty;
           }
           leaf group-limit {
             description "Maximum number of groups an interface can join";
             type union {
               type uint16;
               type string {
                 pattern "<.*>|$.*";
               }
             }
           }
           container static {
             description "Static group or source membership";
             uses apply-advanced;
             list group {
               key name;
               ordered-by user;
               description "IP multicast group address";
               leaf name {
                 description "IP multicast group address";
                 type jt:ipv6addr;
               }
               uses apply-advanced;
               list source {
                 key name;
                 ordered-by user;
                 description "IP multicast source address";
                 leaf name {
                   description "Source address of IP multicast data";
                   type jt:ipv6addr;
                 }
                 uses apply-advanced;
               }
             }
           }
         }
       }
     }
     container traceoptions {
       description "Trace options for MLD Snooping";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "packets" {
               description "Trace all MLD packets";
             }
             enum "query" {
               description "Trace MLD membership query messages";
             }
             enum "report" {
               description "Trace membership report messages";
             }
             enum "leave" {
               description "Trace leave group messages (MLDv2 only)";
             }
             enum "group" {
               description "Trace group operations";
             }
             enum "client-notification" {
               description "Trace notifications";
             }
             enum "host-notification" {
               description "Trace host notifications";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     leaf query-interval {
       description "When to send host query messages";
       default "125";
       units "seconds";
       type union {
         type string {
           pattern "<.*>|$.*";
         }
         type uint32 {
           range "1 .. 1024";
         }
       }
     }
     leaf query-response-interval {
       description "How long to wait for a host query response";
       default "10";
       units "seconds";
       type string {
         junos:posix-pattern "^[0-9]{1,4}(.[0-9])?$";
         junos:pattern-message "Up to 1 digit to right of decimal point";
       }
     }
     leaf query-last-member-interval {
       description "When to send group query messages";
       default "1";
       units "seconds";
       type string {
         junos:posix-pattern "^[0-9]{1,4}(.[0-9])?$";
         junos:pattern-message "Up to 1 digit to right of decimal point";
       }
     }
     leaf robust-count {
       description "Expected packet loss on a subnet";
       default "2";
       type union {
         type string {
           pattern "<.*>|$.*";
         }
         type uint32 {
           range "2 .. 10";
         }
       }
     }
     leaf immediate-leave {
       description "Enable immediate group leave on interfaces";
       type empty;
     }
     leaf evpn-ssm-reports-only {
       description "Accept and process only <s,g> reports of SSM groups";
       type empty;
     }
     container proxy {
       presence "enable proxy";
       description "Enable proxy mode";
       uses apply-advanced;
       leaf source-address {
         description "Source IP address to use for proxy";
         type jt:ipv6addr;
       }
       leaf irb {
         description "Proxy IGMP reports to IRB";
         type empty;
       }
     }
     list interface {
       key name;
       ordered-by user;
       description "Interface options for MLD";
       leaf name {
         description "Interface name";
         junos:must "((\"interfaces $$-IFL family bridge interface-mode\" && !(any \"routing-instances <*> interface $$\")))";
         junos:must-message "interface options can be specified for access/trunk interfaces in this routing instance only";
         type union {
           type jt:interface-name;
           type string {
             pattern "<.*>|$.*";
           }
         }
       }
       uses apply-advanced;
       leaf multicast-router-interface {
         description "Enabling multicast-router-interface on the interface";
         type empty;
       }
       leaf immediate-leave {
         description "Enable immediate group leave on interfaces";
         type empty;
       }
       leaf host-only-interface {
         description "Enable interfaces to be treated as host-side interfaces";
         junos:must "(!(\".. multicast-router-interface\"))";
         junos:must-message "interface cannot be both host-only and multicast-router";
         type empty;
       }
       leaf group-limit {
         description "Maximum number of (source,group) per interface";
         type union {
           type string {
             pattern "<.*>|$.*";
           }
           type uint16 {
             range "1 .. 65535";
           }
         }
       }
       container static {
         description "Static group or source membership";
         uses apply-advanced;
         list group {
           key name;
           ordered-by user;
           description "IP multicast group address";
           leaf name {
             description "IP multicast group address";
             type jt:ipv6addr;
           }
           uses apply-advanced;
           list source {
             key name;
             ordered-by user;
             description "IP multicast source address";
             leaf name {
               description "Source address of IP multicast data";
               type jt:ipv6addr;
             }
             uses apply-advanced;
           }
         }
       }
     }
   }
   grouping juniper-protocols-amt {
     uses apply-advanced;
     container traceoptions {
       description "Trace options for AMT";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "packets" {
               description "Trace all AMT packets";
             }
             enum "errors" {
               description "Trace all error messages";
             }
             enum "tunnels" {
               description "Trace all AMT tunnel messages";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     container relay {
       description "AMT relay";
       presence "enable relay";
       uses juniper-protocols-amt-relay;
     }
   }
   grouping juniper-protocols-amt-relay {
     uses apply-advanced;
     container family {
       presence "enable family";
       description "Protocol family";
       uses apply-advanced;
       container inet {
         presence "enable inet";
         uses apply-advanced;
         leaf anycast-prefix {
           description "IPv4 anycast prefix";
           type jt:ipv4prefix;
         }
         leaf local-address {
           description "IPv4 local address";
           type jt:ipv4addr;
         }
       }
     }
     leaf secret-key-timeout {
       description "Time interval for the secret key to expire";
       units "minutes";
       type union {
         type string {
           pattern "<.*>|$.*";
         }
         type uint32 {
           range "5 .. 1440";
         }
       }
     }
     leaf tunnel-limit {
       description "Number of AMT tunnels";
       type union {
         type uint32;
         type string {
           pattern "<.*>|$.*";
         }
       }
     }
     leaf unicast-stream-limit {
       description "Maximum number of AMT unicast streams(s,g,intf)";
       type union {
         type uint32;
         type string {
           pattern "<.*>|$.*";
         }
       }
     }
     leaf accounting {
       description "Enable AMT accounting";
       type empty;
     }
     leaf-list tunnel-devices {
       ordered-by user;
       description "Tunnel devices to be used for creating ud interfaces";
       type union {
         type jt:interface-device;
         type string {
           pattern "<.*>|$.*";
         }
       }
     }
   }
   grouping juniper-protocols-ancp {
     uses apply-advanced;
     container traceoptions {
       description "Trace options for ANCP";
       uses apply-advanced;
       leaf no-remote-trace {
         description "Disable remote tracing";
         junos:must "(\"system tracing\")";
         junos:must-message "'no-remote-trace' is valid only when [system tracing] is configured";
         type empty;
       }
       container file {
         description "Trace file information";
         leaf filename {
           description "Name of file in which to write trace information";
           type string {
             length "1 .. 1024";
             junos:posix-pattern "![/ %]";
             junos:pattern-message "Must not contain '/', % or a space";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       leaf level {
         description "Level of debugging output";
         default "error";
         type enumeration {
           enum "error" {
             description "Match error conditions";
           }
           enum "warning" {
             description "Match warning messages";
           }
           enum "notice" {
             description "Match conditions that should be handled specially";
           }
           enum "info" {
             description "Match informational messages";
           }
           enum "verbose" {
             description "Match verbose messages";
           }
           enum "all" {
             description "Match all levels";
           }
         }
       }
       list flag {
         key name;
         ordered-by user;
         description "Tracing parameters";
         leaf name {
           type enumeration {
             enum "config" {
               description "Trace config events";
             }
             enum "cos" {
               description "Trace CoS events";
             }
             enum "routing-socket" {
               description "Trace routing-socket events";
             }
             enum "packet" {
               description "Trace ANCP packet Transmit/Receive";
             }
             enum "protocol" {
               description "Trace protocol events";
             }
             enum "process" {
               description "Trace process internals";
             }
             enum "startup" {
               description "Trace ANCP startup events/flow";
             }
             enum "session" {
               description "Trace connection events/sessions";
             }
             enum "general" {
               description "Trace general flow";
             }
             enum "restart" {
               description "Trace process restart flow";
             }
             enum "subscriber" {
               description "Trace subscriber events";
             }
             enum "timer" {
               description "Trace timer processing";
             }
             enum "all" {
               description "Trace everything";
             }
           }
         }
         leaf disable {
           description "Disable this trace flag";
           type empty;
         }
       }
     }
     container qos-adjust {
       presence "enable qos-adjust";
       description "Enable QoS adjust for interfaces and interface-sets";
       uses apply-advanced;
       leaf sdsl-bytes {
         description "Set SDSL byte adjust value";
         status deprecated;
         default "0";
         units "bytes";
         type union {
           type string {
             pattern "<.*>|$.*";
           }
           type int32 {
             range "-100 .. 100";
           }
         }
       }
       leaf sdsl-overhead-adjust {
         description "Set SDSL overhead adjusted";
         status deprecated;
         default "100";
         units "percent";
         type union {
           type string {
             pattern "<.*>|$.*";
           }
           type uint32 {
             range "80 .. 100";
           }
         }
       }
       leaf vdsl-bytes {
         description "Set VDSL byte adjust value";
         status deprecated;
         default "0";
         units "bytes";
         type union {
           type string {
             pattern "<.*>|$.*";
           }
           type int32 {
             range "-100 .. 100";
           }
         }
       }
       leaf vdsl-overhead-adjust {
         description "Set VDSL overhead adjusted";
         status deprecated;
         default "100";
         units "percent";
         type union {
           type string {
             pattern "<.*>|$.*";
           }
           type uint32 {
             range "80 .. 100";
           }
         }
       }
       leaf vdsl2-bytes {
         description "Set VDSL2 byte adjust value";
         status deprecated;
         default "0";
         units "bytes";
         type union {
           type string {
             pattern "<.*>|$.*";
           }
           type int32 {
             range "-100 .. 100";
           }
         }
       }
       leaf vdsl2-overhead-adjust {
         description "Set VDSL2 overhead adjusted";
         status deprecated;
         default "100";
         units "percent";
         type union {
           type string {
             pattern "<.*>|$.*";
           }
           type uint32 {
             range "80 .. 100";
           }
         }
       }
       leaf adsl-bytes {
         description "Set ADSL byte adjust value";
         status deprecated;
         default "0";
         units "bytes";
         type union {
           type string {
             pattern "<.*>|$.*";
           }
           type int32 {
             range "-100 .. 100";
           }
         }
       }
       leaf adsl2-bytes {
         description "Set ADSL2 byte adjust value";
         status deprecated;
         default "0";
         units "bytes";
         type union {
           type string {
             pattern "<.*>|$.*";
           }
           type int32 {
             range "-100 .. 100";
           }
         }
       }
       leaf adsl2-plus-bytes {
         description "Set ADSL-PLUS byte adjust value";
         status deprecated;
         default "0";
         units "bytes";
         type union {
           type string {
             pattern "<.*>|$.*";
           }
           type int32 {
             range "-100 .. 100";
           }
         }
       }
       leaf other-bytes {
         description "Set OTHER byte adjust value";
         status deprecated;
         default "0";
         units "bytes";
         type union {
           type string {
             pattern "<.*>|$.*";
           }
           type int32 {
             range "-100 .. 100";
           }
         }
       }
       leaf other-overhead-adjust {
         description "Set OTHER overhead adjusted";
         status deprecated;
         default "100";
         units "percent";
         type union {
           type string {
             pattern "<.*>|$.*";
           }
           type uint32 {
             range "80 .. 100";
           }
         }
       }
     }
     leaf pre-ietf-mode {
       description "Enable backward compatibility mode";
       type empty;
     }
     leaf maximum-discovery-table-entries {
       description "Maximum number of discovery table entries per neighbor";
       type union {
         type string {
           pattern "<.*>|$.*";
         }
         type uint32 {
           range "1 .. 100000";
         }
       }
     }
     leaf adjacency-timer {
       description "Set adjacency timer in seconds";
       type union {
         type string {
           pattern "<.*>|$.*";
         }
         type uint32 {
           range "1 .. 25";
         }
       }
     }
     leaf maximum-helper-restart-time {
       description "Set maximum helper restart timer";
       units "seconds";
       type union {
         type string {
           pattern "<.*>|$.*";
         }
         type uint32 {
           range "45 .. 600";
         }
       }
     }
     leaf qos-adjust-adsl {
       description "Set ADSL QoS adjustment factor";
       status deprecated;
       default "100";
       units "percent";
       type union {
         type string {
           pattern "<.*>|$.*";
         }
         type uint32 {
           range "0 .. 100";
         }
       }
     }
     leaf qos-adjust-adsl2 {
       description "Set ADSL2 QoS adjustment factor";
       status deprecated;
       default "100";
       units "percent";
       type union {
         type string {
           pattern "<.*>|$.*";
         }
         type uint32 {
           range "0 .. 100";
         }
       }
     }
     leaf qos-adjust-adsl2-plus {
       description "Set ADSL2+ QoS adjustment factor";
       status deprecated;
       default "100";
       units "percent";
       type union {
         type string {
           pattern "<.*>|$.*";
         }
         type uint32 {
           range "0 .. 100";
         }
       }
     }
     leaf qos-adjust-vdsl {
       description "Set VDSL QoS adjustment factor";
       status deprecated;
       default "100";
       units "percent";
       type union {
         type string {
           pattern "<.*>|$.*";
         }
         type uint32 {
           range "0 .. 100";
         }
       }
     }
     leaf qos-adjust-vdsl2 {
       description "Set VDSL2 QoS adjustment factor";
       status deprecated;
       default "100";
       units "percent";
       type union {
         type string {
           pattern "<.*>|$.*";
         }
         type uint32 {
           range "0 .. 100";
         }
       }
     }
     leaf qos-adjust-sdsl {
       description "Set SDSL QoS adjustment factor";
       status deprecated;
       default "100";
       units "percent";
       type union {
         type string {
           pattern "<.*>|$.*";
         }
         type uint32 {
           range "0 .. 100";
         }
       }
     }
     leaf qos-adjust-other {
       description "Set OTHER QoS adjustment factor";
       status deprecated;
       default "100";
       units "percent";
       type union {
         type string {
           pattern "<.*>|$.*";
         }
         type uint32 {
           range "0 .. 100";
         }
       }
     }
     leaf gsmp-syn-wait {
       description "Enable partition ID learning";
       type empty;
     }
     leaf gsmp-syn-timeout {
       description "Set partition ID learning timeout";
       default "30";
       units "seconds";
       type union {
         type string {
           pattern "<.*>|$.*";
         }
         type uint32 {
           range "1 .. 60";
         }
       }
     }
     leaf adjacency-loss-hold-time {
       description "Audit duration upon adjacency loss";
       default "0";
       units "seconds";
       type union {
         type string {
           pattern "<.*>|$.*";
         }
         type uint32 {
           range "0 .. 1800";
         }
       }
     }
     container interfaces {
       description "ANCP interface config options";
       uses apply-advanced;
       list interface-set {
         key name;
         description "ANCP interface-set specific options";
         leaf name {
           description "Name of the interface set";
           type string {
             junos:posix-pattern "^.{1,64}$";
             junos:pattern-message "Must be string of 64 characters or less";
           }
         }
         uses apply-advanced;
         leaf access-identifier {
           description "Subscriber specific access identifier information";
           type string {
             junos:posix-pattern "^.{1,64}$";
             junos:pattern-message "Must be string of 64 characters or less";
           }
         }
         leaf neighbor {
           description "Neighbor IP address";
           status deprecated;
           type jt:ipaddr;
         }
       }
       list interface {
         key name;
         uses ancp_interfaces_type;
       }
     }
     list neighbor {
       key name;
       description "ANCP neighbor config options";
       leaf name {
         description "IP address of neighbor";
         type jt:ipaddr;
       }
       uses apply-advanced;
       leaf discovery-mode {
         description "Enable topology discovery";
         status deprecated;
         type empty;
       }
       choice ietf-mode-option {
         case case_1 {
           leaf pre-ietf-mode {
             description "Enable backward compatibility mode";
             type empty;
           }
         }
         case case_2 {
           leaf ietf-mode {
             description "Enable IETF mode";
             type empty;
           }
         }
       }
       leaf adjacency-timer {
         description "Set adjacency timer in seconds";
         type union {
           type string {
             pattern "<.*>|$.*";
           }
           type uint32 {
             range "1 .. 25";
           }
         }
       }
       leaf maximum-discovery-table-entries {
         description "Maximum number of discovery table entries";
         type union {
           type string {
             pattern "<.*>|$.*";
           }
           type uint32 {
             range "1 .. 100000";
           }
         }
       }
       container auto-configure-trigger {
         presence "enable auto-configure-trigger";
         description "Auto-configure trigger support";
         uses apply-advanced;
         leaf interface {
           junos:must "(\"interfaces $$\")";
           junos:must-message "Interface must be defined";
           type union {
             type jt:interface-device;
             type string {
               pattern "<.*>|$.*";
             }
           }
         }
       }
       leaf adjacency-loss-hold-time {
         description "Audit duration upon adjacency loss";
         units "seconds";
         type union {
           type string {
             pattern "<.*>|$.*";
           }
           type uint32 {
             range "0 .. 1800";
           }
         }
       }
     }
   }
   grouping ancp_interfaces_type {
     description "Physical interface";
     leaf name {
       junos:must "(\"interfaces $$\")";
       junos:must-message "Interface must be defined";
       type union {
         type jt:interface-name;
         type string {
           pattern "<.*>|$.*";
         }
       }
     }
     uses apply-advanced;
     leaf access-identifier {
       description "Subscriber specific access identifier information";
       type string {
         junos:posix-pattern "^.{1,64}$";
         junos:pattern-message "Must be string of 64 characters or less";
       }
     }
     leaf neighbor {
       description "Neighbor IP address";
       status deprecated;
       type jt:ipaddr;
     }
     leaf overhead-accounting {
       description "Enable overhead accounting on per ACI basis";
       status deprecated;
       type empty;
     }
   }
   grouping juniper-protocols-bgp {
     uses apply-advanced;
     container path-selection {
       description "Configure path selection strategy";
       uses apply-advanced;
       leaf l2vpn-use-bgp-rules {
         description "Use standard BGP rules during L2VPN path selection";
         type empty;
       }
       leaf cisco-non-deterministic {
         description "Use Cisco IOS nondeterministic path selection algorithm";
         type empty;
       }
       leaf always-compare-med {
         description "Always compare MED values, regardless of neighbor AS";
         type empty;
       }
       container med-plus-igp {
         presence "enable med-plus-igp";
         description "Add IGP cost to next-hop to MED before comparing MED values";
         uses apply-advanced;
         leaf med-multiplier {
           description "Multiplier for MED";
           default "1";
           type union {
             type string {
               pattern "<.*>|$.*";
             }
             type uint16 {
               range "1 .. 1000";
             }
           }
         }
         leaf igp-multiplier {
           description "Multiplier for IGP cost to next-hop";
           default "1";
           type union {
             type string {
               pattern "<.*>|$.*";
             }
             type uint16 {
               range "1 .. 1000";
             }
           }
         }
       }
       leaf external-router-id {
         description "Compare router ID on BGP externals";
         type empty;
       }
       leaf as-path-ignore {
         description "Ignore AS path comparison during path selection";
         junos:must "(!(\".. .. .. .. routing-options multipath as-path-compare\"))";
         junos:must-message "Configuring 'as-path-ignore' is not allowed when 'as-path-compare' is enabled for this routing instance";
         type empty;
       }
     }
     container accept-prpd-connection {
       presence "enable accept-prpd-connection";
       description "Enable BGP to accept PRPD connections";
     }
     leaf advertise-from-main-vpn-tables {
       description "Advertise VPN routes from bgp.Xvpn.0 tables in master instance";
       type empty;
     }
     leaf stale-labels-holddown-period {
       description "Duration (sec) MPLS labels allocated by BGP are kept after they go stale";
       type union {
         type string {
           pattern "<.*>|$.*";
         }
         type int32 {
           range "1 .. 600";
         }
       }
     }
     leaf holddown-all-stale-labels {
       description "Hold all BGP stale-labels, facilating make-before-break for new label advertisements";
       type empty;
     }
     container egress-te-backup-paths {
       description "Backup-path for Egress-TE peer interface failure";
       uses apply-advanced;
       list template {
         key name;
         description "Backup-path template";
         leaf name {
           description "Name of Egress-TE backup path";
           type string {
             junos:posix-pattern "^.{1,64}$";
             junos:pattern-message "Must be a string of 64 characters or less";
           }
         }
         uses apply-advanced;
         list peer {
           key name;
           ordered-by user;
           description "Egress peer TE backup exit path";
           leaf name {
             description "Address of BGP peer to use as backup next-hop";
             type jt:ipaddr;
           }
           uses apply-advanced;
         }
         container remote-nexthop {
           description "Resolve and use tunnel to this next-hop as backup path";
           uses apply-advanced;
           leaf remote-nh-addr {
             description "Address of remote-nexthop to use as backup path";
             type jt:ipaddr;
           }
         }
         container ip-forward {
           presence "enable ip-forward";
           junos:must "(!(\".. remote-nexthop\"))";
           junos:must-message "'ip-forward' will not take effect as backup when 'remote-nexthop' is in use";
           description "Use IP-forward backup path for Egress TE";
           uses apply-advanced;
           leaf rti-name {
             description "Routing-instance to use as IP forward backup-path";
             type string {
               junos:posix-pattern "!^((__.*__)|(all)|(.*[ ].*)|(\"\")|(.{129,}))$";
               junos:pattern-message "Must be a non-reserved string of 128 characters or less with no spaces.";
             }
           }
         }
       }
     }
     leaf sr-preference-override {
       description "Replace received segment routing traffic engineering preference value with override value";
       type union {
         type uint32;
         type string {
           pattern "<.*>|$.*";
         }
       }
     }
     leaf vpn-apply-export {
       description "Apply BGP export policy when exporting VPN routes";
       type empty;
     }
     container family {
       description "Protocol family for NLRIs in updates";
       uses apply-advanced;
       container inet {
         description "IPv4 NLRI parameters";
         uses apply-advanced;
         container labeled-unicast {
           description "Include labeled unicast NLRI";
           presence "enable labeled-unicast";
           uses bgp-afi-labeled;
         }
         container segment-routing-te {
           description "Include segment-routing TE policy";
           presence "enable segment-routing-te";
           uses bgp-afi-srte;
         }
         container transport {
           description "Include Classful Transport NLRI";
           presence "enable transport";
           uses bgp-afi-inet-transport;
         }
         container unicast {
           description "Include unicast NLRI";
           presence "enable unicast";
           uses bgp-afi-topo;
         }
         container multicast {
           description "Include multicast NLRI";
           presence "enable multicast";
           uses bgp-afi-default;
         }
         container flow {
           description "Include flow NLRI";
           presence "enable flow";
           uses bgp-afi-flow-with-redirect-ip-action;
         }
         container any {
           description "Include unicast or multicast NLRI";
           presence "enable any";
           uses bgp-afi-default;
         }
       }
       container inet-vpn {
         description "IPv4 Layer 3 VPN NLRI parameters";
         uses apply-advanced;
         container unicast {
           description "Include unicast NLRI";
           presence "enable unicast";
           uses bgp-afi-l3vpn;
         }
         container multicast {
           description "Include multicast NLRI";
           presence "enable multicast";
           uses bgp-afi-vpn;
         }
         container flow {
           description "Include flow VPN NLRI";
           presence "enable flow";
           uses bgp-afi-flow-with-redirect-ip-action;
         }
         container any {
           description "Include unicast or multicast NLRI";
           presence "enable any";
           uses bgp-afi-vpn;
         }
       }
       container inet6 {
         description "IPv6 NLRI parameters";
         uses apply-advanced;
         container labeled-unicast {
           description "Include labeled unicast NLRI";
           presence "enable labeled-unicast";
           uses bgp-afi-inet6-labeled;
         }
         container segment-routing-te {
           description "Include segment-routing TE policy";
           presence "enable segment-routing-te";
           uses bgp-afi-srte;
         }
         container transport {
           description "Include Classful Transport NLRI";
           presence "enable transport";
           uses bgp-afi-inet6-transport;
         }
         container unicast {
           description "Include unicast NLRI";
           presence "enable unicast";
           uses bgp-afi-topo;
         }
         container multicast {
           description "Include multicast NLRI";
           presence "enable multicast";
           uses bgp-afi-default;
         }
         container flow {
           description "Include flow NLRI";
           presence "enable flow";
           uses bgp-afi-flow;
         }
         container any {
           description "Include unicast or multicast NLRI";
           presence "enable any";
           uses bgp-afi-default;
         }
       }
       container inet6-vpn {
         description "IPv6 Layer 3 VPN NLRI parameters";
         uses apply-advanced;
         container unicast {
           description "Include unicast NLRI";
           presence "enable unicast";
           uses bgp-afi-l3vpn;
         }
         container multicast {
           description "Include multicast NLRI";
           presence "enable multicast";
           uses bgp-afi-vpn;
         }
         container flow {
           description "Include flow VPN NLRI";
           presence "enable flow";
           uses bgp-afi-flow;
         }
         container any {
           description "Include unicast or multicast NLRI";
           presence "enable any";
           uses bgp-afi-vpn;
         }
       }
       container iso-vpn {
         description "ISO Layer 3 VPN NLRI parameters";
         uses apply-advanced;
         container unicast {
           description "Include unicast NLRI";
           presence "enable unicast";
           uses bgp-afi-vpn-protection;
         }
       }
       container l2vpn {
         description "MPLS-based Layer 2 VPN and VPLS NLRI parameters";
         uses apply-advanced;
         container auto-discovery-only {
           description "Include auto-discovery NLRI for LDP Layer 2 VPN and VPLS";
           presence "enable auto-discovery-only";
           uses bgp-afi-default;
         }
         container auto-discovery-mspw {
           description "Include auto-discovery NLRI for LDP Signalled MultiSegment PW";
           presence "enable auto-discovery-mspw";
           uses bgp-afi-default;
         }
         container signaling {
           description "Include Layer 2 VPN and VPLS signaling NLRI";
           presence "enable signaling";
           uses bgp-afi-l2vpn;
         }
       }
       container evpn {
         description "EVPN NLRI parameters";
         uses apply-advanced;
         container signaling {
           description "Include EVPN signaling NLRI";
           presence "enable signaling";
           uses bgp-afi-default;
         }
       }
       container inet-mvpn {
         description "IPv4 MVPN NLRI parameters";
         uses apply-advanced;
         container signaling {
           description "Include IPv4 multicast VPN signaling NLRI";
           presence "enable signaling";
           uses bgp-afi-default;
         }
       }
       container inet6-mvpn {
         description "IPv6 MVPN NLRI parameters";
         uses apply-advanced;
         container signaling {
           description "Include IPv6 multicast VPN signaling NLRI";
           presence "enable signaling";
           uses bgp-afi-default;
         }
       }
       container inet-mdt {
         description "IPv4 Multicast Distribution Tree (MDT) NLRI parameters";
         uses apply-advanced;
         container signaling {
           description "Include IPv4 multicast VPN auto-discovery NLRI";
           presence "enable signaling";
           uses bgp-afi-default;
         }
       }
       container traffic-engineering {
         description "Traffic Engineering (BGP-TE) NLRI parameters";
         uses apply-advanced;
         container unicast {
           description "Include BGP-TE NLRI";
           presence "enable unicast";
           uses bgp-afi-default;
         }
       }
       container route-target {
         presence "enable route-target";
         description "Route target NLRI used for VPN route filtering";
         uses apply-advanced;
         container prefix-limit {
           description "Limit maximum number of prefixes from a peer";
           uses bgpaf-prefix-limit;
         }
         container accepted-prefix-limit {
           description "Limit maximum number of prefixes accepted from a peer";
           uses bgpaf-accepted-prefix-limit;
         }
         container proxy-generate {
           presence "enable proxy-generate";
           description "Generate route target NLRI for peers that don't support it";
           uses apply-advanced;
           leaf-list route-target-policy {
             ordered-by user;
             description "Limit VPN routes that are used to generate proxy route-target filters";
             type jt:policy-algebra;
           }
         }
         leaf external-paths {
           description "Number of external paths accepted for route filtering";
           type union {
             type string {
               pattern "<.*>|$.*";
             }
             type uint32 {
               range "1 .. 256";
             }
           }
         }
         leaf advertise-default {
           description "Advertise default and suppress more specific routes";
           type empty;
         }
         leaf damping {
           description "Enable route flap damping";
           type empty;
         }
         container graceful-restart {
           description "BGP graceful restart options";
           uses bgp-af-gr;
         }
         leaf local-ipv4-address {
           description "Local IPv4 address";
           type jt:ipv4addr;
         }
         container output-queue-priority {
           description "Default output-queue to assign updates to";
           uses bgp-output-queue-priority-class;
         }
         container route-refresh-priority {
           description "Default output-queue to assign route refreshes to";
           uses bgp-output-queue-priority-class;
         }
         container withdraw-priority {
           description "Default output-queue to assign withdrawn routes to";
           uses bgp-output-queue-priority-class;
         }
       }
       container inet-bgpmcast {
         description "IPv4 BGPMCAST NLRI parameters";
         uses apply-advanced;
         container signaling {
           description "Include IPv4 BGP multicast signaling NLRI";
           presence "enable signaling";
           uses bgp-afi-default;
         }
       }
       container inet6-bgpmcast {
         description "IPv6 BGPMCAST NLRI parameters";
         uses apply-advanced;
         container signaling {
           description "Include IPv6 BGP multicast signaling NLRI";
           presence "enable signaling";
           uses bgp-afi-default;
         }
       }
     }
     container egress-te {
       presence "enable egress-te";
       description "Use Egress Peering traffic engineering";
       uses apply-advanced;
       leaf install-address {
         description "Address to use in egress-te created inet route";
         type jt:ipaddr;
       }
       container rib {
         description "Select primary table for Egress-TE routes";
         uses apply-advanced;
         leaf inet.0 {
           description "Install Egress-TE routes in inet.0";
           type empty;
         }
         leaf inet6.0 {
           description "Install Egress-TE routes in inet6.0";
           type empty;
         }
       }
       leaf no-install {
         description "Avoid installation to FIB or resolving over";
         type empty;
       }
       leaf-list import {
         ordered-by user;
         description "Import policy to set attributes";
         type jt:policy-algebra;
       }
       leaf backup-path {
         description "The 'egress-te-backup-paths template' to use for this peer";
         junos:must "(\"protocols bgp egress-te-backup-paths template $$\")";
         junos:must-message "bgp egress-te-backup-paths template not configured";
         type string {
           junos:posix-pattern "^.{1,64}$";
           junos:pattern-message "Must be a string of 64 characters or less";
         }
       }
     }
     leaf advertise-prefix-sid {
       description "Advertise prefix sid to E-BGP peers";
       type empty;
     }
     leaf accept-prefix-sid {
       description "Accept prefix sid from E-BGP peers";
       type empty;
     }
     leaf advertise-srgb {
       description "Advertise SRGB TLV";
       type empty;
     }
     leaf egress-te-sid-stats {
       description "Create BGP-Peer-SID sensor";
       type empty;
     }
     list egress-te-set-segment {
       key name;
       ordered-by user;
       description "Configure BGP-Peer-Set segment";
       leaf name {
         description "The BGP-Peer-Set segment name";
         type string {
           junos:posix-pattern "^.{1,64}$";
           junos:pattern-message "Must be a string of 64 characters or less";
         }
       }
       uses apply-advanced;
       container label {
         description "BGP-Peer-Set SID label from static label pool";
         uses apply-advanced;
         leaf label-value {
           description "BGP-Peer-Set SID label value from static label pool";
           type union {
             type string {
               pattern "<.*>|$.*";
             }
             type uint32 {
               range "16 .. 1048575";
             }
           }
         }
       }
       container egress-te-backup-segment {
         description "Backup segment for FRR";
         uses apply-advanced;
         container label {
           description "Backup segment label from static label pool";
           uses apply-advanced;
           leaf label-value {
             description "Backup segment label value from static label pool";
             type union {
               type string {
                 pattern "<.*>|$.*";
               }
               type uint32 {
                 range "16 .. 1048575";
               }
             }
           }
         }
       }
       container egress-te-backup-ip-forward {
         presence "enable egress-te-backup-ip-forward";
         description "Use IP-forward backup path for Egress TE";
         uses apply-advanced;
         leaf instance-name {
           description "Routing-instance to use as IP forward backup-path";
           type string {
             junos:posix-pattern "!^((__.*__)|(all)|(.*[ ].*)|(\"\")|(.{129,}))$";
             junos:pattern-message "Must be a non-reserved string of 128 characters or less with no spaces.";
           }
         }
       }
     }
     list group {
       key name;
       ordered-by user;
       description "Define a peer group";
       leaf name {
         description "Group name";
         type string;
       }
       uses apply-advanced;
       leaf type {
         description "Type of peer group";
         type enumeration {
           enum "internal" {
             description "IBGP group";
           }
           enum "external" {
             description "EBGP group";
           }
         }
       }
       leaf protocol {
         description "IGP to use to resolve the next hop";
         status deprecated;
         type enumeration {
           enum "rip" {
             description "Use RIP to resolve the BGP next hop";
             status deprecated;
           }
           enum "ospf" {
             description "Use OSPF to resolve the BGP next hop";
             status deprecated;
           }
           enum "isis" {
             description "Use IS-IS to resolve the BGP next hop";
             status deprecated;
           }
         }
       }
       container traceoptions {
         description "Trace options for BGP";
         uses apply-advanced;
         container file {
           description "Trace file options";
           leaf filename {
             description "Name of file in which to write trace information";
             type string {
               length "1 .. 1024";
               junos:posix-pattern "![/ %]";
               junos:pattern-message "Must not contain '/', % or a space";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "damping" {
                 description "Trace BGP damping information";
               }
               enum "packets" {
                 description "Trace all BGP protocol packets";
               }
               enum "open" {
                 description "Trace BGP open packets";
               }
               enum "update" {
                 description "Trace BGP update packets";
               }
               enum "keepalive" {
                 description "Trace BGP keepalive packets";
               }
               enum "refresh" {
                 description "Trace BGP refresh packets";
               }
               enum "nsr-synchronization" {
                 description "Trace NSR synchronization events";
               }
               enum "bfd" {
                 description "Trace BFD events";
               }
               enum "4byte-as" {
                 description "Trace 4 byte AS events";
               }
               enum "add-path" {
                 description "Trace add-path events";
               }
               enum "graceful-restart" {
                 description "Trace Graceful Restart events";
               }
               enum "egress-te" {
                 description "Egress Peering Traffic-Engineering events";
               }
               enum "thread-io" {
                 description "Trace threaded I/O processing";
               }
               enum "sharding" {
                 description "Trace BGP rib sharding";
               }
               enum "thread-update-io" {
                 description "Trace threaded update I/O processing";
               }
               enum "route-validation" {
                 description "Trace route validation";
               }
               enum "ipsec" {
                 description "Trace ipsec";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
           container filter {
             description "Filter to apply to this flag";
             presence "enable filter";
             uses bgp_filter_obj;
           }
         }
       }
       leaf description {
         description "Text description";
         type string {
           length "1 .. 255";
         }
       }
       container metric-out {
         description "Route metric sent in MED";
         choice metric_param {
           case case_1 {
             leaf metric-value {
               description "Metric value";
               type union {
                 type string {
                   pattern "<.*>|$.*";
                 }
                 type uint32 {
                   range "0 .. 4294967295";
                 }
               }
             }
           }
           case case_2 {
             container minimum-igp {
               presence "enable minimum-igp";
               description "Track the minimum IGP metric";
               leaf metric-offset {
                 description "Metric offset for MED";
                 type union {
                   type int32;
                   type string {
                     pattern "<.*>|$.*";
                   }
                 }
               }
             }
           }
           case case_3 {
             container igp {
               presence "enable igp";
               description "Track the IGP metric";
               leaf metric-offset {
                 description "Metric offset for MED";
                 type union {
                   type int32;
                   type string {
                     pattern "<.*>|$.*";
                   }
                 }
               }
               leaf delay-med-update {
                 description "Delay updating MED when IGP metric increases";
                 type empty;
               }
             }
           }
           case case_4 {
             container effective-aigp {
               presence "enable effective-aigp";
               description "Track the effective AIGP metric";
               leaf metric-offset {
                 description "Metric offset for MED";
                 type union {
                   type int32;
                   type string {
                     pattern "<.*>|$.*";
                   }
                 }
               }
             }
           }
           case case_5 {
             container minimum-effective-aigp {
               presence "enable minimum-effective-aigp";
               description "Track the minimum effective AIGP metric";
               leaf metric-offset {
                 description "Metric offset for MED";
                 type union {
                   type int32;
                   type string {
                     pattern "<.*>|$.*";
                   }
                 }
               }
             }
           }
         }
       }
       container multihop {
         presence "enable multihop";
         description "Configure an EBGP multihop session";
         uses apply-advanced;
         leaf ttl {
           description "TTL value for the session";
           type union {
             type string {
               pattern "<.*>|$.*";
             }
             type uint8 {
               range "1 .. 255";
             }
           }
         }
         leaf no-nexthop-change {
           description "Do not change next hop to self in advertisements";
           type empty;
         }
       }
       container ebgp-community-cleanup {
         presence "enable ebgp-community-cleanup";
         description "Community specific cleanup for eBGP peers";
         uses apply-advanced;
         leaf origin-validation {
           description "Origin Validation State receive behavior";
           type enumeration {
             enum "accept" {
               description "Accept Origin Validation State Community";
             }
             enum "reject" {
               description "Reject Origin Validation State Community";
             }
           }
         }
       }
       leaf route-server-client {
         description "Enable route server client behavior";
         type empty;
       }
       leaf accept-remote-nexthop {
         description "Allow import policy to specify a non-directly connected next-hop";
         type empty;
       }
       leaf preference {
         description "Preference value";
         type union {
           type uint32;
           type string {
             pattern "<.*>|$.*";
           }
         }
       }
       leaf local-preference {
         description "Value of LOCAL_PREF path attribute";
         type union {
           type uint32;
           type string {
             pattern "<.*>|$.*";
           }
         }
       }
       leaf local-address {
         description "Address of local end of BGP session";
         type jt:ipaddr;
       }
       leaf local-interface {
         description "Local interface for IPv6 link local EBGP peering";
         type union {
           type jt:interface-name;
           type string {
             pattern "<.*>|$.*";
           }
         }
       }
       leaf forwarding-context {
         description "Routing-instance used for data-forwarding and transport-session";
         type string {
           junos:posix-pattern "!^((__.*__)|(all)|(.*[ ].*)|(\"\")|(.{129,}))$";
           junos:pattern-message "Must be a non-reserved string of 128 characters or less with no spaces.";
         }
       }
       leaf hold-time {
         description "Hold time used when negotiating with a peer";
         type union {
           type string {
             pattern "<.*>|$.*";
           }
           type uint32 {
             range "0 .. 65535";
           }
         }
       }
       leaf minimum-hold-time {
         description "Minimum hold time accepted from the peer";
         type union {
           type string {
             pattern "<.*>|$.*";
           }
           type uint32 {
             range "3 .. 65535";
           }
         }
       }
       leaf passive {
         description "Do not send open messages to a peer";
         type empty;
       }
       leaf advertise-inactive {
         description "Advertise inactive routes";
         type empty;
       }
       choice advertise-peer-as-choice {
         leaf advertise-peer-as {
           description "Advertise routes received from the same autonomous system";
           type empty;
         }
         leaf no-advertise-peer-as {
           description "Don't advertise routes received from the same autonomous system";
           type empty;
         }
       }
       container advertise-external {
         presence "enable advertise-external";
         description "Advertise best external routes";
         leaf conditional {
           description "Route matches active route upto med-comparison rule";
           type empty;
         }
       }
       leaf keep {
         description "How to retain routes in the routing table";
         type enumeration {
           enum "all" {
             description "Retain all routes";
           }
           enum "none" {
             description "Retain no routes";
           }
         }
       }
       leaf rfc6514-compliant-safi129 {
         description "Compliant with RFC6514 SAFI129 format";
         type empty;
       }
       leaf no-aggregator-id {
         description "Set router ID in aggregator path attribute to 0";
         type empty;
       }
       leaf mtu-discovery {
         description "Enable TCP path MTU discovery";
         type empty;
       }
       leaf enforce-first-as {
         description "Enforce first AS in AS-path is the neighbor's AS";
         type empty;
       }
       leaf out-delay {
         description "How long before exporting routes from routing table";
         type union {
           type string {
             pattern "<.*>|$.*";
           }
           type uint32 {
             range "0 .. 65535";
           }
         }
       }
       leaf ttl {
         description "TTL value for the single-hop peer";
         junos:must "((!(\".. .. type internal\") && !(\".. multihop\")))";
         junos:must-message "This option is valid only for single-hop EBGP neighbor";
         type enumeration {
           enum "1" {
           }
           enum "255" {
           }
         }
       }
       leaf log-updown {
         description "Log a message for peer state transitions";
         type empty;
       }
       leaf damping {
         description "Enable route flap damping";
         type empty;
       }
       leaf-list import {
         ordered-by user;
         description "Import policy";
         type jt:policy-algebra;
       }
       leaf-list nlri {
         ordered-by user;
         description "NLRI type to include in updates";
         status deprecated;
         type enumeration {
           enum "unicast" {
             description "Include unicast NLRI";
             status deprecated;
           }
           enum "multicast" {
             description "Include multicast NLRI";
             status deprecated;
           }
           enum "any" {
             description "Include any kind of NLRI";
             status deprecated;
           }
         }
       }
       container bgp-error-tolerance {
         presence "enable bgp-error-tolerance";
         description "Handle BGP malformed updates softly";
         uses apply-advanced;
         leaf malformed-update-log-interval {
           description "Time used when logging malformed update";
           default "300";
           units "seconds";
           type union {
             type string {
               pattern "<.*>|$.*";
             }
             type uint32 {
               range "10 .. 65535";
             }
           }
         }
         choice malformed-routes-limit-choice {
           case case_1 {
             leaf malformed-route-limit {
               description "Maximum number of malformed routes from a peer";
               default "1000";
               type union {
                 type string {
                   pattern "<.*>|$.*";
                 }
                 type uint32 {
                   range "0 .. 4294967295";
                 }
               }
             }
           }
           case case_2 {
             leaf no-malformed-route-limit {
               description "No malformed route limit";
               type empty;
             }
           }
         }
       }
       container family {
         description "Protocol family for NLRIs in updates";
         uses apply-advanced;
         container inet {
           description "IPv4 NLRI parameters";
           uses apply-advanced;
           container labeled-unicast {
             description "Include labeled unicast NLRI";
             presence "enable labeled-unicast";
             uses bgp-afi-labeled;
           }
           container segment-routing-te {
             description "Include segment-routing TE policy";
             presence "enable segment-routing-te";
             uses bgp-afi-srte;
           }
           container transport {
             description "Include Classful Transport NLRI";
             presence "enable transport";
             uses bgp-afi-inet-transport;
           }
           container unicast {
             description "Include unicast NLRI";
             presence "enable unicast";
             uses bgp-afi-topo;
           }
           container multicast {
             description "Include multicast NLRI";
             presence "enable multicast";
             uses bgp-afi-default;
           }
           container flow {
             description "Include flow NLRI";
             presence "enable flow";
             uses bgp-afi-flow-with-redirect-ip-action;
           }
           container any {
             description "Include unicast or multicast NLRI";
             presence "enable any";
             uses bgp-afi-default;
           }
         }
         container inet-vpn {
           description "IPv4 Layer 3 VPN NLRI parameters";
           uses apply-advanced;
           container unicast {
             description "Include unicast NLRI";
             presence "enable unicast";
             uses bgp-afi-l3vpn;
           }
           container multicast {
             description "Include multicast NLRI";
             presence "enable multicast";
             uses bgp-afi-vpn;
           }
           container flow {
             description "Include flow VPN NLRI";
             presence "enable flow";
             uses bgp-afi-flow-with-redirect-ip-action;
           }
           container any {
             description "Include unicast or multicast NLRI";
             presence "enable any";
             uses bgp-afi-vpn;
           }
         }
         container inet6 {
           description "IPv6 NLRI parameters";
           uses apply-advanced;
           container labeled-unicast {
             description "Include labeled unicast NLRI";
             presence "enable labeled-unicast";
             uses bgp-afi-inet6-labeled;
           }
           container segment-routing-te {
             description "Include segment-routing TE policy";
             presence "enable segment-routing-te";
             uses bgp-afi-srte;
           }
           container transport {
             description "Include Classful Transport NLRI";
             presence "enable transport";
             uses bgp-afi-inet6-transport;
           }
           container unicast {
             description "Include unicast NLRI";
             presence "enable unicast";
             uses bgp-afi-topo;
           }
           container multicast {
             description "Include multicast NLRI";
             presence "enable multicast";
             uses bgp-afi-default;
           }
           container flow {
             description "Include flow NLRI";
             presence "enable flow";
             uses bgp-afi-flow;
           }
           container any {
             description "Include unicast or multicast NLRI";
             presence "enable any";
             uses bgp-afi-default;
           }
         }
         container inet6-vpn {
           description "IPv6 Layer 3 VPN NLRI parameters";
           uses apply-advanced;
           container unicast {
             description "Include unicast NLRI";
             presence "enable unicast";
             uses bgp-afi-l3vpn;
           }
           container multicast {
             description "Include multicast NLRI";
             presence "enable multicast";
             uses bgp-afi-vpn;
           }
           container flow {
             description "Include flow VPN NLRI";
             presence "enable flow";
             uses bgp-afi-flow;
           }
           container any {
             description "Include unicast or multicast NLRI";
             presence "enable any";
             uses bgp-afi-vpn;
           }
         }
         container iso-vpn {
           description "ISO Layer 3 VPN NLRI parameters";
           uses apply-advanced;
           container unicast {
             description "Include unicast NLRI";
             presence "enable unicast";
             uses bgp-afi-vpn-protection;
           }
         }
         container l2vpn {
           description "MPLS-based Layer 2 VPN and VPLS NLRI parameters";
           uses apply-advanced;
           container auto-discovery-only {
             description "Include auto-discovery NLRI for LDP Layer 2 VPN and VPLS";
             presence "enable auto-discovery-only";
             uses bgp-afi-default;
           }
           container auto-discovery-mspw {
             description "Include auto-discovery NLRI for LDP Signalled MultiSegment PW";
             presence "enable auto-discovery-mspw";
             uses bgp-afi-default;
           }
           container signaling {
             description "Include Layer 2 VPN and VPLS signaling NLRI";
             presence "enable signaling";
             uses bgp-afi-l2vpn;
           }
         }
         container evpn {
           description "EVPN NLRI parameters";
           uses apply-advanced;
           container signaling {
             description "Include EVPN signaling NLRI";
             presence "enable signaling";
             uses bgp-afi-default;
           }
         }
         container inet-mvpn {
           description "IPv4 MVPN NLRI parameters";
           uses apply-advanced;
           container signaling {
             description "Include IPv4 multicast VPN signaling NLRI";
             presence "enable signaling";
             uses bgp-afi-default;
           }
         }
         container inet6-mvpn {
           description "IPv6 MVPN NLRI parameters";
           uses apply-advanced;
           container signaling {
             description "Include IPv6 multicast VPN signaling NLRI";
             presence "enable signaling";
             uses bgp-afi-default;
           }
         }
         container inet-mdt {
           description "IPv4 Multicast Distribution Tree (MDT) NLRI parameters";
           uses apply-advanced;
           container signaling {
             description "Include IPv4 multicast VPN auto-discovery NLRI";
             presence "enable signaling";
             uses bgp-afi-default;
           }
         }
         container traffic-engineering {
           description "Traffic Engineering (BGP-TE) NLRI parameters";
           uses apply-advanced;
           container unicast {
             description "Include BGP-TE NLRI";
             presence "enable unicast";
             uses bgp-afi-default;
           }
         }
         container route-target {
           presence "enable route-target";
           description "Route target NLRI used for VPN route filtering";
           uses apply-advanced;
           container prefix-limit {
             description "Limit maximum number of prefixes from a peer";
             uses bgpaf-prefix-limit;
           }
           container accepted-prefix-limit {
             description "Limit maximum number of prefixes accepted from a peer";
             uses bgpaf-accepted-prefix-limit;
           }
           container proxy-generate {
             presence "enable proxy-generate";
             description "Generate route target NLRI for peers that don't support it";
             uses apply-advanced;
             leaf-list route-target-policy {
               ordered-by user;
               description "Limit VPN routes that are used to generate proxy route-target filters";
               type jt:policy-algebra;
             }
           }
           leaf external-paths {
             description "Number of external paths accepted for route filtering";
             type union {
               type string {
                 pattern "<.*>|$.*";
               }
               type uint32 {
                 range "1 .. 256";
               }
             }
           }
           leaf advertise-default {
             description "Advertise default and suppress more specific routes";
             type empty;
           }
           leaf damping {
             description "Enable route flap damping";
             type empty;
           }
           container graceful-restart {
             description "BGP graceful restart options";
             uses bgp-af-gr;
           }
           leaf local-ipv4-address {
             description "Local IPv4 address";
             type jt:ipv4addr;
           }
           container output-queue-priority {
             description "Default output-queue to assign updates to";
             uses bgp-output-queue-priority-class;
           }
           container route-refresh-priority {
             description "Default output-queue to assign route refreshes to";
             uses bgp-output-queue-priority-class;
           }
           container withdraw-priority {
             description "Default output-queue to assign withdrawn routes to";
             uses bgp-output-queue-priority-class;
           }
         }
         container inet-bgpmcast {
           description "IPv4 BGPMCAST NLRI parameters";
           uses apply-advanced;
           container signaling {
             description "Include IPv4 BGP multicast signaling NLRI";
             presence "enable signaling";
             uses bgp-afi-default;
           }
         }
         container inet6-bgpmcast {
           description "IPv6 BGPMCAST NLRI parameters";
           uses apply-advanced;
           container signaling {
             description "Include IPv6 BGP multicast signaling NLRI";
             presence "enable signaling";
             uses bgp-afi-default;
           }
         }
       }
       leaf authentication-key {
         description "MD5 authentication key";
         type string {
           length "1 .. 126";
         }
       }
       leaf authentication-algorithm {
         description "Authentication algorithm name";
         junos:must "(\".. authentication-key-chain\")";
         junos:must-message "May not be configured without authentication-key-chain";
         junos:must "(!(\".. authentication-key\"))";
         junos:must-message "May not be configured with authentication-key";
         type enumeration {
           enum "md5" {
             description "Message Digest 5";
           }
           enum "hmac-sha-1-96" {
             description "Hash-based Message Authentication Code (SHA1) (96 bits)";
           }
           enum "aes-128-cmac-96" {
             description "Cipher-based Message Authentication Code (AES128) (96 bits)";
           }
           enum "ao" {
             description "TCP Authentication Option";
           }
         }
       }
       leaf tcpao-auth-mismatch {
         description "Continue without TCP-AO if any one TCP endpoint does not have TCP-AO configured";
         junos:must "(!(\".. authentication-key\"))";
         junos:must-message "May not be configured with authentication-key";
         type enumeration {
           enum "allow-without-tcpao" {
             description "Allow the connection establishment without TCP-AO";
           }
         }
       }
       leaf authentication-key-chain {
         description "Key chain name";
         junos:must "(!(\".. authentication-key\"))";
         junos:must-message "May not be configured with authentication-key";
         junos:must "(\"security authentication-key-chains key-chain $$\")";
         junos:must-message "Referenced key-chain must be defined";
         type string {
           length "1 .. 128";
         }
       }
       leaf-list export {
         ordered-by user;
         description "Export policy";
         type jt:policy-algebra;
       }
       container remove-private {
         presence "enable remove-private";
         description "Remove well-known private AS numbers";
         uses apply-advanced;
         container all {
           presence "enable all";
           description "Remove all private AS numbers and do not stop at the first public AS number";
           container replace {
             presence "enable replace";
             description "Replace private AS numbers with the BGP Group's local AS number";
             leaf nearest {
               description "Use closest public AS number to replace a private AS number";
               type empty;
             }
           }
         }
         leaf no-peer-loop-check {
           description "Remove peer loop-check";
           type empty;
         }
       }
       leaf cluster {
         description "Cluster identifier";
         type jt:areaid;
       }
       leaf no-client-reflect {
         description "Disable intracluster route redistribution";
         type empty;
       }
       leaf peer-as {
         description " Autonomous system number in plain number or 'higher 16bits'.'Lower 16 bits' (asdot notation) format";
         type string {
           junos:posix-pattern "^[0-9]+(.[0-9]+)?$";
           junos:pattern-message "Use format 'x' or 'x.y' to specify number 'x' (Range 1 .. 4294967295) or number with higher 2 bytes 'x' (Range 0 .. 65535) and lower 2 bytes 'y' (Range 0 .. 65535) respectively";
         }
       }
       container local-as {
         description "Local autonomous system number";
         leaf as-number {
           description " Autonomous system number in plain number or 'higher 16bits'.'Lower 16 bits' (asdot notation) format";
           type string {
             junos:posix-pattern "^[0-9]+(.[0-9]+)?$";
             junos:pattern-message "Use format 'x' or 'x.y' to specify number 'x' (Range 1 .. 4294967295) or number with higher 2 bytes 'x' (Range 0 .. 65535) and lower 2 bytes 'y' (Range 0 .. 65535) respectively";
           }
         }
         leaf loops {
           description "Maximum number of times this AS can be in an AS path";
           type union {
             type string {
               pattern "<.*>|$.*";
             }
             type int32 {
               range "1 .. 10";
             }
           }
         }
         leaf private {
           description "Hide this local AS in paths learned from this peering";
           type empty;
         }
         leaf alias {
           description "Treat this AS as an alias to the system AS";
           type empty;
         }
         leaf no-prepend-global-as {
           description "Do not prepend global autonomous-system number in advertised paths";
           type empty;
         }
       }
       leaf ipsec-sa {
         description "IPSec SA name";
         junos:must "(\"security ipsec security-association $$\")";
         junos:must-message "Referenced IPSec Security Association must be defined";
         type string {
           length "1 .. 32";
         }
       }
       container graceful-shutdown {
         description "BGP peer graceful shutdown option";
         uses apply-advanced;
         container receiver {
           presence "enable receiver";
           description "BGP peer graceful-shutdown receiver";
           uses apply-advanced;
           leaf disable {
             description "Disable graceful-shutdown receiver";
             junos:must "(!(\".. .. sender\"))";
             junos:must-message "Receiver cannot be disabled on Sender";
             type empty;
           }
           leaf local-preference {
             description "Value of receiver LOCAL_PREF path attribute";
             type union {
               type uint32;
               type string {
                 pattern "<.*>|$.*";
               }
             }
           }
         }
         container sender {
           presence "enable sender";
           description "BGP peer graceful-shutdown sender";
           uses apply-advanced;
           leaf local-preference {
             description "Value of sender LOCAL_PREF path attribute";
             type union {
               type uint32;
               type string {
                 pattern "<.*>|$.*";
               }
             }
           }
         }
       }
       container shutdown {
         presence "enable shutdown";
         description "Shutdown";
         uses apply-advanced;
         leaf notify-message {
           description "Notification message";
           type string;
         }
       }
       leaf unconfigured-peer-graceful-restart {
         description "BGP unconfigured peer graceful restart options";
         junos:must "(\".. graceful-restart\")";
         junos:must-message "unconfigured-peer-graceful-restart is only valid with 'graceful-restart'";
         type empty;
       }
       container graceful-restart {
         presence "enable graceful-restart";
         description "BGP graceful restart options";
         uses apply-advanced;
         choice enable-disable {
           case case_1 {
             leaf disable {
               description "Disable graceful restart";
               type empty;
             }
           }
         }
         leaf restart-time {
           description "Restart time used when negotiating with a peer";
           junos:must "((\"routing-options graceful-restart\" || \"fabric routing-options graceful-restart\"))";
           junos:must-message "restart-time is only valid with 'routing-options graceful-restart'";
           type union {
             type string {
               pattern "<.*>|$.*";
             }
             type uint32 {
               range "1 .. 1800";
             }
           }
         }
         leaf stale-routes-time {
           description "Maximum time for which stale routes are kept";
           type union {
             type string {
               pattern "<.*>|$.*";
             }
             type uint32 {
               range "1 .. 1800";
             }
           }
         }
         container long-lived {
           description "Long-lived graceful restart options";
           uses apply-advanced;
           container receiver {
             description "Long-lived graceful restart receiver (helper) options";
             uses apply-advanced;
             choice enable-disable {
               case case_1 {
                 leaf disable {
                   description "Disable receiver (helper) functionality";
                   type empty;
                 }
               }
             }
           }
           container advertise-to-non-llgr-neighbor {
             presence "enable advertise-to-non-llgr-neighbor";
             description "Advertise stale routes to non-LLGR neighbors";
             uses apply-advanced;
             leaf omit-no-export {
               description "Do not attach no-export community to stale routes";
               type empty;
             }
           }
         }
         leaf disable-notification-extensions {
           description "Disable notification extensions";
           type empty;
         }
         leaf forwarding-state-bit {
           description "Control forwarding-state flag negotiation";
           type enumeration {
             enum "as-rr-client" {
               description "As for a route reflector client";
             }
             enum "from-fib" {
               description "Always use state of associated FIB(s)";
             }
           }
         }
         leaf dont-help-shared-fate-bfd-down {
           description "Honor BFD-Down(C=0) if GR-restart not in progress";
           type empty;
         }
       }
       leaf include-mp-next-hop {
         description "Include NEXT-HOP attribute in multiprotocol updates";
         type empty;
       }
       leaf disable-4byte-as {
         description "Disable 4 byte AS capability advertisement";
         type empty;
       }
       container idle-after-switch-over {
         description "Stop peer session from coming up after nonstop-routing switch-over";
         choice idle-interval {
           case case_1 {
             leaf forever {
               description "Idle the peer until the user intervenes";
               type empty;
             }
           }
           case case_2 {
             leaf timeout {
               description "Timeout value, in seconds, for starting peer after switch over";
               type union {
                 type string {
                   pattern "<.*>|$.*";
                 }
                 type uint32 {
                   range "1 .. 4294967295";
                 }
               }
             }
           }
         }
       }
       container outbound-route-filter {
         junos:must "(!(\"system processes routing bgp update-threading\"))";
         junos:must-message "Can't be configured together with update-threading";
         description "Dynamically negotiated cooperative route filtering";
         uses apply-advanced;
         leaf bgp-orf-cisco-mode {
           description "Using BGP ORF capability code 130 and Prefix ORF type 128";
           type empty;
         }
         container extended-community {
           description "Extended community filtering";
           status deprecated;
           uses apply-advanced;
           choice accept-choice {
             leaf accept {
               description "Honor remote requests for extended community ORF";
               type empty;
             }
             leaf no-accept {
               description "Don't honor remote requests for extended community ORF";
               type empty;
             }
           }
           leaf vrf-filter {
             description "Request remote filtering using locally configured VRF import targets";
             type empty;
           }
         }
         container prefix-based {
           presence "enable prefix-based";
           description "Prefix-based outbound route filtering";
           uses apply-advanced;
           container accept {
             presence "enable accept";
             description "Honor Prefix-based ORFs from remote peers";
             uses apply-advanced;
             leaf inet {
               description "Honor IPv4 prefix filters";
               type empty;
             }
             leaf inet6 {
               description "Honor IPv6 prefix filters";
               type empty;
             }
           }
         }
       }
       container message-batching {
         description "DEPRECATED - Batching of outgoing messages";
         status deprecated;
         uses apply-advanced;
         choice enable-disable {
           case case_1 {
             leaf enable {
               description "Enable parameter";
               type empty;
             }
           }
           case case_2 {
             leaf disable {
               description "Disable parameter";
               type empty;
             }
           }
         }
         leaf interval {
           description "DEPRECATED - Interval over which to batch messages";
           default "250";
           units "milliseconds";
           type union {
             type string {
               pattern "<.*>|$.*";
             }
             type uint32 {
               range "100 .. 1000";
             }
           }
         }
       }
       container multipath {
         presence "enable multipath";
         description "Allow load sharing among multiple BGP paths";
         uses apply-advanced;
         leaf disable {
           description "Disable Multipath";
           type empty;
         }
         leaf multiple-as {
           description "Use paths received from different ASs";
           type empty;
         }
         leaf allow-protection {
           description "Allow protection for multipath legs";
           type empty;
         }
         leaf pause-computation-during-churn {
           description "Pause multipath job to absorb churn";
           type empty;
         }
         leaf list-nexthop {
           description "Use List-NH for homogenous nexthop-set also";
           type empty;
         }
       }
       leaf tcp-mss {
         description "Maximum TCP segment size";
         type union {
           type string {
             pattern "<.*>|$.*";
           }
           type uint32 {
             range "1 .. 4096";
           }
         }
       }
       leaf bgp-identifier {
         description "BGP Identifier";
         type jt:ipv4addr;
       }
       leaf tcp-aggressive-transmission {
         description "Enable aggressive transmission of pure TCP ACKs and retransmissions";
         type empty;
       }
       container bmp {
         description "Specific settings to override the routing-options settings";
         uses apply-advanced;
         leaf monitor {
           description "Enable/Disable monitoring";
           type enumeration {
             enum "enable" {
               description "Enable monitoring of BGP peer(s)";
             }
             enum "disable" {
               description "Disable monitoring of BGP peer(s)";
             }
           }
         }
         container route-monitoring {
           description "Control route monitoring settings";
           uses apply-advanced;
           leaf none {
             description "Do not send route monitoring messages";
             junos:must "((!(\".. pre-policy\") && (!(\".. post-policy\") && !(\".. rib-out\"))))";
             junos:must-message "May not be configured with pre-policy or post-policy or rib-out";
             type empty;
           }
           container pre-policy {
             presence "enable pre-policy";
             description "Send pre-policy route monitoring messages";
             leaf exclude-non-feasible {
               description "Exclude looped routes, etc";
               type empty;
             }
           }
           container post-policy {
             presence "enable post-policy";
             description "Send post-policy route monitoring messages";
             leaf exclude-non-eligible {
               description "Exclude unresolved routes, etc.";
               type empty;
             }
           }
           container rib-out {
             presence "enable rib-out";
             junos:must "((!(\"system processes routing bgp update-threading\") || \"system processes routing bgp rib-sharding\"))";
             junos:must-message "Update threading can't be configured together with bmp rib-out monitoring";
             description "Send adj-ribs-out route monitoring messages";
             leaf pre-policy {
               description "Send pre-policy adj-ribs-out route monitoring messages";
               type empty;
             }
             leaf post-policy {
               description "Send post-policy adj-ribs-out route monitoring messages";
               type empty;
             }
           }
         }
       }
       container advertise-bgp-static {
         presence "enable advertise-bgp-static";
         description "Advertise bgp-static routes";
         uses apply-advanced;
         leaf-list policy {
           ordered-by user;
           description "Static route advertisement policy";
           type jt:policy-algebra;
         }
       }
       leaf add-path-display-ipv4-address {
         description "Display add-path path-id in IPv4 address format";
         type empty;
       }
       container bfd-liveness-detection {
         description "Bidirectional Forwarding Detection (BFD) options";
         uses apply-advanced;
         leaf version {
           description "BFD protocol version number";
           default "automatic";
           type enumeration {
             enum "0" {
               description "BFD version 0 (deprecated)";
             }
             enum "1" {
               description "BFD version 1";
             }
             enum "automatic" {
               description "Choose BFD version automatically";
             }
           }
         }
         leaf minimum-interval {
           description "Minimum transmit and receive interval";
           units "milliseconds";
           type union {
             type string {
               pattern "<.*>|$.*";
             }
             type uint32 {
               range "1 .. 255000";
             }
           }
         }
         leaf minimum-transmit-interval {
           description "Minimum transmit interval";
           status deprecated;
           units "milliseconds";
           type union {
             type string {
               pattern "<.*>|$.*";
             }
             type uint32 {
               range "1 .. 255000";
             }
           }
         }
         leaf minimum-receive-interval {
           description "Minimum receive interval";
           units "milliseconds";
           type union {
             type string {
               pattern "<.*>|$.*";
             }
             type uint32 {
               range "1 .. 255000";
             }
           }
         }
         leaf multiplier {
           description "Detection time multiplier";
           default "3";
           type union {
             type string {
               pattern "<.*>|$.*";
             }
             type uint32 {
               range "1 .. 255";
             }
           }
         }
         choice adaptation-choice {
           case case_1 {
             leaf no-adaptation {
               description "Disable adaptation";
               type empty;
             }
           }
         }
         container transmit-interval {
           description "Transmit-interval options";
           uses apply-advanced;
           leaf minimum-interval {
             description "Minimum transmit interval";
             units "milliseconds";
             type union {
               type string {
                 pattern "<.*>|$.*";
               }
               type uint32 {
                 range "1 .. 255000";
               }
             }
           }
           leaf threshold {
             description "High transmit interval triggering a trap";
             units "milliseconds";
             type union {
               type uint32;
               type string {
                 pattern "<.*>|$.*";
               }
             }
           }
         }
         container detection-time {
           description "Detection-time options";
           uses apply-advanced;
           leaf threshold {
             description "High detection-time triggering a trap";
             units "milliseconds";
             type union {
               type uint32;
               type string {
                 pattern "<.*>|$.*";
               }
             }
           }
         }
         container authentication {
           description "Authentication options";
           uses apply-advanced;
           leaf key-chain {
             description "Key chain name";
             junos:must "(\".. algorithm\")";
             junos:must-message "May not be configured without algorithm";
             junos:must "(\"security authentication-key-chains key-chain $$\")";
             junos:must-message "Referenced key-chain must be defined";
             type string;
           }
           leaf algorithm {
             description "Algorithm name";
             junos:must "(\".. key-chain\")";
             junos:must-message "May not be configured without key-chain";
             type enumeration {
               enum "simple-password" {
                 description "Simple password";
               }
               enum "keyed-md5" {
                 description "Keyed message Digest 5";
               }
               enum "meticulous-keyed-md5" {
                 description "Meticulous keyed message Digest 5";
               }
               enum "keyed-sha-1" {
                 description "Keyed secure hash algorithm (SHA1) ";
               }
               enum "meticulous-keyed-sha-1" {
                 description "Meticulous keyed secure hash algorithm (SHA1) ";
               }
             }
           }
           leaf loose-check {
             description "Verify authentication only if authentication is negotiated";
             type empty;
           }
         }
         leaf session-mode {
           description "BFD single-hop or multihop session-mode";
           default "automatic";
           type enumeration {
             enum "automatic" {
               description "Choose session-mode automatically";
             }
             enum "single-hop" {
               description "Use single-hop";
             }
             enum "multihop" {
               description "Use multihop";
             }
           }
         }
         leaf holddown-interval {
           description "Time to hold the session-UP notification to the client";
           units "milliseconds";
           junos:must "(!(\".. .. type internal\"))";
           junos:must-message "bfd holddown-interval is only valid for EBGP.";
           type union {
             type string {
               pattern "<.*>|$.*";
             }
             type uint32 {
               range "0 .. 255000";
             }
           }
         }
       }
       leaf as-override {
         description "Replace neighbor AS number with our AS number";
         type empty;
       }
       leaf-list allow {
         ordered-by user;
         description "Configure peer connections for specific networks";
         type jt:ipprefix;
       }
       list dynamic-neighbor {
         key name;
         ordered-by user;
         description "Configure peer options for specific networks";
         leaf name {
           description "Template name";
           junos:must "((\".. allow\" || \".. peer-auto-discovery\"))";
           junos:must-message "dynamic-neighbor must enable allow or peer-auto-discovery";
           type string;
         }
         uses apply-advanced;
         leaf-list allow {
           ordered-by user;
           description "Configure peer connections for specific networks";
           type jt:ipprefix;
         }
         leaf authentication-key {
           description "MD5 authentication key";
           type string {
             length "1 .. 126";
           }
         }
         leaf authentication-algorithm {
           description "Authentication algorithm name";
           junos:must "(\".. authentication-key-chain\")";
           junos:must-message "May not be configured without authentication-key-chain";
           junos:must "(!(\".. authentication-key\"))";
           junos:must-message "May not be configured with authentication-key";
           type enumeration {
             enum "md5" {
               description "Message Digest 5";
             }
             enum "hmac-sha-1-96" {
               description "Hash-based Message Authentication Code (SHA1) (96 bits)";
             }
             enum "aes-128-cmac-96" {
               description "Cipher-based Message Authentication Code (AES128) (96 bits)";
             }
             enum "ao" {
               description "TCP Authentication Option";
             }
           }
         }
         leaf tcpao-auth-mismatch {
           description "Continue without TCP-AO if any one TCP endpoint does not have TCP-AO configured";
           junos:must "(!(\".. authentication-key\"))";
           junos:must-message "May not be configured with authentication-key";
           type enumeration {
             enum "allow-without-tcpao" {
               description "Allow the connection establishment without TCP-AO";
             }
           }
         }
         leaf authentication-key-chain {
           description "Key chain name";
           junos:must "(!(\".. authentication-key\"))";
           junos:must-message "May not be configured with authentication-key";
           junos:must "(\"security authentication-key-chains key-chain $$\")";
           junos:must-message "Referenced key-chain must be defined";
           type string {
             length "1 .. 128";
           }
         }
         container peer-auto-discovery {
           junos:must "((!(\".. authentication-algorithm\") && (!(\".. .. authentication-algorithm\") && !(\".. .. .. authentication-algorithm\"))))";
           junos:must-message "Can't be configured along with authentication-algorithm";
           junos:must "((!(\".. authentication-key\") && (!(\".. .. authentication-key\") && !(\".. .. .. authentication-key\"))))";
           junos:must-message "Can't be configured along with authentication-key";
           junos:must "(!(\".. allow\"))";
           junos:must-message "peer-auto-discovery and allow cannot be configured in the same dynamic-neighbor";
           junos:must "((!(\".. .. type internal\") && !(\".. .. multihop\")))";
           junos:must-message "peer-auto-discovery is valid only for single-hop EBGP neighbor";
           description "Configure auto-discovery options for BGP neighbors";
           uses apply-advanced;
           container family {
             description "Address family based neighbor auto-discovery parameters";
             container inet6 {
               uses apply-advanced;
               choice auto-discovery-type {
                 case case_1 {
                   container ipv6-nd {
                     presence "enable ipv6-nd";
                     description "Use ipv6 neighbor discovery to learn neighbor address";
                   }
                 }
               }
             }
           }
           list interface {
             key name;
             leaf name {
               description "Configure interfaces over which to discover bgp neighbors";
               type union {
                 type jt:interface-name;
                 type string {
                   pattern "<.*>|$.*";
                 }
               }
             }
             uses apply-advanced;
             choice enable-disable {
               case case_1 {
                 leaf disable {
                   description "Disable peer discovery on interface";
                   type empty;
                 }
               }
             }
           }
         }
       }
       container optimal-route-reflection {
         junos:must "(\".. type internal\")";
         junos:must-message "Must be configured with type internal";
         description "Enable optimal route reflection for this client group";
         uses apply-advanced;
         leaf igp-primary {
           description "Primary node identifier for this client group";
           type jt:ipv4addr;
         }
         leaf igp-backup {
           description "Backup node identifier for this client group";
           type jt:ipv4addr;
         }
       }
       leaf peer-as-list {
         description "Configure list of peer autonomous systems for unconfigured neighbors";
         junos:must "((\".. allow\" || \".. dynamic-neighbor\"))";
         junos:must-message "May be configured only with allow or dynamic-neighbor";
         type string;
       }
       leaf mvpn-iana-rt-import {
         description "Use IANA assigned rt-import type value for MVPN";
         status deprecated;
         type empty;
       }
       list neighbor {
         key name;
         ordered-by user;
         description "Configure a neighbor";
         leaf name {
           type jt:ipaddr-scoped;
         }
         uses apply-advanced;
         container traceoptions {
           description "Trace options for BGP";
           uses apply-advanced;
           container file {
             description "Trace file options";
             leaf filename {
               description "Name of file in which to write trace information";
               type string {
                 length "1 .. 1024";
                 junos:posix-pattern "![/ %]";
                 junos:pattern-message "Must not contain '/', % or a space";
               }
             }
             leaf replace {
               description "Replace trace file rather than appending to it";
               status deprecated;
               type empty;
             }
             leaf size {
               description "Maximum trace file size";
               type string;
             }
             leaf files {
               description "Maximum number of trace files";
               default "10";
               type union {
                 type string {
                   pattern "<.*>|$.*";
                 }
                 type uint32 {
                   range "2 .. 1000";
                 }
               }
             }
             leaf no-stamp {
               description "Do not timestamp trace file";
               status deprecated;
               type empty;
             }
             choice world-readable-choice {
               leaf world-readable {
                 description "Allow any user to read the log file";
                 type empty;
               }
               leaf no-world-readable {
                 description "Don't allow any user to read the log file";
                 type empty;
               }
             }
           }
           list flag {
             key name;
             ordered-by user;
             description "Tracing parameters";
             leaf name {
               type enumeration {
                 enum "damping" {
                   description "Trace BGP damping information";
                 }
                 enum "packets" {
                   description "Trace all BGP protocol packets";
                 }
                 enum "open" {
                   description "Trace BGP open packets";
                 }
                 enum "update" {
                   description "Trace BGP update packets";
                 }
                 enum "keepalive" {
                   description "Trace BGP keepalive packets";
                 }
                 enum "refresh" {
                   description "Trace BGP refresh packets";
                 }
                 enum "nsr-synchronization" {
                   description "Trace NSR synchronization events";
                 }
                 enum "bfd" {
                   description "Trace BFD events";
                 }
                 enum "4byte-as" {
                   description "Trace 4 byte AS events";
                 }
                 enum "add-path" {
                   description "Trace add-path events";
                 }
                 enum "graceful-restart" {
                   description "Trace Graceful Restart events";
                 }
                 enum "egress-te" {
                   description "Egress Peering Traffic-Engineering events";
                 }
                 enum "thread-io" {
                   description "Trace threaded I/O processing";
                 }
                 enum "sharding" {
                   description "Trace BGP rib sharding";
                 }
                 enum "thread-update-io" {
                   description "Trace threaded update I/O processing";
                 }
                 enum "route-validation" {
                   description "Trace route validation";
                 }
                 enum "ipsec" {
                   description "Trace ipsec";
                 }
                 enum "route" {
                   description "Trace routing information";
                 }
                 enum "normal" {
                   description "Trace normal events";
                 }
                 enum "general" {
                   description "Trace general events";
                 }
                 enum "state" {
                   description "Trace state transitions";
                 }
                 enum "policy" {
                   description "Trace policy processing";
                 }
                 enum "task" {
                   description "Trace routing protocol task processing";
                 }
                 enum "timer" {
                   description "Trace routing protocol timer processing";
                 }
                 enum "all" {
                   description "Trace everything";
                 }
               }
             }
             leaf send {
               description "Trace transmitted packets";
               type empty;
             }
             leaf receive {
               description "Trace received packets";
               type empty;
             }
             leaf detail {
               description "Trace detailed information";
               type empty;
             }
             leaf disable {
               description "Disable this trace flag";
               type empty;
             }
             container filter {
               description "Filter to apply to this flag";
               presence "enable filter";
               uses bgp_filter_obj;
             }
           }
         }
         leaf description {
           description "Text description";
           type string {
             length "1 .. 255";
           }
         }
         container metric-out {
           description "Route metric sent in MED";
           choice metric_param {
             case case_1 {
               leaf metric-value {
                 description "Metric value";
                 type union {
                   type string {
                     pattern "<.*>|$.*";
                   }
                   type uint32 {
                     range "0 .. 4294967295";
                   }
                 }
               }
             }
             case case_2 {
               container minimum-igp {
                 presence "enable minimum-igp";
                 description "Track the minimum IGP metric";
                 leaf metric-offset {
                   description "Metric offset for MED";
                   type union {
                     type int32;
                     type string {
                       pattern "<.*>|$.*";
                     }
                   }
                 }
               }
             }
             case case_3 {
               container igp {
                 presence "enable igp";
                 description "Track the IGP metric";
                 leaf metric-offset {
                   description "Metric offset for MED";
                   type union {
                     type int32;
                     type string {
                       pattern "<.*>|$.*";
                     }
                   }
                 }
                 leaf delay-med-update {
                   description "Delay updating MED when IGP metric increases";
                   type empty;
                 }
               }
             }
             case case_4 {
               container effective-aigp {
                 presence "enable effective-aigp";
                 description "Track the effective AIGP metric";
                 leaf metric-offset {
                   description "Metric offset for MED";
                   type union {
                     type int32;
                     type string {
                       pattern "<.*>|$.*";
                     }
                   }
                 }
               }
             }
             case case_5 {
               container minimum-effective-aigp {
                 presence "enable minimum-effective-aigp";
                 description "Track the minimum effective AIGP metric";
                 leaf metric-offset {
                   description "Metric offset for MED";
                   type union {
                     type int32;
                     type string {
                       pattern "<.*>|$.*";
                     }
                   }
                 }
               }
             }
           }
         }
         container multihop {
           presence "enable multihop";
           description "Configure an EBGP multihop session";
           uses apply-advanced;
           leaf ttl {
             description "TTL value for the session";
             type union {
               type string {
                 pattern "<.*>|$.*";
               }
               type uint8 {
                 range "1 .. 255";
               }
             }
           }
           leaf no-nexthop-change {
             description "Do not change next hop to self in advertisements";
             type empty;
           }
         }
         container ebgp-community-cleanup {
           presence "enable ebgp-community-cleanup";
           description "Community specific cleanup for eBGP peers";
           uses apply-advanced;
           leaf origin-validation {
             description "Origin Validation State receive behavior";
             type enumeration {
               enum "accept" {
                 description "Accept Origin Validation State Community";
               }
               enum "reject" {
                 description "Reject Origin Validation State Community";
               }
             }
           }
         }
         leaf route-server-client {
           description "Enable route server client behavior";
           type empty;
         }
         leaf accept-remote-nexthop {
           description "Allow import policy to specify a non-directly connected next-hop";
           type empty;
         }
         leaf preference {
           description "Preference value";
           type union {
             type uint32;
             type string {
               pattern "<.*>|$.*";
             }
           }
         }
         leaf local-preference {
           description "Value of LOCAL_PREF path attribute";
           type union {
             type uint32;
             type string {
               pattern "<.*>|$.*";
             }
           }
         }
         leaf local-address {
           description "Address of local end of BGP session";
           type jt:ipaddr;
         }
         leaf local-interface {
           description "Local interface for IPv6 link local EBGP peering";
           type union {
             type jt:interface-name;
             type string {
               pattern "<.*>|$.*";
             }
           }
         }
         leaf forwarding-context {
           description "Routing-instance used for data-forwarding and transport-session";
           type string {
             junos:posix-pattern "!^((__.*__)|(all)|(.*[ ].*)|(\"\")|(.{129,}))$";
             junos:pattern-message "Must be a non-reserved string of 128 characters or less with no spaces.";
           }
         }
         leaf hold-time {
           description "Hold time used when negotiating with a peer";
           type union {
             type string {
               pattern "<.*>|$.*";
             }
             type uint32 {
               range "0 .. 65535";
             }
           }
         }
         leaf minimum-hold-time {
           description "Minimum hold time accepted from the peer";
           type union {
             type string {
               pattern "<.*>|$.*";
             }
             type uint32 {
               range "3 .. 65535";
             }
           }
         }
         leaf passive {
           description "Do not send open messages to a peer";
           type empty;
         }
         leaf advertise-inactive {
           description "Advertise inactive routes";
           type empty;
         }
         choice advertise-peer-as-choice {
           leaf advertise-peer-as {
             description "Advertise routes received from the same autonomous system";
             type empty;
           }
           leaf no-advertise-peer-as {
             description "Don't advertise routes received from the same autonomous system";
             type empty;
           }
         }
         container advertise-external {
           presence "enable advertise-external";
           description "Advertise best external routes";
           leaf conditional {
             description "Route matches active route upto med-comparison rule";
             type empty;
           }
         }
         leaf keep {
           description "How to retain routes in the routing table";
           type enumeration {
             enum "all" {
               description "Retain all routes";
             }
             enum "none" {
               description "Retain no routes";
             }
           }
         }
         leaf rfc6514-compliant-safi129 {
           description "Compliant with RFC6514 SAFI129 format";
           type empty;
         }
         leaf no-aggregator-id {
           description "Set router ID in aggregator path attribute to 0";
           type empty;
         }
         leaf mtu-discovery {
           description "Enable TCP path MTU discovery";
           type empty;
         }
         leaf enforce-first-as {
           description "Enforce first AS in AS-path is the neighbor's AS";
           type empty;
         }
         leaf out-delay {
           description "How long before exporting routes from routing table";
           type union {
             type string {
               pattern "<.*>|$.*";
             }
             type uint32 {
               range "0 .. 65535";
             }
           }
         }
         leaf ttl {
           description "TTL value for the single-hop peer";
           junos:must "((!(\".. .. type internal\") && !(\".. multihop\")))";
           junos:must-message "This option is valid only for single-hop EBGP neighbor";
           type enumeration {
             enum "1" {
             }
             enum "255" {
             }
           }
         }
         leaf log-updown {
           description "Log a message for peer state transitions";
           type empty;
         }
         leaf damping {
           description "Enable route flap damping";
           type empty;
         }
         leaf-list import {
           ordered-by user;
           description "Import policy";
           type jt:policy-algebra;
         }
         leaf-list nlri {
           ordered-by user;
           description "NLRI type to include in updates";
           status deprecated;
           type enumeration {
             enum "unicast" {
               description "Include unicast NLRI";
               status deprecated;
             }
             enum "multicast" {
               description "Include multicast NLRI";
               status deprecated;
             }
             enum "any" {
               description "Include any kind of NLRI";
               status deprecated;
             }
           }
         }
         container bgp-error-tolerance {
           presence "enable bgp-error-tolerance";
           description "Handle BGP malformed updates softly";
           uses apply-advanced;
           leaf malformed-update-log-interval {
             description "Time used when logging malformed update";
             default "300";
             units "seconds";
             type union {
               type string {
                 pattern "<.*>|$.*";
               }
               type uint32 {
                 range "10 .. 65535";
               }
             }
           }
           choice malformed-routes-limit-choice {
             case case_1 {
               leaf malformed-route-limit {
                 description "Maximum number of malformed routes from a peer";
                 default "1000";
                 type union {
                   type string {
                     pattern "<.*>|$.*";
                   }
                   type uint32 {
                     range "0 .. 4294967295";
                   }
                 }
               }
             }
             case case_2 {
               leaf no-malformed-route-limit {
                 description "No malformed route limit";
                 type empty;
               }
             }
           }
         }
         container family {
           description "Protocol family for NLRIs in updates";
           uses apply-advanced;
           container inet {
             description "IPv4 NLRI parameters";
             uses apply-advanced;
             container labeled-unicast {
               description "Include labeled unicast NLRI";
               presence "enable labeled-unicast";
               uses bgp-afi-labeled;
             }
             container segment-routing-te {
               description "Include segment-routing TE policy";
               presence "enable segment-routing-te";
               uses bgp-afi-srte;
             }
             container transport {
               description "Include Classful Transport NLRI";
               presence "enable transport";
               uses bgp-afi-inet-transport;
             }
             container unicast {
               description "Include unicast NLRI";
               presence "enable unicast";
               uses bgp-afi-topo;
             }
             container multicast {
               description "Include multicast NLRI";
               presence "enable multicast";
               uses bgp-afi-default;
             }
             container flow {
               description "Include flow NLRI";
               presence "enable flow";
               uses bgp-afi-flow-with-redirect-ip-action;
             }
             container any {
               description "Include unicast or multicast NLRI";
               presence "enable any";
               uses bgp-afi-default;
             }
           }
           container inet-vpn {
             description "IPv4 Layer 3 VPN NLRI parameters";
             uses apply-advanced;
             container unicast {
               description "Include unicast NLRI";
               presence "enable unicast";
               uses bgp-afi-l3vpn;
             }
             container multicast {
               description "Include multicast NLRI";
               presence "enable multicast";
               uses bgp-afi-vpn;
             }
             container flow {
               description "Include flow VPN NLRI";
               presence "enable flow";
               uses bgp-afi-flow-with-redirect-ip-action;
             }
             container any {
               description "Include unicast or multicast NLRI";
               presence "enable any";
               uses bgp-afi-vpn;
             }
           }
           container inet6 {
             description "IPv6 NLRI parameters";
             uses apply-advanced;
             container labeled-unicast {
               description "Include labeled unicast NLRI";
               presence "enable labeled-unicast";
               uses bgp-afi-inet6-labeled;
             }
             container segment-routing-te {
               description "Include segment-routing TE policy";
               presence "enable segment-routing-te";
               uses bgp-afi-srte;
             }
             container transport {
               description "Include Classful Transport NLRI";
               presence "enable transport";
               uses bgp-afi-inet6-transport;
             }
             container unicast {
               description "Include unicast NLRI";
               presence "enable unicast";
               uses bgp-afi-topo;
             }
             container multicast {
               description "Include multicast NLRI";
               presence "enable multicast";
               uses bgp-afi-default;
             }
             container flow {
               description "Include flow NLRI";
               presence "enable flow";
               uses bgp-afi-flow;
             }
             container any {
               description "Include unicast or multicast NLRI";
               presence "enable any";
               uses bgp-afi-default;
             }
           }
           container inet6-vpn {
             description "IPv6 Layer 3 VPN NLRI parameters";
             uses apply-advanced;
             container unicast {
               description "Include unicast NLRI";
               presence "enable unicast";
               uses bgp-afi-l3vpn;
             }
             container multicast {
               description "Include multicast NLRI";
               presence "enable multicast";
               uses bgp-afi-vpn;
             }
             container flow {
               description "Include flow VPN NLRI";
               presence "enable flow";
               uses bgp-afi-flow;
             }
             container any {
               description "Include unicast or multicast NLRI";
               presence "enable any";
               uses bgp-afi-vpn;
             }
           }
           container iso-vpn {
             description "ISO Layer 3 VPN NLRI parameters";
             uses apply-advanced;
             container unicast {
               description "Include unicast NLRI";
               presence "enable unicast";
               uses bgp-afi-vpn-protection;
             }
           }
           container l2vpn {
             description "MPLS-based Layer 2 VPN and VPLS NLRI parameters";
             uses apply-advanced;
             container auto-discovery-only {
               description "Include auto-discovery NLRI for LDP Layer 2 VPN and VPLS";
               presence "enable auto-discovery-only";
               uses bgp-afi-default;
             }
             container auto-discovery-mspw {
               description "Include auto-discovery NLRI for LDP Signalled MultiSegment PW";
               presence "enable auto-discovery-mspw";
               uses bgp-afi-default;
             }
             container signaling {
               description "Include Layer 2 VPN and VPLS signaling NLRI";
               presence "enable signaling";
               uses bgp-afi-l2vpn;
             }
           }
           container evpn {
             description "EVPN NLRI parameters";
             uses apply-advanced;
             container signaling {
               description "Include EVPN signaling NLRI";
               presence "enable signaling";
               uses bgp-afi-default;
             }
           }
           container inet-mvpn {
             description "IPv4 MVPN NLRI parameters";
             uses apply-advanced;
             container signaling {
               description "Include IPv4 multicast VPN signaling NLRI";
               presence "enable signaling";
               uses bgp-afi-default;
             }
           }
           container inet6-mvpn {
             description "IPv6 MVPN NLRI parameters";
             uses apply-advanced;
             container signaling {
               description "Include IPv6 multicast VPN signaling NLRI";
               presence "enable signaling";
               uses bgp-afi-default;
             }
           }
           container inet-mdt {
             description "IPv4 Multicast Distribution Tree (MDT) NLRI parameters";
             uses apply-advanced;
             container signaling {
               description "Include IPv4 multicast VPN auto-discovery NLRI";
               presence "enable signaling";
               uses bgp-afi-default;
             }
           }
           container traffic-engineering {
             description "Traffic Engineering (BGP-TE) NLRI parameters";
             uses apply-advanced;
             container unicast {
               description "Include BGP-TE NLRI";
               presence "enable unicast";
               uses bgp-afi-default;
             }
           }
           container route-target {
             presence "enable route-target";
             description "Route target NLRI used for VPN route filtering";
             uses apply-advanced;
             container prefix-limit {
               description "Limit maximum number of prefixes from a peer";
               uses bgpaf-prefix-limit;
             }
             container accepted-prefix-limit {
               description "Limit maximum number of prefixes accepted from a peer";
               uses bgpaf-accepted-prefix-limit;
             }
             container proxy-generate {
               presence "enable proxy-generate";
               description "Generate route target NLRI for peers that don't support it";
               uses apply-advanced;
               leaf-list route-target-policy {
                 ordered-by user;
                 description "Limit VPN routes that are used to generate proxy route-target filters";
                 type jt:policy-algebra;
               }
             }
             leaf external-paths {
               description "Number of external paths accepted for route filtering";
               type union {
                 type string {
                   pattern "<.*>|$.*";
                 }
                 type uint32 {
                   range "1 .. 256";
                 }
               }
             }
             leaf advertise-default {
               description "Advertise default and suppress more specific routes";
               type empty;
             }
             leaf damping {
               description "Enable route flap damping";
               type empty;
             }
             container graceful-restart {
               description "BGP graceful restart options";
               uses bgp-af-gr;
             }
             leaf local-ipv4-address {
               description "Local IPv4 address";
               type jt:ipv4addr;
             }
             container output-queue-priority {
               description "Default output-queue to assign updates to";
               uses bgp-output-queue-priority-class;
             }
             container route-refresh-priority {
               description "Default output-queue to assign route refreshes to";
               uses bgp-output-queue-priority-class;
             }
             container withdraw-priority {
               description "Default output-queue to assign withdrawn routes to";
               uses bgp-output-queue-priority-class;
             }
           }
           container inet-bgpmcast {
             description "IPv4 BGPMCAST NLRI parameters";
             uses apply-advanced;
             container signaling {
               description "Include IPv4 BGP multicast signaling NLRI";
               presence "enable signaling";
               uses bgp-afi-default;
             }
           }
           container inet6-bgpmcast {
             description "IPv6 BGPMCAST NLRI parameters";
             uses apply-advanced;
             container signaling {
               description "Include IPv6 BGP multicast signaling NLRI";
               presence "enable signaling";
               uses bgp-afi-default;
             }
           }
         }
         leaf authentication-key {
           description "MD5 authentication key";
           type string {
             length "1 .. 126";
           }
         }
         leaf authentication-algorithm {
           description "Authentication algorithm name";
           junos:must "(\".. authentication-key-chain\")";
           junos:must-message "May not be configured without authentication-key-chain";
           junos:must "(!(\".. authentication-key\"))";
           junos:must-message "May not be configured with authentication-key";
           type enumeration {
             enum "md5" {
               description "Message Digest 5";
             }
             enum "hmac-sha-1-96" {
               description "Hash-based Message Authentication Code (SHA1) (96 bits)";
             }
             enum "aes-128-cmac-96" {
               description "Cipher-based Message Authentication Code (AES128) (96 bits)";
             }
             enum "ao" {
               description "TCP Authentication Option";
             }
           }
         }
         leaf tcpao-auth-mismatch {
           description "Continue without TCP-AO if any one TCP endpoint does not have TCP-AO configured";
           junos:must "(!(\".. authentication-key\"))";
           junos:must-message "May not be configured with authentication-key";
           type enumeration {
             enum "allow-without-tcpao" {
               description "Allow the connection establishment without TCP-AO";
             }
           }
         }
         leaf authentication-key-chain {
           description "Key chain name";
           junos:must "(!(\".. authentication-key\"))";
           junos:must-message "May not be configured with authentication-key";
           junos:must "(\"security authentication-key-chains key-chain $$\")";
           junos:must-message "Referenced key-chain must be defined";
           type string {
             length "1 .. 128";
           }
         }
         leaf-list export {
           ordered-by user;
           description "Export policy";
           type jt:policy-algebra;
         }
         container remove-private {
           presence "enable remove-private";
           description "Remove well-known private AS numbers";
           uses apply-advanced;
           container all {
             presence "enable all";
             description "Remove all private AS numbers and do not stop at the first public AS number";
             container replace {
               presence "enable replace";
               description "Replace private AS numbers with the BGP Group's local AS number";
               leaf nearest {
                 description "Use closest public AS number to replace a private AS number";
                 type empty;
               }
             }
           }
           leaf no-peer-loop-check {
             description "Remove peer loop-check";
             type empty;
           }
         }
         leaf cluster {
           description "Cluster identifier";
           type jt:areaid;
         }
         leaf no-client-reflect {
           description "Disable intracluster route redistribution";
           type empty;
         }
         leaf peer-as {
           description " Autonomous system number in plain number or 'higher 16bits'.'Lower 16 bits' (asdot notation) format";
           type string {
             junos:posix-pattern "^[0-9]+(.[0-9]+)?$";
             junos:pattern-message "Use format 'x' or 'x.y' to specify number 'x' (Range 1 .. 4294967295) or number with higher 2 bytes 'x' (Range 0 .. 65535) and lower 2 bytes 'y' (Range 0 .. 65535) respectively";
           }
         }
         container local-as {
           description "Local autonomous system number";
           leaf as-number {
             description " Autonomous system number in plain number or 'higher 16bits'.'Lower 16 bits' (asdot notation) format";
             type string {
               junos:posix-pattern "^[0-9]+(.[0-9]+)?$";
               junos:pattern-message "Use format 'x' or 'x.y' to specify number 'x' (Range 1 .. 4294967295) or number with higher 2 bytes 'x' (Range 0 .. 65535) and lower 2 bytes 'y' (Range 0 .. 65535) respectively";
             }
           }
           leaf loops {
             description "Maximum number of times this AS can be in an AS path";
             type union {
               type string {
                 pattern "<.*>|$.*";
               }
               type int32 {
                 range "1 .. 10";
               }
             }
           }
           leaf private {
             description "Hide this local AS in paths learned from this peering";
             type empty;
           }
           leaf alias {
             description "Treat this AS as an alias to the system AS";
             type empty;
           }
           leaf no-prepend-global-as {
             description "Do not prepend global autonomous-system number in advertised paths";
             type empty;
           }
         }
         leaf ipsec-sa {
           description "IPSec SA name";
           junos:must "(\"security ipsec security-association $$\")";
           junos:must-message "Referenced IPSec Security Association must be defined";
           type string {
             length "1 .. 32";
           }
         }
         container graceful-shutdown {
           description "BGP peer graceful shutdown option";
           uses apply-advanced;
           container receiver {
             presence "enable receiver";
             description "BGP peer graceful-shutdown receiver";
             uses apply-advanced;
             leaf disable {
               description "Disable graceful-shutdown receiver";
               junos:must "(!(\".. .. sender\"))";
               junos:must-message "Receiver cannot be disabled on Sender";
               type empty;
             }
             leaf local-preference {
               description "Value of receiver LOCAL_PREF path attribute";
               type union {
                 type uint32;
                 type string {
                   pattern "<.*>|$.*";
                 }
               }
             }
           }
           container sender {
             presence "enable sender";
             description "BGP peer graceful-shutdown sender";
             uses apply-advanced;
             leaf local-preference {
               description "Value of sender LOCAL_PREF path attribute";
               type union {
                 type uint32;
                 type string {
                   pattern "<.*>|$.*";
                 }
               }
             }
           }
         }
         container shutdown {
           presence "enable shutdown";
           description "Shutdown";
           uses apply-advanced;
           leaf notify-message {
             description "Notification message";
             type string;
           }
         }
         leaf unconfigured-peer-graceful-restart {
           description "BGP unconfigured peer graceful restart options";
           junos:must "(\".. graceful-restart\")";
           junos:must-message "unconfigured-peer-graceful-restart is only valid with 'graceful-restart'";
           type empty;
         }
         container graceful-restart {
           presence "enable graceful-restart";
           description "BGP graceful restart options";
           uses apply-advanced;
           choice enable-disable {
             case case_1 {
               leaf disable {
                 description "Disable graceful restart";
                 type empty;
               }
             }
           }
           leaf restart-time {
             description "Restart time used when negotiating with a peer";
             junos:must "((\"routing-options graceful-restart\" || \"fabric routing-options graceful-restart\"))";
             junos:must-message "restart-time is only valid with 'routing-options graceful-restart'";
             type union {
               type string {
                 pattern "<.*>|$.*";
               }
               type uint32 {
                 range "1 .. 1800";
               }
             }
           }
           leaf stale-routes-time {
             description "Maximum time for which stale routes are kept";
             type union {
               type string {
                 pattern "<.*>|$.*";
               }
               type uint32 {
                 range "1 .. 1800";
               }
             }
           }
           container long-lived {
             description "Long-lived graceful restart options";
             uses apply-advanced;
             container receiver {
               description "Long-lived graceful restart receiver (helper) options";
               uses apply-advanced;
               choice enable-disable {
                 case case_1 {
                   leaf disable {
                     description "Disable receiver (helper) functionality";
                     type empty;
                   }
                 }
               }
             }
             container advertise-to-non-llgr-neighbor {
               presence "enable advertise-to-non-llgr-neighbor";
               description "Advertise stale routes to non-LLGR neighbors";
               uses apply-advanced;
               leaf omit-no-export {
                 description "Do not attach no-export community to stale routes";
                 type empty;
               }
             }
           }
           leaf disable-notification-extensions {
             description "Disable notification extensions";
             type empty;
           }
           leaf forwarding-state-bit {
             description "Control forwarding-state flag negotiation";
             type enumeration {
               enum "as-rr-client" {
                 description "As for a route reflector client";
               }
               enum "from-fib" {
                 description "Always use state of associated FIB(s)";
               }
             }
           }
           leaf dont-help-shared-fate-bfd-down {
             description "Honor BFD-Down(C=0) if GR-restart not in progress";
             type empty;
           }
         }
         leaf include-mp-next-hop {
           description "Include NEXT-HOP attribute in multiprotocol updates";
           type empty;
         }
         leaf disable-4byte-as {
           description "Disable 4 byte AS capability advertisement";
           type empty;
         }
         container idle-after-switch-over {
           description "Stop peer session from coming up after nonstop-routing switch-over";
           choice idle-interval {
             case case_1 {
               leaf forever {
                 description "Idle the peer until the user intervenes";
                 type empty;
               }
             }
             case case_2 {
               leaf timeout {
                 description "Timeout value, in seconds, for starting peer after switch over";
                 type union {
                   type string {
                     pattern "<.*>|$.*";
                   }
                   type uint32 {
                     range "1 .. 4294967295";
                   }
                 }
               }
             }
           }
         }
         container outbound-route-filter {
           junos:must "(!(\"system processes routing bgp update-threading\"))";
           junos:must-message "Can't be configured together with update-threading";
           description "Dynamically negotiated cooperative route filtering";
           uses apply-advanced;
           leaf bgp-orf-cisco-mode {
             description "Using BGP ORF capability code 130 and Prefix ORF type 128";
             type empty;
           }
           container extended-community {
             description "Extended community filtering";
             status deprecated;
             uses apply-advanced;
             choice accept-choice {
               leaf accept {
                 description "Honor remote requests for extended community ORF";
                 type empty;
               }
               leaf no-accept {
                 description "Don't honor remote requests for extended community ORF";
                 type empty;
               }
             }
             leaf vrf-filter {
               description "Request remote filtering using locally configured VRF import targets";
               type empty;
             }
           }
           container prefix-based {
             presence "enable prefix-based";
             description "Prefix-based outbound route filtering";
             uses apply-advanced;
             container accept {
               presence "enable accept";
               description "Honor Prefix-based ORFs from remote peers";
               uses apply-advanced;
               leaf inet {
                 description "Honor IPv4 prefix filters";
                 type empty;
               }
               leaf inet6 {
                 description "Honor IPv6 prefix filters";
                 type empty;
               }
             }
           }
         }
         container message-batching {
           description "DEPRECATED - Batching of outgoing messages";
           status deprecated;
           uses apply-advanced;
           choice enable-disable {
             case case_1 {
               leaf enable {
                 description "Enable parameter";
                 type empty;
               }
             }
             case case_2 {
               leaf disable {
                 description "Disable parameter";
                 type empty;
               }
             }
           }
           leaf interval {
             description "DEPRECATED - Interval over which to batch messages";
             default "250";
             units "milliseconds";
             type union {
               type string {
                 pattern "<.*>|$.*";
               }
               type uint32 {
                 range "100 .. 1000";
               }
             }
           }
         }
         container multipath {
           presence "enable multipath";
           description "Allow load sharing among multiple BGP paths";
           uses apply-advanced;
           leaf disable {
             description "Disable Multipath";
             type empty;
           }
           leaf multiple-as {
             description "Use paths received from different ASs";
             type empty;
           }
           leaf allow-protection {
             description "Allow protection for multipath legs";
             type empty;
           }
           leaf pause-computation-during-churn {
             description "Pause multipath job to absorb churn";
             type empty;
           }
           leaf list-nexthop {
             description "Use List-NH for homogenous nexthop-set also";
             type empty;
           }
         }
         leaf tcp-mss {
           description "Maximum TCP segment size";
           type union {
             type string {
               pattern "<.*>|$.*";
             }
             type uint32 {
               range "1 .. 4096";
             }
           }
         }
         leaf bgp-identifier {
           description "BGP Identifier";
           type jt:ipv4addr;
         }
         leaf tcp-aggressive-transmission {
           description "Enable aggressive transmission of pure TCP ACKs and retransmissions";
           type empty;
         }
         container bmp {
           description "Specific settings to override the routing-options settings";
           uses apply-advanced;
           leaf monitor {
             description "Enable/Disable monitoring";
             type enumeration {
               enum "enable" {
                 description "Enable monitoring of BGP peer(s)";
               }
               enum "disable" {
                 description "Disable monitoring of BGP peer(s)";
               }
             }
           }
           container route-monitoring {
             description "Control route monitoring settings";
             uses apply-advanced;
             leaf none {
               description "Do not send route monitoring messages";
               junos:must "((!(\".. pre-policy\") && (!(\".. post-policy\") && !(\".. rib-out\"))))";
               junos:must-message "May not be configured with pre-policy or post-policy or rib-out";
               type empty;
             }
             container pre-policy {
               presence "enable pre-policy";
               description "Send pre-policy route monitoring messages";
               leaf exclude-non-feasible {
                 description "Exclude looped routes, etc";
                 type empty;
               }
             }
             container post-policy {
               presence "enable post-policy";
               description "Send post-policy route monitoring messages";
               leaf exclude-non-eligible {
                 description "Exclude unresolved routes, etc.";
                 type empty;
               }
             }
             container rib-out {
               presence "enable rib-out";
               junos:must "((!(\"system processes routing bgp update-threading\") || \"system processes routing bgp rib-sharding\"))";
               junos:must-message "Update threading can't be configured together with bmp rib-out monitoring";
               description "Send adj-ribs-out route monitoring messages";
               leaf pre-policy {
                 description "Send pre-policy adj-ribs-out route monitoring messages";
                 type empty;
               }
               leaf post-policy {
                 description "Send post-policy adj-ribs-out route monitoring messages";
                 type empty;
               }
             }
           }
         }
         container advertise-bgp-static {
           presence "enable advertise-bgp-static";
           description "Advertise bgp-static routes";
           uses apply-advanced;
           leaf-list policy {
             ordered-by user;
             description "Static route advertisement policy";
             type jt:policy-algebra;
           }
         }
         leaf add-path-display-ipv4-address {
           description "Display add-path path-id in IPv4 address format";
           type empty;
         }
         container bfd-liveness-detection {
           description "Bidirectional Forwarding Detection (BFD) options";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
           container authentication {
             description "Authentication options";
             uses apply-advanced;
             leaf key-chain {
               description "Key chain name";
               junos:must "(\".. algorithm\")";
               junos:must-message "May not be configured without algorithm";
               junos:must "(\"security authentication-key-chains key-chain $$\")";
               junos:must-message "Referenced key-chain must be defined";
               type string;
             }
             leaf algorithm {
               description "Algorithm name";
               junos:must "(\".. key-chain\")";
               junos:must-message "May not be configured without key-chain";
               type enumeration {
                 enum "simple-password" {
                   description "Simple password";
                 }
                 enum "keyed-md5" {
                   description "Keyed message Digest 5";
                 }
                 enum "meticulous-keyed-md5" {
                   description "Meticulous keyed message Digest 5";
                 }
                 enum "keyed-sha-1" {
                   description "Keyed secure hash algorithm (SHA1) ";
                 }
                 enum "meticulous-keyed-sha-1" {
                   description "Meticulous keyed secure hash algorithm (SHA1) ";
                 }
               }
             }
             leaf loose-check {
               description "Verify authentication only if authentication is negotiated";
               type empty;
             }
           }
           leaf session-mode {
             description "BFD single-hop or multihop session-mode";
             default "automatic";
             type enumeration {
               enum "automatic" {
                 description "Choose session-mode automatically";
               }
               enum "single-hop" {
                 description "Use single-hop";
               }
               enum "multihop" {
                 description "Use multihop";
               }
             }
           }
           leaf holddown-interval {
             description "Time to hold the session-UP notification to the client";
             units "milliseconds";
             junos:must "(!(\".. .. .. type internal\"))";
             junos:must-message "bfd holddown-interval is only valid for EBGP.";
             type union {
               type string {
                 pattern "<.*>|$.*";
               }
               type uint32 {
                 range "0 .. 255000";
               }
             }
           }
         }
         leaf as-override {
           description "Replace neighbor AS number with our AS number";
           type empty;
         }
         container egress-te-node-segment {
           description "Configure BGP-Peer-Node segment";
           uses apply-advanced;
           container label {
             description "BGP-Peer-Node SID label from static label pool";
             uses apply-advanced;
             leaf label-value {
               description "BGP-Peer-Node SID label value from static label pool";
               type union {
                 type string {
                   pattern "<.*>|$.*";
                 }
                 type uint32 {
                   range "16 .. 1048575";
                 }
               }
             }
           }
           container egress-te-set {
             description "Configure as a member of a SET segment";
             uses apply-advanced;
             leaf set-name {
               description "Set name";
               junos:must "(\"protocols bgp egress-te-set-segment $$\")";
               junos:must-message "protocols bgp egress-te-set-segment not configured";
               type string {
                 junos:posix-pattern "^.{1,64}$";
                 junos:pattern-message "Must be a string of 64 characters or less";
               }
             }
             leaf weight {
               description "Weight for set segment";
               type union {
                 type string {
                   pattern "<.*>|$.*";
                 }
                 type uint32 {
                   range "1 .. 255";
                 }
               }
             }
           }
           container egress-te-backup-segment {
             description "Backup segment for FRR";
             uses apply-advanced;
             container label {
               description "Backup segment label from static label pool";
               uses apply-advanced;
               leaf label-value {
                 description "Backup segment label value from static label pool";
                 type union {
                   type string {
                     pattern "<.*>|$.*";
                   }
                   type uint32 {
                     range "16 .. 1048575";
                   }
                 }
               }
             }
           }
           container egress-te-backup-ip-forward {
             presence "enable egress-te-backup-ip-forward";
             description "Use IP-forward backup path for Egress TE";
             uses apply-advanced;
             leaf instance-name {
               description "Routing-instance to use as IP forward backup-path";
               type string {
                 junos:posix-pattern "!^((__.*__)|(all)|(.*[ ].*)|(\"\")|(.{129,}))$";
                 junos:pattern-message "Must be a non-reserved string of 128 characters or less with no spaces.";
               }
             }
           }
         }
         list egress-te-adj-segment {
           key name;
           description "Configure BGP-Peer-Adj segment";
           leaf name {
             description "The BGP-Adj-Set segment name";
             type string {
               junos:posix-pattern "^.{1,64}$";
               junos:pattern-message "Must be a string of 64 characters or less";
             }
           }
           uses apply-advanced;
           container label {
             junos:must "(\".. next-hop\")";
             junos:must-message "The 'egress-te-adj-segment next-hop' must be configured";
             description "BGP-Peer-Adj SID label from static label pool";
             uses apply-advanced;
             leaf label-value {
               description "BGP-Peer-Adj SID label value from static label pool";
               type union {
                 type string {
                   pattern "<.*>|$.*";
                 }
                 type uint32 {
                   range "16 .. 1048575";
                 }
               }
             }
           }
           container next-hop {
             junos:must "(\".. label\")";
             junos:must-message "The 'egress-te-adj-segment label' must be configured";
             description "Address of directly connected next-hop to use";
             uses apply-advanced;
             leaf next-hop-addr {
               description "Address of directly connected next-hop";
               type jt:ipaddr;
             }
           }
           container egress-te-set {
             description "Configure as a member of a SET segment";
             uses apply-advanced;
             leaf set-name {
               description "Set name";
               junos:must "(\"protocols bgp egress-te-set-segment $$\")";
               junos:must-message "protocols bgp egress-te-set-segment not configured";
               type string {
                 junos:posix-pattern "^.{1,64}$";
                 junos:pattern-message "Must be a string of 64 characters or less";
               }
             }
             leaf weight {
               description "Weight for set segment";
               type union {
                 type string {
                   pattern "<.*>|$.*";
                 }
                 type uint32 {
                   range "1 .. 255";
                 }
               }
             }
           }
           container egress-te-backup-segment {
             description "Backup segment for FRR";
             uses apply-advanced;
             container label {
               description "Backup segment label from static label pool";
               uses apply-advanced;
               leaf label-value {
                 description "Backup segment label value from static label pool";
                 type union {
                   type string {
                     pattern "<.*>|$.*";
                   }
                   type uint32 {
                     range "16 .. 1048575";
                   }
                 }
               }
             }
           }
           container egress-te-backup-ip-forward {
             presence "enable egress-te-backup-ip-forward";
             description "Use IP-forward backup path for Egress TE";
             uses apply-advanced;
             leaf instance-name {
               description "Routing-instance to use as IP forward backup-path";
               type string {
                 junos:posix-pattern "!^((__.*__)|(all)|(.*[ ].*)|(\"\")|(.{129,}))$";
                 junos:pattern-message "Must be a non-reserved string of 128 characters or less with no spaces.";
               }
             }
           }
           container te-link-attribute {
             presence "enable te-link-attribute";
             description "Link attribute";
             uses apply-advanced;
             leaf te-metric {
               description "TE Metric value";
               default "1";
               type union {
                 type string {
                   pattern "<.*>|$.*";
                 }
                 type uint32 {
                   range "1 .. 4294967295";
                 }
               }
             }
             leaf igp-metric {
               description "IGP Metric value";
               default "1";
               type union {
                 type string {
                   pattern "<.*>|$.*";
                 }
                 type uint32 {
                   range "1 .. 16777215";
                 }
               }
             }
             leaf delay-metric {
               description "Delay Metric";
               units "microseconds";
               type union {
                 type string {
                   pattern "<.*>|$.*";
                 }
                 type uint32 {
                   range "1 .. 16777215";
                 }
               }
             }
             leaf-list admin-group {
               ordered-by user;
               description "Administrative groups";
               type string;
               max-elements 16;
             }
           }
         }
         leaf vpn-apply-export {
           description "Apply BGP export policy when exporting VPN routes";
           type empty;
         }
         container egress-te {
           presence "enable egress-te";
           description "Use Egress Peering traffic engineering";
           uses apply-advanced;
           leaf install-address {
             description "Address to use in egress-te created inet route";
             type jt:ipaddr;
           }
           container rib {
             description "Select primary table for Egress-TE routes";
             uses apply-advanced;
             leaf inet.0 {
               description "Install Egress-TE routes in inet.0";
               type empty;
             }
             leaf inet6.0 {
               description "Install Egress-TE routes in inet6.0";
               type empty;
             }
           }
           leaf no-install {
             description "Avoid installation to FIB or resolving over";
             type empty;
           }
           leaf-list import {
             ordered-by user;
             description "Import policy to set attributes";
             type jt:policy-algebra;
           }
           leaf backup-path {
             description "The 'egress-te-backup-paths template' to use for this peer";
             junos:must "(\"protocols bgp egress-te-backup-paths template $$\")";
             junos:must-message "bgp egress-te-backup-paths template not configured";
             type string {
               junos:posix-pattern "^.{1,64}$";
               junos:pattern-message "Must be a string of 64 characters or less";
             }
           }
         }
         leaf advertise-prefix-sid {
           description "Advertise prefix sid to E-BGP peers";
           type empty;
         }
         leaf accept-prefix-sid {
           description "Accept prefix sid from E-BGP peers";
           type empty;
         }
         leaf advertise-srgb {
           description "Advertise SRGB TLV";
           type empty;
         }
       }
       leaf vpn-apply-export {
         description "Apply BGP export policy when exporting VPN routes";
         type empty;
       }
       container egress-te {
         presence "enable egress-te";
         description "Use Egress Peering traffic engineering";
         uses apply-advanced;
         leaf install-address {
           description "Address to use in egress-te created inet route";
           type jt:ipaddr;
         }
         container rib {
           description "Select primary table for Egress-TE routes";
           uses apply-advanced;
           leaf inet.0 {
             description "Install Egress-TE routes in inet.0";
             type empty;
           }
           leaf inet6.0 {
             description "Install Egress-TE routes in inet6.0";
             type empty;
           }
         }
         leaf no-install {
           description "Avoid installation to FIB or resolving over";
           type empty;
         }
         leaf-list import {
           ordered-by user;
           description "Import policy to set attributes";
           type jt:policy-algebra;
         }
         leaf backup-path {
           description "The 'egress-te-backup-paths template' to use for this peer";
           junos:must "(\"protocols bgp egress-te-backup-paths template $$\")";
           junos:must-message "bgp egress-te-backup-paths template not configured";
           type string {
             junos:posix-pattern "^.{1,64}$";
             junos:pattern-message "Must be a string of 64 characters or less";
           }
         }
       }
       leaf advertise-prefix-sid {
         description "Advertise prefix sid to E-BGP peers";
         type empty;
       }
       leaf accept-prefix-sid {
         description "Accept prefix sid from E-BGP peers";
         type empty;
       }
       leaf advertise-srgb {
         description "Advertise SRGB TLV";
         type empty;
       }
     }
     container traffic-statistics-labeled-path {
       presence "enable traffic-statistics-labeled-path";
       description "Collect periodic ingress labeled statistics for BGP label-switched paths ";
       uses apply-advanced;
       container file {
         description "Statistics file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       leaf interval {
         description "Time interval to collect statistics";
         units "seconds";
         type union {
           type string {
             pattern "<.*>|$.*";
           }
           type int32 {
             range "60 .. 65535";
           }
         }
       }
     }
     container source-packet-routing {
       description "Enable Source Packet Routing (SPRING)";
       uses apply-advanced;
       container srgb {
         junos:must "(!(\".. .. .. .. protocols mpls disable\"))";
         junos:must-message "SPRING configuration is not allowed with 'protocols mpls disable'";
         junos:must "(\".. .. .. .. protocols mpls \")";
         junos:must-message "SPRING configuration is not allowed without 'protocols mpls'";
         description "Set the SRGB global block in SPRING";
         leaf start-label {
           description "Start range for SRGB label block";
           type union {
             type string {
               pattern "<.*>|$.*";
             }
             type uint32;
           }
         }
         leaf index-range {
           description "Index to the SRGB start label block";
           type union {
             type string {
               pattern "<.*>|$.*";
             }
             type uint32;
           }
         }
       }
       container srv6 {
         description "Enable IPv6 Segment Routing (SRv6)";
         uses apply-advanced;
         list locator {
           key name;
           ordered-by user;
           description "SRv6 Locator";
           leaf name {
             description "Locator name";
             junos:must "(\"routing-options source-packet-routing srv6 locator $$\")";
             junos:must-message "Referenced srv6 locator must be defined";
             type string;
           }
           uses apply-advanced;
           leaf end-dt4-sid {
             description "End dt4 sid with 128 bit address";
             type jt:ipv6addr;
           }
           leaf end-dt6-sid {
             description "End dt6 sid with 128 bit address";
             type jt:ipv6addr;
           }
           leaf end-dt46-sid {
             description "End dt46 sid with 128 bit address";
             type jt:ipv6addr;
           }
         }
       }
     }
     choice enable-disable {
       case case_1 {
         leaf disable {
           description "Disable BGP";
           type empty;
         }
       }
     }
     choice precision-timers-choice {
       leaf precision-timers {
         description "Use precision timers for scheduling keepalives";
         type empty;
       }
       leaf no-precision-timers {
         description "Don't use precision timers for scheduling keepalives";
         type empty;
       }
     }
     container snmp-options {
       description "Customize SNMP behaviors specifically for BGP MIBs";
       uses apply-advanced;
       leaf backward-traps-only-from-established {
         description "Limit traps for backward transitions to only those moving from Established state.";
         type empty;
       }
       leaf emit-inet-address-length-in-oid {
         description "Emit Length in OID for InetAddress MIB type.";
         type empty;
       }
     }
     leaf route-age-bgp-view {
       description "Maintain BGP route's age based on Update messages only";
       type empty;
     }
     leaf prioritize-route-queueing {
       description "Let route-queue building happen without getting throttled";
       type empty;
     }
     container traceoptions {
       description "Trace options for BGP";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "damping" {
               description "Trace BGP damping information";
             }
             enum "packets" {
               description "Trace all BGP protocol packets";
             }
             enum "open" {
               description "Trace BGP open packets";
             }
             enum "update" {
               description "Trace BGP update packets";
             }
             enum "keepalive" {
               description "Trace BGP keepalive packets";
             }
             enum "refresh" {
               description "Trace BGP refresh packets";
             }
             enum "nsr-synchronization" {
               description "Trace NSR synchronization events";
             }
             enum "bfd" {
               description "Trace BFD events";
             }
             enum "4byte-as" {
               description "Trace 4 byte AS events";
             }
             enum "add-path" {
               description "Trace add-path events";
             }
             enum "graceful-restart" {
               description "Trace Graceful Restart events";
             }
             enum "egress-te" {
               description "Egress Peering Traffic-Engineering events";
             }
             enum "thread-io" {
               description "Trace threaded I/O processing";
             }
             enum "sharding" {
               description "Trace BGP rib sharding";
             }
             enum "thread-update-io" {
               description "Trace threaded update I/O processing";
             }
             enum "route-validation" {
               description "Trace route validation";
             }
             enum "ipsec" {
               description "Trace ipsec";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
         container filter {
           description "Filter to apply to this flag";
           presence "enable filter";
           uses bgp_filter_obj;
         }
       }
     }
     leaf description {
       description "Text description";
       type string {
         length "1 .. 255";
       }
     }
     container metric-out {
       description "Route metric sent in MED";
       choice metric_param {
         case case_1 {
           leaf metric-value {
             description "Metric value";
             type union {
               type string {
                 pattern "<.*>|$.*";
               }
               type uint32 {
                 range "0 .. 4294967295";
               }
             }
           }
         }
         case case_2 {
           container minimum-igp {
             presence "enable minimum-igp";
             description "Track the minimum IGP metric";
             leaf metric-offset {
               description "Metric offset for MED";
               type union {
                 type int32;
                 type string {
                   pattern "<.*>|$.*";
                 }
               }
             }
           }
         }
         case case_3 {
           container igp {
             presence "enable igp";
             description "Track the IGP metric";
             leaf metric-offset {
               description "Metric offset for MED";
               type union {
                 type int32;
                 type string {
                   pattern "<.*>|$.*";
                 }
               }
             }
             leaf delay-med-update {
               description "Delay updating MED when IGP metric increases";
               type empty;
             }
           }
         }
         case case_4 {
           container effective-aigp {
             presence "enable effective-aigp";
             description "Track the effective AIGP metric";
             leaf metric-offset {
               description "Metric offset for MED";
               type union {
                 type int32;
                 type string {
                   pattern "<.*>|$.*";
                 }
               }
             }
           }
         }
         case case_5 {
           container minimum-effective-aigp {
             presence "enable minimum-effective-aigp";
             description "Track the minimum effective AIGP metric";
             leaf metric-offset {
               description "Metric offset for MED";
               type union {
                 type int32;
                 type string {
                   pattern "<.*>|$.*";
                 }
               }
             }
           }
         }
       }
     }
     container multihop {
       presence "enable multihop";
       description "Configure an EBGP multihop session";
       uses apply-advanced;
       leaf ttl {
         description "TTL value for the session";
         type union {
           type string {
             pattern "<.*>|$.*";
           }
           type uint8 {
             range "1 .. 255";
           }
         }
       }
       leaf no-nexthop-change {
         description "Do not change next hop to self in advertisements";
         type empty;
       }
     }
     container ebgp-community-cleanup {
       presence "enable ebgp-community-cleanup";
       description "Community specific cleanup for eBGP peers";
       uses apply-advanced;
       leaf origin-validation {
         description "Origin Validation State receive behavior";
         type enumeration {
           enum "accept" {
             description "Accept Origin Validation State Community";
           }
           enum "reject" {
             description "Reject Origin Validation State Community";
           }
         }
       }
     }
     leaf route-server-client {
       description "Enable route server client behavior";
       type empty;
     }
     leaf accept-remote-nexthop {
       description "Allow import policy to specify a non-directly connected next-hop";
       type empty;
     }
     leaf preference {
       description "Preference value";
       type union {
         type uint32;
         type string {
           pattern "<.*>|$.*";
         }
       }
     }
     leaf local-preference {
       description "Value of LOCAL_PREF path attribute";
       type union {
         type uint32;
         type string {
           pattern "<.*>|$.*";
         }
       }
     }
     leaf local-address {
       description "Address of local end of BGP session";
       type jt:ipaddr;
     }
     leaf local-interface {
       description "Local interface for IPv6 link local EBGP peering";
       type union {
         type jt:interface-name;
         type string {
           pattern "<.*>|$.*";
         }
       }
     }
     leaf forwarding-context {
       description "Routing-instance used for data-forwarding and transport-session";
       type string {
         junos:posix-pattern "!^((__.*__)|(all)|(.*[ ].*)|(\"\")|(.{129,}))$";
         junos:pattern-message "Must be a non-reserved string of 128 characters or less with no spaces.";
       }
     }
     leaf hold-time {
       description "Hold time used when negotiating with a peer";
       type union {
         type string {
           pattern "<.*>|$.*";
         }
         type uint32 {
           range "0 .. 65535";
         }
       }
     }
     leaf minimum-hold-time {
       description "Minimum hold time accepted from the peer";
       type union {
         type string {
           pattern "<.*>|$.*";
         }
         type uint32 {
           range "3 .. 65535";
         }
       }
     }
     leaf passive {
       description "Do not send open messages to a peer";
       type empty;
     }
     leaf advertise-inactive {
       description "Advertise inactive routes";
       type empty;
     }
     choice advertise-peer-as-choice {
       leaf advertise-peer-as {
         description "Advertise routes received from the same autonomous system";
         type empty;
       }
       leaf no-advertise-peer-as {
         description "Don't advertise routes received from the same autonomous system";
         type empty;
       }
     }
     container advertise-external {
       presence "enable advertise-external";
       description "Advertise best external routes";
       leaf conditional {
         description "Route matches active route upto med-comparison rule";
         type empty;
       }
     }
     leaf keep {
       description "How to retain routes in the routing table";
       type enumeration {
         enum "all" {
           description "Retain all routes";
         }
         enum "none" {
           description "Retain no routes";
         }
       }
     }
     leaf rfc6514-compliant-safi129 {
       description "Compliant with RFC6514 SAFI129 format";
       type empty;
     }
     leaf no-aggregator-id {
       description "Set router ID in aggregator path attribute to 0";
       type empty;
     }
     leaf mtu-discovery {
       description "Enable TCP path MTU discovery";
       type empty;
     }
     leaf enforce-first-as {
       description "Enforce first AS in AS-path is the neighbor's AS";
       type empty;
     }
     leaf out-delay {
       description "How long before exporting routes from routing table";
       type union {
         type string {
           pattern "<.*>|$.*";
         }
         type uint32 {
           range "0 .. 65535";
         }
       }
     }
     leaf ttl {
       description "TTL value for the single-hop peer";
       junos:must "((!(\".. .. type internal\") && !(\".. multihop\")))";
       junos:must-message "This option is valid only for single-hop EBGP neighbor";
       type enumeration {
         enum "1" {
         }
         enum "255" {
         }
       }
     }
     leaf log-updown {
       description "Log a message for peer state transitions";
       type empty;
     }
     leaf damping {
       description "Enable route flap damping";
       type empty;
     }
     leaf-list import {
       ordered-by user;
       description "Import policy";
       type jt:policy-algebra;
     }
     leaf-list nlri {
       ordered-by user;
       description "NLRI type to include in updates";
       status deprecated;
       type enumeration {
         enum "unicast" {
           description "Include unicast NLRI";
           status deprecated;
         }
         enum "multicast" {
           description "Include multicast NLRI";
           status deprecated;
         }
         enum "any" {
           description "Include any kind of NLRI";
           status deprecated;
         }
       }
     }
     container bgp-error-tolerance {
       presence "enable bgp-error-tolerance";
       description "Handle BGP malformed updates softly";
       uses apply-advanced;
       leaf malformed-update-log-interval {
         description "Time used when logging malformed update";
         default "300";
         units "seconds";
         type union {
           type string {
             pattern "<.*>|$.*";
           }
           type uint32 {
             range "10 .. 65535";
           }
         }
       }
       choice malformed-routes-limit-choice {
         case case_1 {
           leaf malformed-route-limit {
             description "Maximum number of malformed routes from a peer";
             default "1000";
             type union {
               type string {
                 pattern "<.*>|$.*";
               }
               type uint32 {
                 range "0 .. 4294967295";
               }
             }
           }
         }
         case case_2 {
           leaf no-malformed-route-limit {
             description "No malformed route limit";
             type empty;
           }
         }
       }
     }
     leaf authentication-key {
       description "MD5 authentication key";
       type string {
         length "1 .. 126";
       }
     }
     leaf authentication-algorithm {
       description "Authentication algorithm name";
       default "hmac-sha-1-96";
       junos:must "(\".. authentication-key-chain\")";
       junos:must-message "May not be configured without authentication-key-chain";
       junos:must "(!(\".. authentication-key\"))";
       junos:must-message "May not be configured with authentication-key";
       type enumeration {
         enum "md5" {
           description "Message Digest 5";
         }
         enum "hmac-sha-1-96" {
           description "Hash-based Message Authentication Code (SHA1) (96 bits)";
         }
         enum "aes-128-cmac-96" {
           description "Cipher-based Message Authentication Code (AES128) (96 bits)";
         }
         enum "ao" {
           description "TCP Authentication Option";
         }
       }
     }
     leaf tcpao-auth-mismatch {
       description "Continue without TCP-AO if any one TCP endpoint does not have TCP-AO configured";
       junos:must "(!(\".. authentication-key\"))";
       junos:must-message "May not be configured with authentication-key";
       type enumeration {
         enum "allow-without-tcpao" {
           description "Allow the connection establishment without TCP-AO";
         }
       }
     }
     leaf authentication-key-chain {
       description "Key chain name";
       junos:must "(!(\".. authentication-key\"))";
       junos:must-message "May not be configured with authentication-key";
       junos:must "(\"security authentication-key-chains key-chain $$\")";
       junos:must-message "Referenced key-chain must be defined";
       type string {
         length "1 .. 128";
       }
     }
     leaf-list export {
       ordered-by user;
       description "Export policy";
       type jt:policy-algebra;
     }
     container remove-private {
       presence "enable remove-private";
       description "Remove well-known private AS numbers";
       uses apply-advanced;
       container all {
         presence "enable all";
         description "Remove all private AS numbers and do not stop at the first public AS number";
         container replace {
           presence "enable replace";
           description "Replace private AS numbers with the BGP Group's local AS number";
           leaf nearest {
             description "Use closest public AS number to replace a private AS number";
             type empty;
           }
         }
       }
       leaf no-peer-loop-check {
         description "Remove peer loop-check";
         type empty;
       }
     }
     leaf cluster {
       description "Cluster identifier";
       type jt:areaid;
     }
     leaf no-client-reflect {
       description "Disable intracluster route redistribution";
       type empty;
     }
     leaf peer-as {
       description " Autonomous system number in plain number or 'higher 16bits'.'Lower 16 bits' (asdot notation) format";
       type string {
         junos:posix-pattern "^[0-9]+(.[0-9]+)?$";
         junos:pattern-message "Use format 'x' or 'x.y' to specify number 'x' (Range 1 .. 4294967295) or number with higher 2 bytes 'x' (Range 0 .. 65535) and lower 2 bytes 'y' (Range 0 .. 65535) respectively";
       }
     }
     container local-as {
       description "Local autonomous system number";
       leaf as-number {
         description " Autonomous system number in plain number or 'higher 16bits'.'Lower 16 bits' (asdot notation) format";
         type string {
           junos:posix-pattern "^[0-9]+(.[0-9]+)?$";
           junos:pattern-message "Use format 'x' or 'x.y' to specify number 'x' (Range 1 .. 4294967295) or number with higher 2 bytes 'x' (Range 0 .. 65535) and lower 2 bytes 'y' (Range 0 .. 65535) respectively";
         }
       }
       leaf loops {
         description "Maximum number of times this AS can be in an AS path";
         type union {
           type string {
             pattern "<.*>|$.*";
           }
           type int32 {
             range "1 .. 10";
           }
         }
       }
       leaf private {
         description "Hide this local AS in paths learned from this peering";
         type empty;
       }
       leaf alias {
         description "Treat this AS as an alias to the system AS";
         type empty;
       }
       leaf no-prepend-global-as {
         description "Do not prepend global autonomous-system number in advertised paths";
         type empty;
       }
     }
     leaf ipsec-sa {
       description "IPSec SA name";
       junos:must "(\"security ipsec security-association $$\")";
       junos:must-message "Referenced IPSec Security Association must be defined";
       type string {
         length "1 .. 32";
       }
     }
     container graceful-shutdown {
       description "BGP peer graceful shutdown option";
       uses apply-advanced;
       container receiver {
         presence "enable receiver";
         description "BGP peer graceful-shutdown receiver";
         uses apply-advanced;
         leaf disable {
           description "Disable graceful-shutdown receiver";
           junos:must "(!(\".. .. sender\"))";
           junos:must-message "Receiver cannot be disabled on Sender";
           type empty;
         }
         leaf local-preference {
           description "Value of receiver LOCAL_PREF path attribute";
           type union {
             type uint32;
             type string {
               pattern "<.*>|$.*";
             }
           }
         }
       }
       container sender {
         presence "enable sender";
         description "BGP peer graceful-shutdown sender";
         uses apply-advanced;
         leaf local-preference {
           description "Value of sender LOCAL_PREF path attribute";
           type union {
             type uint32;
             type string {
               pattern "<.*>|$.*";
             }
           }
         }
       }
     }
     container shutdown {
       presence "enable shutdown";
       description "Shutdown";
       uses apply-advanced;
       leaf notify-message {
         description "Notification message";
         type string;
       }
     }
     leaf unconfigured-peer-graceful-restart {
       description "BGP unconfigured peer graceful restart options";
       junos:must "(\".. graceful-restart\")";
       junos:must-message "unconfigured-peer-graceful-restart is only valid with 'graceful-restart'";
       type empty;
     }
     container graceful-restart {
       presence "enable graceful-restart";
       description "BGP graceful restart options";
       uses apply-advanced;
       choice enable-disable {
         case case_1 {
           leaf disable {
             description "Disable graceful restart";
             type empty;
           }
         }
       }
       leaf restart-time {
         description "Restart time used when negotiating with a peer";
         junos:must "((\"routing-options graceful-restart\" || \"fabric routing-options graceful-restart\"))";
         junos:must-message "restart-time is only valid with 'routing-options graceful-restart'";
         type union {
           type string {
             pattern "<.*>|$.*";
           }
           type uint32 {
             range "1 .. 1800";
           }
         }
       }
       leaf stale-routes-time {
         description "Maximum time for which stale routes are kept";
         type union {
           type string {
             pattern "<.*>|$.*";
           }
           type uint32 {
             range "1 .. 1800";
           }
         }
       }
       container long-lived {
         description "Long-lived graceful restart options";
         uses apply-advanced;
         container receiver {
           description "Long-lived graceful restart receiver (helper) options";
           uses apply-advanced;
           choice enable-disable {
             case case_1 {
               leaf disable {
                 description "Disable receiver (helper) functionality";
                 type empty;
               }
             }
           }
         }
         container advertise-to-non-llgr-neighbor {
           presence "enable advertise-to-non-llgr-neighbor";
           description "Advertise stale routes to non-LLGR neighbors";
           uses apply-advanced;
           leaf omit-no-export {
             description "Do not attach no-export community to stale routes";
             type empty;
           }
         }
       }
       leaf disable-notification-extensions {
         description "Disable notification extensions";
         type empty;
       }
       leaf forwarding-state-bit {
         description "Control forwarding-state flag negotiation";
         type enumeration {
           enum "as-rr-client" {
             description "As for a route reflector client";
           }
           enum "from-fib" {
             description "Always use state of associated FIB(s)";
           }
         }
       }
       leaf dont-help-shared-fate-bfd-down {
         description "Honor BFD-Down(C=0) if GR-restart not in progress";
         type empty;
       }
     }
     leaf include-mp-next-hop {
       description "Include NEXT-HOP attribute in multiprotocol updates";
       type empty;
     }
     leaf disable-4byte-as {
       description "Disable 4 byte AS capability advertisement";
       type empty;
     }
     container idle-after-switch-over {
       description "Stop peer session from coming up after nonstop-routing switch-over";
       choice idle-interval {
         case case_1 {
           leaf forever {
             description "Idle the peer until the user intervenes";
             type empty;
           }
         }
         case case_2 {
           leaf timeout {
             description "Timeout value, in seconds, for starting peer after switch over";
             type union {
               type string {
                 pattern "<.*>|$.*";
               }
               type uint32 {
                 range "1 .. 4294967295";
               }
             }
           }
         }
       }
     }
     container outbound-route-filter {
       junos:must "(!(\"system processes routing bgp update-threading\"))";
       junos:must-message "Can't be configured together with update-threading";
       description "Dynamically negotiated cooperative route filtering";
       uses apply-advanced;
       leaf bgp-orf-cisco-mode {
         description "Using BGP ORF capability code 130 and Prefix ORF type 128";
         type empty;
       }
       container extended-community {
         description "Extended community filtering";
         status deprecated;
         uses apply-advanced;
         choice accept-choice {
           leaf accept {
             description "Honor remote requests for extended community ORF";
             type empty;
           }
           leaf no-accept {
             description "Don't honor remote requests for extended community ORF";
             type empty;
           }
         }
         leaf vrf-filter {
           description "Request remote filtering using locally configured VRF import targets";
           type empty;
         }
       }
       container prefix-based {
         presence "enable prefix-based";
         description "Prefix-based outbound route filtering";
         uses apply-advanced;
         container accept {
           presence "enable accept";
           description "Honor Prefix-based ORFs from remote peers";
           uses apply-advanced;
           leaf inet {
             description "Honor IPv4 prefix filters";
             type empty;
           }
           leaf inet6 {
             description "Honor IPv6 prefix filters";
             type empty;
           }
         }
       }
     }
     container message-batching {
       description "DEPRECATED - Batching of outgoing messages";
       status deprecated;
       uses apply-advanced;
       choice enable-disable {
         case case_1 {
           leaf enable {
             description "Enable parameter";
             type empty;
           }
         }
         case case_2 {
           leaf disable {
             description "Disable parameter";
             type empty;
           }
         }
       }
       leaf interval {
         description "DEPRECATED - Interval over which to batch messages";
         default "250";
         units "milliseconds";
         type union {
           type string {
             pattern "<.*>|$.*";
           }
           type uint32 {
             range "100 .. 1000";
           }
         }
       }
     }
     container multipath {
       presence "enable multipath";
       description "Allow load sharing among multiple BGP paths";
       uses apply-advanced;
       leaf disable {
         description "Disable Multipath";
         type empty;
       }
       leaf multiple-as {
         description "Use paths received from different ASs";
         type empty;
       }
       leaf allow-protection {
         description "Allow protection for multipath legs";
         type empty;
       }
       leaf pause-computation-during-churn {
         description "Pause multipath job to absorb churn";
         type empty;
       }
       leaf list-nexthop {
         description "Use List-NH for homogenous nexthop-set also";
         type empty;
       }
     }
     leaf tcp-mss {
       description "Maximum TCP segment size";
       type union {
         type string {
           pattern "<.*>|$.*";
         }
         type uint32 {
           range "1 .. 4096";
         }
       }
     }
     leaf bgp-identifier {
       description "BGP Identifier";
       type jt:ipv4addr;
     }
     leaf tcp-aggressive-transmission {
       description "Enable aggressive transmission of pure TCP ACKs and retransmissions";
       type empty;
     }
     container bmp {
       description "Specific settings to override the routing-options settings";
       uses apply-advanced;
       leaf monitor {
         description "Enable/Disable monitoring";
         type enumeration {
           enum "enable" {
             description "Enable monitoring of BGP peer(s)";
           }
           enum "disable" {
             description "Disable monitoring of BGP peer(s)";
           }
         }
       }
       container route-monitoring {
         description "Control route monitoring settings";
         uses apply-advanced;
         leaf none {
           description "Do not send route monitoring messages";
           junos:must "((!(\".. pre-policy\") && (!(\".. post-policy\") && !(\".. rib-out\"))))";
           junos:must-message "May not be configured with pre-policy or post-policy or rib-out";
           type empty;
         }
         container pre-policy {
           presence "enable pre-policy";
           description "Send pre-policy route monitoring messages";
           leaf exclude-non-feasible {
             description "Exclude looped routes, etc";
             type empty;
           }
         }
         container post-policy {
           presence "enable post-policy";
           description "Send post-policy route monitoring messages";
           leaf exclude-non-eligible {
             description "Exclude unresolved routes, etc.";
             type empty;
           }
         }
         container rib-out {
           presence "enable rib-out";
           junos:must "((!(\"system processes routing bgp update-threading\") || \"system processes routing bgp rib-sharding\"))";
           junos:must-message "Update threading can't be configured together with bmp rib-out monitoring";
           description "Send adj-ribs-out route monitoring messages";
           leaf pre-policy {
             description "Send pre-policy adj-ribs-out route monitoring messages";
             type empty;
           }
           leaf post-policy {
             description "Send post-policy adj-ribs-out route monitoring messages";
             type empty;
           }
         }
       }
     }
     container advertise-bgp-static {
       presence "enable advertise-bgp-static";
       description "Advertise bgp-static routes";
       uses apply-advanced;
       leaf-list policy {
         ordered-by user;
         description "Static route advertisement policy";
         type jt:policy-algebra;
       }
     }
     leaf add-path-display-ipv4-address {
       description "Display add-path path-id in IPv4 address format";
       type empty;
     }
     container bfd-liveness-detection {
       description "Bidirectional Forwarding Detection (BFD) options";
       uses apply-advanced;
       leaf version {
         description "BFD protocol version number";
         default "automatic";
         type enumeration {
           enum "0" {
             description "BFD version 0 (deprecated)";
           }
           enum "1" {
             description "BFD version 1";
           }
           enum "automatic" {
             description "Choose BFD version automatically";
           }
         }
       }
       leaf minimum-interval {
         description "Minimum transmit and receive interval";
         units "milliseconds";
         type union {
           type string {
             pattern "<.*>|$.*";
           }
           type uint32 {
             range "1 .. 255000";
           }
         }
       }
       leaf minimum-transmit-interval {
         description "Minimum transmit interval";
         status deprecated;
         units "milliseconds";
         type union {
           type string {
             pattern "<.*>|$.*";
           }
           type uint32 {
             range "1 .. 255000";
           }
         }
       }
       leaf minimum-receive-interval {
         description "Minimum receive interval";
         units "milliseconds";
         type union {
           type string {
             pattern "<.*>|$.*";
           }
           type uint32 {
             range "1 .. 255000";
           }
         }
       }
       leaf multiplier {
         description "Detection time multiplier";
         default "3";
         type union {
           type string {
             pattern "<.*>|$.*";
           }
           type uint32 {
             range "1 .. 255";
           }
         }
       }
       choice adaptation-choice {
         case case_1 {
           leaf no-adaptation {
             description "Disable adaptation";
             type empty;
           }
         }
       }
       container transmit-interval {
         description "Transmit-interval options";
         uses apply-advanced;
         leaf minimum-interval {
           description "Minimum transmit interval";
           units "milliseconds";
           type union {
             type string {
               pattern "<.*>|$.*";
             }
             type uint32 {
               range "1 .. 255000";
             }
           }
         }
         leaf threshold {
           description "High transmit interval triggering a trap";
           units "milliseconds";
           type union {
             type uint32;
             type string {
               pattern "<.*>|$.*";
             }
           }
         }
       }
       container detection-time {
         description "Detection-time options";
         uses apply-advanced;
         leaf threshold {
           description "High detection-time triggering a trap";
           units "milliseconds";
           type union {
             type uint32;
             type string {
               pattern "<.*>|$.*";
             }
           }
         }
       }
       container authentication {
         description "Authentication options";
         uses apply-advanced;
         leaf key-chain {
           description "Key chain name";
           junos:must "(\".. algorithm\")";
           junos:must-message "May not be configured without algorithm";
           junos:must "(\"security authentication-key-chains key-chain $$\")";
           junos:must-message "Referenced key-chain must be defined";
           type string;
         }
         leaf algorithm {
           description "Algorithm name";
           junos:must "(\".. key-chain\")";
           junos:must-message "May not be configured without key-chain";
           type enumeration {
             enum "simple-password" {
               description "Simple password";
             }
             enum "keyed-md5" {
               description "Keyed message Digest 5";
             }
             enum "meticulous-keyed-md5" {
               description "Meticulous keyed message Digest 5";
             }
             enum "keyed-sha-1" {
               description "Keyed secure hash algorithm (SHA1) ";
             }
             enum "meticulous-keyed-sha-1" {
               description "Meticulous keyed secure hash algorithm (SHA1) ";
             }
           }
         }
         leaf loose-check {
           description "Verify authentication only if authentication is negotiated";
           type empty;
         }
       }
       leaf session-mode {
         description "BFD single-hop or multihop session-mode";
         default "automatic";
         type enumeration {
           enum "automatic" {
             description "Choose session-mode automatically";
           }
           enum "single-hop" {
             description "Use single-hop";
           }
           enum "multihop" {
             description "Use multihop";
           }
         }
       }
       leaf holddown-interval {
         description "Time to hold the session-UP notification to the client";
         units "milliseconds";
         type union {
           type string {
             pattern "<.*>|$.*";
           }
           type uint32 {
             range "0 .. 255000";
           }
         }
       }
     }
     container output-queue-priority {
       description "BGP output queue priority scheduler for updates";
       uses apply-advanced;
       container expedited {
         presence "enable expedited";
         description "Expedited queue; highest priority";
         leaf update-tokens {
           description "Number of tokens";
           type union {
             type string {
               pattern "<.*>|$.*";
             }
             type uint32 {
               range "1 .. 100";
             }
           }
         }
       }
       list priority {
         key name;
         description "Output queue priority 1..16; higher is better";
         leaf name {
           description "Output queue priority; higher is better";
           type union {
             type string {
               pattern "<.*>|$.*";
             }
             type uint32 {
               range "1 .. 16";
             }
           }
         }
         leaf update-tokens {
           description "Number of tokens";
           type union {
             type string {
               pattern "<.*>|$.*";
             }
             type uint32 {
               range "1 .. 100";
             }
           }
         }
       }
       container defaults {
         description "Map policy's priority class and BGP output-queue";
         uses apply-advanced;
         container low {
           description "Assign the 'low' priority class to this output-queue";
           uses bgp-output-queue-priority-class;
         }
         container medium {
           description "Assign the 'medium' priority class to this output-queue";
           uses bgp-output-queue-priority-class;
         }
         container high {
           description "Assign the 'high' priority class to this output-queue";
           uses bgp-output-queue-priority-class;
         }
       }
     }
     container multipath-build-priority {
       description "Configure the multipath build priority";
       uses apply-advanced;
       choice multipath-priority {
         case case_1 {
           leaf low {
             description "Do multipath build with low priority";
             type empty;
           }
         }
         case case_2 {
           leaf medium {
             description "Do multipath build with medium priority";
             type empty;
           }
         }
       }
     }
     leaf send-addpath-optimization {
       description "Enable BGP addpath advertisement optimization";
       type empty;
     }
     container defaults {
       uses apply-advanced;
       container ebgp {
         description "Options impacting external BGP default behaviors";
         uses apply-advanced;
         container no-policy {
           description "Default ebgp behaviors in the absence of configured policy";
           uses apply-advanced;
           leaf receive {
             description "Default ebgp receive behavior";
             type enumeration {
               enum "accept" {
                 description "By default, accept routes from all address families";
               }
               enum "reject" {
                 description "By default, reject routes from IPv4/IPv6 unicast address families";
               }
               enum "reject-always" {
                 description "By default, reject routes from all address families";
               }
             }
           }
           leaf advertise {
             description "Default ebgp advertise behavior";
             type enumeration {
               enum "accept" {
                 description "By default, advertise routes for all address families";
               }
               enum "reject" {
                 description "By default, do not advertise routes from IPv4/IPv6 unicast address families";
               }
               enum "reject-always" {
                 description "By default, do not advertise routes from any address families";
               }
             }
           }
         }
       }
     }
   }
   grouping bgp-af-gr {
     uses apply-advanced;
     container long-lived {
       description "Long-lived graceful restart options";
       uses apply-advanced;
       container restarter {
         description "Long-lived graceful restart restarter options";
         uses apply-advanced;
         choice enable-disable {
           case case_1 {
             leaf disable {
               description "Disable restarter functionality";
               type empty;
             }
           }
         }
         leaf stale-time {
           description "Stale time in seconds or dhms notation (1..16777215)";
           type string;
         }
       }
       container extended-route-retention {
         description "Extended route retention (LLGR-helper extended) options";
         uses apply-advanced;
         choice enable-disable {
           case case_1 {
             leaf disable {
               description "Disable extended-route-retention (LLGR-helper) functionality";
               type empty;
             }
           }
         }
         leaf retention-time {
           description "Retention time in seconds or dhms notation (1..16777215)";
           type string;
         }
         leaf-list retention-policy {
           ordered-by user;
           description "Retention policy for Extended Route Retention";
           type jt:policy-algebra;
         }
       }
     }
     leaf forwarding-state-bit {
       description "Control forwarding-state flag negotiation";
       type enumeration {
         enum "set" {
           description "Always set";
         }
         enum "from-fib" {
           description "Use state of associated FIB(s)";
         }
       }
     }
   }
   grouping bgp-afi-default {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       junos:must "(!(\"system processes routing bgp rib-sharding\"))";
       junos:must-message "Can't be configured together with rib-sharding";
       description "Delay route updates for this family until FIB-sync";
       uses apply-advanced;
       leaf always-wait-for-krt-drain {
         description "Wait for KRT-queue drain for more-specific prefixes";
         type empty;
       }
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
   }
   grouping apath-options {
     description "Number of paths to advertise";
     uses apply-advanced;
     leaf receive {
       description "Receive multiple paths from peer";
       type empty;
     }
     container send {
       presence "enable send";
       description "Send multiple paths to peer";
       uses apply-advanced;
       container path-selection-mode {
         junos:must "(!(\".. multipath\"))";
         junos:must-message "Multipath must be disabled";
         description "Configure how to select add-path routes";
         uses apply-advanced;
         choice mode {
           case case_1 {
             leaf all-paths {
               description "Advertise all paths allowed by path count";
               type empty;
             }
           }
           case case_2 {
             leaf equal-cost-paths {
               description "Advertise equal cost paths";
               type empty;
             }
           }
         }
       }
       leaf-list prefix-policy {
         ordered-by user;
         description "Perform add-path only for prefixes that match policy";
         type jt:policy-algebra;
       }
       leaf path-count {
         description "Number of paths to advertise";
         type union {
           type string {
             pattern "<.*>|$.*";
           }
           type int32 {
             range "2 .. 64";
           }
         }
       }
       leaf include-backup-path {
         description "Number of backup paths to advertise";
         type union {
           type string {
             pattern "<.*>|$.*";
           }
           type int32 {
             range "1 .. 2";
           }
         }
       }
       leaf multipath {
         description "Include only multipath contributor routes";
         type empty;
       }
     }
   }
   grouping bgp-afi-flow {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       junos:must "(!(\"system processes routing bgp rib-sharding\"))";
       junos:must-message "Can't be configured together with rib-sharding";
       description "Delay route updates for this family until FIB-sync";
       uses apply-advanced;
       leaf always-wait-for-krt-drain {
         description "Wait for KRT-queue drain for more-specific prefixes";
         type empty;
       }
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     leaf-list no-validate {
       ordered-by user;
       description "Bypass validation procedure for routes that match policy";
       type jt:policy-algebra;
     }
     leaf strip-nexthop {
       description "Strip the next-hop from the outgoing flow update";
       type empty;
     }
     leaf allow-policy-add-nexthop {
       description "Allow policy to add nexthop to a route without nexthop";
       status deprecated;
       type empty;
     }
   }
   grouping bgp-afi-flow-with-redirect-ip-action {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       junos:must "(!(\"system processes routing bgp rib-sharding\"))";
       junos:must-message "Can't be configured together with rib-sharding";
       description "Delay route updates for this family until FIB-sync";
       uses apply-advanced;
       leaf always-wait-for-krt-drain {
         description "Wait for KRT-queue drain for more-specific prefixes";
         type empty;
       }
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     leaf-list no-validate {
       ordered-by user;
       description "Bypass validation procedure for routes that match policy";
       type jt:policy-algebra;
     }
     leaf strip-nexthop {
       description "Strip the next-hop from the outgoing flow update";
       type empty;
     }
     container legacy-redirect-ip-action {
       presence "enable legacy-redirect-ip-action";
       description "Configure legacy redirect to IP support";
       uses apply-advanced;
       leaf receive {
         description "Accept legacy encoded redirect-to-ip action attribute";
         type empty;
       }
       leaf send {
         description "Advertise Redirect action as legacy redirect attribute";
         type empty;
       }
     }
     leaf secondary-independent-resolution {
       description "Resolve FLOW routes in VRF table independent of VPN FLOW route";
       type empty;
     }
   }
   grouping bgp-afi-inet-transport {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       junos:must "(!(\"system processes routing bgp rib-sharding\"))";
       junos:must-message "Can't be configured together with rib-sharding";
       description "Delay route updates for this family until FIB-sync";
       uses apply-advanced;
       leaf always-wait-for-krt-drain {
         description "Wait for KRT-queue drain for more-specific prefixes";
         type empty;
       }
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     container aggregate-label {
       presence "enable aggregate-label";
       description "Aggregate labels of incoming routes with the same FEC";
       uses apply-advanced;
       leaf community {
         description "Community to identify the FEC of incoming routes";
         type string;
       }
     }
     leaf per-prefix-label {
       description "Allocate a unique label to each advertised prefix";
       type empty;
     }
     leaf per-group-label {
       description "Advertise prefixes with unique labels per group";
       type empty;
     }
     container traffic-statistics {
       description "Collect statistics for BGP label-switched paths";
       presence "enable traffic-statistics";
       uses bgpaf-traffic-statistics;
     }
     container protection {
       presence "enable protection";
       description "Compute backup path for active nexthop failure";
     }
   }
   grouping bgp-afi-inet6-labeled {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       junos:must "(!(\"system processes routing bgp rib-sharding\"))";
       junos:must-message "Can't be configured together with rib-sharding";
       description "Delay route updates for this family until FIB-sync";
       uses apply-advanced;
       leaf always-wait-for-krt-drain {
         description "Wait for KRT-queue drain for more-specific prefixes";
         type empty;
       }
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     container aggregate-label {
       presence "enable aggregate-label";
       description "Aggregate labels of incoming routes with the same FEC";
       uses apply-advanced;
       leaf community {
         description "Community to identify the FEC of incoming routes";
         type string;
       }
     }
     leaf per-group-label {
       description "Advertise prefixes with unique labels per group";
       type empty;
     }
     container traffic-statistics {
       description "Collect statistics for BGP label-switched paths";
       presence "enable traffic-statistics";
       uses bgpaf-traffic-statistics;
     }
     container rib {
       description "Select table used by labeled unicast routes";
       uses apply-advanced;
       leaf inet6.3 {
         description "Use inet6.3 to exchange labeled unicast routes";
         type empty;
       }
     }
     container explicit-null {
       presence "enable explicit-null";
       description "Advertise explicit null";
       leaf connected-only {
         description "Advertise explicit null only for connected routes";
         type empty;
       }
     }
     container protection {
       presence "enable protection";
       junos:must "((!(\".. .. .. .. type internal\") && !(\".. .. .. .. .. type internal\")))";
       junos:must-message "Protection for labeled-bgp valid only for EBGP";
       description "Compute backup path for active nexthop failure";
     }
     list topology {
       key name;
       ordered-by user;
       description "Multi topology routing tables";
       junos:must "(!(\"system processes routing bgp rib-sharding\"))";
       junos:must-message "Can't be configured together with rib-sharding";
       junos:must "(!(\"routing-options no-multi-topology-routing\"))";
       junos:must-message "Multi topology routing is disabled";
       leaf name {
         description "Topology name";
         type string {
           junos:posix-pattern "!^((.*:.*)|(.{129,}))$";
           junos:pattern-message "Must be a non-reserved string of 128 characters or less";
         }
       }
       uses apply-advanced;
       leaf community {
         description "Community to identify multi topology routes";
         type string;
       }
     }
   }
   grouping bgp-afi-inet6-transport {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       junos:must "(!(\"system processes routing bgp rib-sharding\"))";
       junos:must-message "Can't be configured together with rib-sharding";
       description "Delay route updates for this family until FIB-sync";
       uses apply-advanced;
       leaf always-wait-for-krt-drain {
         description "Wait for KRT-queue drain for more-specific prefixes";
         type empty;
       }
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     container aggregate-label {
       presence "enable aggregate-label";
       description "Aggregate labels of incoming routes with the same FEC";
       uses apply-advanced;
       leaf community {
         description "Community to identify the FEC of incoming routes";
         type string;
       }
     }
     leaf per-prefix-label {
       description "Allocate a unique label to each advertised prefix";
       type empty;
     }
     leaf per-group-label {
       description "Advertise prefixes with unique labels per group";
       type empty;
     }
     container traffic-statistics {
       description "Collect statistics for BGP label-switched paths";
       presence "enable traffic-statistics";
       uses bgpaf-traffic-statistics;
     }
     container lu-export {
       presence "enable lu-export";
       description "Install Classful Transport routes in inet6.3";
       uses apply-advanced;
     }
     container protection {
       presence "enable protection";
       description "Compute backup path for active nexthop failure";
     }
   }
   grouping bgp-afi-l2vpn {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       junos:must "(!(\"system processes routing bgp rib-sharding\"))";
       junos:must-message "Can't be configured together with rib-sharding";
       description "Delay route updates for this family until FIB-sync";
       uses apply-advanced;
       leaf always-wait-for-krt-drain {
         description "Wait for KRT-queue drain for more-specific prefixes";
         type empty;
       }
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     container egress-protection {
       presence "enable egress-protection";
       junos:must "(!(\".. .. .. .. type external\"))";
       junos:must-message "Egress-protection is valid only for IBGP";
       description "Egress router protection";
       uses apply-advanced;
       container context-identifier {
         description "Context identifier";
         uses apply-advanced;
         leaf context-id {
           description "IP address";
           junos:must "(\"protocols mpls egress-protection context-identifier $$ primary\")";
           junos:must-message "context-identifier must be type primary";
           junos:must "(\"protocols mpls egress-protection context-identifier $$\")";
           junos:must-message "same context-identifier must be defined in protocols mpls egress-protection";
           type jt:ipv4addr;
         }
       }
       leaf-list keep-import {
         ordered-by user;
         description "Import policy";
         junos:must "(\"policy-options policy-statement \")";
         junos:must-message "policy-options policy-statement";
         type jt:policy-algebra;
       }
     }
   }
   grouping bgp-afi-l3vpn {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       junos:must "(!(\"system processes routing bgp rib-sharding\"))";
       junos:must-message "Can't be configured together with rib-sharding";
       description "Delay route updates for this family until FIB-sync";
       uses apply-advanced;
       leaf always-wait-for-krt-drain {
         description "Wait for KRT-queue drain for more-specific prefixes";
         type empty;
       }
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     container aggregate-label {
       presence "enable aggregate-label";
       description "Aggregate labels of incoming routes with the same FEC";
       uses apply-advanced;
       leaf community {
         description "Community to identify the FEC of incoming routes";
         type string;
       }
     }
     container egress-protection {
       presence "enable egress-protection";
       junos:must "(!(\".. .. .. .. type external\"))";
       junos:must-message "Egress-protection is valid only for IBGP";
       description "Egress router protection";
       uses apply-advanced;
       container context-identifier {
         description "Context identifier";
         uses apply-advanced;
         leaf context-id {
           description "IP address";
           junos:must "(\"protocols mpls egress-protection context-identifier $$ primary\")";
           junos:must-message "context-identifier must be type primary";
           junos:must "(\"protocols mpls egress-protection context-identifier $$\")";
           junos:must-message "same context-identifier must be defined in protocols mpls egress-protection";
           type jt:ipv4addr;
         }
       }
       leaf-list keep-import {
         ordered-by user;
         description "Import policy";
         junos:must "(\"policy-options policy-statement \")";
         junos:must-message "policy-options policy-statement";
         type jt:policy-algebra;
       }
     }
     leaf accept-local-nexthop {
       description "Enable processing of routes with own nexthop";
       type empty;
     }
     leaf accept-own {
       description "Enable processing of routes with own originator-id or nexthop";
       type empty;
     }
   }
   grouping bgp-afi-labeled {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       junos:must "(!(\"system processes routing bgp rib-sharding\"))";
       junos:must-message "Can't be configured together with rib-sharding";
       description "Delay route updates for this family until FIB-sync";
       uses apply-advanced;
       leaf always-wait-for-krt-drain {
         description "Wait for KRT-queue drain for more-specific prefixes";
         type empty;
       }
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     container aggregate-label {
       presence "enable aggregate-label";
       description "Aggregate labels of incoming routes with the same FEC";
       uses apply-advanced;
       leaf community {
         description "Community to identify the FEC of incoming routes";
         type string;
       }
     }
     leaf per-prefix-label {
       description "Allocate a unique label to each advertised prefix";
       type empty;
     }
     leaf per-group-label {
       description "Advertise prefixes with unique labels per group";
       type empty;
     }
     container traffic-statistics {
       description "Collect statistics for BGP label-switched paths";
       presence "enable traffic-statistics";
       uses bgpaf-traffic-statistics;
     }
     list topology {
       key name;
       ordered-by user;
       description "Multi topology routing tables";
       junos:must "(!(\"system processes routing bgp rib-sharding\"))";
       junos:must-message "Can't be configured together with rib-sharding";
       junos:must "(!(\"routing-options no-multi-topology-routing\"))";
       junos:must-message "Multi topology routing is disabled";
       leaf name {
         description "Topology name";
         type string {
           junos:posix-pattern "!^((.*:.*)|(.{129,}))$";
           junos:pattern-message "Must be a non-reserved string of 128 characters or less";
         }
       }
       uses apply-advanced;
       leaf community {
         description "Community to identify multi topology routes";
         type string;
       }
     }
     container rib {
       description "Select table used by labeled unicast routes";
       uses rib-inet3;
     }
     container explicit-null {
       presence "enable explicit-null";
       description "Advertise explicit null";
       leaf connected-only {
         description "Advertise explicit null only for connected routes";
         type empty;
       }
     }
     container protection {
       presence "enable protection";
       junos:must "((!(\".. .. .. .. type internal\") && !(\".. .. .. .. .. type internal\")))";
       junos:must-message "Protection for labeled-bgp valid only for EBGP";
       description "Compute backup path for active nexthop failure";
       uses apply-advanced;
     }
     container egress-protection {
       presence "enable egress-protection";
       junos:must "(!(\".. .. .. .. type external\"))";
       junos:must-message "Egress-protection is valid only for IBGP";
       description "Egress router protection";
       uses apply-advanced;
       container context-identifier {
         description "Context identifier";
         uses apply-advanced;
         leaf context-id {
           description "IP address";
           junos:must "(\"protocols mpls egress-protection context-identifier $$ primary\")";
           junos:must-message "context-identifier must be type primary";
           junos:must "(\"protocols mpls egress-protection context-identifier $$\")";
           junos:must-message "same context-identifier must be defined in protocols mpls egress-protection";
           type jt:ipv4addr;
         }
       }
       leaf-list keep-import {
         ordered-by user;
         description "Import policy";
         junos:must "(\"policy-options policy-statement \")";
         junos:must-message "policy-options policy-statement";
         type jt:policy-algebra;
       }
     }
     leaf resolve-vpn {
       description "Install received NLRI in inet.3 also";
       type empty;
     }
     container entropy-label {
       presence "enable entropy-label";
       description "Use entropy label for entropy label capable BGP LSPs";
       uses apply-advanced;
       leaf-list import {
         ordered-by user;
         description "Policy to select BGP LSPs to use entropy label";
         type jt:policy-algebra;
       }
       leaf no-next-hop-validation {
         description "Don't validate next hop field against route next hop";
         type empty;
       }
     }
   }
   grouping bgp-afi-srte {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     leaf damping {
       description "Enable route flap damping";
       type empty;
     }
     container loops {
       description "Allow local AS in received AS paths";
       uses bgpaf-loops;
     }
     container graceful-restart {
       description "BGP graceful restart options";
       uses bgp-af-gr;
     }
     leaf no-install {
       description "Dont install received routes in forwarding";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
   }
   grouping bgp-afi-topo {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       junos:must "(!(\"system processes routing bgp rib-sharding\"))";
       junos:must-message "Can't be configured together with rib-sharding";
       description "Delay route updates for this family until FIB-sync";
       uses apply-advanced;
       leaf always-wait-for-krt-drain {
         description "Wait for KRT-queue drain for more-specific prefixes";
         type empty;
       }
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     container protection {
       presence "enable protection";
       junos:must "((!(\".. .. .. .. type internal\") && !(\".. .. .. .. .. type internal\")))";
       junos:must-message "Protection is valid only for EBGP";
       description "Compute backup path for active nexthop failure";
     }
     list topology {
       key name;
       ordered-by user;
       description "Multi topology routing tables";
       junos:must "(!(\"system processes routing bgp rib-sharding\"))";
       junos:must-message "Can't be configured together with rib-sharding";
       junos:must "(!(\"routing-options no-multi-topology-routing\"))";
       junos:must-message "Multi topology routing is disabled";
       leaf name {
         description "Topology name";
         type string {
           junos:posix-pattern "!^((.*:.*)|(.{129,}))$";
           junos:pattern-message "Must be a non-reserved string of 128 characters or less";
         }
       }
       uses apply-advanced;
       leaf community {
         description "Community to identify multi topology routes";
         type string;
       }
     }
   }
   grouping bgp-afi-vpn {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       junos:must "(!(\"system processes routing bgp rib-sharding\"))";
       junos:must-message "Can't be configured together with rib-sharding";
       description "Delay route updates for this family until FIB-sync";
       uses apply-advanced;
       leaf always-wait-for-krt-drain {
         description "Wait for KRT-queue drain for more-specific prefixes";
         type empty;
       }
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     container aggregate-label {
       presence "enable aggregate-label";
       description "Aggregate labels of incoming routes with the same FEC";
       uses apply-advanced;
       leaf community {
         description "Community to identify the FEC of incoming routes";
         type string;
       }
     }
   }
   grouping bgp-afi-vpn-protection {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       junos:must "(!(\"system processes routing bgp rib-sharding\"))";
       junos:must-message "Can't be configured together with rib-sharding";
       description "Delay route updates for this family until FIB-sync";
       uses apply-advanced;
       leaf always-wait-for-krt-drain {
         description "Wait for KRT-queue drain for more-specific prefixes";
         type empty;
       }
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     container aggregate-label {
       presence "enable aggregate-label";
       description "Aggregate labels of incoming routes with the same FEC";
       uses apply-advanced;
       leaf community {
         description "Community to identify the FEC of incoming routes";
         type string;
       }
     }
     container egress-protection {
       presence "enable egress-protection";
       junos:must "(!(\".. .. .. .. type external\"))";
       junos:must-message "Egress-protection is valid only for IBGP";
       description "Egress router protection";
       uses apply-advanced;
       container context-identifier {
         description "Context identifier";
         uses apply-advanced;
         leaf context-id {
           description "IP address";
           junos:must "(\"protocols mpls egress-protection context-identifier $$ primary\")";
           junos:must-message "context-identifier must be type primary";
           junos:must "(\"protocols mpls egress-protection context-identifier $$\")";
           junos:must-message "same context-identifier must be defined in protocols mpls egress-protection";
           type jt:ipv4addr;
         }
       }
       leaf-list keep-import {
         ordered-by user;
         description "Import policy";
         junos:must "(\"policy-options policy-statement \")";
         junos:must-message "policy-options policy-statement";
         type jt:policy-algebra;
       }
     }
   }
   grouping bgp-output-queue-priority-class {
     choice class {
       case case_1 {
         leaf priority {
           description "Output queue priority; higher is better";
           type union {
             type string {
               pattern "<.*>|$.*";
             }
             type uint32 {
               range "1 .. 16";
             }
           }
         }
       }
       case case_2 {
         leaf expedited {
           description "Expedited queue; highest priority";
           type empty;
         }
       }
     }
   }
   grouping bgp_filter_obj {
     description "Filter to apply to tracing";
     leaf match-on {
       description "Argument on which to match";
       type enumeration {
         enum "prefix" {
           description "Filter based on prefix";
         }
       }
     }
     leaf-list policy {
       ordered-by user;
       description "Filter policy";
       type jt:policy-algebra;
     }
   }
   grouping bgpaf-accepted-prefix-limit {
     uses apply-advanced;
     leaf maximum {
       description "Maximum number of prefixes accepted from a peer";
       type union {
         type string {
           pattern "<.*>|$.*";
         }
         type uint32 {
           range "1 .. 4294967295";
         }
       }
     }
     container teardown {
       presence "enable teardown";
       junos:must "(!(\".. hide-excess\"))";
       junos:must-message "Can't be configured together with hide-excess";
       junos:must "(!(\".. drop-excess\"))";
       junos:must-message "Can't be configured together with drop-excess";
       description "Clear peer connection on reaching limit";
       uses apply-advanced;
       leaf limit-threshold {
         description "Percentage of prefix-limit to start warnings";
         type union {
           type string {
             pattern "<.*>|$.*";
           }
           type uint32 {
             range "1 .. 100";
           }
         }
       }
       container idle-timeout {
         presence "enable idle-timeout";
         description "Timeout before attempting to restart peer";
         choice idle-parm {
           case case_1 {
             leaf forever {
               description "Idle the peer until the user intervenes";
               type empty;
             }
           }
           case case_2 {
             leaf timeout {
               description "Timeout value, in minutes, for restarting peer";
               type union {
                 type string {
                   pattern "<.*>|$.*";
                 }
                 type uint32 {
                   range "1 .. 2400";
                 }
               }
             }
           }
         }
       }
     }
     container drop-excess {
       presence "enable drop-excess";
       junos:must "(!(\".. hide-excess\"))";
       junos:must-message "Can't be configured together with hide-excess";
       junos:must "(!(\".. teardown\"))";
       junos:must-message "Can't be configured together with teardown";
       description "Drop routes from peer on reaching limit";
       uses apply-advanced;
       leaf limit-threshold {
         description "Percentage of prefix-limit to start warnings";
         type union {
           type string {
             pattern "<.*>|$.*";
           }
           type uint32 {
             range "1 .. 100";
           }
         }
       }
     }
     container hide-excess {
       presence "enable hide-excess";
       junos:must "(!(\".. teardown\"))";
       junos:must-message "Can't be configured together with teardown";
       junos:must "(!(\".. drop-excess\"))";
       junos:must-message "Can't be configured together with drop-excess";
       description "Hide routes from peer on reaching limit";
       uses apply-advanced;
       leaf limit-threshold {
         description "Percentage of prefix-limit to start warnings";
         type union {
           type string {
             pattern "<.*>|$.*";
           }
           type uint32 {
             range "1 .. 100";
           }
         }
       }
     }
   }
   grouping bgpaf-aigp-options {
     uses apply-advanced;
     leaf disable {
       description "Disable sending and receiving of AIGP attribute";
       type empty;
     }
   }
   grouping bgpaf-loops {
     uses apply-advanced;
     leaf loops {
       description "AS-Path loop count";
       type union {
         type string {
           pattern "<.*>|$.*";
         }
         type int32 {
           range "1 .. 10";
         }
       }
     }
   }
   grouping bgpaf-prefix-limit {
     uses apply-advanced;
     leaf maximum {
       description "Maximum number of prefixes from a peer";
       type union {
         type string {
           pattern "<.*>|$.*";
         }
         type uint32 {
           range "1 .. 4294967295";
         }
       }
     }
     container teardown {
       presence "enable teardown";
       junos:must "(!(\".. hide-excess\"))";
       junos:must-message "Can't be configured together with hide-excess";
       junos:must "(!(\".. drop-excess\"))";
       junos:must-message "Can't be configured together with drop-excess";
       description "Clear peer connection on reaching limit";
       uses apply-advanced;
       leaf limit-threshold {
         description "Percentage of prefix-limit to start warnings";
         type union {
           type string {
             pattern "<.*>|$.*";
           }
           type uint32 {
             range "1 .. 100";
           }
         }
       }
       container idle-timeout {
         presence "enable idle-timeout";
         description "Timeout before attempting to restart peer";
         choice idle-parm {
           case case_1 {
             leaf forever {
               description "Idle the peer until the user intervenes";
               type empty;
             }
           }
           case case_2 {
             leaf timeout {
               description "Timeout value, in minutes, for restarting peer";
               type union {
                 type string {
                   pattern "<.*>|$.*";
                 }
                 type uint32 {
                   range "1 .. 2400";
                 }
               }
             }
           }
         }
       }
     }
     container drop-excess {
       presence "enable drop-excess";
       junos:must "(!(\".. hide-excess\"))";
       junos:must-message "Can't be configured together with hide-excess";
       junos:must "(!(\".. teardown\"))";
       junos:must-message "Can't be configured together with teardown";
       description "Drop routes from peer on reaching limit";
       uses apply-advanced;
       leaf limit-threshold {
         description "Percentage of prefix-limit to start warnings";
         type union {
           type string {
             pattern "<.*>|$.*";
           }
           type uint32 {
             range "1 .. 100";
           }
         }
       }
     }
     container hide-excess {
       presence "enable hide-excess";
       junos:must "(!(\".. teardown\"))";
       junos:must-message "Can't be configured together with teardown";
       junos:must "(!(\".. drop-excess\"))";
       junos:must-message "Can't be configured together with drop-excess";
       description "Hide routes from peer on reaching limit";
       uses apply-advanced;
       leaf limit-threshold {
         description "Percentage of prefix-limit to start warnings";
         type union {
           type string {
             pattern "<.*>|$.*";
           }
           type uint32 {
             range "1 .. 100";
           }
         }
       }
     }
   }
   grouping bgpaf-traffic-statistics {
     uses apply-advanced;
     leaf labeled-path {
       description "Ingress labeled path statistics";
       type empty;
     }
     container file {
       description "Statistics file options";
       leaf filename {
         description "Name of file in which to write trace information";
         type string {
           length "1 .. 1024";
           junos:posix-pattern "![/ %]";
           junos:pattern-message "Must not contain '/', % or a space";
         }
       }
       leaf replace {
         description "Replace trace file rather than appending to it";
         status deprecated;
         type empty;
       }
       leaf size {
         description "Maximum trace file size";
         type string;
       }
       leaf files {
         description "Maximum number of trace files";
         default "10";
         type union {
           type string {
             pattern "<.*>|$.*";
           }
           type uint32 {
             range "2 .. 1000";
           }
         }
       }
       leaf no-stamp {
         description "Do not timestamp trace file";
         status deprecated;
         type empty;
       }
       choice world-readable-choice {
         leaf world-readable {
           description "Allow any user to read the log file";
           type empty;
         }
         leaf no-world-readable {
           description "Don't allow any user to read the log file";
           type empty;
         }
       }
     }
     leaf interval {
       description "Time to collect statistics (seconds)";
       type union {
         type string {
           pattern "<.*>|$.*";
         }
         type int32 {
           range "60 .. 65535";
         }
       }
     }
   }
   grouping juniper-protocols-bgpmcast {
     description "BGP Multicast configuration";
     uses apply-advanced;
     container traceoptions {
       description "Trace options for BGP Multicast";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
   }
   grouping juniper-protocols-bridge {
     uses apply-advanced;
     container traceoptions {
       description "Trace options for Layer 2 address service";
       uses apply-advanced;
       leaf no-remote-trace {
         description "Disable remote tracing";
         junos:must "(\"system tracing\")";
         junos:must-message "'no-remote-trace' is valid only when [system tracing] is configured";
         type empty;
       }
       container file {
         description "Trace file information";
         leaf filename {
           description "Name of file in which to write trace information";
           type string {
             length "1 .. 1024";
             junos:posix-pattern "![/ %]";
             junos:pattern-message "Must not contain '/', % or a space";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       leaf level {
         description "Level of debugging output";
         default "error";
         type enumeration {
           enum "error" {
             description "Match error conditions";
           }
           enum "warning" {
             description "Match warning messages";
           }
           enum "notice" {
             description "Match conditions that should be handled specially";
           }
           enum "info" {
             description "Match informational messages";
           }
           enum "verbose" {
             description "Match verbose messages";
           }
           enum "all" {
             description "Match all levels";
           }
         }
       }
       list flag {
         key name;
         ordered-by user;
         description "Type of operation or event to include in trace";
         leaf name {
           type enumeration {
             enum "configuration" {
               description "Configuration operations";
             }
             enum "routing-socket" {
               description "Routing socket operations";
             }
             enum "interface-device" {
               description "Interface device operations";
             }
             enum "interface-logical" {
               description "Logical interface operations";
             }
             enum "interface-family" {
               description "Interface family operations";
             }
             enum "bridging-domain" {
               description "Bridging domain operations";
             }
             enum "routing-instance" {
               description "Routing instance operations";
             }
             enum "bridge-interface" {
               description "Interface bridge operations";
             }
             enum "learning-domain" {
               description "Learning domain operations";
             }
             enum "ipc" {
               description "Inter-process communications operations";
             }
             enum "mac-learning" {
               description "MAC address learning operations";
             }
             enum "initialization" {
               description "Initialization operations";
             }
             enum "flood-next-hop" {
               description "Flood next hop operations";
             }
             enum "irb" {
               description "Integrated routing and bridging operations";
             }
             enum "vpls-ping" {
               description "VPLS ping operations";
             }
             enum "vpls-loop-prev" {
               description "VPLS loop prevention";
             }
             enum "logical-system" {
               description "Logical system operations";
             }
             enum "bmac-next-hop" {
               description "Backbone Mac Next hop operations ";
             }
             enum "bridge-bmac-next-hop" {
               description "Bmac Next hop bridge operations";
             }
             enum "isid" {
               description "I-Tagged Service ID";
             }
             enum "mc-ae" {
               description "Multi-chassis AE";
             }
             enum "kack" {
               description "Kernel-acknowledgment";
             }
             enum "storm-control" {
               description "Storm-control";
             }
             enum "redundant-trunk-group" {
               description "Redundant trunk group";
             }
             enum "unknown-unicast-forwarding" {
               description "Trace unknown unicast forwarding events";
             }
             enum "vxlan" {
               description "VXLAN";
             }
             enum "l2-license" {
               description "L2 license trace";
             }
             enum "telemetry" {
               description "Telemetry";
             }
             enum "network-isolation" {
               description "Network isolation detection";
             }
             enum "all" {
               description "All operations";
             }
           }
         }
       }
       container in-memory-debug {
         presence "enable in-memory-debug";
         description "Enable trace parameters in the memory";
       }
     }
     container global-mac-move {
       presence "enable global-mac-move";
       description "Enable mac move related options at global level";
       uses apply-advanced;
       leaf notification-time {
         description "Periodical time interval in secs during which MAC move notification occurs";
         units "seconds";
         type union {
           type uint32;
           type string {
             pattern "<.*>|$.*";
           }
         }
       }
       leaf threshold-time {
         description "Time during which if certain number of MAC moves happen warrant recording";
         units "seconds";
         type union {
           type uint32;
           type string {
             pattern "<.*>|$.*";
           }
         }
       }
       leaf reopen-time {
         description "Time after which a blocked interface is reopened";
         units "seconds";
         type union {
           type uint32;
           type string {
             pattern "<.*>|$.*";
           }
         }
       }
       leaf threshold-count {
         description "Count of MAC moves which warrant recording when happen in certain time";
         units "seconds";
         type union {
           type uint32;
           type string {
             pattern "<.*>|$.*";
           }
         }
       }
       container traceoptions {
         description "Enable logging for the MAC moves";
         uses apply-advanced;
         leaf no-remote-trace {
           description "Disable remote tracing";
           junos:must "(\"system tracing\")";
           junos:must-message "'no-remote-trace' is valid only when [system tracing] is configured";
           type empty;
         }
         container file {
           description "Trace file information";
           leaf filename {
             description "Name of file in which to write trace information";
             type string {
               length "1 .. 1024";
               junos:posix-pattern "![/ %]";
               junos:pattern-message "Must not contain '/', % or a space";
             }
           }
           leaf size {
             description "Maximum trace file size";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
       }
       leaf log {
         description "Syslog all the MAC moves as stored in the mac-move-buffer";
         type empty;
       }
       leaf disable-action {
         description "Disable mac move action globally";
         type empty;
       }
       list exclusive-mac {
         key name;
         ordered-by user;
         description "MAC addresses to be excluded in mac-move-limit or in VPLS loop prevention algorithm";
         leaf name {
           description "Source MAC address";
           type jt:mac-addr-prefix;
         }
         uses apply-advanced;
       }
     }
     leaf global-mac-table-aging-time {
       description "System level MAC table aging time";
       units "seconds";
       type union {
         type string {
           pattern "<.*>|$.*";
         }
         type uint32;
       }
     }
     leaf global-mac-ip-table-aging-time {
       description "System level MAC+IP table aging time";
       units "seconds";
       type union {
         type string {
           pattern "<.*>|$.*";
         }
         type uint32 {
           range "60 .. 1000000";
         }
       }
     }
     leaf mclag-arpreq-sync {
       description "Enable syncing ARP REQ packets to peer MCLAG PE";
       type empty;
     }
     leaf global-mac-pinning-discard-notification-interval {
       description "Set interval for MAC Pinning discard notification";
       units "seconds";
       type union {
         type string {
           pattern "<.*>|$.*";
         }
         type uint32 {
           range "2 .. 86400";
         }
       }
     }
     container global-ctx-limit {
       presence "enable global-ctx-limit";
       description "Debug context history limit";
       uses apply-advanced;
       leaf ctx-limit {
         description "Debug context history limit";
         type union {
           type string {
             pattern "<.*>|$.*";
           }
           type uint32 {
             range "0 .. 5000000";
           }
         }
       }
     }
     container global-mac-limit {
       presence "enable global-mac-limit";
       description "System level MAC limit options";
       uses apply-advanced;
       leaf mac-limit {
         description "System level MAC limit";
         type union {
           type string {
             pattern "<.*>|$.*";
           }
           type uint64;
         }
       }
       leaf packet-action {
         type enumeration {
           enum "drop" {
             description "Enable packet-action drop when MAC limit is reached";
           }
         }
       }
     }
     container global-mac-ip-limit {
       presence "enable global-mac-ip-limit";
       description "System level MAC+IP limit options";
       uses apply-advanced;
       leaf mac-ip-limit {
         description "System level MAC+IP limit";
         type union {
           type string {
             pattern "<.*>|$.*";
           }
           type uint64 {
             range "20 .. 1048575";
           }
         }
       }
     }
     leaf global-mac-statistics {
       description "Enable MAC address statistics at system level";
       type empty;
     }
     leaf source-udp-port {
       description "VXLAN source UDP port";
       type union {
         type string {
           pattern "<.*>|$.*";
         }
         type uint16 {
           range "49152 .. 65535";
         }
       }
     }
     container telemetry {
       presence "enable telemetry";
       description "Streaming Telemetry Data";
       uses apply-advanced;
       leaf enable-remote-entries {
         description "Enable Remote mac and mac-ip entries";
         type empty;
       }
     }
     leaf global-no-mac-learning {
       description "Disable dynamic MAC address learning at system level";
       type empty;
     }
     leaf global-no-hw-mac-learning {
       description "Disable hardware MAC-address learning at system level";
       type empty;
     }
     leaf global-no-control-mac-aging {
       description "Disable control MAC-address aging from software";
       type empty;
     }
     leaf mclag-arp-nd-sync {
       description "Arp and ND entry sync from peer device.";
       type empty;
     }
     container crb-proxy-mac {
       description "Configure proxy MAC address to be used in MAC-IP refresh";
       uses apply-advanced;
       container family {
         description "Address family";
         uses apply-advanced;
         container inet {
           description "Inet version 4 family";
           uses apply-advanced;
           leaf mac-address {
             description "Proxy MAC address";
             type jt:mac-unicast;
           }
         }
         container inet6 {
           description "Inet version 6 family";
           uses apply-advanced;
           leaf mac-address {
             description "Proxy MAC address";
             type jt:mac-unicast;
           }
         }
       }
     }
   }
   grouping juniper-protocols-dot1x {
     uses apply-advanced;
     container traceoptions {
       description "Trace options for 802.1X";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         junos:must "(\".. file\")";
         junos:must-message "Trace file name required to enable tracing";
         leaf name {
           type enumeration {
             enum "dot1x-debug" {
               description "Trace dot1x events";
               junos:must "(!(\"protocols dot1x traceoptions flag dot1x-event\"))";
               junos:must-message "Can not configure dot1x-event with dot1x-debug flag";
             }
             enum "parse" {
               description "Trace configuration parsing";
             }
             enum "esw-if" {
               description "Trace ESW Interactions";
               junos:must "(!(\"protocols dot1x traceoptions flag dot1x-ipc\"))";
               junos:must-message "Can not configure dot1x-ipc with esw-if flag";
             }
             enum "eapol" {
               description "Trace EAPOL Transmit/Receive";
             }
             enum "config-internal" {
               description "Trace configuration internals";
             }
             enum "normal" {
               description "Trace normal events";
             }
             enum "general" {
               description "Trace general events";
             }
             enum "state" {
               description "Trace state transitions";
             }
             enum "task" {
               description "Trace routing protocol task processing";
             }
             enum "timer" {
               description "Trace routing protocol task timer processing";
             }
             enum "vlan" {
               description "Trace VLAN transactions";
             }
             enum "all" {
               description "Trace everything";
             }
             enum "dot1x-ipc" {
               description "Trace dot1x IPC interactions";
             }
             enum "dot1x-event" {
               description "Trace dot1x events";
             }
             enum "iccp" {
               description "Trace iccp events";
             }
           }
         }
         leaf disable {
           description "Disable this trace flag";
           type empty;
         }
       }
     }
     leaf ssl-certificate-path {
       description "Load SSL certificates for authentication";
       default "/var/tmp/";
       type string;
     }
     container authenticator {
       presence "enable authenticator";
       description "802.1X authenticator options";
       uses apply-advanced;
       leaf authentication-profile-name {
         description "Access profile name to use for authentication";
         junos:must "(\"access profile $$\")";
         junos:must-message "Access profile name must be defined in the [edit access profile] hierarchy";
         type string {
           length "1 .. 63";
         }
       }
       leaf no-mac-table-binding {
         description "Disable association between mac table and dot1x";
         type empty;
       }
       leaf ip-mac-session-binding {
         description "DHCP or DHCPv6 or SLAAC snooping checking for mac ageout";
         junos:must "(\".. no-mac-table-binding\")";
         junos:must-message "no-mac-table-binding must be defined in the [edit protocols dot1x authenticator] hierarchy";
         type empty;
       }
       leaf dynamic-vlan-cleanup-interval {
         description "Dynamic vlan cleanup interval";
         units "seconds";
         type union {
           type string {
             pattern "<.*>|$.*";
           }
           type uint32 {
             range "60 .. 86400";
           }
         }
       }
       container radius-reachability {
         presence "enable radius-reachability";
         description "Enable radius-rechability feature";
         uses apply-advanced;
         leaf query-period {
           description "Query period interval";
           default "120";
           units "seconds";
           type union {
             type string {
               pattern "<.*>|$.*";
             }
             type uint32 {
               range "20 .. 65535";
             }
           }
         }
       }
       container radius-options {
         presence "enable radius-options";
         description "Info sent to radius server";
         uses apply-advanced;
         leaf add-interface-text-description {
           description "Appends interface text description to NAS-Port-Id";
           type empty;
         }
         choice vlan {
           case case_1 {
             leaf use-vlan-name {
               description "Vlan name";
               type empty;
             }
           }
           case case_2 {
             leaf use-vlan-id {
               description "Vlan id";
               type empty;
             }
           }
         }
       }
       list static {
         key name;
         ordered-by user;
         description "Static MAC configuration needed to bypass 802.1X";
         leaf name {
           description "MAC addresses to bypass authentication";
           type jt:mac-addr-prefix;
         }
         uses apply-advanced;
         leaf vlan-assignment {
           description "VLAN name or 802.1q tag for the MAC address";
           junos:must "(!(\"vlans $$ vlan-id-list\"))";
           junos:must-message "vlan with vlan-id-list not supported under static MAC vlan-assignment";
           junos:must "((\"vlans $$\" || any \"vlans <*> vlan-id $$\"))";
           junos:must-message "vlan assigned is not configured";
           type string {
           }
         }
         leaf interface {
           description "Interface on which authentication is bypassed";
           junos:must "(\".. .. interface $$ supplicant multiple\")";
           junos:must-message "Static MAC cannot be configured on interface in single or single-secure mode";
           junos:must "((!(\"interfaces ${interface} vlan-tagging\") || (!(\"interfaces ${interface} flexible-vlan-tagging\") || !(\"interfaces ${interface} stacked-vlan-tagging\"))))";
           junos:must-message "Cannot configure dot1x on this interface since flexible-vlan-tagging / vlan-tagging / stacked-vlan-tagging is configured";
           junos:must "((\"interfaces $$-IFL family ethernet-switching\" || \"interfaces $$-IFL family bridge\"))";
           junos:must-message "Interface must be defined in the interfaces hierarchy with family ethernet-switching/bridge";
           type union {
             type jt:interface-name;
             type string {
               pattern "<.*>|$.*";
             }
           }
         }
       }
       list interface {
         key name;
         description "802.1X  interface specific options";
         leaf name {
           junos:must "(!(\"switch-options interface $$ no-mac-learning\"))";
           junos:must-message "no-mac-learning can not be configured on dot1x enabled interface";
           junos:must "(!(\"switch-options interface $$ persistent-learning\"))";
           junos:must-message "persistent learning can not be configured on dot1x enabled interface";
           type string;
         }
         uses apply-advanced;
         leaf ignore-port-bounce {
           description "To ignore the port-bounce request received from RADIUS server";
           type empty;
         }
         leaf-list authentication-order {
           ordered-by user;
           description "Flexible authentication order";
           junos:must "((\"interfaces ${interface} family bridge\" || \"interfaces ${interface} family ethernet-switching\"))";
           junos:must-message "Only supported for layer-2 intefaces";
           type enumeration {
             enum "dot1x" {
               description "Dot1x mode";
             }
             enum "mac-radius" {
               description "Mac radius mode";
               junos:must "(!(\"protocols dot1x supplicant interface ${interface}\"))";
               junos:must-message "Must not configure supplicant and mac-radius on same interface";
             }
             enum "captive-portal" {
               description "Captive portal mode";
               junos:must "(!(\"system phone-home\"))";
               junos:must-message "Can't configure captive-portal along with Phone-home. Delete phone-home config to enable captive-portal";
               junos:must "(!(\"protocols dot1x supplicant interface ${interface}\"))";
               junos:must-message "Must not configure supplicant and captive-portal on same interface";
               junos:must "((!(\"interfaces ${interface} family ethernet-switching interface-mode trunk\") && !(\"interfaces ${interface} family bridge interface-mode trunk\")))";
               junos:must-message "Must not configure captive-portal on trunk interface";
             }
           }
         }
         leaf disable {
           description "Disable 802.1X on this interface";
           type empty;
         }
         leaf supplicant {
           description "Set supplicant mode for this interface";
           default "single";
           type enumeration {
             enum "single" {
               description "Allow multiple clients; authenticate first client only";
             }
             enum "single-secure" {
               description "Allow and authenticate only a single client";
               junos:must "((\"interfaces ${interface} family bridge\" || \"interfaces ${interface} family ethernet-switching\"))";
               junos:must-message "Only supported for layer-2 intefaces";
             }
             enum "multiple" {
               description "Allow multiple clients; authenticate each individually";
               junos:must "(!(\"protocols dot1x supplicant interface ${interface}\"))";
               junos:must-message "Mutual authentication and multiple mode cannot be enabled on same interface";
               junos:must "((!(\"interfaces ${interface} family ethernet-switching interface-mode trunk\") && !(\"interfaces ${interface} family bridge interface-mode trunk\")))";
               junos:must-message "Must not configure multi supplicant on trunk interface";
               junos:must "((\"interfaces ${interface} family bridge\" || \"interfaces ${interface} family ethernet-switching\"))";
               junos:must-message "Only supported for layer-2 intefaces";
             }
           }
         }
         leaf retries {
           description "Number of retries after which port is placed into wait state";
           type union {
             type string {
               pattern "<.*>|$.*";
             }
             type uint32 {
               range "0 .. 10";
             }
           }
         }
         leaf quiet-period {
           description "Time to wait after an authentication failure";
           units "seconds";
           type union {
             type string {
               pattern "<.*>|$.*";
             }
             type uint32 {
               range "0 .. 65535";
             }
           }
         }
         leaf transmit-period {
           description "Interval before retransmitting initial EAPOL PDUs";
           units "seconds";
           type union {
             type string {
               pattern "<.*>|$.*";
             }
             type uint32 {
               range "1 .. 65535";
             }
           }
         }
         container multi-domain {
           presence "enable multi-domain";
           junos:must "((\"interfaces ${interface} family bridge\" || \"interfaces ${interface} family ethernet-switching\"))";
           junos:must-message "Only supported for layer-2 intefaces";
           junos:must "(\".. supplicant multiple\")";
           junos:must-message "multi-domain feature cannot be configured with single or single-secure mode";
           description "Enable multi domain authentication";
           uses apply-advanced;
           leaf packet-action {
             description "Set packet action for this interface";
             default "drop-and-log";
             type enumeration {
               enum "drop-and-log" {
                 description " Drop the client and generate the log message";
               }
               enum "shutdown" {
                 description "Disable port for excessive client authentication";
               }
             }
           }
           leaf max-data-session {
             description "Data session limit in multi domain authentication";
             type union {
               type string {
                 pattern "<.*>|$.*";
               }
               type uint32 {
                 range "1 .. 1000";
               }
             }
           }
           leaf recovery-timeout {
             description "Multi domain recovery timeout";
             units "seconds";
             type union {
               type string {
                 pattern "<.*>|$.*";
               }
               type uint32 {
                 range "60 .. 3600";
               }
             }
           }
         }
         container mac-radius {
           presence "enable mac-radius";
           junos:must "(!(\"protocols dot1x supplicant interface ${interface}\"))";
           junos:must-message "Must not configure supplicant and mac-radius on same interface";
           junos:must "((\"interfaces ${interface} family bridge\" || \"interfaces ${interface} family ethernet-switching\"))";
           junos:must-message "Only supported for layer-2 intefaces";
           description "Enable MAC-RADIUS";
           uses apply-advanced;
           leaf restrict {
             description "Bypass dot1x authentication, use MAC RADIUS only";
             type empty;
           }
           leaf flap-on-disconnect {
             description "Reset an interface on receiving a disconnect request";
             type empty;
           }
           container authentication-protocol {
             description "Set mac-radius authentication method";
             uses apply-advanced;
             choice protocols {
               case case_1 {
                 leaf eap-md5 {
                   description "Authentication protocol EAP-MD5";
                   type empty;
                 }
               }
               case case_2 {
                 leaf pap {
                   description "Authentication protocol PAP";
                   type empty;
                 }
               }
               case case_3 {
                 container eap-peap {
                   presence "enable eap-peap";
                   description "Authentication protocol EAP-PEAP";
                   uses apply-advanced;
                   leaf resume {
                     description "Enable resume functionality for faster authentication";
                     type empty;
                   }
                 }
               }
             }
           }
         }
         choice reauthentication-mode {
           case case_1 {
             leaf no-reauthentication {
               description "Disable reauthentication";
               type empty;
             }
           }
           case case_2 {
             leaf reauthentication {
               description "Reauthentication interval";
               units "seconds";
               type union {
                 type string {
                   pattern "<.*>|$.*";
                 }
                 type uint32 {
                   range "1 .. 65535";
                 }
               }
             }
           }
         }
         leaf supplicant-timeout {
           description "Time to wait for a client response";
           units "seconds";
           type union {
             type string {
               pattern "<.*>|$.*";
             }
             type uint32 {
               range "1 .. 60";
             }
           }
         }
         leaf server-timeout {
           description "Authentication server timeout interval";
           units "seconds";
           type union {
             type string {
               pattern "<.*>|$.*";
             }
             type uint32 {
               range "1 .. 60";
             }
           }
         }
         leaf maximum-requests {
           description "Number of EAPOL RequestIDs to send before timing out";
           type union {
             type string {
               pattern "<.*>|$.*";
             }
             type uint32 {
               range "1 .. 10";
             }
           }
         }
         leaf request-retry-count {
           description "Number of requests to send before timing out";
           type union {
             type string {
               pattern "<.*>|$.*";
             }
             type uint32 {
               range "1 .. 10";
             }
           }
         }
         leaf guest-vlan {
           description "VLAN name or 802.1q tag for unauthenticated or non-responsive hosts";
           junos:must "(!(\"vlans $$ vlan-id-list\"))";
           junos:must-message "vlan with vlan-id-list not supported under guest-vlan";
           junos:must "((\"vlans $$\" || any \"vlans <*> vlan-id $$\"))";
           junos:must-message "vlan assigned is not configured";
           junos:must "(!(\"interfaces ${interface} family ethernet-switching interface-mode trunk\"))";
           junos:must-message "Must not configure on this interface since the interface-mode is defined as trunk";
           junos:must "((\"interfaces ${interface} family bridge\" || \"interfaces ${interface} family ethernet-switching\"))";
           junos:must-message "Only supported for layer-2 intefaces";
           type string {
           }
         }
         container server-reject-vlan {
           junos:must "(!(\"interfaces ${interface} family ethernet-switching interface-mode trunk\"))";
           junos:must-message "Must not configure on this interface since the interface-mode is defined as trunk";
           junos:must "((\"interfaces ${interface} family bridge\" || \"interfaces ${interface} family ethernet-switching\"))";
           junos:must-message "Only supported for layer-2 intefaces";
           description "VLAN name or 802.1q tag for authentication rejected clients";
           leaf vlan-name {
             description "VLAN name or VLAN Tag (1..4095)";
             junos:must "(!(\"vlans $$ vlan-id-list\"))";
             junos:must-message "vlan with vlan-id-list not supported under server-reject-vlan";
             junos:must "((\"vlans $$\" || any \"vlans <*> vlan-id $$\"))";
             junos:must-message "vlan assigned is not configured";
             type string {
             }
           }
           leaf block-interval {
             description "Interval for authenticator to ignore the EAP-Start packets.";
             units "seconds";
             type union {
               type string {
                 pattern "<.*>|$.*";
               }
               type uint32 {
                 range "120 .. 65535";
               }
             }
           }
           leaf eapol-block {
             description "Force the authenticator to ignore EAPOL-Start packets.";
             type empty;
           }
         }
         container eapol-block {
           junos:must "((\"interfaces ${interface} family bridge\" || \"interfaces ${interface} family ethernet-switching\"))";
           junos:must-message "Only supported for layer-2 intefaces";
           description "Force the authenticator to ignore EAPOL-Start packets";
           uses apply-advanced;
           container server-fail {
             presence "enable server-fail";
             junos:must "(\".. .. server-fail\")";
             junos:must-message "server-fail action must be configured";
             description "Block EAPOL-Start during RADIUS Timeout";
             uses apply-advanced;
             leaf block-interval {
               description "Interval for authenticator to ignore the EAP-Start packets.";
               units "seconds";
               type union {
                 type string {
                   pattern "<.*>|$.*";
                 }
                 type uint32 {
                   range "120 .. 65535";
                 }
               }
             }
           }
           container mac-radius {
             presence "enable mac-radius";
             description "Block EAPOL-Start when client is authenticated in mac-radius mode";
           }
           container captive-portal {
             presence "enable captive-portal";
             description "Block EAPOL-Start when client is authenticated in captive-portal mode";
           }
         }
         leaf lldp-med-bypass {
           description "Bypass dot1x authentication, use lldp-med based authentication";
           junos:must "(\".. supplicant multiple\")";
           junos:must-message "lldp-med-bypass cannot be configured on interface in single or single-secure mode";
           type empty;
         }
         container server-fail {
           description "Action to be taken when server is inaccessible";
           choice server-fail-options {
             case case_1 {
               leaf deny {
                 description "Force client authentication to fail";
                 type empty;
               }
             }
             case case_2 {
               leaf permit {
                 description "Force client authentication to succeed";
                 type empty;
               }
             }
             case case_3 {
               leaf vlan-name {
                 description "VLAN name or 802.1q tag for unreachable servers";
                 junos:must "(!(\"vlans $$ vlan-id-list\"))";
                 junos:must-message "vlan with vlan-id-list not supported under server-fail vlan";
                 junos:must "((\"vlans $$\" || any \"vlans <*> vlan-id $$\"))";
                 junos:must-message "vlan assigned is not configured";
                 junos:must "(!(\"interfaces ${interface} family ethernet-switching interface-mode trunk\"))";
                 junos:must-message "Must not configure on this interface since the interface-mode is defined as trunk";
                 junos:must "((\"interfaces ${interface} family bridge\" || \"interfaces ${interface} family ethernet-switching\"))";
                 junos:must-message "Only supported for layer-2 intefaces";
                 type string {
                 }
               }
             }
             case case_4 {
             }
             case case_5 {
               leaf use-cache {
                 description "Use the previous state of the client";
                 type empty;
               }
             }
           }
         }
         container server-fail-voip {
           junos:must "((\"interfaces ${interface} family bridge\" || \"interfaces ${interface} family ethernet-switching\"))";
           junos:must-message "Only supported for layer-2 intefaces";
           junos:must "((\".. server-fail \" && !(\".. server-fail deny\")))";
           junos:must-message "'server-fail permit' or 'vlan-name' or 'use-cache' must be configured";
           description "Action to be taken for VOIP client when server is inaccessible";
           choice server-fail-options {
             case case_1 {
               leaf deny {
                 description "Force VoIP client authentication to fail";
                 type empty;
               }
             }
             case case_2 {
               leaf permit {
                 description "Force VoIP client authentication to succeed";
                 type empty;
               }
             }
             case case_3 {
               leaf vlan-name {
                 description "Configured VoIP VLAN name or 802.1q tag for unreachable servers";
                 junos:must "(!(\"interfaces ${interface} family ethernet-switching interface-mode trunk\"))";
                 junos:must-message "Must not configure on this interface since the interface-mode is defined as trunk";
                 type string {
                 }
               }
             }
             case case_4 {
               leaf use-cache {
                 description "Use the previous state of the VoIP client";
                 type empty;
               }
             }
           }
         }
         leaf redirect-url {
           description "CWA redirect URL to be used for unauthenticated users";
           junos:must "((\"interfaces ${interface} family bridge\" || \"interfaces ${interface} family ethernet-switching\"))";
           junos:must-message "Only supported for layer-2 intefaces";
           junos:must "((!(\"interfaces ${interface} family ethernet-switching interface-mode trunk\") && !(\"interfaces ${interface} family bridge interface-mode trunk\")))";
           junos:must-message "Must not configure redirect-url on this interface since the interface-mode is defined as trunk";
           type string {
             length "10 .. 247";
             junos:posix-pattern "^((http)|(https))://";
             junos:pattern-message "URL starts with http or https";
           }
         }
         leaf no-tagged-mac-authentication {
           description "Don't allow tagged mac for radius authentication";
           junos:must "((\"interfaces ${interface} family bridge\" || \"interfaces ${interface} family ethernet-switching\"))";
           junos:must-message "Only supported for layer-2 intefaces";
           junos:must "(\"interfaces ${interface} family ethernet-switching interface-mode trunk\")";
           junos:must-message "This option is supported only on trunk interface";
           junos:must "(!(\".. supplicant single-secure\"))";
           junos:must-message "Cannot be configured on single-secure dot1x interface";
           junos:must "(!(\".. supplicant multiple\"))";
           junos:must-message "Cannot be configured on multiple supplicant dot1x interface";
           type empty;
         }
         leaf retain-mac-aged-session {
           description "Retain mac aged out session";
           type empty;
         }
       }
     }
     container supplicant {
       description "802.1X supplicant options";
       uses apply-advanced;
       list interface {
         key name;
         description "802.1X supplicant interface specific options";
         leaf name {
           type string;
         }
         uses apply-advanced;
         leaf authentication-method {
           description "802.1X supplicant authentication protocol for this interface";
           default "eap-tls";
           type enumeration {
             enum "eap-tls" {
               description "Supplicant authentication protocol EAP-TLS";
               junos:must "(\".. local-certificate\")";
               junos:must-message "local-certificate must be configured";
             }
           }
         }
         leaf local-certificate {
           description "Local certificate identifier to be presented for authentication";
           type string {
             junos:posix-pattern "^.{1,32}$";
             junos:pattern-message "Must be string of 32 characters or less";
           }
         }
         leaf user-id {
           description "User id, to be presented for authentication";
           type string {
             length "1 .. 63";
           }
         }
         leaf password {
           description "Password, to be presented for authentication";
           type string {
             length "1 .. 63";
           }
         }
       }
     }
   }
   grouping juniper-protocols-esis {
     uses apply-advanced;
     choice enable-disable {
       case case_1 {
         leaf disable {
           description "Disable ES-IS";
           type empty;
         }
       }
     }
     container traceoptions {
       description "Trace options for ES-IS";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "error" {
               description "Trace errored packets";
             }
             enum "esh" {
               description "Trace end system hello packets";
             }
             enum "ish" {
               description "Trace intermediate system hello packets";
             }
             enum "graceful-restart" {
               description "Trace graceful restart events";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     leaf preference {
       description "Preference of routes";
       type union {
         type uint32;
         type string {
           pattern "<.*>|$.*";
         }
       }
     }
     container graceful-restart {
       description "ES-IS graceful restart options";
       choice enable-disable {
         case case_1 {
           leaf disable {
             description "Disable graceful restart";
             type empty;
           }
         }
       }
       leaf restart-duration {
         description "Maximum time for graceful restart to finish";
         units "seconds";
         type union {
           type string {
             pattern "<.*>|$.*";
           }
           type uint32 {
             range "30 .. 300";
           }
         }
       }
     }
     list interface {
       key name;
       description "Interface configuration";
       leaf name {
         description "Interface name";
         type union {
           type jt:interface-name;
           type string {
             pattern "<.*>|$.*";
           }
         }
       }
       uses apply-advanced;
       leaf hold-time {
         description "Time after which neighbors think the interface is down";
         units "seconds";
         type union {
           type string {
             pattern "<.*>|$.*";
           }
           type uint32 {
             range "1 .. 65535";
           }
         }
       }
       leaf end-system-configuration-timer {
         description "Suggested end system configuration timer";
         units "seconds";
         type union {
           type string {
             pattern "<.*>|$.*";
           }
           type uint32 {
             range "1 .. 65535";
           }
         }
       }
       choice enable-disable {
         case case_1 {
           leaf disable {
             description "Disable ES-IS on this interface";
             type empty;
           }
         }
       }
     }
   }
   grouping juniper-protocols-evpn-interconnect {
     description "Interconnect configuration for the routing instance";
     uses apply-advanced;
     leaf-list vrf-import {
       ordered-by user;
       description "Import policy for Interconnect";
       junos:must "(\".. route-distinguisher\")";
       junos:must-message "route distinguisher must be defined for vrf-import";
       type jt:policy-algebra;
     }
     leaf-list vrf-export {
       ordered-by user;
       description "Export policy for Interconnect";
       junos:must "(\".. route-distinguisher\")";
       junos:must-message "route distinguisher must be defined for vrf-export";
       type jt:policy-algebra;
     }
     container vrf-target {
       junos:must "(\".. route-distinguisher\")";
       junos:must-message "route distinguisher must be defined for vrf-target";
       description "Interconnect target community configuration";
       uses apply-advanced;
       leaf community {
         description "Target community to use in import and export";
         type string {
           junos:posix-pattern "^[a-z]+:[0-9.]+L?:[0-9]+$";
           junos:pattern-message "Use format 'target:x:y' where 'x' is an AS number followed by an optional 'L' (To indicate 4 byte AS), or an IP address and 'y' is a number. e.g. target:123456L:100";
         }
       }
       leaf import {
         description "Target community to use when filtering on import";
         type string {
           junos:posix-pattern "^[a-z]+:[0-9.]+L?:[0-9]+$";
           junos:pattern-message "Use format 'target:x:y' where 'x' is an AS number followed by an optional 'L' (To indicate 4 byte AS), or an IP address and 'y' is a number. e.g. target:123456L:100";
         }
       }
       leaf export {
         description "Target community to use when marking routes on export";
         type string {
           junos:posix-pattern "^[a-z]+:[0-9.]+L?:[0-9]+$";
           junos:pattern-message "Use format 'target:x:y' where 'x' is an AS number followed by an optional 'L' (To indicate 4 byte AS), or an IP address and 'y' is a number. e.g. target:123456L:100";
         }
       }
     }
     container route-distinguisher {
       description "Route distinguisher for this interconnect";
       leaf rd-type {
         description "Number in (16 bit:32 bit) or (32 bit 'L':16 bit) or (IP address:16 bit) format";
         type string {
           junos:posix-pattern "^[0-9.]+L?:[0-9]+$";
           junos:pattern-message "Use format 'x:y' where 'x' is an AS number followed by an optional 'L' (To indicate 4 byte AS), or an IP address and 'y' is a number. e.g. 123456L:100";
         }
       }
     }
     container esi {
       description "ESI configuration of interconnect";
       uses apply-advanced;
       leaf identifier {
         description "ESI value for interconnect";
         junos:must "(unique \"interfaces <*> esi $$\")";
         junos:must-message "ESI value must be unique across all IFDs and IFLs";
         type jt:esi;
       }
       choice mode {
         case case_1 {
           leaf all-active {
             description "All-active mode";
             type empty;
           }
         }
       }
       container df-election-type {
         presence "enable df-election-type";
         description "DF Election Type";
         uses apply-advanced;
         choice pref_choice {
           case case_1 {
             container preference {
               presence "enable preference";
               description "Preference based DF election";
               uses apply-advanced;
               leaf value {
                 description "Preference value for EVPN Multihoming DF election";
                 default "32767";
                 type union {
                   type string {
                     pattern "<.*>|$.*";
                   }
                   type uint32 {
                     range "0 .. 65535";
                   }
                 }
               }
             }
           }
         }
         choice mod_choice {
           case case_1 {
             container mod {
               presence "enable mod";
               junos:must "(!(\".. preference\"))";
               junos:must-message "preference must not be configured";
               description "MOD based DF election";
             }
           }
         }
       }
     }
     leaf-list interconnected-vni-list {
       description "List of translated VNIs (1..16777214) or all, that are to be EVPN interconnected";
       type string;
     }
     leaf encapsulation {
       type enumeration {
         enum "mpls" {
           description "MPLS encapsulation";
         }
         enum "vxlan" {
           description "VXLAN encapsulation";
         }
       }
     }
   }
   grouping juniper-protocols-isis {
     uses apply-advanced;
     list interface {
       key name;
       description "Interface configuration";
       leaf name {
         description "Interface name";
         type union {
           type jt:interface-name;
           type string {
             pattern "<.*>|$.*";
           }
         }
       }
       uses apply-advanced;
       container ldp-synchronization {
         description "Advertise maximum metric until LDP is operational";
         presence "enable ldp-synchronization";
         uses ldp-sync-obj;
       }
       list level {
         key name;
         ordered-by user;
         description "Configure levels on this interface";
         leaf name {
           description "IS-IS level number";
           type union {
             type string {
               pattern "<.*>|$.*";
             }
             type uint32 {
               range "1 .. 2";
             }
           }
         }
         uses apply-advanced;
         leaf te-metric {
           description "Traffic engineering metric";
           type union {
             type string {
               pattern "<.*>|$.*";
             }
             type uint32 {
               range "0 .. 16777215";
             }
           }
         }
         leaf no-advertise-adjacency-segment {
           description "Do not advertise an adjacency segment for this level";
           type empty;
         }
         container ipv4-adjacency-segment {
           junos:must "(!(\".. no-advertise-adjacency-segment\"))";
           junos:must-message "ipv4-adjacency-segment can't be configured if no-advertise-adjacency-segment is configured in the level";
           junos:must "(!(\".. .. no-advertise-adjacency-segment\"))";
           junos:must-message "ipv4-adjacency-segment can't be configured if no-advertise-adjacency-segment is configured in the same interface";
           description "Configure ipv4 adjacency segment";
           uses apply-advanced;
           container protected {
             description "Adjacency SID is eligible for protection";
             choice adjsid-type {
               case case_1 {
                 container index {
                   description "Adjacency SID indexed from SRGB";
                   leaf index-number {
                     type union {
                       type string {
                         pattern "<.*>|$.*";
                       }
                       type uint32 {
                         range "0 .. 199999";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
           container unprotected {
             description "Adjacency SID uneligible for protection";
             choice adjsid-type {
               case case_1 {
                 container index {
                   description "Adjacency SID indexed from SRGB";
                   leaf index-number {
                     type union {
                       type string {
                         pattern "<.*>|$.*";
                       }
                       type uint32 {
                         range "0 .. 199999";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
         }
         container ipv6-adjacency-segment {
           junos:must "(!(\".. no-advertise-adjacency-segment\"))";
           junos:must-message "ipv6-adjacency-segment can't be configured if no-advertise-adjacency-segment is configured in the same level";
           junos:must "(!(\".. .. no-advertise-adjacency-segment\"))";
           junos:must-message "ipv6-adjacency-segment can't be configured if no-advertise-adjacency-segment is configured in the same interface";
           description "Configure ipv6 adjacency segment";
           uses apply-advanced;
           container protected {
             description "Adjacency SID is eligible for protection";
             choice adjsid-type {
               case case_1 {
                 container index {
                   description "Adjacency SID indexed from SRGB";
                   leaf index-number {
                     type union {
                       type string {
                         pattern "<.*>|$.*";
                       }
                       type uint32 {
                         range "0 .. 199999";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
           container unprotected {
             description "Adjacency SID uneligible for protection";
             choice adjsid-type {
               case case_1 {
                 container index {
                   description "Adjacency SID indexed from SRGB";
                   leaf index-number {
                     type union {
                       type string {
                         pattern "<.*>|$.*";
                       }
                       type uint32 {
                         range "0 .. 199999";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
         }
         container srm6-adjacency-segment {
           description "Configure srm6 adjacency segment";
           uses apply-advanced;
           container unprotected {
             description "Adjacency SID uneligible for protection";
             leaf sid {
               description "Set Adjacency SID Value";
               type union {
                 type string {
                   pattern "<.*>|$.*";
                 }
                 type uint32 {
                   range "1 .. 65535";
                 }
               }
             }
           }
         }
         container srv6-adjacency-segment {
           description "Configure srv6 adjacency segment";
           uses apply-advanced;
           container protected {
             presence "enable protected";
             description "SRv6 Adjacency segment is eligible for protection";
             uses apply-advanced;
             list locator {
               key name;
               ordered-by user;
               description "Locator to bind SRv6 adjacency segment";
               leaf name {
                 description "Locator name";
                 junos:must "(\"routing-options source-packet-routing srv6 locator $$\")";
                 junos:must-message "Referenced source-packet-routing srv6 must be defined";
                 type string;
               }
               uses apply-advanced;
               list end-x-sid {
                 key name;
                 ordered-by user;
                 description "Endpoint 128 bit address";
                 leaf name {
                   type jt:ipv6addr;
                 }
                 uses apply-advanced;
                 container flavor {
                   presence "enable flavor";
                   uses apply-advanced;
                   leaf psp {
                     description "Penultimate segment pop of the SRH";
                     type empty;
                   }
                   leaf usp {
                     description "Ultimate segment pop of the SRH";
                     type empty;
                   }
                   leaf usd {
                     description "Ultimate segment decapsulation";
                     type empty;
                   }
                 }
               }
             }
           }
           container unprotected {
             presence "enable unprotected";
             description "SRv6 Adjacency segment is uneligible for protection";
             uses apply-advanced;
             list locator {
               key name;
               ordered-by user;
               description "Locator to bind SRv6 adjacency segment";
               leaf name {
                 description "Locator name";
                 junos:must "(\"routing-options source-packet-routing srv6 locator $$\")";
                 junos:must-message "Referenced source-packet-routing srv6 must be defined";
                 type string;
               }
               uses apply-advanced;
               list end-x-sid {
                 key name;
                 ordered-by user;
                 description "Endpoint 128 bit address";
                 leaf name {
                   type jt:ipv6addr;
                 }
                 uses apply-advanced;
                 container flavor {
                   presence "enable flavor";
                   uses apply-advanced;
                   leaf psp {
                     description "Penultimate segment pop of the SRH";
                     type empty;
                   }
                   leaf usp {
                     description "Ultimate segment pop of the SRH";
                     type empty;
                   }
                   leaf usd {
                     description "Ultimate segment decapsulation";
                     type empty;
                   }
                 }
               }
             }
           }
         }
         list lan-neighbor {
           key name;
           ordered-by user;
           description "Configuration specific to a LAN neighbor";
           junos:must "(!(\".. ipv6-adjacency-segment\"))";
           junos:must-message "lan-neighbor can't be configured if ipv6-adjacency-segment is configured in the same interface";
           junos:must "(!(\".. ipv4-adjacency-segment\"))";
           junos:must-message "lan-neighbor can't be configured if ipv4-adjacency-segment is configured in the same interface";
           junos:must "(!(\".. no-advertise-adjacency-segment\"))";
           junos:must-message "lan-neighbor can't be configured if no-advertise-adjacency-segment is configured in the same level";
           junos:must "(!(\".. .. no-advertise-adjacency-segment\"))";
           junos:must-message "lan-neighbor can't be configured if  no-advertise-adjacency-segment is configured in the same interface";
           junos:must "(!(\".. .. point-to-point\"))";
           junos:must-message "lan-neighbor can't be configured for point-to-point interfaces";
           leaf name {
             description "Neighbor's sysid";
             type jt:sysid;
           }
           uses apply-advanced;
           container ipv4-adjacency-segment {
             junos:must "(!(\".. no-advertise-adjacency-segment\"))";
             junos:must-message "ipv4-adjacency-segment can't be configured if no-advertise-adjacency-segment is configured in the level";
             junos:must "(!(\".. .. no-advertise-adjacency-segment\"))";
             junos:must-message "ipv4-adjacency-segment can't be configured if no-advertise-adjacency-segment is configured in the same interface";
             description "Configure ipv4 adjacency segment";
             uses apply-advanced;
             container protected {
               description "Adjacency SID is eligible for protection";
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
             container unprotected {
               description "Adjacency SID uneligible for protection";
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
           }
           container ipv6-adjacency-segment {
             junos:must "(!(\".. no-advertise-adjacency-segment\"))";
             junos:must-message "ipv6-adjacency-segment can't be configured if no-advertise-adjacency-segment is configured in the same level";
             junos:must "(!(\".. .. no-advertise-adjacency-segment\"))";
             junos:must-message "ipv6-adjacency-segment can't be configured if no-advertise-adjacency-segment is configured in the same interface";
             description "Configure ipv6 adjacency segment";
             uses apply-advanced;
             container protected {
               description "Adjacency SID is eligible for protection";
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
             container unprotected {
               description "Adjacency SID uneligible for protection";
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
           }
           container srm6-adjacency-segment {
             description "Configure srm6 adjacency segment";
             uses apply-advanced;
             container unprotected {
               description "Adjacency SID uneligible for protection";
               leaf sid {
                 description "Set Adjacency SID Value";
                 type union {
                   type string {
                     pattern "<.*>|$.*";
                   }
                   type uint32 {
                     range "1 .. 65535";
                   }
                 }
               }
             }
           }
           container srv6-adjacency-segment {
             description "Configure srv6 adjacency segment";
             uses apply-advanced;
             container protected {
               presence "enable protected";
               description "SRv6 Adjacency segment is eligible for protection";
               uses apply-advanced;
               list locator {
                 key name;
                 ordered-by user;
                 description "Locator to bind SRv6 adjacency segment";
                 leaf name {
                   description "Locator name";
                   junos:must "(\"routing-options source-packet-routing srv6 locator $$\")";
                   junos:must-message "Referenced source-packet-routing srv6 must be defined";
                   type string;
                 }
                 uses apply-advanced;
                 list end-x-sid {
                   key name;
                   ordered-by user;
                   description "Endpoint 128 bit address";
                   leaf name {
                     type jt:ipv6addr;
                   }
                   uses apply-advanced;
                   container flavor {
                     presence "enable flavor";
                     uses apply-advanced;
                     leaf psp {
                       description "Penultimate segment pop of the SRH";
                       type empty;
                     }
                     leaf usp {
                       description "Ultimate segment pop of the SRH";
                       type empty;
                     }
                     leaf usd {
                       description "Ultimate segment decapsulation";
                       type empty;
                     }
                   }
                 }
               }
             }
             container unprotected {
               presence "enable unprotected";
               description "SRv6 Adjacency segment is uneligible for protection";
               uses apply-advanced;
               list locator {
                 key name;
                 ordered-by user;
                 description "Locator to bind SRv6 adjacency segment";
                 leaf name {
                   description "Locator name";
                   junos:must "(\"routing-options source-packet-routing srv6 locator $$\")";
                   junos:must-message "Referenced source-packet-routing srv6 must be defined";
                   type string;
                 }
                 uses apply-advanced;
                 list end-x-sid {
                   key name;
                   ordered-by user;
                   description "Endpoint 128 bit address";
                   leaf name {
                     type jt:ipv6addr;
                   }
                   uses apply-advanced;
                   container flavor {
                     presence "enable flavor";
                     uses apply-advanced;
                     leaf psp {
                       description "Penultimate segment pop of the SRH";
                       type empty;
                     }
                     leaf usp {
                       description "Ultimate segment pop of the SRH";
                       type empty;
                     }
                     leaf usd {
                       description "Ultimate segment decapsulation";
                       type empty;
                     }
                   }
                 }
               }
             }
           }
         }
         container post-convergence-lfa {
           presence "enable post-convergence-lfa";
           junos:must "(\".. .. .. backup-spf-options use-post-convergence-lfa\")";
           junos:must-message "Not allowed without 'protocols isis backup-spf-options use-post-convergence-lfa'";
           description "Configure backup along post convergence on this interface";
           uses apply-advanced;
           container node-protection {
             presence "enable node-protection";
             description "Enable node protection";
             uses apply-advanced;
             leaf cost {
               description "Cost for node protection";
               type union {
                 type string {
                   pattern "<.*>|$.*";
                 }
                 type uint32 {
                   range "0 .. 16777215";
                 }
               }
             }
           }
           leaf srlg-protection {
             description "Enable srlg protection";
             type empty;
           }
           leaf fate-sharing-protection {
             description "Enable fate-sharing protection";
             type empty;
           }
         }
         container application-specific {
           description "Advertise application-specific TE attributes";
           uses apply-advanced;
           list attribute-group {
             key name;
             ordered-by user;
             description "Link attribute group name";
             max-elements 1;
             leaf name {
               description "Link attribute group name";
               type string;
             }
             uses apply-advanced;
             leaf te-metric {
               description "Traffic engineering metric for this attribute group";
               junos:must "(\".. application\")";
               junos:must-message "Atleast one application is must";
               type union {
                 type string {
                   pattern "<.*>|$.*";
                 }
                 type uint32 {
                   range "0 .. 16777215";
                 }
               }
             }
             leaf-list admin-group {
               ordered-by user;
               description "Administrative groups for this attribute-group";
               type string;
               max-elements 16;
             }
             container application {
               junos:must "((\".. delay-metric\" || (\".. admin-group\" || (\".. te-metric\" || (\".. admin-groups\" || (\".. legacy\" || \".. advertise-delay-metric\"))))))";
               junos:must-message "Atleast one attribute must be configured";
               description "Standard Applications part of this attribute-group";
               uses apply-advanced;
               leaf flex-algorithm {
                 description "Set X flag in standard application bit mask";
                 type empty;
               }
             }
           }
         }
         choice enable-disable {
           case case_1 {
             leaf disable {
               description "Disable IS-IS for this level";
               type empty;
             }
           }
         }
         leaf metric {
           description "Metric for this level";
           type union {
             type string {
               pattern "<.*>|$.*";
             }
             type uint32 {
               range "0 .. 16777215";
             }
           }
         }
         leaf ipv4-multicast-metric {
           description "IPv4 multicast metric for this level";
           type union {
             type string {
               pattern "<.*>|$.*";
             }
             type uint32 {
               range "0 .. 16777215";
             }
           }
         }
         leaf ipv6-unicast-metric {
           description "IPv6 unicast metric for this level";
           type union {
             type string {
               pattern "<.*>|$.*";
             }
             type uint32 {
               range "0 .. 16777215";
             }
           }
         }
         leaf ipv6-multicast-metric {
           description "IPv6 multicast metric for this level";
           type union {
             type string {
               pattern "<.*>|$.*";
             }
             type uint32 {
               range "0 .. 16777215";
             }
           }
         }
         list topology {
           key name;
           ordered-by user;
           description "Topology specific attributes";
           leaf name {
             description "Topology name";
             type enumeration {
               enum "default" {
                 description "Default topology";
               }
               enum "ipv4-multicast" {
                 description "IPv4 multicast topology";
               }
               enum "ipv6-unicast" {
                 description "IPv6 unicast topology";
               }
               enum "ipv6-multicast" {
                 description "IPv6 multicast topology";
               }
             }
           }
           uses apply-advanced;
           leaf metric {
             description "Topology metric";
             type union {
               type string {
                 pattern "<.*>|$.*";
               }
               type uint32 {
                 range "0 .. 16777215";
               }
             }
           }
           container bandwidth-based-metrics {
             junos:must "(\".. metric\")";
             junos:must-message "Metric must be configured";
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint32 {
                     range "0 .. 16777215";
                   }
                 }
               }
             }
           }
         }
         leaf authentication-key {
           description "Authentication key (password)";
           status deprecated;
           type jt:unreadable;
         }
         leaf authentication-type {
           description "Authentication type";
           status deprecated;
           type enumeration {
             enum "md5" {
               description "MD5 authentication";
               status deprecated;
             }
             enum "simple" {
               description "Simple password authentication";
               status deprecated;
             }
           }
         }
         leaf hello-authentication-key {
           description "Authentication key (password) for hello packets";
           type jt:unreadable;
         }
         leaf hello-authentication-type {
           description "Authentication type for hello packets";
           type enumeration {
             enum "md5" {
               description "MD5 authentication";
             }
             enum "simple" {
               description "Simple password authentication";
             }
           }
         }
         leaf hello-authentication-key-chain {
           description "Key chain name";
           junos:must "(!(\".. hello-authentication-type\"))";
           junos:must-message "May not be configured with hello-authentication-type";
           junos:must "(!(\".. hello-authentication-key\"))";
           junos:must-message "May not be configured with hello-authentication-key";
           junos:must "(!(\".. authentication-key\"))";
           junos:must-message "May not be configured with authentication-key";
           junos:must "(\"security authentication-key-chains key-chain $$\")";
           junos:must-message "Referenced key-chain must be defined";
           type string {
             length "1 .. 128";
             junos:posix-pattern "[A-za-z]$";
             junos:pattern-message "Keychain name must not end with number.";
           }
         }
         leaf hello-interval {
           description "Interval between hello packet transmissions";
           units "seconds";
           type union {
             type string {
               pattern "<.*>|$.*";
             }
             type uint32 {
               range "1 .. 21845";
             }
           }
         }
         leaf hold-time {
           description "Time after which neighbors think the interface is down";
           units "seconds";
           type union {
             type string {
               pattern "<.*>|$.*";
             }
             type uint32 {
               range "1 .. 65535";
             }
           }
         }
         leaf priority {
           description "Designated router election priority";
           type union {
             type string {
               pattern "<.*>|$.*";
             }
             type uint32 {
               range "0 .. 127";
             }
           }
         }
         container flood-reflector {
           presence "enable flood-reflector";
           junos:must "(\".. .. level 1 disable\")";
           junos:must-message "flood-reflector cannot be enabled on level 1 interface";
           junos:must "((\".. .. .. level 2 flood-reflector\" && !(\".. .. level 1 flood-reflector\")))";
           junos:must-message "flood-reflector is only supported on level 2 interfaces";
           description "Configure interface as flood-reflector";
           uses apply-advanced;
           leaf cluster-id {
             description "Cluster-ID";
             junos:must "(\".. .. .. .. level 2 flood-reflector client\")";
             junos:must-message "flood-reflector client is not configured at isis level";
             type union {
               type string {
                 pattern "<.*>|$.*";
               }
               type uint32 {
                 range "1 .. 4294967295";
               }
             }
           }
         }
         container passive {
           presence "enable passive";
           description "Do not run IS-IS at this level, but advertise it";
           uses apply-advanced;
           leaf remote-node-iso {
             description "ISO System-ID of the remote node";
             junos:must "(\".. remote-node-id\")";
             junos:must-message "remote-node-id must be configured";
             type jt:sysid;
           }
           leaf remote-node-id {
             description "Remote address of the link";
             junos:must "(\".. remote-node-iso\")";
             junos:must-message "remote-node-iso must be configured";
             type jt:ipv4addr;
           }
         }
       }
       leaf delay-metric {
         description "Delay metric";
         units "microseconds";
         type union {
           type string {
             pattern "<.*>|$.*";
           }
           type uint32 {
             range "0 .. 16777215";
           }
         }
       }
       container delay-measurement {
         presence "enable delay-measurement";
         description "Enable delay measurement";
         uses apply-advanced;
         leaf probe-interval {
           description "Probe interval";
           units "seconds";
           type union {
             type string {
               pattern "<.*>|$.*";
             }
             type uint32 {
               range "1 .. 255";
             }
           }
         }
         leaf probe-count {
           description "Probe count";
           units "seconds";
           type union {
             type string {
               pattern "<.*>|$.*";
             }
             type uint32 {
               range "1 .. 15";
             }
           }
         }
         container advertisement {
           description "Delay advertisement";
           uses apply-advanced;
           container periodic {
             description "Periodic advertisement parameters";
             uses apply-advanced;
             leaf threshold {
               description "Threshold";
               units "percentage";
               type union {
                 type string {
                   pattern "<.*>|$.*";
                 }
                 type uint32 {
                   range "0 .. 100";
                 }
               }
             }
             leaf interval {
               description "Interval";
               units "seconds";
               type union {
                 type string {
                   pattern "<.*>|$.*";
                 }
                 type uint32 {
                   range "30 .. 3600";
                 }
               }
             }
           }
           container accelerated {
             presence "enable accelerated";
             description "Accelerated advertisement parameters";
             uses apply-advanced;
             leaf threshold {
               description "Threshold";
               units "percentage";
               type union {
                 type string {
                   pattern "<.*>|$.*";
                 }
                 type uint32 {
                   range "0 .. 100";
                 }
               }
             }
           }
         }
       }
       leaf no-advertise-adjacency-segment {
         description "Do not advertise an adjacency segment for this interface";
         type empty;
       }
       container auto-bandwidth {
         description "Auto bandwidth configuration";
         uses apply-advanced;
         leaf template-name {
           description "Auto bandwidth template name";
           junos:must "(\"protocols isis source-packet-routing traffic-statistics statistics-granularity per-interface\")";
           junos:must-message "Config protocols isis source-packet-routing traffic-statistics statistics-granularity per-interface is must";
           junos:must "(\"routing-options auto-bandwidth template $$\")";
           junos:must-message "Referenced auto-bandwidth template must be defined";
           type string;
         }
         choice enable-disable {
           case case_1 {
             leaf disable {
               description "Disable Auto bandwidth on this interface";
               type empty;
             }
           }
         }
       }
       choice protection-type {
         case case_1 {
           leaf link-protection {
             description "Protect interface from link faults only";
             type empty;
           }
         }
         case case_2 {
           leaf node-link-protection {
             description "Protect interface from both link and node faults";
             type empty;
           }
         }
       }
       leaf no-eligible-backup {
         description "Not eligible for backup traffic from protected interfaces";
         type empty;
       }
       leaf no-eligible-remote-backup {
         description "Not eligible for Remote-LFA backup traffic from protected interfaces";
         type empty;
       }
       container link-degradation-threshold {
         presence "enable link-degradation-threshold";
         description "Link up and down thresholds (in %) for proactive link protection";
         leaf link-down {
           description "Signal degradation threshold above which link marked down";
           type union {
             type string {
               pattern "<.*>|$.*";
             }
             type uint32 {
               range "0 .. 100";
             }
           }
         }
         leaf link-up {
           description "Signal degradation threshold below which link is marked up.";
           type union {
             type string {
               pattern "<.*>|$.*";
             }
             type uint32 {
               range "0 .. 100";
             }
           }
         }
       }
       choice enable-disable {
         case case_1 {
           leaf disable {
             description "Disable IS-IS on this interface";
             type empty;
           }
         }
       }
       leaf authentication-key {
         description "Authentication key (password)";
         status deprecated;
         type jt:unreadable;
       }
       leaf authentication-type {
         description "Authentication type";
         status deprecated;
         type enumeration {
           enum "md5" {
             description "MD5 authentication";
             status deprecated;
           }
           enum "simple" {
             description "Simple password authentication";
             status deprecated;
           }
         }
       }
       leaf flood-group {
         description "ISO Area that this interface should send LSPs to";
         type string {
           junos:posix-pattern "^[[:xdigit:]]{2}.(([[:xdigit:]]){2}){1,2}((.(([[:xdigit:]]){2}){1,2}){0,1}){0,5}$";
           junos:pattern-message "At max 26 hexa decimal digits, standard ISO area ID format";
         }
       }
       leaf hello-authentication-key {
         description "Authentication key (password) for hello packets";
         status deprecated;
         type jt:unreadable;
       }
       leaf hello-authentication-type {
         description "Authentication type for hello packets";
         status deprecated;
         type enumeration {
           enum "md5" {
             description "MD5 authentication";
             status deprecated;
           }
           enum "simple" {
             description "Simple password authentication";
             status deprecated;
           }
         }
       }
       leaf hello-padding-type {
         description "Type of padding for hello packets";
         default "loose";
         type enumeration {
           enum "strict" {
             description "Padding for all adjacency states";
           }
           enum "adaptive" {
             description "Padding until state of neighbor adjacency is 'up'";
           }
           enum "loose" {
             description "Padding until state of adjacency is 'initializing'";
           }
           enum "disable" {
             description "Do not add any padding for hello packets";
           }
         }
       }
       leaf interface-group-holddown-delay {
         description "Time to wait before including in BBM calculation";
         units "seconds";
         type union {
           type string {
             pattern "<.*>|$.*";
           }
           type uint32 {
             range "0 .. 60";
           }
         }
       }
       choice layer2-map-choice {
         leaf layer2-map {
           description "Kernel ARP/ND creation for nexthops";
           type empty;
         }
         leaf no-layer2-map {
           description "Don't kernel ARP/ND creation for nexthops";
           type empty;
         }
       }
       leaf max-hello-size {
         description "Maximum size allowed for ISIS Hello PDUs";
         type union {
           type string {
             pattern "<.*>|$.*";
           }
           type uint32 {
             range "512 .. 16000";
           }
         }
       }
       leaf lsp-interval {
         description "Interval between LSP transmissions";
         default "100";
         units "milliseconds";
         type union {
           type string {
             pattern "<.*>|$.*";
           }
           type uint32 {
             range "1 .. 1000";
           }
         }
       }
       container csnp-interval {
         description "Rate of CSN packets (for LAN interfaces only)";
         choice csnp_interval_option {
           case case_1 {
             leaf csnp-interval-number {
               description "Interval between CSN packets";
               units "seconds";
               type union {
                 type string {
                   pattern "<.*>|$.*";
                 }
                 type uint32 {
                   range "1 .. 65535";
                 }
               }
             }
           }
           case case_2 {
             leaf disable {
               description "Do not send CSN packets on this interface";
               type empty;
             }
           }
         }
       }
       container strict-dual-isis {
         presence "enable strict-dual-isis";
         junos:must "(!(\".. .. topologies\"))";
         junos:must-message "strict-dual-isis is not allowed with multi-topologies";
         description "Enable dual isis if spf computation is required for both ipv4 and ipv6 family";
         uses apply-advanced;
         leaf holdown {
           description "Time to wait for ipv4 and ipv6 connectivity";
           status deprecated;
           default "12";
           type union {
             type string {
               pattern "<.*>|$.*";
             }
             type uint32 {
               range "1 .. 65535";
             }
           }
         }
         leaf holddown {
           description "Time to wait for ipv4 and ipv6 connectivity";
           default "12";
           type union {
             type string {
               pattern "<.*>|$.*";
             }
             type uint32 {
               range "1 .. 65535";
             }
           }
         }
       }
       container mesh-group {
         description "Add the interface to a mesh group";
         choice mesh_group_option {
           case case_1 {
             leaf mesh-group-number {
               description "Mesh group number for this interface";
               type union {
                 type uint32;
                 type string {
                   pattern "<.*>|$.*";
                 }
               }
             }
           }
           case case_2 {
             leaf blocked {
               description "Do not flood new LSPs on this interface";
               type empty;
             }
           }
         }
       }
       leaf point-to-point {
         description "Treat interface as point to point";
         type empty;
       }
       container passive {
         presence "enable passive";
         description "Do not run IS-IS, but advertise it";
         uses apply-advanced;
         leaf remote-node-iso {
           description "ISO System-ID of the remote node";
           junos:must "(\".. remote-node-id\")";
           junos:must-message "remote-node-id must be configured";
           type jt:sysid;
         }
         leaf remote-node-id {
           description "Remote address of the link";
           junos:must "(\".. remote-node-iso\")";
           junos:must-message "remote-node-iso must be configured";
           type jt:ipv4addr;
         }
       }
       leaf checksum {
         description "Enable checksum for packets on this interface";
         type empty;
       }
       leaf no-unicast-topology {
         description "Do not include this interface in the unicast topology";
         type empty;
       }
       leaf no-ipv4-multicast {
         description "Do not include this interface in the IPv4 multicast topology";
         type empty;
       }
       leaf no-ipv6-unicast {
         description "Do not include this interface in the IPv6 unicast topology";
         type empty;
       }
       leaf no-ipv6-multicast {
         description "Do not include this interface in the IPv6 multicast topology";
         type empty;
       }
       leaf no-adjacency-down-notification {
         description "Do not inform other protocols about adjacency down events";
         type empty;
       }
       container bfd-liveness-detection {
         junos:must "(!(\".. family inet bfd-liveness-detection\"))";
         junos:must-message "To configure bfd-liveness-detection, 'family inet bfd-liveness-detection' must not be configured";
         description "Bidirectional Forwarding Detection options";
         status deprecated;
         uses apply-advanced;
         leaf version {
           description "BFD protocol version number";
           default "automatic";
           type enumeration {
             enum "0" {
               description "BFD version 0 (deprecated)";
             }
             enum "1" {
               description "BFD version 1";
             }
             enum "automatic" {
               description "Choose BFD version automatically";
             }
           }
         }
         leaf minimum-interval {
           description "Minimum transmit and receive interval";
           units "milliseconds";
           type union {
             type string {
               pattern "<.*>|$.*";
             }
             type uint32 {
               range "1 .. 255000";
             }
           }
         }
         leaf minimum-transmit-interval {
           description "Minimum transmit interval";
           status deprecated;
           units "milliseconds";
           type union {
             type string {
               pattern "<.*>|$.*";
             }
             type uint32 {
               range "1 .. 255000";
             }
           }
         }
         leaf minimum-receive-interval {
           description "Minimum receive interval";
           units "milliseconds";
           type union {
             type string {
               pattern "<.*>|$.*";
             }
             type uint32 {
               range "1 .. 255000";
             }
           }
         }
         leaf multiplier {
           description "Detection time multiplier";
           default "3";
           type union {
             type string {
               pattern "<.*>|$.*";
             }
             type uint32 {
               range "1 .. 255";
             }
           }
         }
         choice adaptation-choice {
           case case_1 {
             leaf no-adaptation {
               description "Disable adaptation";
               type empty;
             }
           }
         }
         container transmit-interval {
           description "Transmit-interval options";
           uses apply-advanced;
           leaf minimum-interval {
             description "Minimum transmit interval";
             units "milliseconds";
             type union {
               type string {
                 pattern "<.*>|$.*";
               }
               type uint32 {
                 range "1 .. 255000";
               }
             }
           }
           leaf threshold {
             description "High transmit interval triggering a trap";
             units "milliseconds";
             type union {
               type uint32;
               type string {
                 pattern "<.*>|$.*";
               }
             }
           }
         }
         container detection-time {
           description "Detection-time options";
           uses apply-advanced;
           leaf threshold {
             description "High detection-time triggering a trap";
             units "milliseconds";
             type union {
               type uint32;
               type string {
                 pattern "<.*>|$.*";
               }
             }
           }
         }
         container authentication {
           description "Authentication options";
           uses apply-advanced;
           leaf key-chain {
             description "Key chain name";
             junos:must "(\".. algorithm\")";
             junos:must-message "May not be configured without algorithm";
             junos:must "(\"security authentication-key-chains key-chain $$\")";
             junos:must-message "Referenced key-chain must be defined";
             type string;
           }
           leaf algorithm {
             description "Algorithm name";
             junos:must "(\".. key-chain\")";
             junos:must-message "May not be configured without key-chain";
             type enumeration {
               enum "simple-password" {
                 description "Simple password";
               }
               enum "keyed-md5" {
                 description "Keyed message Digest 5";
               }
               enum "meticulous-keyed-md5" {
                 description "Meticulous keyed message Digest 5";
               }
               enum "keyed-sha-1" {
                 description "Keyed secure hash algorithm (SHA1) ";
               }
               enum "meticulous-keyed-sha-1" {
                 description "Meticulous keyed secure hash algorithm (SHA1) ";
               }
             }
           }
           leaf loose-check {
             description "Verify authentication only if authentication is negotiated";
             type empty;
           }
         }
       }
       list family {
         key name;
         ordered-by user;
         description "Address family specific interface attributes";
         leaf name {
           type enumeration {
             enum "inet" {
               description "IPv4 family";
             }
             enum "inet6" {
               description "IPv6 family";
             }
           }
         }
         uses apply-advanced;
         container bfd-liveness-detection {
           junos:must "(!((\".. .. bfd-liveness-detection\" && \".. .. family inet bfd-liveness-detection\")))";
           junos:must-message "bfd-liveness-detection and 'family inet bfd-liveness-detection' cannot be configured at the same time";
           description "Bidirectional Forwarding Detection options";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
           container authentication {
             description "Authentication options";
             uses apply-advanced;
             leaf key-chain {
               description "Key chain name";
               junos:must "(\".. algorithm\")";
               junos:must-message "May not be configured without algorithm";
               junos:must "(\"security authentication-key-chains key-chain $$\")";
               junos:must-message "Referenced key-chain must be defined";
               type string;
             }
             leaf algorithm {
               description "Algorithm name";
               junos:must "(\".. key-chain\")";
               junos:must-message "May not be configured without key-chain";
               type enumeration {
                 enum "simple-password" {
                   description "Simple password";
                 }
                 enum "keyed-md5" {
                   description "Keyed message Digest 5";
                 }
                 enum "meticulous-keyed-md5" {
                   description "Meticulous keyed message Digest 5";
                 }
                 enum "keyed-sha-1" {
                   description "Keyed secure hash algorithm (SHA1) ";
                 }
                 enum "meticulous-keyed-sha-1" {
                   description "Meticulous keyed secure hash algorithm (SHA1) ";
                 }
               }
             }
             leaf loose-check {
               description "Verify authentication only if authentication is negotiated";
               type empty;
             }
           }
         }
       }
     }
     container source-packet-routing {
       presence "enable source-packet-routing";
       junos:must "(!(\".. srm6\"))";
       junos:must-message "must not have 'protocols isis srm6' configured";
       description "Enable Source Packet Routing (SPRING)";
       uses apply-advanced;
       container adjacency-segment {
         junos:must "(!(\".. .. .. .. protocols mpls disable\"))";
         junos:must-message "SPRING configuration is not allowed with 'protocols mpls disable'";
         description "Configure attributes for Adjacency Segments in SPRING";
         uses apply-advanced;
         leaf hold-time {
           description "Duration(ms) for which adjacency segments will be retained after isolating from an interface";
           type union {
             type string {
               pattern "<.*>|$.*";
             }
             type uint32 {
               range "180000 .. 900000";
             }
           }
         }
       }
       container udp-tunneling {
         junos:must "(!(\".. .. .. .. protocols mpls disable\"))";
         junos:must-message "SPRING configuration is not allowed with 'protocols mpls disable'";
         description "Enable SR over UDP feature";
         uses apply-advanced;
         leaf encapsulation {
           description "Enable UDP Tunnel Encapsulation";
           type empty;
         }
         leaf decapsulation {
           description "Enable UDP Tunnel decapsulation";
           type empty;
         }
       }
       container srgb {
         junos:must "(!(\".. node-segment index-range\"))";
         junos:must-message "May not be confiugred with node-segment index-range";
         junos:must "(!(\".. .. .. .. protocols mpls disable\"))";
         junos:must-message "SPRING configuration is not allowed with 'protocols mpls disable'";
         description "Set the SRGB global block in SPRING";
         leaf start-label {
           description "Start range for SRGB label block";
           type union {
             type string {
               pattern "<.*>|$.*";
             }
             type uint32;
           }
         }
         leaf index-range {
           description "Index to the SRGB start label block";
           type union {
             type string {
               pattern "<.*>|$.*";
             }
             type uint32;
           }
         }
       }
       container node-segment {
         junos:must "(!(\".. .. .. .. protocols mpls disable\"))";
         junos:must-message "SPRING configuration is not allowed with 'protocols mpls disable'";
         description "Enable support for Node segments in SPRING";
         uses apply-advanced;
         leaf ipv4-index {
           description "Set IPv4 Node Segment index";
           type union {
             type string {
               pattern "<.*>|$.*";
             }
             type uint32 {
               range "0 .. 199999";
             }
           }
         }
         leaf ipv6-index {
           description "Set IPv6 Node Segment index";
           type union {
             type string {
               pattern "<.*>|$.*";
             }
             type uint32 {
               range "0 .. 199999";
             }
           }
         }
         leaf index-range {
           description "Set Range of Node Segment indices allowed";
           type union {
             type string {
               pattern "<.*>|$.*";
             }
             type uint32 {
               range "32 .. 16385";
             }
           }
         }
       }
       leaf-list flex-algorithm {
         description "Flex-algorithms we would like to participate in";
         type union {
           type string {
             pattern "<.*>|$.*";
           }
           type uint32 {
             range "128 .. 255";
           }
         }
         max-elements 16;
       }
       leaf use-flex-algorithm-metric-always {
         description "Use flex-algo prefix metric whenever available";
         type empty;
       }
       leaf strict-asla-based-flex-algorithm {
         description "Flex-Algorithm to ignore links not having ASLA sub-TLVs";
         type empty;
       }
       leaf new-capability-subtlv {
         description "Advertise all ranges in single spring capability subtlv";
         junos:must "(!(\".. .. .. .. protocols mpls disable\"))";
         junos:must-message "SPRING configuration is not allowed with 'protocols mpls disable'";
         type empty;
       }
       leaf explicit-null {
         description "Set E and P bits in all Prefix SID advertisements";
         junos:must "(!(\".. .. .. .. protocols mpls disable\"))";
         junos:must-message "SPRING configuration is not allowed with 'protocols mpls disable'";
         type empty;
       }
       leaf mapping-server {
         description "Mapping server name";
         junos:must "(!(\".. .. .. .. protocols mpls disable\"))";
         junos:must-message "SPRING configuration is not allowed with 'protocols mpls disable'";
         junos:must "(\"routing-options source-packet-routing mapping-server-entry $$\")";
         junos:must-message "Referenced source-packet-routing mapping-server-entry must be defined";
         type string;
       }
       leaf no-strict-spf {
         description " Disable strict spf algo 1 advertisement";
         type empty;
       }
       leaf no-binding-sid-leaking {
         description " Disable SRMS binding sid leaking";
         type empty;
       }
       leaf ldp-stitching {
         description "Enable SR to LDP stitching";
         junos:must "(!(\".. .. .. .. protocols mpls disable\"))";
         junos:must-message "SPRING configuration is not allowed with 'protocols mpls disable'";
         type empty;
       }
       container srv6 {
         presence "enable srv6";
         description "Enable IPv6 Segment Routing (SRv6)";
         uses apply-advanced;
         list locator {
           key name;
           ordered-by user;
           description "SRv6 Locator";
           leaf name {
             description "Locator name";
             junos:must "(\"routing-options source-packet-routing srv6 locator $$\")";
             junos:must-message "Referenced source-packet-routing srv6 must be defined";
             type string;
           }
           uses apply-advanced;
           leaf anycast {
             description "Set A flag in the Prefix-Attribute sub-TLV";
             type empty;
           }
           list end-sid {
             key name;
             ordered-by user;
             leaf name {
               type jt:ipv6addr;
             }
             uses apply-advanced;
             container flavor {
               presence "enable flavor";
               uses apply-advanced;
               leaf psp {
                 description "Penultimate segment pop of the SRH";
                 type empty;
               }
               leaf usp {
                 description "Ultimate segment pop of the SRH";
                 type empty;
               }
               leaf usd {
                 description "Ultimate segment decapsulation";
                 type empty;
               }
             }
           }
         }
       }
       container sensor-based-stats {
         junos:must "(!(\".. .. .. .. protocols mpls disable\"))";
         junos:must-message "SPRING configuration is not allowed with 'protocols mpls disable'";
         description "Configure sensor based stats in SPRING";
         uses apply-advanced;
         container per-interface-per-member-link {
           description "Configure sensor based stats per nexthop";
           leaf ingress {
             description "Enable sensor based stats on ingress interface";
             type empty;
           }
           leaf egress {
             description "Enable sensor based stats on egress interface";
             type empty;
           }
         }
         container per-sid {
           description "Configure sensor based stats per spring route";
           leaf ingress {
             description "Enable sensor based stats for per-sid ingress accounting";
             type empty;
           }
           leaf egress {
             description "Enable sensor based stats for IP-MPLS egress accounting";
             type empty;
           }
         }
       }
       container traffic-statistics {
         junos:must "(!(\".. .. .. .. protocols mpls disable\"))";
         junos:must-message "SPRING configuration is not allowed with 'protocols mpls disable'";
         description "Enable support for traffic statistics in SPRING";
         uses apply-advanced;
         container statistics-granularity {
           description "Granularity for traffic statistics in SPRING";
           uses apply-advanced;
           leaf per-interface {
             description "Interface Based traffic statistics in SPRING";
             type empty;
           }
         }
         leaf auto-bandwidth {
           description "Auto bandwidth name";
           junos:must "(\"protocols isis source-packet-routing traffic-statistics statistics-granularity per-interface\")";
           junos:must-message "Config protocols isis source-packet-routing traffic-statistics statistics-granularity per-interface is must";
           junos:must "(\"routing-options auto-bandwidth template $$\")";
           junos:must-message "Referenced auto-bandwidth template must be defined";
           type string;
         }
       }
     }
     container srm6 {
       presence "enable srm6";
       junos:must "(!(\".. source-packet-routing\"))";
       junos:must-message "must not have 'protocols isis source-packet-routing' configured";
       description "Enable SRm6";
       uses apply-advanced;
       container sid {
         description "Configure attributes for SID in srm6";
         uses apply-advanced;
         leaf node-sid {
           description "Set Node SID Value";
           type union {
             type string {
               pattern "<.*>|$.*";
             }
             type uint32 {
               range "1 .. 65535";
             }
           }
         }
         leaf address {
           description "IPv6 address corresponding to SID";
           type jt:ipv6addr;
         }
       }
     }
     list level {
       key name;
       ordered-by user;
       description "Configure global level attributes";
       leaf name {
         description "IS-IS level number";
         type union {
           type string {
             pattern "<.*>|$.*";
           }
           type uint32 {
             range "1 .. 2";
           }
         }
       }
       uses apply-advanced;
       leaf labeled-preference {
         description "Preference of labeled IS-IS routes";
         junos:must "(\".. .. source-packet-routing\")";
         junos:must-message "labeled-preference cannot be specified without 'protocols isis source-packet-routing'";
         type union {
           type uint32;
           type string {
             pattern "<.*>|$.*";
           }
         }
       }
       leaf srv6-preference {
         description "Preference of SRV6 IS-IS routes";
         junos:must "(\".. .. source-packet-routing\")";
         junos:must-message "srv6-preference cannot be specified without 'protocols isis source-packet-routing'";
         type union {
           type uint32;
           type string {
             pattern "<.*>|$.*";
           }
         }
       }
       leaf flex-algorithm-preference {
         description "Preference of flex-algorithm L-ISIS routes";
         junos:must "(\".. .. source-packet-routing\")";
         junos:must-message "flex-algorithm-preference cannot be specified without 'protocols isis source-packet-routing'";
         type union {
           type uint32;
           type string {
             pattern "<.*>|$.*";
           }
         }
       }
       container source-packet-routing {
         presence "enable source-packet-routing";
         description "Enable Source Packet Routing (SPRING)";
         uses apply-advanced;
         choice enable-disable {
           case case_1 {
             leaf disable {
               description "Disable Source Packet Routing on this level";
               type empty;
             }
           }
         }
         leaf srms-preference {
           description "Set SRMS preference value";
           type union {
             type string {
               pattern "<.*>|$.*";
             }
             type uint32 {
               range "0 .. 255";
             }
           }
         }
       }
       choice enable-disable {
         case case_1 {
           leaf disable {
             description "Disable IS-IS on this level";
             type empty;
           }
         }
       }
       leaf authentication-key {
         description "Authentication key (password)";
         type jt:unreadable;
       }
       leaf authentication-type {
         description "Authentication type";
         type enumeration {
           enum "md5" {
             description "MD5 authentication";
           }
           enum "simple" {
             description "Simple password authentication";
           }
         }
       }
       leaf purge-originator {
         description "Add Purge Originator information";
         type enumeration {
           enum "self" {
             description "Add POI only for self-originated purge LSPs";
           }
           enum "empty" {
             description "Add POI for purge LSPs who do not have POI information";
           }
         }
       }
       leaf no-hello-authentication {
         description "Disable authentication for hello packets";
         type empty;
       }
       leaf no-csnp-authentication {
         description "Disable authentication for CSN packets";
         type empty;
       }
       leaf no-psnp-authentication {
         description "Disable authentication for PSN packets";
         type empty;
       }
       leaf authentication-key-chain {
         description "Key chain name";
         junos:must "(!(\".. authentication-type\"))";
         junos:must-message "May not be configured with authentication-type";
         junos:must "(!(\".. authentication-key\"))";
         junos:must-message "May not be configured with authentication-key";
         junos:must "(\"security authentication-key-chains key-chain $$\")";
         junos:must-message "Referenced key-chain must be defined";
         type string {
           length "1 .. 128";
           junos:posix-pattern "[A-za-z]$";
           junos:pattern-message "Keychain name must not end with number.";
         }
       }
       leaf wide-metrics-only {
         description "Generate wide metrics only";
         junos:must "(!(\".. .. clns-routing\"))";
         junos:must-message "wide-metrics-only cannot be specified with clns-routing";
         type empty;
       }
       leaf preference {
         description "Preference of internal routes";
         type union {
           type uint32;
           type string {
             pattern "<.*>|$.*";
           }
         }
       }
       leaf external-preference {
         description "Preference of external routes";
         type union {
           type uint32;
           type string {
             pattern "<.*>|$.*";
           }
         }
       }
       leaf prefix-export-limit {
         description "Maximum number of external prefixes that can be exported";
         type union {
           type string {
             pattern "<.*>|$.*";
           }
           type uint32 {
             range "0 .. 4294967295";
           }
         }
       }
       container flood-reflector {
         junos:must "(!(\".. .. level 1 flood-reflector\"))";
         junos:must-message "Flood-reflector is supported only in level 2";
         description "Enable flood-reflector";
         uses apply-advanced;
         choice flood-reflector-choice {
           case case_1 {
             container reflector {
               junos:must "(!(\".. client\"))";
               junos:must-message "flood-reflector and client can't be configured together";
               description "Configure this as a flood-reflector";
               uses apply-advanced;
               leaf cluster-id {
                 description "Cluster-ID";
                 type union {
                   type string {
                     pattern "<.*>|$.*";
                   }
                   type uint32 {
                     range "1 .. 4294967295";
                   }
                 }
               }
             }
           }
           case case_2 {
             leaf client {
               description "Configure interface as flood-reflector client";
               type empty;
             }
           }
         }
       }
     }
     list interface-group {
       key name;
       description "Interface grouping configuration";
       leaf name {
         description "Interface group name";
         type string;
       }
       uses apply-advanced;
       list level {
         key name;
         ordered-by user;
         description "Configure levels on this interface-group";
         leaf name {
           description "IS-IS level number";
           type union {
             type string {
               pattern "<.*>|$.*";
             }
             type uint32 {
               range "1 .. 2";
             }
           }
         }
         uses apply-advanced;
         container ipv4-adjacency-segment {
           junos:must "(!(\".. no-advertise-adjacency-segment\"))";
           junos:must-message "ipv4-adjacency-segment can't be configured if no-advertise-adjacency-segment is configured in the level";
           junos:must "(!(\".. .. no-advertise-adjacency-segment\"))";
           junos:must-message "ipv4-adjacency-segment can't be configured if no-advertise-adjacency-segment is configured in the same interface";
           description "Configure ipv4 adjacency segment";
           uses apply-advanced;
           container protected {
             description "Adjacency SID is eligible for protection";
             choice adjsid-type {
               case case_1 {
                 container index {
                   description "Adjacency SID indexed from SRGB";
                   leaf index-number {
                     type union {
                       type string {
                         pattern "<.*>|$.*";
                       }
                       type uint32 {
                         range "0 .. 199999";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
           container unprotected {
             description "Adjacency SID uneligible for protection";
             choice adjsid-type {
               case case_1 {
                 container index {
                   description "Adjacency SID indexed from SRGB";
                   leaf index-number {
                     type union {
                       type string {
                         pattern "<.*>|$.*";
                       }
                       type uint32 {
                         range "0 .. 199999";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
         }
         container ipv6-adjacency-segment {
           junos:must "(!(\".. no-advertise-adjacency-segment\"))";
           junos:must-message "ipv6-adjacency-segment can't be configured if no-advertise-adjacency-segment is configured in the same level";
           junos:must "(!(\".. .. no-advertise-adjacency-segment\"))";
           junos:must-message "ipv6-adjacency-segment can't be configured if no-advertise-adjacency-segment is configured in the same interface";
           description "Configure ipv6 adjacency segment";
           uses apply-advanced;
           container protected {
             description "Adjacency SID is eligible for protection";
             choice adjsid-type {
               case case_1 {
                 container index {
                   description "Adjacency SID indexed from SRGB";
                   leaf index-number {
                     type union {
                       type string {
                         pattern "<.*>|$.*";
                       }
                       type uint32 {
                         range "0 .. 199999";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
           container unprotected {
             description "Adjacency SID uneligible for protection";
             choice adjsid-type {
               case case_1 {
                 container index {
                   description "Adjacency SID indexed from SRGB";
                   leaf index-number {
                     type union {
                       type string {
                         pattern "<.*>|$.*";
                       }
                       type uint32 {
                         range "0 .. 199999";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
         }
         container srm6-adjacency-segment {
           description "Configure srm6 adjacency segment";
           uses apply-advanced;
           container unprotected {
             description "Adjacency SID uneligible for protection";
             leaf sid {
               description "Set Adjacency SID Value";
               type union {
                 type string {
                   pattern "<.*>|$.*";
                 }
                 type uint32 {
                   range "1 .. 65535";
                 }
               }
             }
           }
         }
         list topology {
           key name;
           ordered-by user;
           description "Topology specific attributes";
           leaf name {
             description "Topology name";
             type enumeration {
               enum "default" {
                 description "Default topology";
               }
               enum "ipv4-multicast" {
                 description "IPv4 multicast topology";
               }
               enum "ipv6-unicast" {
                 description "IPv6 unicast topology";
               }
               enum "ipv6-multicast" {
                 description "IPv6 multicast topology";
               }
             }
           }
           uses apply-advanced;
           leaf metric {
             description "Topology metric";
             type union {
               type string {
                 pattern "<.*>|$.*";
               }
               type uint32 {
                 range "0 .. 16777215";
               }
             }
           }
           container bandwidth-based-metrics {
             junos:must "(\".. metric\")";
             junos:must-message "Metric must be configured";
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint32 {
                     range "0 .. 16777215";
                   }
                 }
               }
             }
           }
         }
       }
       container link-group-protection {
         junos:must "(!(\".. .. backup-spf-options\"))";
         junos:must-message "Backup SPF options can't be configured";
         description "Configure link group protection";
         uses apply-advanced;
         leaf minimum-bandwidth {
           description "Minimum bandwidth to carry traffic";
           type string;
         }
         leaf revert-bandwidth {
           description "Revert bandwidth to carry traffic";
           type string;
         }
       }
       list interface {
         key name;
         description "List interfaces for this group";
         leaf name {
           description "Interface name";
           type union {
             type jt:interface-name;
             type string {
               pattern "<.*>|$.*";
             }
           }
         }
         uses apply-advanced;
         leaf weight {
           description "Interface weight for adjacency set";
           type union {
             type string {
               pattern "<.*>|$.*";
             }
             type uint32 {
               range "1 .. 255";
             }
           }
         }
       }
     }
     container spf-options {
       description "Configure SPF attributes";
       uses apply-advanced;
       container microloop-avoidance {
         description "Configure microloop avoidance mechanisms";
         uses apply-advanced;
         container post-convergence-path {
           presence "enable post-convergence-path";
           junos:must "(\".. .. .. source-packet-routing\")";
           junos:must-message "Please configure source-packet-routing under isis/isis-instance";
           junos:must "(!(\".. use-route-convergence-delay\"))";
           junos:must-message "use-route-convergence-delay is not allowed with post-convergence-path";
           description "Temporarily install post-convergence path for routes potentially affected by microloops";
           uses apply-advanced;
           leaf delay {
             description "Time after which temporary post-convergence paths are removed";
             units "milliseconds";
             type union {
               type string {
                 pattern "<.*>|$.*";
               }
               type uint32 {
                 range "500 .. 60000";
               }
             }
           }
           leaf maximum-labels {
             description "Set maximum number of label supported for Micro-Loop-Avoidance calculations";
             type union {
               type string {
                 pattern "<.*>|$.*";
               }
               type uint32 {
                 range "2 .. 8";
               }
             }
           }
           leaf maximum-srv6-sids {
             description "Set maximum number of SRV6 SIDs supported for Micro-Loop-Avoidance calculations";
             type union {
               type string {
                 pattern "<.*>|$.*";
               }
               type uint32 {
                 range "2 .. 6";
               }
             }
           }
         }
       }
       leaf delay {
         description "Time to wait before running an SPF";
         units "milliseconds";
         type union {
           type string {
             pattern "<.*>|$.*";
           }
           type uint32 {
             range "50 .. 1000";
           }
         }
       }
       leaf holddown {
         description "Time to hold down before running an SPF";
         units "milliseconds";
         type union {
           type string {
             pattern "<.*>|$.*";
           }
           type uint32 {
             range "2000 .. 10000";
           }
         }
       }
       leaf rapid-runs {
         description "Number of rapid SPF runs before SPF holddown";
         type union {
           type string {
             pattern "<.*>|$.*";
           }
           type uint32 {
             range "1 .. 5";
           }
         }
       }
       container multipath {
         description "Configure multipath options";
         uses apply-advanced;
         container weighted {
           description "Weighted multipath options";
           uses apply-advanced;
           leaf one-hop {
             description "Enable load balancing on onehop multipath based on interface bandwidth";
             type empty;
           }
         }
       }
     }
     container traceoptions {
       description "Trace options for IS-IS";
       uses apply-advanced;
       list flag {
         key name;
         ordered-by user;
         description "Tracing parameters";
         leaf name {
           type enumeration {
             enum "traffic-statistics" {
               description "Trace traffic-statistics related events";
             }
             enum "post-convergence-lfa" {
               description "Trace post-convergence-lfa related events";
             }
             enum "error" {
               description "Trace errored packets";
             }
             enum "spf" {
               description "Trace SPF events";
             }
             enum "packets" {
               description "Trace IS-IS packets";
             }
             enum "hello" {
               description "Trace hello packets";
             }
             enum "lsp" {
               description "Trace link-state packets";
             }
             enum "psn" {
               description "Trace partial sequence number (PSN) packets";
             }
             enum "csn" {
               description "Trace complete sequence number (CSN) packets";
             }
             enum "layer2-map" {
               description "Trace ARP/ND kernel state manipulation";
             }
             enum "lsp-generation" {
               description "Trace LSP generation";
             }
             enum "graceful-restart" {
               description "Trace graceful restart events";
             }
             enum "ldp-synchronization" {
               description "Trace synchronization between IS-IS and LDP";
             }
             enum "nsr-synchronization" {
               description "Trace NSR synchronization events";
             }
             enum "spring" {
               description "Trace source packet routing";
             }
             enum "prefix-sid" {
               description "Trace source packet routing, prefix-sids";
             }
             enum "flex-algorithm" {
               description "Trace flex-algorithm related events";
             }
             enum "adj-sid" {
               description "Trace adj-sid related events";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "srv6" {
               description "Trace srv6 related events";
             }
             enum "rmopd" {
               description "Trace rmopd interactions";
             }
             enum "mapping-server" {
               description "Trace mapping server related events";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
     }
     container backup-spf-options {
       description "Configure backup SPF attributes";
       uses apply-advanced;
       container remote-backup-calculation {
         presence "enable remote-backup-calculation";
         junos:must "(!(\".. .. backup-spf-options use-post-convergence-lfa\"))";
         junos:must-message "Not allowed with 'protocols isis backup-spf-options use-post-convergence-lfa'";
         description "Calculate Remote LFA backup nexthops";
         uses apply-advanced;
       }
       container use-post-convergence-lfa {
         presence "enable use-post-convergence-lfa";
         junos:must "(\".. .. source-packet-routing\")";
         junos:must-message "Configuration of 'protocols isis source-packet-routing' is must";
         description "Calculate Post Convergence Backup Nexthops";
         uses apply-advanced;
         leaf maximum-labels {
           description "Set maximum number of label supported for post convergence path calculations";
           type union {
             type string {
               pattern "<.*>|$.*";
             }
             type uint32 {
               range "2 .. 8";
             }
           }
         }
         leaf maximum-srv6-sids {
           description "Set maximum number of SRV6 SIDs for post convergence path calculations";
           type union {
             type string {
               pattern "<.*>|$.*";
             }
             type uint32 {
               range "2 .. 6";
             }
           }
         }
         leaf maximum-backup-paths {
           description "Set maximum equal cost backup post convergence paths";
           type union {
             type string {
               pattern "<.*>|$.*";
             }
             type uint32 {
               range "1 .. 8";
             }
           }
         }
       }
       container use-source-packet-routing {
         presence "enable use-source-packet-routing";
         junos:must "(\".. .. source-packet-routing\")";
         junos:must-message "Use of SPRING paths as backup can't be configured without configuring 'protocols isis source-packet-routing'";
         description "Use SPRING routed paths for protection";
         uses apply-advanced;
       }
       leaf per-prefix-calculation {
         description "Calculate backup nexthops for non-best prefix originators";
         type empty;
       }
       leaf node-link-degradation {
         description "Degrade to link protection when nodelink protection not available";
         junos:must "(!(\".. .. backup-spf-options use-post-convergence-lfa\"))";
         junos:must-message "Not allowed with 'protocols isis backup-spf-options use-post-convergence-lfa'";
         type empty;
       }
     }
     list context-identifier {
       key name;
       ordered-by user;
       description "Configuration for advertisement of a context-identifier ";
       leaf name {
         description "Context identifier range";
         type jt:ipprefix;
       }
       uses apply-advanced;
       list level {
         key name;
         ordered-by user;
         description "Configure global level attributes";
         leaf name {
           description "IS-IS level number";
           type union {
             type string {
               pattern "<.*>|$.*";
             }
             type uint32 {
               range "1 .. 2";
             }
           }
         }
         uses apply-advanced;
         choice enable-disable {
           case case_1 {
             leaf disable {
               description "Disable advertisements to this level";
               type empty;
             }
           }
         }
       }
     }
     container traffic-engineering {
       description "Configure traffic engineering attributes";
       uses apply-advanced;
       choice enable-disable {
         case case_1 {
           leaf disable {
             description "Disable traffic engineering";
             type empty;
           }
         }
       }
       leaf l3-unicast-topology {
         description "Download IGP topology into TED";
         type empty;
       }
       leaf ipv6 {
         description "Enable TEDv6";
         type empty;
       }
       leaf credibility-protocol-preference {
         description "Follow IGP protocol preference for TED protocol credibility";
         type empty;
       }
       leaf ipv4-multicast-rpf-routes {
         description "Install IPv4 routes for multicast RPF checks into inet.2";
         status deprecated;
         junos:must "(!(\".. .. topologies ipv4-multicast\"))";
         junos:must-message "ipv4-multicast-rpf-routes cannot be used with the ipv4-multicast topology";
         junos:must "(!(\".. .. multicast-topology\"))";
         junos:must-message "ipv4-multicast-rpf-routes cannot be used with multicast-topology";
         junos:must "(\".. shortcuts\")";
         junos:must-message "ipv4-multicast-rpf-routes cannot be used without shortcuts";
         type empty;
       }
       leaf ignore-lsp-metrics {
         description "Ignore label-switched path metrics when doing shortcuts";
         type empty;
       }
       container tunnel-source-protocol {
         description "Protocols from which to pick label-switched paths";
         uses apply-advanced;
         container rsvp {
           presence "enable rsvp";
           description "Pick label-switched paths from rsvp";
           uses apply-advanced;
           leaf preference {
             description "Preference for label-switched paths from this protocol";
             type union {
               type string {
                 pattern "<.*>|$.*";
               }
               type uint32 {
                 range "1 .. 255";
               }
             }
           }
         }
         container spring-te {
           presence "enable spring-te";
           description "Pick label-switched paths from spring-te";
           uses apply-advanced;
           leaf preference {
             description "Preference for label-switched paths from this protocol";
             type union {
               type string {
                 pattern "<.*>|$.*";
               }
               type uint32 {
                 range "1 .. 255";
               }
             }
           }
         }
       }
       list family {
         key name;
         ordered-by user;
         description "Address family specific traffic-engineering attributes";
         leaf name {
           type enumeration {
             enum "inet" {
               description "IPv4 family";
             }
             enum "inet6" {
               description "IPv6 family";
             }
             enum "inet-mpls" {
               description "IPv4-MPLS family";
             }
             enum "inet6-mpls" {
               description "IPv6-MPLS family";
             }
           }
         }
         uses apply-advanced;
         container shortcuts {
           presence "enable shortcuts";
           junos:must "(!(\".. .. no-ldp-shortcuts\"))";
           junos:must-message "Shortcuts configuration cannot be used with no-ldp-shortcuts";
           junos:must "(!(\".. .. shortcuts\"))";
           junos:must-message "per-family shortcuts configuration cannot be used with global shortcuts enabled";
           junos:must "(!(\".. .. disable\"))";
           junos:must-message "shortcuts cannot be used without traffic-engineering enabled";
           description "Use label-switched paths as next hops, if possible";
           uses apply-advanced;
           leaf multicast-rpf-routes {
             description "Install routes for multicast RPF checks into multicast RIB";
             junos:must "(!(\".. .. .. .. multicast-topology\"))";
             junos:must-message "ipv4 multicast-rpf-routes cannot be used with the multicast-topology";
             junos:must "(!(\".. .. .. .. topologies ipv4-multicast\"))";
             junos:must-message "ipv4 multicast-rpf-routes cannot be used with the ipv4-multicast topology";
             type empty;
           }
           leaf-list import {
             ordered-by user;
             description "Import policy for shortcut";
             type jt:policy-algebra;
           }
         }
       }
       container shortcuts {
         presence "enable shortcuts";
         description "Use label-switched paths as next hops, if possible";
         status deprecated;
         uses apply-advanced;
         leaf ignore-lsp-metrics {
           description "Ignore label-switched path metrics when doing shortcuts";
           status deprecated;
           type empty;
         }
       }
       container multipath {
         description "Configure label-switched-path multipath behavior";
         uses apply-advanced;
         leaf lsp-equal-cost {
           description "Include equal cost label-switched-paths";
           junos:must "((\".. .. shortcuts\" || (\".. .. family $$={inet} shortcuts\" || (\".. .. family $$={inet6} shortcuts\" || \".. .. family $$={iso} shortcuts\"))))";
           junos:must-message "Traffic engineering shortcuts for inet, inet6 or iso family must be configured.";
           type empty;
         }
       }
       container advertisement {
         description "Configure traffic engineering attribute advertisements";
         uses apply-advanced;
         leaf always {
           description "Advertise applicable legacy TE attributes always";
           type empty;
         }
         container application-specific {
           description "Advertise application-specific TE attributes";
           uses apply-advanced;
           container all-applications {
             presence "enable all-applications";
             description "Advertise common application-specific link attributes";
             uses apply-advanced;
             leaf legacy {
               description "Use legacy TE attributes for this application";
               type empty;
             }
           }
         }
       }
     }
     list label-switched-path {
       key name;
       ordered-by user;
       description "Configuration for advertisement of a label-switched path";
       junos:must "(!(\".. traffic-engineering ipv4-multicast-rpf-routes\"))";
       junos:must-message "cannot advertise LSPs when using ipv4-multicast-rpf-routes";
       leaf name {
         description "Name of label-switched path to be advertised";
         type string {
           length "1 .. 64";
         }
       }
       uses apply-advanced;
       list level {
         key name;
         ordered-by user;
         description "Configure global level attributes";
         leaf name {
           description "IS-IS level number";
           type union {
             type string {
               pattern "<.*>|$.*";
             }
             type uint32 {
               range "1 .. 2";
             }
           }
         }
         uses apply-advanced;
         choice enable-disable {
           case case_1 {
             leaf disable {
               description "Disable advertisements to this level";
               type empty;
             }
           }
         }
         leaf metric {
           description "SPF metric for this level";
           type union {
             type string {
               pattern "<.*>|$.*";
             }
             type uint32 {
               range "0 .. 16777215";
             }
           }
         }
       }
     }
     choice enable-disable {
       case case_1 {
         leaf disable {
           description "Disable IS-IS";
           type empty;
         }
       }
     }
     leaf-list export {
       ordered-by user;
       description "Export policy";
       type jt:policy-algebra;
     }
     leaf-list import {
       ordered-by user;
       description "Import policy";
       type jt:policy-algebra;
     }
     leaf reference-bandwidth {
       description "Bandwidth for calculating metric defaults";
       type string;
     }
     choice layer2-map-choice {
       leaf layer2-map {
         description "Kernel ARP/ND creation for nexthops";
         type empty;
       }
       leaf no-layer2-map {
         description "Don't kernel ARP/ND creation for nexthops";
         type empty;
       }
     }
     leaf job-stats {
       description "Collect job statistics";
       type empty;
     }
     leaf lsp-lifetime {
       description "Lifetime of LSPs";
       units "seconds";
       type union {
         type string {
           pattern "<.*>|$.*";
         }
         type uint32 {
           range "350 .. 65535";
         }
       }
     }
     leaf max-lsp-size {
       description "Maximum size allowed for LSPs";
       default "1492";
       type union {
         type string {
           pattern "<.*>|$.*";
         }
         type uint32 {
           range "512 .. 1492";
         }
       }
     }
     leaf max-hello-size {
       description "Maximum size allowed for ISIS Hello PDUs";
       default "1492";
       type union {
         type string {
           pattern "<.*>|$.*";
         }
         type uint32 {
           range "512 .. 16000";
         }
       }
     }
     leaf max-snp-size {
       description "Maximum size allowed for Sequence Number (Complete/Partial) PDUs";
       default "1400";
       type union {
         type string {
           pattern "<.*>|$.*";
         }
         type uint32 {
           range "512 .. 1400";
         }
       }
     }
     leaf spf-delay {
       description "Time to wait before running an SPF";
       status deprecated;
       units "milliseconds";
       junos:must "(!(\".. spf-options delay\"))";
       junos:must-message "You can only configure either spf-delay or delay under spf-options";
       type union {
         type string {
           pattern "<.*>|$.*";
         }
         type uint32 {
           range "50 .. 120000";
         }
       }
     }
     leaf authentication-key {
       description "Authentication key (password)";
       status deprecated;
       type jt:unreadable;
     }
     leaf authentication-type {
       description "Authentication type";
       status deprecated;
       type enumeration {
         enum "md5" {
           description "MD5 authentication";
           status deprecated;
         }
         enum "simple" {
           description "Simple password authentication";
           status deprecated;
         }
       }
     }
     leaf loose-authentication-check {
       description "Verify authentication only if PDU has authentication TLV";
       type empty;
     }
     leaf max-areas {
       description "Maximum number of advertised Areas";
       default "3";
       type union {
         type string {
           pattern "<.*>|$.*";
         }
         type uint32 {
           range "3 .. 64";
         }
       }
     }
     leaf no-authentication-check {
       description "Disable authentication checking";
       type empty;
     }
     leaf no-ipv4-routing {
       description "Disable IPv4 routing";
       type empty;
     }
     leaf no-ipv6-routing {
       description "Disable IPv6 routing";
       type empty;
     }
     leaf no-adjacency-holddown {
       description "Disable adjacency hold down";
       type empty;
     }
     leaf multicast-topology {
       description "Enable multicast topology";
       status deprecated;
       type empty;
     }
     leaf ignore-attached-bit {
       description "Ignore the attached bit in Level 1 LSPs";
       type empty;
     }
     container rib-group {
       description "Routing table group for importing IS-IS routes";
       uses rib_group_type;
     }
     container strict-dual-isis {
       presence "enable strict-dual-isis";
       junos:must "(!(\".. topologies\"))";
       junos:must-message "strict-dual-isis is not allowed with multi-topologies";
       description "Enable dual isis if spf computation is required for both ipv4 and ipv6 family";
       uses apply-advanced;
       leaf holdown {
         description "Time to wait for ipv4 and ipv6 connectivity";
         status deprecated;
         default "12";
         type union {
           type string {
             pattern "<.*>|$.*";
           }
           type uint32 {
             range "1 .. 65535";
           }
         }
       }
       leaf holddown {
         description "Time to wait for ipv4 and ipv6 connectivity";
         default "12";
         type union {
           type string {
             pattern "<.*>|$.*";
           }
           type uint32 {
             range "1 .. 65535";
           }
         }
       }
     }
     container topologies {
       description "Enable topologies";
       uses apply-advanced;
       leaf ipv4-multicast {
         description "Enable IPv4-multicast topology";
         type empty;
       }
       leaf ipv6-unicast {
         description "Enable IPv6-unicast topology";
         type empty;
       }
       leaf ipv6-multicast {
         description "Enable IPv6-multicast topology";
         type empty;
       }
     }
     container overload {
       presence "enable overload";
       description "Set the overload bit (no transit traffic)";
       uses apply-advanced;
       leaf timeout {
         description "Time after which overload bit is reset";
         units "seconds";
         type union {
           type string {
             pattern "<.*>|$.*";
           }
           type uint32 {
             range "60 .. 3600";
           }
         }
       }
       leaf advertise-high-metrics {
         description "Advertise high metrics instead of setting the overload bit";
         type empty;
       }
       leaf allow-route-leaking {
         description "Allow routes to be leaked when overload is configured";
         type empty;
       }
       leaf internal-prefixes {
         description "Allow internal prefixes to be advertised with high metric";
         type empty;
       }
       leaf external-prefixes {
         description "Allow external prefixes to be advertised with high metric";
         type empty;
       }
     }
     container graceful-restart {
       description "IS-IS graceful restart options";
       choice enable-disable {
         case case_1 {
           leaf disable {
             description "Disable graceful restart";
             type empty;
           }
         }
       }
       leaf helper-disable {
         description "Disable graceful restart helper capability";
         type empty;
       }
       leaf restart-duration {
         description "Maximum time for graceful restart to finish";
         units "seconds";
         type union {
           type string {
             pattern "<.*>|$.*";
           }
           type uint32 {
             range "30 .. 300";
           }
         }
       }
     }
   }
   grouping juniper-protocols-l2control {
     uses apply-advanced;
     container traceoptions {
       description "Global tracing options for STP";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "parse" {
               description "Trace configuration parsing";
             }
             enum "regex-parse" {
               description "Trace regular-expression parsing";
             }
             enum "config-internal" {
               description "Trace configuration internals";
             }
             enum "normal" {
               description "Trace normal events";
             }
             enum "general" {
               description "Trace general events";
             }
             enum "state" {
               description "Trace state transitions";
             }
             enum "task" {
               description "Trace routing protocol task processing";
             }
             enum "timer" {
               description "Trace routing protocol task timer processing";
             }
             enum "ppmlite" {
               description "Trace libppmlite processing";
             }
             enum "all" {
               description "Trace everything";
             }
           }
         }
         leaf disable {
           description "Disable this trace flag";
           type empty;
         }
       }
     }
     leaf nonstop-bridging {
       description "Enable nonstop operation";
       junos:must "(\"chassis redundancy graceful-switchover\")";
       junos:must-message "Graceful switchover needs to be configured";
       type empty;
     }
     container bpdu-block {
       presence "enable bpdu-block";
       description "Block BPDU on interface (BPDU Protect)";
       uses apply-advanced;
       list interface {
         key name;
         ordered-by user;
         description "Interface name to block BPDU on";
         leaf name {
           type string;
         }
         uses apply-advanced;
         leaf disable {
           description "Disable bpdu-block on a port";
           type empty;
         }
         leaf drop {
           description "Drop xSTP BPDUs";
           junos:must "((((!(\"protocols rstp interface ${interface}\") && !(\"protocols rstp interface all\")) || \"protocols rstp interface ${interface} disable\") && ((((!(\"protocols vstp interface ${interface}\") && !(\"protocols vstp interface all\")) && (!(\"protocols vstp vlan all interface all\") && (!(any \"protocols vstp vlan <*> interface ${interface}\") && !(any \"protocols vstp vlan <*> interface all\")))) || \"protocols vstp interface ${interface} disable\") && ((!(\"protocols mstp interface ${interface}\") && !(\"protocols mstp interface all\")) || \"protocols mstp interface ${interface} disable\"))))";
           junos:must-message "Cannot configure bpdu-block with xSTP protocol";
           type empty;
         }
       }
       leaf disable-timeout {
         description "Disable timeout for BPDU Protect";
         units "seconds";
         type union {
           type string {
             pattern "<.*>|$.*";
           }
           type int32 {
             range "10 .. 3600";
           }
         }
       }
     }
     container mac-rewrite {
       description "Mac rewrite functionality";
       uses apply-advanced;
       list interface {
         key name;
         ordered-by user;
         leaf name {
           type union {
             type jt:interface-device;
             type string {
               pattern "<.*>|$.*";
             }
           }
         }
         uses apply-advanced;
         leaf enable-all-ifl {
           description "Enable tunneling for all the IFLs under the interface";
           type empty;
         }
         container protocol {
           presence "enable protocol";
           description "Protocols for which mac rewrite need to be enabled";
           uses apply-advanced;
           container stp {
             presence "enable stp";
             description "Enable mac rewrite for STP";
           }
           container vtp {
             presence "enable vtp";
             description "Enable mac rewrite for VTP";
           }
           container cdp {
             presence "enable cdp";
             description "Enable mac rewrite for CDP";
           }
           container pvstp {
             presence "enable pvstp";
             description "Enable mac rewrite for PVSTP+";
           }
         }
       }
     }
   }
   grouping juniper-protocols-ldp {
     uses apply-advanced;
     container traceoptions {
       description "Trace options for LDP";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "error" {
               description "Trace errored packets";
             }
             enum "event" {
               description "Trace LDP state machine events";
             }
             enum "packet-dump" {
               description "Dump the contents of selected packet types";
             }
             enum "packets" {
               description "Trace all LDP packets";
             }
             enum "periodic" {
               description "Trace periodic (hello and keepalive) packets";
             }
             enum "initialization" {
               description "Trace initialization packets";
             }
             enum "notification" {
               description "Trace notification packets";
             }
             enum "address" {
               description "Trace address packets";
             }
             enum "label" {
               description "Trace label packets";
             }
             enum "binding" {
               description "Trace label binding state";
             }
             enum "path" {
               description "Trace label path state";
             }
             enum "ppmd" {
               description "Trace state and events for ppmd process";
             }
             enum "nsr-synchronization" {
               description "Trace NSR synchronization events";
             }
             enum "link-protection" {
               description "Trace link protection events";
             }
             enum "p2mp-nsr-synchronization" {
               description "Trace p2mp NSR synchronization events";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
         container filter {
           description "Filter to apply to this flag";
           presence "enable filter";
           uses ldp_filter_obj;
         }
       }
     }
     container traffic-statistics {
       description "Collect statistics for LDP label-switched paths";
       uses apply-advanced;
       container file {
         description "Statistics file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       leaf interval {
         description "Time to collect statistics (seconds)";
         type union {
           type string {
             pattern "<.*>|$.*";
           }
           type int32 {
             range "60 .. 65535";
           }
         }
       }
       leaf no-penultimate-hop {
         description "No penultimate hop statistics collection";
         type empty;
       }
     }
     container graceful-restart {
       description "Configure graceful restart attributes";
       uses apply-advanced;
       choice enable-disable {
         case case_1 {
           leaf disable {
             description "Disable graceful restart";
             type empty;
           }
         }
       }
       leaf helper-disable {
         description "Disable the graceful restart helper capability";
         type empty;
       }
       leaf recovery-time {
         description "Time required for recovery";
         units "seconds";
         type union {
           type string {
             pattern "<.*>|$.*";
           }
           type uint32 {
             range "120 .. 1800";
           }
         }
       }
       leaf maximum-neighbor-recovery-time {
         description "Maximum time stale mappings are maintained";
         units "seconds";
         type union {
           type string {
             pattern "<.*>|$.*";
           }
           type uint32 {
             range "140 .. 1900";
           }
         }
       }
       leaf reconnect-time {
         description "Time required to reestablish session after graceful restart";
         units "seconds";
         type union {
           type string {
             pattern "<.*>|$.*";
           }
           type uint32 {
             range "30 .. 300";
           }
         }
       }
       leaf maximum-neighbor-reconnect-time {
         description "Maximum reconnect time allowed from a restarting neighbor";
         units "seconds";
         type union {
           type string {
             pattern "<.*>|$.*";
           }
           type uint32 {
             range "30 .. 300";
           }
         }
       }
     }
     container auto-targeted-session {
       presence "enable auto-targeted-session";
       description "Configure auto targeted session parameters";
       uses apply-advanced;
       leaf teardown-delay {
         description "Auto targeted session tear down delay";
         default "90";
         units "seconds";
         type union {
           type string {
             pattern "<.*>|$.*";
           }
           type uint32 {
             range "1 .. 300";
           }
         }
       }
       leaf maximum-sessions {
         description "Auto targeted maximum sessions";
         default "100";
         type union {
           type string {
             pattern "<.*>|$.*";
           }
           type uint32 {
             range "1 .. 1000";
           }
         }
       }
       leaf no-rlfa {
         description "Do not allow RLFA in auto targeted sessions";
         type empty;
       }
       leaf no-dynamic-tunnels {
         description "Do not allow dynamic tunnels in auto targeted sessions";
         type empty;
       }
     }
     leaf preference {
       description "Route preference";
       type union {
         type uint32;
         type string {
           pattern "<.*>|$.*";
         }
       }
     }
     leaf no-forwarding {
       description "Do not use LDP ingress routes for forwarding";
       type empty;
     }
     leaf rib-group {
       description "Routing table group for importing ingress routes";
       junos:must "(\"routing-options rib-groups $$\")";
       junos:must-message "Referenced rib-group must be defined";
       type string;
     }
     leaf rib-group6 {
       description "Routing table group for importing ingress v6 routes";
       junos:must "(\"routing-options rib-groups $$\")";
       junos:must-message "Referenced rib-group must be defined";
       type string;
     }
     leaf l2-smart-policy {
       description "Do not export or import Layer 3 FECs for Layer 2 sessions";
       type empty;
     }
     leaf track-igp-metric {
       description "Track the IGP metric";
       type empty;
     }
     leaf strict-targeted-hellos {
       description "Do not send targeted hellos to unconfigured neighbors";
       type empty;
     }
     container longest-match {
       presence "enable longest-match";
       description "Configure longest match";
       uses apply-advanced;
       leaf-list policy {
         ordered-by user;
         description "Longest match import policy";
         type jt:policy-algebra;
       }
     }
     leaf-list color-import-policy {
       ordered-by user;
       description "Import color policy";
       type jt:policy-algebra;
     }
     leaf-list import {
       ordered-by user;
       description "Import policy";
       type jt:policy-algebra;
     }
     leaf-list export {
       ordered-by user;
       description "Export policy";
       type jt:policy-algebra;
     }
     leaf-list egress-policy {
       ordered-by user;
       description "Configure LSP egress policy";
       type jt:policy-algebra;
     }
     leaf-list dod-request-policy {
       ordered-by user;
       description "Configure DoD label request policy";
       type jt:policy-algebra;
     }
     container next-hop {
       description "LDP next-hop control";
       uses apply-advanced;
       container merged {
         junos:must "(\"protocols ldp deaggregate\")";
         junos:must-message "next-hop merged policy requires deaggregate to be enabled.";
         description "Merged next hop";
         uses apply-advanced;
         leaf-list policy {
           ordered-by user;
           description "Merged next-hop policy";
           type jt:policy-algebra;
         }
       }
       container no-rsvp-tunneling {
         junos:must "(\"protocols ldp deaggregate\")";
         junos:must-message "next-hop no-rsvp-tunneling policy requires deaggregate to be enabled.";
         description "No rsvp tunneling";
         uses apply-advanced;
         leaf-list policy {
           ordered-by user;
           description "No rsvp tunneling next-hop policy";
           type jt:policy-algebra;
         }
       }
     }
     choice mtu-discovery-choice {
       leaf mtu-discovery {
         description "Enable TCP path MTU discovery";
         type empty;
       }
       leaf no-mtu-discovery {
         description "Don't enable TCP path MTU discovery";
         type empty;
       }
     }
     choice deaggregate-choice {
       leaf deaggregate {
         description "Deaggregate FECs into separate labels";
         type empty;
       }
       leaf no-deaggregate {
         description "Don't deaggregate FECs into separate labels";
         type empty;
       }
     }
     leaf explicit-null {
       description "Advertise the EXPLICIT_NULL label for egress FECs";
       type empty;
     }
     leaf label-withdrawal-delay {
       description "Delay label withdrawal for FECs to avoid label churn";
       default "60";
       units "seconds";
       type union {
         type string {
           pattern "<.*>|$.*";
         }
         type uint32 {
           range "0 .. 120";
         }
       }
     }
     container make-before-break {
       presence "enable make-before-break";
       description "Configure make before break";
       uses apply-advanced;
       leaf timeout {
         description "Make before break timeout";
         default "30";
         units "seconds";
         type union {
           type string {
             pattern "<.*>|$.*";
           }
           type uint32 {
             range "1 .. 300";
           }
         }
       }
       leaf switchover-delay {
         description "Make before break switchover delay";
         default "3";
         units "seconds";
         type union {
           type string {
             pattern "<.*>|$.*";
           }
           type uint32 {
             range "1 .. 300";
           }
         }
       }
     }
     container transport-address {
       description "Address used for TCP sessions";
       choice address-choice {
         case case_1 {
           leaf router-id {
             description "Use router ID for TCP connections";
             type empty;
           }
         }
         case case_2 {
           leaf interface {
             description "Use interface address for TCP connections";
             type empty;
           }
         }
         case case_3 {
           leaf address {
             description "Use specified address for TCP connections";
             type jt:ipaddr;
           }
         }
       }
     }
     leaf keepalive-interval {
       description "Keepalive interval (seconds)";
       type union {
         type string {
           pattern "<.*>|$.*";
         }
         type uint32 {
           range "1 .. 65535";
         }
       }
     }
     leaf keepalive-timeout {
       description "Keepalive timeout (seconds)";
       type union {
         type string {
           pattern "<.*>|$.*";
         }
         type uint32 {
           range "1 .. 65535";
         }
       }
     }
     list interface {
       key name;
       description "Enable LDP on this interface";
       leaf name {
         description "Interface name";
         type union {
           type jt:interface-name;
           type string {
             pattern "<.*>|$.*";
           }
         }
       }
       uses apply-advanced;
       choice enable-disable {
         case case_1 {
           leaf disable {
             description "Disable LDP on this interface";
             type empty;
           }
         }
       }
       leaf hello-interval {
         description "Hello interval (seconds)";
         type union {
           type string {
             pattern "<.*>|$.*";
           }
           type uint32 {
             range "1 .. 65535";
           }
         }
       }
       leaf hold-time {
         description "Hello hold time (seconds)";
         type union {
           type string {
             pattern "<.*>|$.*";
           }
           type uint32 {
             range "1 .. 65535";
           }
         }
       }
       container link-protection {
         presence "enable link-protection";
         description "Enable link protection to protect interface for link faults only";
         uses apply-advanced;
         choice enable-disable {
           case case_1 {
             leaf disable {
               description "Disable link-protection";
               type empty;
             }
           }
         }
         leaf dynamic-rsvp-lsp {
           description "Enable setup of dynamic rsvp lsp for link protection";
           type empty;
         }
       }
       container transport-address {
         description "Address used for TCP sessions";
         choice address-choice {
           case case_1 {
             leaf router-id {
               description "Use router ID for TCP connections";
               type empty;
             }
           }
           case case_2 {
             leaf interface {
               description "Use interface address for TCP connections";
               type empty;
             }
           }
           case case_3 {
             leaf address {
               description "Use specified address for TCP connections";
               type jt:ipaddr;
             }
           }
         }
       }
       choice allow-subnet-mismatch-choice {
         leaf allow-subnet-mismatch {
           description "Allow subnet mismatch for source address in hello packet";
           type empty;
         }
         leaf no-allow-subnet-mismatch {
           description "Don't allow subnet mismatch for source address in hello packet";
           type empty;
         }
       }
     }
     list neighbor {
       key name;
       description "Configure a remote LDP neighbor";
       leaf name {
         description "Neighbor address";
         type jt:ipaddr;
       }
       uses apply-advanced;
     }
     list session {
       key name;
       description "Configure session parameters";
       leaf name {
         description "Session destination address";
         type jt:ipaddr;
       }
       uses apply-advanced;
       leaf authentication-key {
         description "MD5 authentication key";
         type string {
           length "1 .. 126";
         }
       }
       leaf authentication-algorithm {
         description "Authentication algorithm name";
         default "hmac-sha-1-96";
         junos:must "(\".. authentication-key-chain\")";
         junos:must-message "May not be configured without authentication-key-chain";
         junos:must "(!(\".. authentication-key\"))";
         junos:must-message "May not be configured with authentication-key";
         type enumeration {
           enum "md5" {
             description "Message Digest 5";
           }
           enum "hmac-sha-1-96" {
             description "Hash-based Message Authentication Code (SHA1) (96 bits)";
           }
           enum "aes-128-cmac-96" {
             description "Cipher-based Message Authentication Code (AES128) (96 bits)";
           }
           enum "ao" {
             description "TCP Authentication Option";
           }
         }
       }
       leaf tcpao-auth-mismatch {
         description "Continue without TCP-AO if any one TCP endpoint does not have TCP-AO configured";
         junos:must "(!(\".. authentication-key\"))";
         junos:must-message "May not be configured with authentication-key";
         type enumeration {
           enum "allow-without-tcpao" {
             description "Allow the connection establishment without TCP-AO";
           }
         }
       }
       leaf authentication-key-chain {
         description "Key chain name";
         junos:must "(!(\".. authentication-key\"))";
         junos:must-message "May not be configured with authentication-key";
         junos:must "(\"security authentication-key-chains key-chain $$\")";
         junos:must-message "Referenced key-chain must be defined";
         type string {
           length "1 .. 128";
         }
       }
       leaf downstream-on-demand {
         description "Configure downstream on demand label distribution mode";
         type empty;
       }
       leaf transport-address {
         description "Address used for TCP sessions to the neighbor";
         type jt:ipaddr;
       }
       choice mtu-discovery-choice {
         leaf mtu-discovery {
           description "Enable TCP path MTU discovery";
           type empty;
         }
         leaf no-mtu-discovery {
           description "Don't enable TCP path MTU discovery";
           type empty;
         }
       }
     }
     list session-group {
       key name;
       description "Configure session group parameters";
       leaf name {
         description "Session destination address/prefix length";
         type jt:ipprefix;
       }
       uses apply-advanced;
       leaf authentication-key {
         description "MD5 authentication key";
         type string {
           length "1 .. 126";
         }
       }
       leaf authentication-algorithm {
         description "Authentication algorithm name";
         default "hmac-sha-1-96";
         junos:must "(\".. authentication-key-chain\")";
         junos:must-message "May not be configured without authentication-key-chain";
         junos:must "(!(\".. authentication-key\"))";
         junos:must-message "May not be configured with authentication-key";
         type enumeration {
           enum "md5" {
             description "Message Digest 5";
           }
           enum "hmac-sha-1-96" {
             description "Hash-based Message Authentication Code (SHA1) (96 bits)";
           }
           enum "aes-128-cmac-96" {
             description "Cipher-based Message Authentication Code (AES128) (96 bits)";
           }
           enum "ao" {
             description "TCP Authentication Option";
           }
         }
       }
       leaf tcpao-auth-mismatch {
         description "Continue without TCP-AO if any one TCP endpoint does not have TCP-AO configured";
         junos:must "(!(\".. authentication-key\"))";
         junos:must-message "May not be configured with authentication-key";
         type enumeration {
           enum "allow-without-tcpao" {
             description "Allow the connection establishment without TCP-AO";
           }
         }
       }
       leaf authentication-key-chain {
         description "Key chain name";
         junos:must "(!(\".. authentication-key\"))";
         junos:must-message "May not be configured with authentication-key";
         junos:must "(\"security authentication-key-chains key-chain $$\")";
         junos:must-message "Referenced key-chain must be defined";
         type string {
           length "1 .. 128";
         }
       }
       leaf downstream-on-demand {
         description "Configure downstream on demand label distribution mode";
         type empty;
       }
       leaf transport-address {
         description "Address used for TCP sessions to the neighbor";
         type jt:ipaddr;
       }
       choice mtu-discovery-choice {
         leaf mtu-discovery {
           description "Enable TCP path MTU discovery";
           type empty;
         }
         leaf no-mtu-discovery {
           description "Don't enable TCP path MTU discovery";
           type empty;
         }
       }
     }
     container session-protection {
       presence "enable session-protection";
       description "Configure session protection";
       leaf timeout {
         description "Session protection timeout";
         units "seconds";
         type union {
           type string {
             pattern "<.*>|$.*";
           }
           type uint16 {
             range "1 .. 65535";
           }
         }
       }
     }
     container igp-synchronization {
       description "Configure IGP synchronization parameters";
       uses apply-advanced;
       leaf holddown-interval {
         description "Time to hold the up notification to the IGPs";
         units "seconds";
         type union {
           type string {
             pattern "<.*>|$.*";
           }
           type uint32 {
             range "10 .. 300";
           }
         }
       }
     }
     container log-updown {
       description "Logging actions for LSP up/down events";
       uses apply-advanced;
       container trap {
         description "SNMP traps options";
         choice enable-disable {
           case case_1 {
             leaf disable {
               description "Disable LDP LSP up/down trap";
               type empty;
             }
           }
         }
       }
     }
     container policing {
       description "Configure policing for an LDP FEC";
       uses apply-advanced;
       list fec {
         key name;
         ordered-by user;
         description "Forwarding equivalence class";
         leaf name {
           description "Forwarding equivalence class address";
           type jt:ipv4prefix;
         }
         uses apply-advanced;
         leaf ingress-traffic {
           description "Name of filter to use for policing ingress LDP traffic";
           junos:must "((\"firewall family any filter $$\" || (!(\"firewall\") && \".. .. .. .. .. .. .. .. firewall family any filter $$\")))";
           junos:must-message "referenced filter must be defined under firewall family any";
           type string {
             junos:posix-pattern "!^((__.*)|(.{65,}))$";
             junos:pattern-message "Must be a non-reserved string of 64 characters or less";
           }
         }
         leaf transit-traffic {
           description "Name of filter to use for policing transit LDP traffic";
           junos:must "((\"firewall family any filter $$\" || (!(\"firewall\") && \".. .. .. .. .. .. .. .. firewall family any filter $$\")))";
           junos:must-message "referenced filter must be defined under firewall family any";
           type string {
             junos:posix-pattern "!^((__.*)|(.{65,}))$";
             junos:pattern-message "Must be a non-reserved string of 64 characters or less";
           }
         }
       }
     }
     container entropy-label {
       description "Insert entropy label for  a LDP FEC";
       uses apply-advanced;
       leaf-list ingress-policy {
         ordered-by user;
         description "Entropy label ingress policy";
         type jt:policy-algebra;
       }
     }
     container oam {
       description "Configure periodic OAM for a LDP FEC";
       uses apply-advanced;
       leaf-list ingress-policy {
         ordered-by user;
         description "OAM ingress policy";
         type jt:policy-algebra;
       }
       leaf-list bfd-port-egress-policy {
         ordered-by user;
         description "OAM egress policy";
         type jt:policy-algebra;
       }
       list fec {
         key name;
         ordered-by user;
         description "Forwarding equivalence class";
         leaf name {
           description "Forwarding equivalence class address";
           type jt:ipv4prefix;
         }
         uses apply-advanced;
         choice bfd_liveness_detection_type {
           case case_1 {
             container bfd-liveness-detection {
               description "Bidirectional Forwarding Detection (BFD) options";
               uses apply-advanced;
               leaf version {
                 description "BFD protocol version number";
                 default "automatic";
                 type enumeration {
                   enum "0" {
                     description "BFD version 0 (deprecated)";
                   }
                   enum "1" {
                     description "BFD version 1";
                   }
                   enum "automatic" {
                     description "Choose BFD version automatically";
                   }
                 }
               }
               leaf minimum-interval {
                 description "Minimum transmit and receive interval";
                 units "milliseconds";
                 type union {
                   type string {
                     pattern "<.*>|$.*";
                   }
                   type uint32 {
                     range "1 .. 255000";
                   }
                 }
               }
               leaf minimum-transmit-interval {
                 description "Minimum transmit interval";
                 status deprecated;
                 units "milliseconds";
                 type union {
                   type string {
                     pattern "<.*>|$.*";
                   }
                   type uint32 {
                     range "1 .. 255000";
                   }
                 }
               }
               leaf minimum-receive-interval {
                 description "Minimum receive interval";
                 units "milliseconds";
                 type union {
                   type string {
                     pattern "<.*>|$.*";
                   }
                   type uint32 {
                     range "1 .. 255000";
                   }
                 }
               }
               leaf multiplier {
                 description "Detection time multiplier";
                 default "3";
                 type union {
                   type string {
                     pattern "<.*>|$.*";
                   }
                   type uint32 {
                     range "1 .. 255";
                   }
                 }
               }
               choice adaptation-choice {
                 case case_1 {
                   leaf no-adaptation {
                     description "Disable adaptation";
                     type empty;
                   }
                 }
               }
               container transmit-interval {
                 description "Transmit-interval options";
                 uses apply-advanced;
                 leaf minimum-interval {
                   description "Minimum transmit interval";
                   units "milliseconds";
                   type union {
                     type string {
                       pattern "<.*>|$.*";
                     }
                     type uint32 {
                       range "1 .. 255000";
                     }
                   }
                 }
                 leaf threshold {
                   description "High transmit interval triggering a trap";
                   units "milliseconds";
                   type union {
                     type uint32;
                     type string {
                       pattern "<.*>|$.*";
                     }
                   }
                 }
               }
               container detection-time {
                 description "Detection-time options";
                 uses apply-advanced;
                 leaf threshold {
                   description "High detection-time triggering a trap";
                   units "milliseconds";
                   type union {
                     type uint32;
                     type string {
                       pattern "<.*>|$.*";
                     }
                   }
                 }
               }
               leaf ecmp {
                 description "Enable equal cost multipath (ECMP) support for BFD";
                 type empty;
               }
               container failure-action {
                 description "Action to take when BFD session goes down";
                 choice action-choice {
                   case case_1 {
                     leaf remove-route {
                       description "Remove LDP route from the ribs";
                       type empty;
                     }
                   }
                   case case_2 {
                     leaf remove-nexthop {
                       description "Remove LDP nexthop from the route";
                       type empty;
                     }
                   }
                 }
               }
               leaf holddown-interval {
                 description "Time to hold the session-UP notification to the client";
                 default "0";
                 units "milliseconds";
                 type union {
                   type string {
                     pattern "<.*>|$.*";
                   }
                   type uint32 {
                     range "0 .. 255000";
                   }
                 }
               }
               leaf no-router-alert-option {
                 description "Do not set Router-Alert options in IP header for MPLS-BFD";
                 type empty;
               }
               leaf use-ip-ttl-1 {
                 description "Set TTL value to 1 in IP header for MPLS-BFD";
                 type empty;
               }
             }
           }
           case case_2 {
             leaf no-bfd-liveness-detection {
               description "Disable BFD liveness detection";
               type empty;
             }
           }
         }
         container periodic-traceroute {
           presence "enable periodic-traceroute";
           description "Configure periodic traceroute";
           uses apply-advanced;
           leaf frequency {
             description "Time between traceroute attempts";
             units "minutes";
             type union {
               type string {
                 pattern "<.*>|$.*";
               }
               type uint16 {
                 range "15 .. 120";
               }
             }
           }
           leaf ttl {
             description "Maximum time-to-live value";
             type union {
               type string {
                 pattern "<.*>|$.*";
               }
               type uint16 {
                 range "1 .. 255";
               }
             }
           }
           leaf retries {
             description "Number of times to resend probe";
             type union {
               type string {
                 pattern "<.*>|$.*";
               }
               type uint16 {
                 range "1 .. 9";
               }
             }
           }
           leaf wait {
             description "Time to wait before resending probe";
             units "seconds";
             type union {
               type string {
                 pattern "<.*>|$.*";
               }
               type uint16 {
                 range "5 .. 15";
               }
             }
           }
           leaf paths {
             description "Maximum number of paths to traverse";
             type union {
               type string {
                 pattern "<.*>|$.*";
               }
               type uint16 {
                 range "1 .. 255";
               }
             }
           }
           leaf source {
             description "Source address to use when sending probes";
             type jt:ipv4addr;
           }
           leaf exp {
             description "Class-of-service value to use when sending probes";
             type union {
               type string {
                 pattern "<.*>|$.*";
               }
               type uint16 {
                 range "0 .. 7";
               }
             }
           }
           leaf fanout {
             description "Maximum number of nexthops to search per node";
             type union {
               type string {
                 pattern "<.*>|$.*";
               }
               type uint16 {
                 range "1 .. 64";
               }
             }
           }
           leaf disable {
             description "Disable periodic traceroute for a FEC";
             type empty;
           }
         }
       }
       container bfd-liveness-detection {
         description "Bidirectional Forwarding Detection (BFD) options";
         uses apply-advanced;
         leaf version {
           description "BFD protocol version number";
           default "automatic";
           type enumeration {
             enum "0" {
               description "BFD version 0 (deprecated)";
             }
             enum "1" {
               description "BFD version 1";
             }
             enum "automatic" {
               description "Choose BFD version automatically";
             }
           }
         }
         leaf minimum-interval {
           description "Minimum transmit and receive interval";
           units "milliseconds";
           type union {
             type string {
               pattern "<.*>|$.*";
             }
             type uint32 {
               range "1 .. 255000";
             }
           }
         }
         leaf minimum-transmit-interval {
           description "Minimum transmit interval";
           status deprecated;
           units "milliseconds";
           type union {
             type string {
               pattern "<.*>|$.*";
             }
             type uint32 {
               range "1 .. 255000";
             }
           }
         }
         leaf minimum-receive-interval {
           description "Minimum receive interval";
           units "milliseconds";
           type union {
             type string {
               pattern "<.*>|$.*";
             }
             type uint32 {
               range "1 .. 255000";
             }
           }
         }
         leaf multiplier {
           description "Detection time multiplier";
           default "3";
           type union {
             type string {
               pattern "<.*>|$.*";
             }
             type uint32 {
               range "1 .. 255";
             }
           }
         }
         choice adaptation-choice {
           case case_1 {
             leaf no-adaptation {
               description "Disable adaptation";
               type empty;
             }
           }
         }
         container transmit-interval {
           description "Transmit-interval options";
           uses apply-advanced;
           leaf minimum-interval {
             description "Minimum transmit interval";
             units "milliseconds";
             type union {
               type string {
                 pattern "<.*>|$.*";
               }
               type uint32 {
                 range "1 .. 255000";
               }
             }
           }
           leaf threshold {
             description "High transmit interval triggering a trap";
             units "milliseconds";
             type union {
               type uint32;
               type string {
                 pattern "<.*>|$.*";
               }
             }
           }
         }
         container detection-time {
           description "Detection-time options";
           uses apply-advanced;
           leaf threshold {
             description "High detection-time triggering a trap";
             units "milliseconds";
             type union {
               type uint32;
               type string {
                 pattern "<.*>|$.*";
               }
             }
           }
         }
         leaf ecmp {
           description "Enable equal cost multipath (ECMP) support for BFD";
           type empty;
         }
         container failure-action {
           description "Action to take when BFD session goes down";
           choice action-choice {
             case case_1 {
               leaf remove-route {
                 description "Remove LDP route from the ribs";
                 type empty;
               }
             }
             case case_2 {
               leaf remove-nexthop {
                 description "Remove LDP nexthop from the route";
                 type empty;
               }
             }
           }
         }
         leaf holddown-interval {
           description "Time to hold the session-UP notification to the client";
           default "0";
           units "milliseconds";
           type union {
             type string {
               pattern "<.*>|$.*";
             }
             type uint32 {
               range "0 .. 255000";
             }
           }
         }
         leaf no-router-alert-option {
           description "Do not set Router-Alert options in IP header for MPLS-BFD";
           type empty;
         }
         leaf use-ip-ttl-1 {
           description "Set TTL value to 1 in IP header for MPLS-BFD";
           type empty;
         }
       }
       container periodic-traceroute {
         presence "enable periodic-traceroute";
         description "Configure periodic traceroute";
         uses apply-advanced;
         leaf frequency {
           description "Time between traceroute attempts";
           units "minutes";
           type union {
             type string {
               pattern "<.*>|$.*";
             }
             type uint16 {
               range "15 .. 120";
             }
           }
         }
         leaf ttl {
           description "Maximum time-to-live value";
           type union {
             type string {
               pattern "<.*>|$.*";
             }
             type uint16 {
               range "1 .. 255";
             }
           }
         }
         leaf retries {
           description "Number of times to resend probe";
           type union {
             type string {
               pattern "<.*>|$.*";
             }
             type uint16 {
               range "1 .. 9";
             }
           }
         }
         leaf wait {
           description "Time to wait before resending probe";
           units "seconds";
           type union {
             type string {
               pattern "<.*>|$.*";
             }
             type uint16 {
               range "5 .. 15";
             }
           }
         }
         leaf paths {
           description "Maximum number of paths to traverse";
           type union {
             type string {
               pattern "<.*>|$.*";
             }
             type uint16 {
               range "1 .. 255";
             }
           }
         }
         leaf source {
           description "Source address to use when sending probes";
           type jt:ipv4addr;
         }
         leaf exp {
           description "Class-of-service value to use when sending probes";
           type union {
             type string {
               pattern "<.*>|$.*";
             }
             type uint16 {
               range "0 .. 7";
             }
           }
         }
         leaf fanout {
           description "Maximum number of nexthops to search per node";
           type union {
             type string {
               pattern "<.*>|$.*";
             }
             type uint16 {
               range "1 .. 64";
             }
           }
         }
       }
       leaf lsp-ping-interval {
         description "Time interval between LSP ping messages";
         default "60";
         units "seconds";
         type union {
           type string {
             pattern "<.*>|$.*";
           }
           type uint16 {
             range "30 .. 3600";
           }
         }
       }
       leaf lsp-ping-multiplier {
         description "Number of ping reply missed before declaring BFD down";
         type union {
           type string {
             pattern "<.*>|$.*";
           }
           type uint8 {
             range "1 .. 5";
           }
         }
       }
     }
     container targeted-hello {
       description "Configure targeted hello parameters";
       uses apply-advanced;
       leaf hello-interval {
         description "Hello interval (seconds)";
         type union {
           type string {
             pattern "<.*>|$.*";
           }
           type uint32 {
             range "1 .. 65535";
           }
         }
       }
       leaf hold-time {
         description "Hold interval (seconds)";
         type union {
           type string {
             pattern "<.*>|$.*";
           }
           type uint32 {
             range "1 .. 65535";
           }
         }
       }
     }
     container p2mp {
       presence "enable p2mp";
       description "Advertise P2MP capability to peers";
       uses apply-advanced;
       container recursive {
         description "Configure P2MP recursive parameters";
         uses apply-advanced;
         leaf route {
           description "Allow recursive route resolution to signal P2MP FEC";
           type empty;
         }
       }
       list root-address {
         key name;
         description "Configure the root address of P2MP LSP";
         leaf name {
           description "Root address of the P2MP LSP";
           type jt:ipaddr;
         }
         uses apply-advanced;
         list lsp-id {
           key name;
           description "Configure the generic LSP identifier";
           leaf name {
             description "Generic LSP identifier value";
             type union {
               type string {
                 pattern "<.*>|$.*";
               }
               type uint32 {
                 range "1 .. 65535";
               }
             }
           }
           uses apply-advanced;
         }
         list group-address {
           key name;
           description "IPv4/Ipv6 group address for mLDP LSP";
           leaf name {
             description "IPv4/Ipv6 group address";
             type jt:ipaddr;
           }
           uses apply-advanced;
           list source-address {
             key name;
             description "IPv4/Ipv6 source address";
             leaf name {
               description "IPv4/Ipv6 source address for mLDP LSP";
               type jt:ipaddr;
             }
             uses apply-advanced;
           }
         }
       }
       leaf no-rsvp-tunneling {
         description "Do not allow LDP P2MP to use RSVP-TE LSPs for tunneling";
         type empty;
       }
     }
     container sr-mapping-client {
       presence "enable sr-mapping-client";
       description "Enable LDP to SR mapping-client functionality";
       uses apply-advanced;
       leaf-list policy {
         ordered-by user;
         description "SR mapping-client policy";
         type jt:policy-algebra;
       }
     }
     leaf upstream-label-assignment {
       description "Allow Upstream Label Assignment capability";
       type empty;
     }
     list family {
       key name;
       ordered-by user;
       description "Address family";
       leaf name {
         type enumeration {
           enum "inet" {
             description "IPv4 family";
           }
           enum "inet6" {
             description "IPv6 family";
           }
         }
       }
       uses apply-advanced;
     }
     leaf transport-preference {
       description "TCP transport preference";
       type enumeration {
         enum "ipv4" {
           description "Use IPv4 for TCP connections";
         }
         enum "ipv6" {
           description "Use IPv6 for TCP connections";
         }
       }
     }
     container dual-transport {
       presence "enable dual-transport";
       description "Use separate IPv4 and IPv6 TCP transport";
       uses apply-advanced;
       leaf inet-lsr-id {
         description "LSR identifier for address family inet";
         type jt:ipv4addr;
       }
       leaf inet6-lsr-id {
         description "LSR identifier for address family inet6";
         type jt:ipv4addr;
       }
     }
     leaf no-propagate-ttl {
       description "Disable TTL propagation from IP to MPLS (on push) and MPLS to IP (on pop)";
       type empty;
     }
   }
   grouping juniper-protocols-lmp {
     uses apply-advanced;
     list te-link {
       key name;
       ordered-by user;
       description "Traffic engineering link";
       leaf name {
         description "Name of TE link";
         type string;
       }
       uses apply-advanced;
       leaf local-address {
         description "Address of the local end of the link";
         junos:must "(!(\".. remote-address $$\"))";
         junos:must-message "Local and remote addresses of the TE link must be different";
         junos:must "(\".. remote-address\")";
         junos:must-message "Remote address of the TE link must be configured";
         type jt:ipaddr;
       }
       leaf remote-address {
         description "Address of the remote end of the link";
         junos:must "(!(\".. local-address $$\"))";
         junos:must-message "Local and remote addresses of the TE link must be different";
         junos:must "(\".. local-address\")";
         junos:must-message "Local address of the TE link must be configured";
         type jt:ipaddr;
       }
       leaf remote-id {
         description "Link ID for the remote end of the link";
         type union {
           type string {
             pattern "<.*>|$.*";
           }
           type uint32 {
             range "1 .. 4294967295";
           }
         }
       }
       leaf te-metric {
         description "Traffic engineering metric of the link";
         type union {
           type string {
             pattern "<.*>|$.*";
           }
           type uint32 {
             range "1 .. 65535";
           }
         }
       }
       choice enable-disable {
         case case_1 {
           leaf disable {
             description "Disable TE link";
             type empty;
           }
         }
       }
       container ethernet-vlan {
         presence "enable ethernet-vlan";
         description "TE link used for setup of  L2 VLAN LSP";
         uses apply-advanced;
         leaf-list vlan-id-range {
           description "VLAN id";
           type jt:vlan-range;
           max-elements 1;
         }
       }
       choice resource-option {
         case case_1 {
           list interface {
             key name;
             ordered-by user;
             description "Member interface of TE link";
             leaf name {
               description "Interface name";
               type union {
                 type jt:interface-device;
                 type string {
                   pattern "<.*>|$.*";
                 }
               }
             }
             uses apply-advanced;
             leaf local-address {
               description "Local address of the resource";
               junos:must "(!(\".. remote-address $$\"))";
               junos:must-message "Local and remote addresses of the resource must be different";
               junos:must "(\".. remote-address\")";
               junos:must-message "Remote address of the resource must be configured";
               type jt:ipaddr;
             }
             leaf remote-address {
               description "Remote address of the resource";
               junos:must "(!(\".. local-address $$\"))";
               junos:must-message "Local and remote addresses of the resource must be different";
               junos:must "(\".. local-address\")";
               junos:must-message "Local address of the resource must be configured";
               type jt:ipaddr;
             }
             leaf remote-id {
               description "Interface ID for the remote end of the resource";
               type union {
                 type string {
                   pattern "<.*>|$.*";
                 }
                 type uint32 {
                   range "1 .. 4294967295";
                 }
               }
             }
             choice enable-disable {
               case case_1 {
                 leaf disable {
                   description "Disable resource on this TE link";
                   type empty;
                 }
               }
             }
           }
         }
         case case_2 {
           list label-switched-path {
             key name;
             ordered-by user;
             description "Member forwarding adjacency LSP of TE link";
             max-elements 1;
             leaf name {
               description "Name of label-switched path";
               type string;
             }
             uses apply-advanced;
             leaf local-address {
               description "Local address of the resource";
               junos:must "(!(\".. remote-address $$\"))";
               junos:must-message "Local and remote addresses of the resource must be different";
               junos:must "(\".. remote-address\")";
               junos:must-message "Remote address of the resource must be configured";
               type jt:ipaddr;
             }
             leaf remote-address {
               description "Remote address of the resource";
               junos:must "(!(\".. local-address $$\"))";
               junos:must-message "Local and remote addresses of the resource must be different";
               junos:must "(\".. local-address\")";
               junos:must-message "Local address of the resource must be configured";
               type jt:ipaddr;
             }
             leaf remote-id {
               description "Interface ID for the remote end of the resource";
               type union {
                 type string {
                   pattern "<.*>|$.*";
                 }
                 type uint32 {
                   range "1 .. 4294967295";
                 }
               }
             }
             choice enable-disable {
               case case_1 {
                 leaf disable {
                   description "Disable resource on this TE link";
                   type empty;
                 }
               }
             }
           }
         }
       }
     }
     list peer {
       key name;
       ordered-by user;
       description "Define a network or LMP peer";
       leaf name {
         description "Name of peer";
         type string;
       }
       uses apply-advanced;
       leaf address {
         description "Address of peer";
         type jt:ipaddr;
       }
       container lmp-protocol {
         presence "enable lmp-protocol";
         description "LMP protocol attributes";
         uses apply-advanced;
         leaf hello-interval {
           description "Interval between Hello messages";
           units "milliseconds";
           type union {
             type string {
               pattern "<.*>|$.*";
             }
             type uint32 {
               range "150 .. 21845";
             }
           }
         }
         leaf hello-dead-interval {
           description "Delay for control channel shutdown when no Hello received";
           units "milliseconds";
           type union {
             type string {
               pattern "<.*>|$.*";
             }
             type uint32 {
               range "500 .. 65535";
             }
           }
         }
         leaf retransmission-interval {
           description "Minimum time before retransmitting a message";
           units "milliseconds";
           type union {
             type string {
               pattern "<.*>|$.*";
             }
             type uint32 {
               range "500 .. 300000";
             }
           }
         }
         leaf retry-limit {
           description "Number of times to retransmit a message";
           type union {
             type string {
               pattern "<.*>|$.*";
             }
             type uint32 {
               range "3 .. 1000";
             }
           }
         }
         leaf passive {
           description "Do not send Config messages to peer";
           type empty;
         }
       }
       leaf-list control-channel {
         ordered-by user;
         description "Control channel interfaces by priority";
         type union {
           type jt:interface-name;
           type string {
             pattern "<.*>|$.*";
           }
         }
       }
       list lmp-control-channel {
         key name;
         ordered-by user;
         description "Control channel IDs";
         junos:must "(!(\".. control-channel\"))";
         junos:must-message "control-channel and lmp-control-channel are mutually exclusive";
         uses lmp_control_channel_type;
       }
       leaf-list te-link {
         ordered-by user;
         description "List of TE links managed by this peer";
         type string;
       }
     }
     container traceoptions {
       description "LMP trace options";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "init" {
               description "Trace initialization events";
             }
             enum "show" {
               description "Trace show command servicing";
             }
             enum "route-socket" {
               description "Trace route-socket events";
             }
             enum "parse" {
               description "Trace parser processing";
             }
             enum "process" {
               description "Trace general configuration processing";
             }
             enum "server" {
               description "Trace server processing";
             }
             enum "routing" {
               description "Trace routing protocols interworking";
             }
             enum "packets" {
               description "Trace packet processing";
             }
             enum "hello-packets" {
               description "Trace hello packet processing";
             }
             enum "state" {
               description "Trace state transitions";
             }
             enum "nsr-synchronization" {
               description "Trace mirror and nsr transitions";
             }
             enum "all" {
               description "Trace everything";
             }
           }
         }
         leaf send {
           description "Trace transmitted packets";
           status deprecated;
           type empty;
         }
         leaf receive {
           description "Trace received packets";
           status deprecated;
           type empty;
         }
         leaf detail {
           description "Trace detailed information";
           status deprecated;
           type empty;
         }
         leaf disable {
           description "Disable this trace flag";
           status deprecated;
           type empty;
         }
       }
     }
   }
   grouping juniper-protocols-mpls {
     description "Multiprotocol Label Switching options";
     uses apply-advanced;
     list lsp-external-controller {
       key name;
       ordered-by user;
       description "External path computing entity";
       leaf name {
         description "Name of the external path computing entity";
         type string {
           junos:posix-pattern "^.{1,64}$";
           junos:pattern-message "Must be a string of less than 64 characters";
         }
       }
       uses apply-advanced;
       container label-switched-path-template {
         description "Template for externally provisioned LSP parameters";
         uses apply-advanced;
         choice dynamic-template {
           case case_1 {
             leaf template-name {
               description "Name of point-to-point LSP template";
               junos:must "(!(\"protocols mpls label-switched-path $$ p2mp\"))";
               junos:must-message "Referenced template cannot be a p2mp template";
               junos:must "(\"protocols mpls label-switched-path $$ template\")";
               junos:must-message "Referenced point-to-point LSP template does not exist";
               type string {
                 length "1 .. 32";
                 junos:posix-pattern "![*<>]";
                 junos:pattern-message "Template name should not contain '*' and angle brackets";
               }
             }
           }
           case case_2 {
             leaf default-template {
               description "Use default parameters";
               type empty;
             }
           }
         }
       }
       container label-switched-path-p2mp-template {
         description "Template for externally provisioned P2MP LSP parameters";
         uses apply-advanced;
         choice dynamic-template {
           case case_1 {
             leaf template-name {
               description "Name of point-to-multipoint LSP template";
               junos:must "(\"protocols mpls label-switched-path $$ p2mp\")";
               junos:must-message "Referenced template should be a p2mp template";
               junos:must "(\"protocols mpls label-switched-path $$ template\")";
               junos:must-message "Referenced point-to-multipoint LSP template does not exist";
               type string {
                 length "1 .. 32";
                 junos:posix-pattern "![*<>]";
                 junos:pattern-message "Template name should not contain '*' and angle brackets";
               }
             }
           }
           case case_2 {
             leaf default-template {
               description "Use default parameters";
               type empty;
             }
           }
         }
       }
       list pce-controlled-lsp {
         key name;
         ordered-by user;
         description "Template for externally provisioned LSP using regular expression";
         leaf name {
           description "Template regular expression";
           type string {
             junos:posix-pattern "^.{1,64}$";
             junos:pattern-message "Must be a string of less than 64 characters";
           }
         }
         uses apply-advanced;
         container label-switched-path-template {
           description "Template for externally provisioned LSP parameters";
           uses apply-advanced;
           leaf template-name {
             description "Name of point-to-point LSP template";
             junos:must "(!(\"protocols mpls label-switched-path $$ p2mp\"))";
             junos:must-message "Referenced template cannot be a p2mp template";
             junos:must "(\"protocols mpls label-switched-path $$ template\")";
             junos:must-message "Referenced point-to-point LSP template does not exist";
             type string {
               length "1 .. 64";
               junos:posix-pattern "![*<>]";
               junos:pattern-message "Template name should not contain '*' and angle brackets";
             }
           }
         }
         container label-switched-path-p2mp-template {
           description "Template for externally provisioned P2MP LSP parameters";
           uses apply-advanced;
           leaf template-name {
             description "Name of point-to-multipoint LSP template";
             junos:must "(\"protocols mpls label-switched-path $$ p2mp\")";
             junos:must-message "Referenced template should be a p2mp template";
             junos:must "(\"protocols mpls label-switched-path $$ template\")";
             junos:must-message "Referenced point-to-multipoint LSP template does not exist";
             type string {
               length "1 .. 64";
               junos:posix-pattern "![*<>]";
               junos:pattern-message "Template name should not contain '*' and angle brackets";
             }
           }
         }
       }
     }
     container path-mtu {
       presence "enable path-mtu";
       description "Path MTU configuration";
       uses apply-advanced;
       leaf allow-fragmentation {
         description "If needed, fragment IP before encapsulating in MPLS";
         type empty;
       }
       container rsvp {
         presence "enable rsvp";
         description "RSVP-specific path MTU options";
         uses apply-advanced;
         leaf mtu-signaling {
           description "Enable RSVP path MTU signaling";
           type empty;
         }
       }
     }
     container diffserv-te {
       description "Global diffserv-traffic-engineering options";
       uses apply-advanced;
       leaf bandwidth-model {
         description "Bandwidth constraint model supported";
         type enumeration {
           enum "extended-mam" {
             description "Maximum allocation model with support for E-LSPs";
           }
           enum "mam" {
             description "Maximum allocation model";
           }
           enum "rdm" {
             description "Russian dolls model";
           }
         }
       }
       container te-class-matrix {
         description "Supported combinations of traffic-class and preemption";
         uses apply-advanced;
         container te0 {
           description "Definition for traffic-engineering class te0";
           uses te-class-object;
         }
         container te1 {
           description "Definition for traffic-engineering class te1";
           uses te-class-object;
         }
         container te2 {
           description "Definition for traffic-engineering class te2";
           uses te-class-object;
         }
         container te3 {
           description "Definition for traffic-engineering class te3";
           uses te-class-object;
         }
         container te4 {
           description "Definition for traffic-engineering class te4";
           uses te-class-object;
         }
         container te5 {
           description "Definition for traffic-engineering class te5";
           uses te-class-object;
         }
         container te6 {
           description "Definition for traffic-engineering class te6";
           uses te-class-object;
         }
         container te7 {
           description "Definition for traffic-engineering class te7";
           uses te-class-object;
         }
       }
     }
     container auto-policing {
       description "Automatic policing of LSPs";
       uses apply-advanced;
       list class {
         key name;
         ordered-by user;
         description "Forwarding class";
         leaf name {
           type enumeration {
             enum "all" {
               description "All forwarding classes";
             }
             enum "ct0" {
               description "Forwarding class 0";
             }
             enum "ct1" {
               description "Forwarding class 1";
             }
             enum "ct2" {
               description "Forwarding class 2";
             }
             enum "ct3" {
               description "Forwarding class 3";
             }
           }
         }
         uses apply-advanced;
         choice policing-action {
           case case_1 {
             leaf drop {
               description "Drop packets if bandwidth is exceeded";
               type empty;
             }
           }
           case case_2 {
             leaf loss-priority-high {
               description "Set loss priority to high if bandwidth is exceeded";
               type empty;
             }
           }
           case case_3 {
             leaf loss-priority-low {
               description "Set loss priority to low if bandwidth is exceeded";
               type empty;
             }
           }
         }
       }
     }
     container statistics {
       description "Collect statistics for signaled label-switched paths";
       uses apply-advanced;
       container file {
         presence "enable file";
         description "Statistics file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       leaf interval {
         description "Time to collect statistics (seconds)";
         type union {
           type string {
             pattern "<.*>|$.*";
           }
           type int32 {
             range "1 .. 65535";
           }
         }
       }
       leaf auto-bandwidth {
         description "Enable auto bandwidth allocation";
         type empty;
       }
       leaf no-transit-statistics {
         description "Disable transit LSP statistics collection";
         type empty;
       }
       choice transit-polling-type {
         case case_1 {
           leaf no-transit-statistics-polling {
             description "Disable polling and display of transit lsp statistics";
             status deprecated;
             type empty;
           }
         }
         case case_2 {
           leaf transit-statistics-polling {
             description "Enable polling and display of transit lsp statistics";
             junos:must "(!(\" .. no-transit-statistics\"))";
             junos:must-message "no-transit-statistics and transit-statistics-polling cannot coexist";
             type empty;
           }
         }
       }
       leaf no-bypass-statistics-polling {
         description "Disable polling and display of bypass lsp statistics";
         type empty;
       }
       leaf statistics-query-batch-size {
         description "Number of LSPs for which statistics will be queried together";
         type union {
           type string {
             pattern "<.*>|$.*";
           }
           type int32 {
             range "1 .. 25";
           }
         }
       }
     }
     container p2mp-lsp {
       description "P2MP LSP control configuration";
       uses apply-advanced;
       leaf single-abr {
         description "Try to use same exit node for all inter-domain sub LSPs";
         type empty;
       }
       leaf no-re-merge {
         description "Avoid LSP CSPF creating remerge";
         type empty;
       }
     }
     container log-updown {
       description "Logging actions for LSP up/down events";
       uses apply-advanced;
       choice syslog-choice {
         leaf syslog {
           description "Send syslog messages";
           type empty;
         }
         leaf no-syslog {
           description "Don't send syslog messages";
           type empty;
         }
       }
       choice trap-choice {
         case case_1 {
           leaf trap {
             description "Send SNMP traps";
             type empty;
           }
         }
         case case_2 {
           container no-trap {
             presence "enable no-trap";
             description "Don't send SNMP traps";
             uses apply-advanced;
             leaf mpls-lsp-traps {
               description "Dont send mpls lsp up/down traps";
               type empty;
             }
             leaf rfc3812-traps {
               description "Dont send rfc3812 traps";
               type empty;
             }
           }
         }
       }
       leaf trap-path-down {
         description "Send SNMP traps when a path goes down";
         type empty;
       }
       leaf trap-path-up {
         description "Send SNMP traps when a path goes up";
         type empty;
       }
     }
     container optimize-adaptive-teardown {
       description "Post make before break adaptive teardown";
       uses apply-advanced;
       leaf p2p {
         description "Turn on post make before break adaptive teardown for p2p";
         type empty;
       }
       leaf timeout {
         description "Timeout for adaptive teardown to clean up LSP";
         units "seconds";
         junos:must "(\".. p2p\")";
         junos:must-message "adaptive-teardown must include 'p2p' attribute";
         type union {
           type string {
             pattern "<.*>|$.*";
           }
           type int32 {
             range "1 .. 65535";
           }
         }
       }
       container delay {
         junos:must "(\".. p2p\")";
         junos:must-message "adaptive-teardown must include 'p2p' attribute";
         description "Delay tearing down old optimized path after adaptive-teardown kicks in";
         uses apply-advanced;
         leaf delay-value {
           description "Delay tearing down old optimized path after adaptive-teardown kicks in";
           units "seconds";
           type union {
             type string {
               pattern "<.*>|$.*";
             }
             type int32 {
               range "3 .. 65535";
             }
           }
         }
       }
     }
     container traffic-engineering {
       presence "enable traffic-engineering";
       description "Traffic-engineering control";
       uses apply-advanced;
       choice protocols {
         case case_1 {
           leaf bgp {
             description "BGP destinations only";
             type empty;
           }
         }
         case case_2 {
           leaf bgp-igp {
             description "BGP and IGP destinations";
             type empty;
           }
         }
         case case_3 {
           leaf bgp-igp-both-ribs {
             description "BGP and IGP destinations with routes in both routing tables";
             type empty;
           }
         }
         case case_4 {
           leaf mpls-forwarding {
             description "Use MPLS routes for forwarding, not routing";
             type empty;
           }
         }
       }
       container database {
         description "Traffic engineering database";
         uses apply-advanced;
         container import {
           description "Configure TED import parameters";
           uses apply-advanced;
           container l3-unicast-topology {
             presence "enable l3-unicast-topology";
             description "Download L3-Unicast topology into RIB";
             uses apply-advanced;
             leaf bgp-link-state {
               description "Export L3-Unicast topology, instead of TE topology, into BGP-LS";
               type empty;
             }
           }
           leaf-list policy {
             ordered-by user;
             description "Configure import policy";
             type jt:policy-algebra;
           }
           leaf identifier {
             description "BGP-TE identifier";
             type union {
               type string {
                 pattern "<.*>|$.*";
               }
               type uint64 {
                 range "2 .. 18446744073709551615";
               }
             }
           }
           leaf bgp-ls-identifier {
             description "BGP-TE domain identifier";
             type union {
               type uint32;
               type string {
                 pattern "<.*>|$.*";
               }
             }
           }
           leaf ipv6 {
             description "Import ipv6 addresses";
             type empty;
           }
         }
         container export {
           description "Configure TED export related parameters";
           uses apply-advanced;
           leaf-list policy {
             ordered-by user;
             description "Export policy";
             type jt:policy-algebra;
           }
           container credibility {
             description "TED credibility value for entries from BGP-TE";
             uses apply-advanced;
             leaf unknown {
               description "Entries sourced from unknown entities";
               type union {
                 type string {
                   pattern "<.*>|$.*";
                 }
                 type uint32 {
                   range "0 .. 512";
                 }
               }
             }
             leaf direct {
               description "Entries sourced from directly connected links";
               type union {
                 type string {
                   pattern "<.*>|$.*";
                 }
                 type uint32 {
                   range "0 .. 512";
                 }
               }
             }
             leaf static {
               description "Entries sourced from static configuration";
               type union {
                 type string {
                   pattern "<.*>|$.*";
                 }
                 type uint32 {
                   range "0 .. 512";
                 }
               }
             }
             leaf ospf {
               description "Entries sourced from ospf";
               type union {
                 type string {
                   pattern "<.*>|$.*";
                 }
                 type uint32 {
                   range "0 .. 512";
                 }
               }
             }
             leaf isis-level-1 {
               description "Entries sourced from ISIS Level 1";
               type union {
                 type string {
                   pattern "<.*>|$.*";
                 }
                 type uint32 {
                   range "0 .. 512";
                 }
               }
             }
             leaf isis-level-2 {
               description "Entries sourced from ISIS Level 2";
               type union {
                 type string {
                   pattern "<.*>|$.*";
                 }
                 type uint32 {
                   range "0 .. 512";
                 }
               }
             }
             leaf bgp {
               description "Entries sourced from BGP";
               type union {
                 type string {
                   pattern "<.*>|$.*";
                 }
                 type uint32 {
                   range "0 .. 512";
                 }
               }
             }
           }
           leaf l3-unicast-topology {
             description "Download RIB entries into L3-Unicast topology";
             type empty;
           }
         }
       }
     }
     list admin-groups {
       key name;
       ordered-by user;
       description "Administrative groups";
       leaf name {
         description "Group name";
         type string;
       }
       uses apply-advanced;
       leaf group-value {
         description "Group bit position";
         type union {
           type string {
             pattern "<.*>|$.*";
           }
           type uint32 {
             range "0 .. 31";
           }
         }
       }
     }
     leaf advertisement-hold-time {
       description "Time that an 'LSP down' advertisement will be delayed";
       default "5";
       units "seconds";
       type union {
         type string {
           pattern "<.*>|$.*";
         }
         type uint32 {
           range "0 .. 65535";
         }
       }
     }
     leaf rsvp-error-hold-time {
       description "Time that RSVP PathErr events will be remembered";
       default "25";
       units "seconds";
       type union {
         type string {
           pattern "<.*>|$.*";
         }
         type uint32 {
           range "0 .. 240";
         }
       }
     }
     leaf optimize-aggressive {
       description "Run aggressive optimization algorithm based on IGP metric only";
       type empty;
     }
     leaf smart-optimize-timer {
       description "Path optimization interval after a link traversed by the path goes down";
       units "seconds";
       type union {
         type string {
           pattern "<.*>|$.*";
         }
         type int32 {
           range "0 .. 65535";
         }
       }
     }
     leaf optimize-switchover-delay {
       description "Delay before switching LSP to newly optimized path";
       units "seconds";
       type union {
         type string {
           pattern "<.*>|$.*";
         }
         type int32 {
           range "1 .. 900";
         }
       }
     }
     leaf no-propagate-ttl {
       description "Disable TTL propagation from IP to MPLS (on push) and MPLS to IP (on pop)";
       type empty;
     }
     leaf explicit-null {
       description "Advertise the EXPLICIT_NULL label when the router is the egress";
       type empty;
     }
     leaf icmp-tunneling {
       description "Allow MPLS LSPs to be used for tunneling ICMP error packets";
       type empty;
     }
     leaf revert-timer {
       description "Hold-down window before reverting back to primary path, 0 means disable";
       units "seconds";
       type union {
         type string {
           pattern "<.*>|$.*";
         }
         type int32 {
           range "0 .. 65535";
         }
       }
     }
     leaf optimize-hold-dead-delay {
       description "Delay before tearing down the old optimized path";
       units "seconds";
       type union {
         type string {
           pattern "<.*>|$.*";
         }
         type int32 {
           range "0 .. 65535";
         }
       }
     }
     leaf cspf-backoff-time {
       description "Delay before CSPF, when there is PathErr on backup path";
       units "seconds";
       type union {
         type string {
           pattern "<.*>|$.*";
         }
         type int32 {
           range "0 .. 65535";
         }
       }
     }
     leaf expand-loose-hop {
       description "Perform CSPF path computation to expand loose hops";
       type empty;
     }
     leaf mib-mpls-show-p2mp {
       description "Show p2mp tunnels entries in mpls mib walk";
       type empty;
     }
     container bandwidth {
       description "Bandwidth to reserve (bps)";
       uses bandwidth-type;
     }
     container admin-group {
       description "Administrative group policy";
       uses admin_group_include_exclude;
     }
     container admin-group-extended {
       description "Extended administrative group policy";
       uses admin_group_include_exclude;
     }
     container priority {
       presence "enable priority";
       description "Preemption priorities";
     }
     leaf setup-priority {
       description "Set-up priority";
       type union {
         type string {
           pattern "<.*>|$.*";
         }
         type uint32 {
           range "0 .. 7";
         }
       }
     }
     leaf reservation-priority {
       description "Reservation priority";
       type union {
         type string {
           pattern "<.*>|$.*";
         }
         type uint32 {
           range "0 .. 7";
         }
       }
     }
     container oam {
       description "Periodic OAM";
       uses periodic_oam;
     }
     leaf class-of-service {
       description "Class-of-service value";
       type union {
         type string {
           pattern "<.*>|$.*";
         }
         type int32 {
           range "0 .. 7";
         }
       }
     }
     leaf no-decrement-ttl {
       description "Do not decrement the TTL within an LSP";
       type empty;
     }
     leaf hop-limit {
       description "Maximum allowed router hops";
       type union {
         type string {
           pattern "<.*>|$.*";
         }
         type int32 {
           range "2 .. 255";
         }
       }
     }
     leaf no-cspf {
       description "Disable automatic path computation";
       type empty;
     }
     leaf admin-down {
       description "Set GMPLS LSP to administrative down state";
       type empty;
     }
     leaf optimize-timer {
       description "Periodical path reoptimizations";
       units "seconds";
       type union {
         type string {
           pattern "<.*>|$.*";
         }
         type int32 {
           range "0 .. 65535";
         }
       }
     }
     leaf preference {
       description "Preference value";
       type union {
         type uint32;
         type string {
           pattern "<.*>|$.*";
         }
       }
     }
     choice record-choice {
       leaf record {
         description "Record transit routers";
         type empty;
       }
       leaf no-record {
         description "Don't record transit routers";
         type empty;
       }
     }
     leaf standby {
       description "Keep backup paths in continuous standby";
       type empty;
     }
     leaf exclude-srlg {
       description "Exclude SRLG links for secondary path";
       type empty;
     }
     leaf ultimate-hop-popping {
       description "Request ultimate hop popping from egress";
       type empty;
     }
     leaf sync-active-path-bandwidth {
       description "Signal standby path with bandwidth obtained from active path";
       type empty;
     }
     leaf cross-credibility-cspf {
       description "Compute paths across multi-protocol links and nodes";
       type empty;
     }
     leaf top-credibility-only-cspf {
       description "Compute paths only using highest credibility links and nodes";
       junos:must "(!(\".. cross-credibility-cspf\"))";
       junos:must-message "cross-credibility-cspf cannot be used with top-credibility-only-cspf";
       type empty;
     }
     list label-switched-path {
       key name;
       ordered-by user;
       description "Label-switched path";
       leaf name {
         description "Name of path";
         type string {
           length "1 .. 64";
         }
       }
       uses apply-advanced;
       choice enable-disable {
         case case_1 {
           leaf disable {
             description "Disable MPLS label-switched path";
             type empty;
           }
         }
       }
       container traceoptions {
         description "Trace options for MPLS label-switched path";
         uses apply-advanced;
         container file {
           description "Trace file options";
           leaf filename {
             description "Name of file in which to write trace information";
             type string {
               length "1 .. 1024";
               junos:posix-pattern "![/ %]";
               junos:pattern-message "Must not contain '/', % or a space";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "cspf" {
                 description "Trace CSPF computation";
               }
               enum "cspf-node" {
                 description "Trace nodes visited during CSPF";
               }
               enum "cspf-link" {
                 description "Trace links visited during CSPF";
               }
               enum "cspf-abstract" {
                 description "Trace abstract hop based CSPF details";
               }
               enum "state" {
                 description "Trace state transitions";
               }
               enum "all" {
                 description "Trace everything";
               }
             }
           }
         }
       }
       leaf no-install-to-address {
         description "Don't install host route 'to' address into routing tables";
         type empty;
       }
       leaf backup {
         description "Use LSP for IGP backup";
         type empty;
       }
       leaf from {
         description "Address of ingress router";
         type jt:ipv4addr;
       }
       container pop-and-forward {
         presence "enable pop-and-forward";
         junos:must "(!(\".. lsp-external-controller\"))";
         junos:must-message "lsp-external-controller unsupported for pop-and-forward LSP";
         junos:must "(!(\".. lsp-attributes\"))";
         junos:must-message "lsp-attributes unsupported for pop-and-forward LSP";
         junos:must "(!(\".. single-sided-associated-bidirectional\"))";
         junos:must-message "single-sided-associated-bidirectional unsupported for pop-and-forward LSP";
         junos:must "(!(\".. associate-lsp\"))";
         junos:must-message "associate-lsp unsupported for pop-and-forward LSP";
         junos:must "(!(\".. corouted-bidirectional-passive\"))";
         junos:must-message "corouted-bidirectional-passive unsupported for pop-and-forward LSP";
         junos:must "(!(\".. corouted-bidirectional\"))";
         junos:must-message "corouted-bidirectional unsupported for pop-and-forward LSP";
         junos:must "(!(\".. backup\"))";
         junos:must-message "backup unsupported for pop-and-forward LSP";
         junos:must "(!(\".. no-cspf\"))";
         junos:must-message "no-cspf unsupported for pop-and-forward LSP";
         junos:must "(!((\".. ultimate-hop-popping\" || \".. .. ultimate-hop-popping\")))";
         junos:must-message "ultimate hop popping unsupported for pop-and-forward LSP";
         junos:must "(!(\".. p2mp\"))";
         junos:must-message "p2mp unsupported for pop-and-forward LSP";
         junos:must "(!(\".. node-link-protection\"))";
         junos:must-message "link/node protection unsupported for pop-and-forward LSP";
         junos:must "(!(\".. fast-reroute\"))";
         junos:must-message "fast-reroute unsupported for pop-and-forward LSP";
         description "Enable LSP as pop-and-forward with auto-delegation";
       }
       choice label-switched-path-or-template {
         case case_1 {
           leaf to {
             description "Address of egress router";
             type jt:ipv4addr;
           }
         }
         case case_2 {
           leaf template {
             description "Template for dynamic lsp paramaters";
             junos:must "(!(\".. associate-lsp\"))";
             junos:must-message "Template cannot have associate-lsp";
             junos:must "(!(\".. corouted-bidirectional-passive\"))";
             junos:must-message "Template cannot be passive bidirectional";
             junos:must "(!(\".. corouted-bidirectional\"))";
             junos:must-message "Template cannot be active bidirectional";
             junos:must "(!(\".. lsp-external-controller\"))";
             junos:must-message "Can't configure external controller in template";
             junos:must "(!(\".. disable\"))";
             junos:must-message "Not applicable for template";
             junos:must "(!((\".. primary\" || \".. secondary\")))";
             junos:must-message "Template cannot include 'path' statement";
             type empty;
           }
         }
       }
       leaf corouted-bidirectional {
         description "Setup the LSP as a corouted bidirectional LSP";
         junos:must "(!(\".. p2mp\"))";
         junos:must-message "p2mp unsupported for bidirectional LSP";
         junos:must "(!(\".. auto-bandwidth\"))";
         junos:must-message "auto-bandwidth unsupported for bidirectional LSP";
         junos:must "(!((\".. link-protection\" || \".. node-link-protection\")))";
         junos:must-message "link/node protection unsupported for bidirectional LSP";
         junos:must "(!(\".. fast-reroute\"))";
         junos:must-message "fast-reroute unsupported for bidirectional LSP";
         junos:must "(!(\".. corouted-bidirectional-passive\"))";
         junos:must-message "Passive and active bidirectional attributes cannot coexist";
         type empty;
       }
       leaf corouted-bidirectional-passive {
         description "Associate LSP with incoming corouted bidirectional LSP";
         junos:must "(!(\".. p2mp\"))";
         junos:must-message "p2mp unsupported for bidirectional LSP";
         junos:must "(!(\".. auto-bandwidth\"))";
         junos:must-message "auto-bandwidth unsupported for bidirectional LSP";
         junos:must "(!((\".. link-protection\" || \".. node-link-protection\")))";
         junos:must-message "link/node protection unsupported for bidirectional LSP";
         junos:must "(!(\".. fast-reroute\"))";
         junos:must-message "fast-reroute unsupported for bidirectional LSP";
         junos:must "(!((\".. standby\" || \".. .. standby\")))";
         junos:must-message "standby unsupported for passive bidirectional LSP";
         junos:must "(!(\".. soft-preemption\"))";
         junos:must-message "soft-preemption unsupported for passive bidirectional LSP";
         junos:must "(!((\".. oam bfd-liveness-detection\" || \".. .. oam bfd-liveness-detection\")))";
         junos:must-message "oam bfd-liveness-detection unsupported for passive bidirectional LSP";
         junos:must "(!((\".. no-decrement-ttl\" || \".. .. no-decrement-ttl\")))";
         junos:must-message "no-decrement-ttl unsupported for passive bidirectional LSP";
         junos:must "(!((\".. exclude-srlg\" || \".. .. exclude-srlg\")))";
         junos:must-message "exclude-srlg unsupported for passive bidirectional LSP";
         junos:must "(!((\".. bandwidth\" || \".. .. bandwidth\")))";
         junos:must-message "bandwidth unsupported for passive bidirectional LSP";
         junos:must "(!((\".. admin-group-extended\" || \".. .. admin-group-extended\")))";
         junos:must-message "admin-group-extended unsupported for passive bidirectional LSP";
         junos:must "(!((\".. admin-group\" || \".. .. admin-group\")))";
         junos:must-message "admin-group unsupported for passive bidirectional LSP";
         junos:must "(!(\".. adaptive\"))";
         junos:must-message "adaptive unsupported for passive bidirectional LSP";
         junos:must "(!(\".. lsp-attributes\"))";
         junos:must-message "Passive bidirectional LSP cannot include 'lsp-attributes' statement";
         junos:must "(!((\".. primary\" || \".. secondary\")))";
         junos:must-message "Passive bidirectional LSP cannot include 'path' statement";
         type empty;
       }
       leaf metric {
         description "Metric value";
         type union {
           type string {
             pattern "<.*>|$.*";
           }
           type uint32 {
             range "1 .. 16777215";
           }
         }
       }
       container conditional-metric {
         junos:must "(!(\".. metric\"))";
         junos:must-message "Static metric cannot be configured with Conditional metric";
         description "Set a conditional metric value for the LSP";
         uses apply-advanced;
         list igp-metric-threshold {
           key name;
           description "Set conditional LSP metric based on IGP metric, up to 4 conditions";
           max-elements 4;
           leaf name {
             description "Conditional IGP metric threshold";
             type union {
               type string {
                 pattern "<.*>|$.*";
               }
               type uint32 {
                 range "1 .. 16777215";
               }
             }
           }
           leaf conditional-metric-value {
             description "Conditional LSP metric value";
             type union {
               type string {
                 pattern "<.*>|$.*";
               }
               type uint32 {
                 range "1 .. 16777215";
               }
             }
           }
         }
       }
       container metric-type {
         junos:must "(!((\".. no-cspf\" || \".. .. no-cspf\")))";
         junos:must-message "Metric type of cspf cannot be configured for no-cspf LSP";
         description "Metric type used for computaion";
         uses apply-advanced;
         choice metric-type-choice {
           case case_1 {
             leaf te {
               description "TE metric";
               type empty;
             }
           }
           case case_2 {
             leaf igp {
               description "IGP metric";
               type empty;
             }
           }
           case case_3 {
             container delay {
               presence "enable delay";
               description "Delay metric";
               uses apply-advanced;
               choice metric-choice {
                 case case_1 {
                   leaf minimum {
                     description "Minimum delay metric type";
                     type empty;
                   }
                 }
                 case case_2 {
                   leaf maximum {
                     description "Maximum delay metric type";
                     type empty;
                   }
                 }
                 case case_3 {
                   leaf average {
                     description "Average delay metric type";
                     type empty;
                   }
                 }
               }
               leaf delay-variation-threshold {
                 description "Link delay variation threshold";
                 type union {
                   type string {
                     pattern "<.*>|$.*";
                   }
                   type uint32 {
                     range "1 .. 16777215";
                   }
                 }
               }
             }
           }
         }
       }
       leaf ldp-tunneling {
         description "Allow LDP to use this LSP for tunneling";
         type empty;
       }
       leaf soft-preemption {
         description "Attempt make-before-break service while preempting this LSP";
         junos:must "(!(\".. fast-reroute\"))";
         junos:must-message "soft-preemption is unsupported when fast-reroute is desired";
         type empty;
       }
       list install {
         key name;
         ordered-by user;
         description "Install prefix";
         leaf name {
           description "Destination prefix";
           type jt:ipprefix;
         }
         leaf active {
           description "Install prefix into forwarding table";
           type empty;
         }
       }
       leaf retry-timer {
         description "Time before retrying the primary path";
         units "seconds";
         type union {
           type string {
             pattern "<.*>|$.*";
           }
           type uint32 {
             range "1 .. 600";
           }
         }
       }
       leaf retry-limit {
         description "Maximum number of times to retry primary path";
         type union {
           type string {
             pattern "<.*>|$.*";
           }
           type uint32 {
             range "0 .. 10000";
           }
         }
       }
       container lsp-attributes {
         description "Attributes for generalized LSP";
         uses apply-advanced;
         leaf signal-bandwidth {
           description "Signal bandwidth for the LSP";
           junos:must "(!((\".. switching-type l2sc\" || (\".. switching-type psc-1\" || \".. switching-type ethernet-vlan\"))))";
           junos:must-message "signal-bandwidth invalid for VLAN LSP and Packet LSP";
           type enumeration {
             enum "ds1" {
               description "1.544 Mbps";
             }
             enum "vt1-5" {
               description "1.728 Mbps";
             }
             enum "e1" {
               description "2.048 Mbps";
             }
             enum "vt2" {
               description "2.304 Mbps";
             }
             enum "ethernet" {
               description "10 Mbps";
             }
             enum "e3" {
               description "34.368 Mbps";
             }
             enum "ds3" {
               description "44.736 Mbps";
             }
             enum "sts-1" {
               description "51.84 Mbps";
             }
             enum "fastether" {
               description "100.00 Mbps";
             }
             enum "stm-1" {
               description "155.52 Mbps";
             }
             enum "stm-4" {
               description "622.08 Mbps";
             }
             enum "gigether" {
               description "1000.00 Mbps";
             }
             enum "stm-16" {
               description "2488.32 Mbps";
             }
             enum "stm-64" {
               description "9953.28 Mbps";
             }
             enum "10gigether" {
               description "10000.00 Mbps";
             }
             enum "stm-256" {
               description "39813.12 Mbps";
             }
             enum "100gige" {
               description "100000.00 Mbps";
             }
           }
         }
         leaf switching-type {
           description "LSP switching type desired";
           type enumeration {
             enum "psc-1" {
               description "Packet switching";
             }
             enum "lambda" {
               description "Lambda switching";
             }
             enum "fiber" {
               description "Fiber switching";
             }
             enum "tdm" {
               description "TDM switching";
             }
             enum "ethernet-vlan" {
               description "Ethernet VLAN switching";
               junos:must "((!(\".. encoding-type\") || \".. encoding-type ethernet\"))";
               junos:must-message "Only ethernet encoding supported for VLAN LSP";
             }
           }
         }
         leaf encoding-type {
           description "LSP encoding type desired";
           type enumeration {
             enum "packet" {
               description "Packet encoding";
             }
             enum "ethernet" {
               description "Ethernet encoding";
             }
             enum "pdh" {
               description "PDH encoding";
             }
             enum "sonet-sdh" {
               description "SONET-SDH encoding";
             }
           }
         }
         leaf gpid {
           description "Generalized PID";
           type enumeration {
             enum "ipv4" {
             }
             enum "ethernet" {
             }
             enum "ppp" {
             }
             enum "hdlc" {
             }
             enum "pos-no-scrambling-crc-16" {
             }
             enum "pos-no-scrambling-crc-32" {
             }
             enum "pos-scrambling-crc-16" {
             }
             enum "pos-scrambling-crc-32" {
             }
           }
         }
         container upstream-label {
           description "Upstream Label for the bidirectional label-switched path";
           uses apply-advanced;
           leaf vlan-id {
             description "VLAN ID label for the label-switched path";
             junos:must "(\".. .. switching-type ethernet-vlan\")";
             junos:must-message "VLAN label is valid only for VLAN LSP";
             type union {
               type string {
                 pattern "<.*>|$.*";
               }
               type uint32 {
                 range "1 .. 4094";
               }
             }
           }
         }
       }
       leaf revert-timer {
         description "Hold-down window before reverting back to primary path, 0 means disable";
         units "seconds";
         type union {
           type string {
             pattern "<.*>|$.*";
           }
           type int32 {
             range "0 .. 65535";
           }
         }
       }
       leaf optimize-hold-dead-delay {
         description "Delay before tearing down the old optimized path";
         units "seconds";
         type union {
           type string {
             pattern "<.*>|$.*";
           }
           type int32 {
             range "0 .. 65535";
           }
         }
       }
       leaf cspf-backoff-time {
         description "Delay before CSPF, when there is PathErr on backup path";
         units "seconds";
         type union {
           type string {
             pattern "<.*>|$.*";
           }
           type int32 {
             range "0 .. 65535";
           }
         }
       }
       container bandwidth {
         description "Bandwidth to reserve (bps)";
         uses bandwidth-type;
       }
       container admin-group {
         description "Administrative group policy";
         uses admin_group_include_exclude;
       }
       container admin-group-extended {
         description "Extended administrative group policy";
         uses admin_group_include_exclude;
       }
       container priority {
         presence "enable priority";
         description "Preemption priorities";
       }
       leaf setup-priority {
         description "Set-up priority";
         type union {
           type string {
             pattern "<.*>|$.*";
           }
           type uint32 {
             range "0 .. 7";
           }
         }
       }
       leaf reservation-priority {
         description "Reservation priority";
         type union {
           type string {
             pattern "<.*>|$.*";
           }
           type uint32 {
             range "0 .. 7";
           }
         }
       }
       container oam {
         description "Periodic OAM";
         uses periodic_oam;
       }
       leaf class-of-service {
         description "Class-of-service value";
         type union {
           type string {
             pattern "<.*>|$.*";
           }
           type int32 {
             range "0 .. 7";
           }
         }
       }
       leaf no-decrement-ttl {
         description "Do not decrement the TTL within an LSP";
         type empty;
       }
       leaf hop-limit {
         description "Maximum allowed router hops";
         type union {
           type string {
             pattern "<.*>|$.*";
           }
           type int32 {
             range "2 .. 255";
           }
         }
       }
       leaf no-cspf {
         description "Disable automatic path computation";
         type empty;
       }
       leaf admin-down {
         description "Set GMPLS LSP to administrative down state";
         type empty;
       }
       leaf optimize-timer {
         description "Periodical path reoptimizations";
         units "seconds";
         type union {
           type string {
             pattern "<.*>|$.*";
           }
           type int32 {
             range "0 .. 65535";
           }
         }
       }
       leaf preference {
         description "Preference value";
         type union {
           type uint32;
           type string {
             pattern "<.*>|$.*";
           }
         }
       }
       choice record-choice {
         leaf record {
           description "Record transit routers";
           type empty;
         }
         leaf no-record {
           description "Don't record transit routers";
           type empty;
         }
       }
       leaf standby {
         description "Keep backup paths in continuous standby";
         type empty;
       }
       leaf exclude-srlg {
         description "Exclude SRLG links for secondary path";
         type empty;
       }
       leaf ultimate-hop-popping {
         description "Request ultimate hop popping from egress";
         type empty;
       }
       leaf sync-active-path-bandwidth {
         description "Signal standby path with bandwidth obtained from active path";
         type empty;
       }
       leaf cross-credibility-cspf {
         description "Compute paths across multi-protocol links and nodes";
         type empty;
       }
       leaf top-credibility-only-cspf {
         description "Compute paths only using highest credibility links and nodes";
         junos:must "(!(\".. cross-credibility-cspf\"))";
         junos:must-message "cross-credibility-cspf cannot be used with top-credibility-only-cspf";
         type empty;
       }
       leaf entropy-label {
         description "Enable entropy label";
         type empty;
       }
       leaf self-ping-duration {
         description "Duration over which to run self-ping (65535 = until success). Default = 1800s";
         units "seconds";
         type union {
           type string {
             pattern "<.*>|$.*";
           }
           type int32 {
             range "1 .. 65535";
           }
         }
       }
       leaf no-self-ping {
         description "Do not run self-ping for this LSP";
         type empty;
       }
       choice cspf-attribute {
         case case_1 {
           leaf random {
             description "Randomly select among equal-cost paths";
             type empty;
           }
         }
         case case_2 {
           leaf least-fill {
             description "Select the least filled among equal-cost paths";
             type empty;
           }
         }
         case case_3 {
           leaf most-fill {
             description "Select the most filled among equal-cost paths";
             type empty;
           }
         }
       }
       leaf description {
         description "Text description of label-switched path";
         type string {
           length "1 .. 80";
         }
       }
       choice lp-type {
         case case_1 {
           leaf link-protection {
             description "Protect LSP from link faults only";
             type empty;
           }
         }
         case case_2 {
           leaf node-link-protection {
             description "Protect LSP from both link and node faults";
             type empty;
           }
         }
       }
       leaf intra-domain {
         description "Intra-domain LSP";
         status deprecated;
         type empty;
       }
       leaf inter-domain {
         description "Inter-domain LSP";
         type empty;
       }
       leaf adaptive {
         description "Have the LSP smoothly cut over to new routes";
         type empty;
       }
       container in-place-lsp-bandwidth-update {
         presence "enable in-place-lsp-bandwidth-update";
         junos:must "(!(\".. fast-reroute\"))";
         junos:must-message "In-place update unsupported for LSPs requesting detour protection";
         junos:must "(!(\".. lsp-external-controller\"))";
         junos:must-message "In-place update unsupported for externally controlled LSPs";
         junos:must "(!(\".. single-sided-associated-bidirectional\"))";
         junos:must-message "In-place update unsupported for single-sided-associated-bidirectional LSPs";
         junos:must "(!(\".. corouted-bidirectional-passive\"))";
         junos:must-message "In-place update unsupported for corouted-bidirectional-passive LSPs";
         junos:must "(!(\".. corouted-bidirectional\"))";
         junos:must-message "In-place update unsupported for corouted-bidirectional LSPs";
         junos:must "(!((\".. no-cspf\" || \".. .. no-cspf\")))";
         junos:must-message "In-place update unsupported for no-cspf LSPs";
         junos:must "(!(\".. p2mp\"))";
         junos:must-message "In-place update unsupported for p2mp sub-LSPs";
         description "Update LSP in-place re-using the same LSP identifier";
       }
       container fast-reroute {
         presence "enable fast-reroute";
         description "Fast reroute";
         uses apply-advanced;
         leaf hop-limit {
           description "Maximum allowed router hops";
           type union {
             type string {
               pattern "<.*>|$.*";
             }
             type int32 {
               range "0 .. 255";
             }
           }
         }
         choice bw-attribute {
           case case_1 {
             leaf bandwidth {
               description "Bandwidth to reserve (bps)";
               type string;
             }
           }
           case case_2 {
             leaf bandwidth-percent {
               description "Percentage of main path bandwidth to reserve";
               type union {
                 type string {
                   pattern "<.*>|$.*";
                 }
                 type int32 {
                   range "1 .. 100";
                 }
               }
             }
           }
         }
         choice include_any_or_no_include_any {
           case case_1 {
             leaf no-include-any {
               description "Disable include-any checking";
               type empty;
             }
           }
           case case_2 {
             leaf-list include-any {
               ordered-by user;
               description "Groups, one or more of which must be present";
               type string;
             }
           }
         }
         choice include_all_or_no_include_all {
           case case_1 {
             leaf no-include-all {
               description "Disable include-all checking";
               type empty;
             }
           }
           case case_2 {
             leaf-list include-all {
               ordered-by user;
               description "Groups, all of which must be present";
               type string;
             }
           }
         }
         choice exclude_or_no_exclude {
           case case_1 {
             leaf no-exclude {
               description "Disable exclude checking";
               type empty;
             }
           }
           case case_2 {
             leaf-list exclude {
               ordered-by user;
               description "Groups, all of which must be absent";
               type string;
             }
           }
         }
       }
       container p2mp {
         presence "enable p2mp";
         junos:must "(!(\".. associate-backup-pe-groups\"))";
         junos:must-message "backup-pe-group cannot be associated with P2MP LSP";
         junos:must "(!(\".. egress-protection\"))";
         junos:must-message "egress-protection unsupported for P2MP LSP branch";
         junos:must "(!(any \".. primary <*> adaptive\"))";
         junos:must-message "adaptive unsupported for P2MP LSP branch path";
         junos:must "(!(\".. adaptive\"))";
         junos:must-message "adaptive unsupported for P2MP LSP branch";
         junos:must "(!(\".. install\"))";
         junos:must-message "install prefixes invalid for P2MP LSP branch";
         junos:must "(!(\".. ldp-tunneling\"))";
         junos:must-message "ldp-tunneling unsupported for P2MP LSP branch";
         junos:must "(!(\".. backup\"))";
         junos:must-message "backup invalid for P2MP LSP branch";
         junos:must "(!(\".. no-install-to-address\"))";
         junos:must-message "no-install-to-address invalid for P2MP LSP branch";
         junos:must "(!(\".. node-link-protection\"))";
         junos:must-message "node protection unsupported for P2MP LSP branch";
         junos:must "(!(\".. fast-reroute\"))";
         junos:must-message "fast-reroute unsupported for P2MP LSP branch";
         junos:must "(!(\".. secondary\"))";
         junos:must-message "secondary paths unsupported for P2MP LSP branch";
         junos:must "(!(\".. ultimate-hop-popping\"))";
         junos:must-message "For point-to-multipoint LSP, ultimate hop popping cannot be configured";
         junos:must "(!(\".. lsp-external-controller\"))";
         junos:must-message "Can't configure lsp-external-controller knob in p2mp LSPs";
         junos:must "((!(\".. .. .. .. .. logical-systems\") || !(\".. .. ipv6-tunneling\")))";
         junos:must-message "In logical systems, IPv6 tunneling cannot be configured with P2MP LSPs";
         junos:must "((any \".. p2mp <*>\" || \".. template\"))";
         junos:must-message "For S2L point-to-multipoint LSP, parent point-to-multipoint LSP name must be configured";
         description "Point-to-multipoint label-switched path";
         leaf path_name {
           description "Name of point-to-multipoint LSP";
           junos:must "(!(\".. .. .. label-switched-path $$\"))";
           junos:must-message "The P2MP name is the same as an existing LSP name";
           junos:must "(!(\".. .. template\"))";
           junos:must-message "Name not applicable for point-to-multipoint template";
           type string {
             junos:posix-pattern "^.{1,64}$";
             junos:pattern-message "Must be a string of less than 64 characters";
           }
         }
       }
       container auto-bandwidth {
         presence "enable auto-bandwidth";
         junos:must "(!(\".. p2mp\"))";
         junos:must-message "Cannot do auto-bandwidth for P2MP LSP branch";
         junos:must "((!(\".. lsp-attributes\") || (\".. lsp-attributes switching-type psc-1\" && (!(\".. lsp-attributes encoding-type\") || \".. lsp-attributes encoding-type packet\"))))";
         junos:must-message "Cannot do auto-bandwidth for non-packet LSP";
         description "Do auto bandwidth allocation for this LSP";
         uses apply-advanced;
         leaf adjust-interval {
           description "Time to adjust LSP bandwidth";
           default "86400";
           units "seconds";
           type union {
             type string {
               pattern "<.*>|$.*";
             }
             type uint32 {
               range "300 .. 315360000";
             }
           }
         }
         leaf adjust-threshold {
           description "Percentage change in average LSP utilization to trigger auto-adjustment";
           default "0";
           units "percent";
           type union {
             type string {
               pattern "<.*>|$.*";
             }
             type uint32 {
               range "0 .. 50";
             }
           }
         }
         leaf adjust-threshold-absolute {
           description "Change in average LSP utilization to trigger auto-adjustment";
           default "0";
           units "bps";
           type string;
         }
         leaf adjust-threshold-activate-bandwidth {
           description "Adjusts signaled bw if greater than this value";
           units "bps";
           type string;
         }
         leaf minimum-bandwidth {
           description "Minimum LSP bandwidth";
           units "bps";
           type string;
         }
         leaf maximum-bandwidth {
           description "Maximum LSP bandwidth";
           units "bps";
           type string;
         }
         leaf minimum-bandwidth-adjust-interval {
           description "Duration for which minimum bandwidth will be frozen";
           units "seconds";
           type union {
             type string {
               pattern "<.*>|$.*";
             }
             type uint32 {
               range "300 .. 31536000";
             }
           }
         }
         leaf minimum-bandwidth-adjust-threshold-change {
           description "Change in max average bandwidth to freeze min bandwidth";
           units "percent";
           junos:must "(\".. minimum-bandwidth-adjust-interval\")";
           junos:must-message "minimum-bandwidth-adjust-interval must be configured";
           type union {
             type string {
               pattern "<.*>|$.*";
             }
             type uint32 {
               range "0 .. 100";
             }
           }
         }
         leaf minimum-bandwidth-adjust-threshold-value {
           description "Freeze min bandwidth if max average bandwidth falls below this bw";
           status deprecated;
           units "bps";
           junos:must "(!(\".. minimum-bandwidth-adjust-threshold-change\"))";
           junos:must-message "minimum-bandwidth-adjust-threshold-change cannot be configured with minimum-bandwidth-adjust-threshold-value";
           junos:must "(\".. minimum-bandwidth-adjust-interval\")";
           junos:must-message "minimum-bandwidth-adjust-interval must be configured";
           type string;
         }
         leaf monitor-bandwidth {
           description "Monitor LSP bandwidth without adjustments";
           type empty;
         }
         leaf adjust-threshold-overflow-limit {
           description "Number of consecutive overflow samples to trigger auto-adjustment";
           junos:must "(((\".. adjust-threshold\" && \".. maximum-bandwidth\") && (!(\".. adjust-threshold $$={0}\") && !(\".. maximum-bandwidth $$={0}\"))))";
           junos:must-message "Non-zero adjust-threshold and maximum-bandwidth MUST be configured";
           junos:must "(!(\".. monitor-bandwidth\"))";
           junos:must-message "adjust-threshold-overflow-limit cannot be used with monitor-bandwidth";
           type union {
             type string {
               pattern "<.*>|$.*";
             }
             type uint32 {
               range "1 .. 65535";
             }
           }
         }
         leaf adjust-threshold-underflow-limit {
           description "Number of consecutive underflow samples to trigger auto-adjustment";
           junos:must "((\".. adjust-threshold\" && !(\".. adjust-threshold 0\")))";
           junos:must-message "Non-zero adjust-threshold must be configured";
           junos:must "(!(\".. monitor-bandwidth\"))";
           junos:must-message "adjust-threshold-underflow-limit cannot be used with monitor-bandwidth";
           type union {
             type string {
               pattern "<.*>|$.*";
             }
             type uint32 {
               range "1 .. 65535";
             }
           }
         }
         leaf resignal-minimum-bandwidth {
           description "Resignal the LSP using minimum-bandwidth";
           type empty;
         }
         leaf sync-active-path-bandwidth {
           description "Signal standby path with bandwidth obtained from active path";
           type empty;
         }
       }
       container optimize-on-change {
         description "Specify additional re-optimization triggers for this LSP";
         uses apply-advanced;
         leaf link-congestion {
           description "Optimize when a link becomes congested";
           type empty;
         }
       }
       container deselect-on-bandwidth-failure {
         presence "enable deselect-on-bandwidth-failure";
         description "Deselect active path if it cannot meet the bandwidth constraint";
         uses apply-advanced;
         leaf tear-lsp {
           description "Bring down active path when all paths fail to reserve required bandwidth";
           type empty;
         }
       }
       container track-igp-metric {
         description "Track IGP metric for LSP install prefixes";
         uses apply-advanced;
         leaf install-v4-prefixes {
           description "Track IGP metric for IPV4 prefixes";
           type empty;
         }
         leaf install-v6-prefixes {
           description "Track IGP metric for IPV6 prefixes";
           type empty;
         }
       }
       container associate-lsp {
         junos:must "((\".. oam mpls-tp-mode\" || \".. .. oam mpls-tp-mode\"))";
         junos:must-message "mpls-tp-mode must be configured for associate-lsp";
         description "Associate the LSP for OAM";
         uses apply-advanced;
         leaf lsp-name {
           description "Name of assocation LSP";
           type string {
             junos:posix-pattern "^.{1,64}$";
             junos:pattern-message "Must be a string of 64 characters or less";
           }
         }
         leaf from {
           description "Address of ingress router of associated LSP";
           type jt:ipv4addr;
         }
       }
       list primary {
         key name;
         ordered-by user;
         description "Preferred path";
         leaf name {
           description "Name of path";
           type string {
             length "1 .. 64";
           }
         }
         uses apply-advanced;
         container bandwidth {
           description "Bandwidth to reserve (bps)";
           uses bandwidth-type;
         }
         container admin-group {
           description "Administrative group policy";
           uses admin_group_include_exclude;
         }
         container admin-group-extended {
           description "Extended administrative group policy";
           uses admin_group_include_exclude;
         }
         container priority {
           presence "enable priority";
           description "Preemption priorities";
         }
         leaf setup-priority {
           description "Set-up priority";
           type union {
             type string {
               pattern "<.*>|$.*";
             }
             type uint32 {
               range "0 .. 7";
             }
           }
         }
         leaf reservation-priority {
           description "Reservation priority";
           type union {
             type string {
               pattern "<.*>|$.*";
             }
             type uint32 {
               range "0 .. 7";
             }
           }
         }
         container oam {
           description "Periodic OAM";
           uses periodic_oam;
         }
         leaf class-of-service {
           description "Class-of-service value";
           type union {
             type string {
               pattern "<.*>|$.*";
             }
             type int32 {
               range "0 .. 7";
             }
           }
         }
         leaf no-decrement-ttl {
           description "Do not decrement the TTL within an LSP";
           type empty;
         }
         leaf hop-limit {
           description "Maximum allowed router hops";
           type union {
             type string {
               pattern "<.*>|$.*";
             }
             type int32 {
               range "2 .. 255";
             }
           }
         }
         leaf no-cspf {
           description "Disable automatic path computation";
           type empty;
         }
         leaf admin-down {
           description "Set GMPLS LSP to administrative down state";
           type empty;
         }
         leaf optimize-timer {
           description "Periodical path reoptimizations";
           units "seconds";
           type union {
             type string {
               pattern "<.*>|$.*";
             }
             type int32 {
               range "0 .. 65535";
             }
           }
         }
         leaf preference {
           description "Preference value";
           type union {
             type uint32;
             type string {
               pattern "<.*>|$.*";
             }
           }
         }
         choice record-choice {
           leaf record {
             description "Record transit routers";
             type empty;
           }
           leaf no-record {
             description "Don't record transit routers";
             type empty;
           }
         }
         leaf standby {
           description "Keep backup paths in continuous standby";
           type empty;
         }
         leaf exclude-srlg {
           description "Exclude SRLG links for secondary path";
           type empty;
         }
         leaf ultimate-hop-popping {
           description "Request ultimate hop popping from egress";
           type empty;
         }
         leaf sync-active-path-bandwidth {
           description "Signal standby path with bandwidth obtained from active path";
           type empty;
         }
         leaf cross-credibility-cspf {
           description "Compute paths across multi-protocol links and nodes";
           type empty;
         }
         leaf top-credibility-only-cspf {
           description "Compute paths only using highest credibility links and nodes";
           junos:must "(!(\".. cross-credibility-cspf\"))";
           junos:must-message "cross-credibility-cspf cannot be used with top-credibility-only-cspf";
           type empty;
         }
         leaf adaptive {
           description "Have the LSP smoothly cut over to new routes";
           type empty;
         }
         leaf select {
           type enumeration {
             enum "manual" {
               description "Manual override as preferred active path, if up and stable";
             }
             enum "unconditional" {
               description "Unconditional override as preferred active path, regardless of up/down status";
             }
           }
         }
         container upstream-label {
           description "Upstream Label for the bidirectional label-switched path";
           uses apply-advanced;
           leaf vlan-id {
             description "VLAN ID label for the label-switched path";
             junos:must "(\".. .. .. lsp-attributes switching-type ethernet-vlan\")";
             junos:must-message "VLAN label is valid only for VLAN LSP";
             type union {
               type string {
                 pattern "<.*>|$.*";
               }
               type uint32 {
                 range "1 .. 4094";
               }
             }
           }
         }
         container optimize-on-change {
           junos:must "(!(\"protocols mpls label-switched-path $$ optimize-on-change\"))";
           junos:must-message "LSP already has optimize-on-change";
           description "Specify additional re-optimization triggers for this path";
           uses apply-advanced;
           leaf link-congestion {
             description "Optimize when a link becomes congested";
             type empty;
           }
         }
       }
       list secondary {
         key name;
         ordered-by user;
         description "Backup path";
         leaf name {
           description "Name of path";
           type string {
             length "1 .. 64";
           }
         }
         uses apply-advanced;
         container bandwidth {
           description "Bandwidth to reserve (bps)";
           uses bandwidth-type;
         }
         container admin-group {
           description "Administrative group policy";
           uses admin_group_include_exclude;
         }
         container admin-group-extended {
           description "Extended administrative group policy";
           uses admin_group_include_exclude;
         }
         container priority {
           presence "enable priority";
           description "Preemption priorities";
         }
         leaf setup-priority {
           description "Set-up priority";
           type union {
             type string {
               pattern "<.*>|$.*";
             }
             type uint32 {
               range "0 .. 7";
             }
           }
         }
         leaf reservation-priority {
           description "Reservation priority";
           type union {
             type string {
               pattern "<.*>|$.*";
             }
             type uint32 {
               range "0 .. 7";
             }
           }
         }
         container oam {
           description "Periodic OAM";
           uses periodic_oam;
         }
         leaf class-of-service {
           description "Class-of-service value";
           type union {
             type string {
               pattern "<.*>|$.*";
             }
             type int32 {
               range "0 .. 7";
             }
           }
         }
         leaf no-decrement-ttl {
           description "Do not decrement the TTL within an LSP";
           type empty;
         }
         leaf hop-limit {
           description "Maximum allowed router hops";
           type union {
             type string {
               pattern "<.*>|$.*";
             }
             type int32 {
               range "2 .. 255";
             }
           }
         }
         leaf no-cspf {
           description "Disable automatic path computation";
           type empty;
         }
         leaf admin-down {
           description "Set GMPLS LSP to administrative down state";
           type empty;
         }
         leaf optimize-timer {
           description "Periodical path reoptimizations";
           units "seconds";
           type union {
             type string {
               pattern "<.*>|$.*";
             }
             type int32 {
               range "0 .. 65535";
             }
           }
         }
         leaf preference {
           description "Preference value";
           type union {
             type uint32;
             type string {
               pattern "<.*>|$.*";
             }
           }
         }
         choice record-choice {
           leaf record {
             description "Record transit routers";
             type empty;
           }
           leaf no-record {
             description "Don't record transit routers";
             type empty;
           }
         }
         leaf standby {
           description "Keep backup paths in continuous standby";
           type empty;
         }
         leaf exclude-srlg {
           description "Exclude SRLG links for secondary path";
           type empty;
         }
         leaf ultimate-hop-popping {
           description "Request ultimate hop popping from egress";
           type empty;
         }
         leaf sync-active-path-bandwidth {
           description "Signal standby path with bandwidth obtained from active path";
           type empty;
         }
         leaf cross-credibility-cspf {
           description "Compute paths across multi-protocol links and nodes";
           type empty;
         }
         leaf top-credibility-only-cspf {
           description "Compute paths only using highest credibility links and nodes";
           junos:must "(!(\".. cross-credibility-cspf\"))";
           junos:must-message "cross-credibility-cspf cannot be used with top-credibility-only-cspf";
           type empty;
         }
         leaf adaptive {
           description "Have the LSP smoothly cut over to new routes";
           type empty;
         }
         leaf select {
           type enumeration {
             enum "manual" {
               description "Manual override as preferred active path, if up and stable";
             }
             enum "unconditional" {
               description "Unconditional override as preferred active path, regardless of up/down status";
             }
           }
         }
         container upstream-label {
           description "Upstream Label for the bidirectional label-switched path";
           uses apply-advanced;
           leaf vlan-id {
             description "VLAN ID label for the label-switched path";
             junos:must "(\".. .. .. lsp-attributes switching-type ethernet-vlan\")";
             junos:must-message "VLAN label is valid only for VLAN LSP";
             type union {
               type string {
                 pattern "<.*>|$.*";
               }
               type uint32 {
                 range "1 .. 4094";
               }
             }
           }
         }
         container optimize-on-change {
           junos:must "(!(\"protocols mpls label-switched-path $$ optimize-on-change\"))";
           junos:must-message "LSP already has optimize-on-change";
           description "Specify additional re-optimization triggers for this path";
           uses apply-advanced;
           leaf link-congestion {
             description "Optimize when a link becomes congested";
             type empty;
           }
         }
         container non-active-hold-priority {
           description "Non-active hold priority";
           leaf non-active-hold-prio-value {
             description "Non-active hold priority value";
             junos:must "(!((\".. .. no-cspf\" || (\".. .. .. no-cspf\" || \".. .. .. .. no-cspf\"))))";
             junos:must-message "Non-active hold priority unsupported for no-cspf LSPs";
             junos:must "((\".. .. standby\" || (\".. .. .. standby\" || \".. .. .. .. standby\")))";
             junos:must-message "Non-active hold priority supported only for standby path";
             type union {
               type string {
                 pattern "<.*>|$.*";
               }
               type uint32 {
                 range "0 .. 7";
               }
             }
           }
         }
       }
       container policing {
         description "Traffic policing for this LSP";
         leaf filter {
           description "Name of filter to use for policing LSP traffic";
           junos:must "(!(\".. .. p2mp\"))";
           junos:must-message "Manual policing not supported for P2MP LSPs";
           junos:must "(!(\"firewall family any filter $$ interface-specific\"))";
           junos:must-message "LSP policing filter must not be interface-specific";
           junos:must "((\"firewall family any filter $$\" || (!(\"firewall\") && \".. .. .. .. .. .. .. .. firewall family any filter $$\")))";
           junos:must-message "referenced filter must be defined under firewall family any";
           type string {
             junos:posix-pattern "!^((__.*)|(.{65,}))$";
             junos:pattern-message "Must be a non-reserved string of 64 characters or less";
           }
         }
         leaf no-auto-policing {
           description "Turn off automatic policing for this LSP";
           type empty;
         }
       }
       leaf lsp-external-controller {
         description "Name of the external path computing entity";
         junos:must "(!(\".. single-sided-associated-bidirectional\"))";
         junos:must-message "Single-sided associated bidir LSP cannot be externally controlled";
         junos:must "(!(\".. corouted-bidirectional\"))";
         junos:must-message "Externally controlled LSP cannot be corouted bidirectional";
         junos:must "(!(\".. corouted-bidirectional-passive\"))";
         junos:must-message "Externally controlled LSP cannot be corouted bidirectional";
         junos:must "(\"protocols mpls lsp-external-controller $$\")";
         junos:must-message "Referenced lsp-external-controller is not defined";
         type string {
           junos:posix-pattern "^.{1,64}$";
           junos:pattern-message "Must be a string of less than 64 characters";
         }
       }
       leaf associate-backup-pe-groups {
         description "Associate this LSP with backup-pe groups";
         junos:must "(\".. oam bfd-liveness-detection\")";
         junos:must-message "bfd-liveness-detection must be configured for this feature.";
         type empty;
       }
       leaf egress-protection {
         description "Use this LSP for egress protection data transport";
         junos:must "(!(\".. install\"))";
         junos:must-message "Cannot install routes for an egress protection LSP";
         type empty;
       }
       leaf transport-class {
         description "Transport class this LSP belongs to";
         junos:must "(\"routing-options transport-class name $$\")";
         junos:must-message "Referenced transport class is not defined";
         type string {
           junos:posix-pattern "^.{1,64}$";
           junos:pattern-message "Must be a string of less than 64 characters";
         }
       }
     }
     container deselect-on-bandwidth-failure {
       presence "enable deselect-on-bandwidth-failure";
       description "Deselect active path if it cannot meet the bandwidth constraint";
       uses apply-advanced;
       leaf tear-lsp {
         description "Bring down active path when all paths fail to reserve required bandwidth";
         type empty;
       }
     }
     container track-igp-metric {
       description "Track IGP metric for LSP install prefixes";
       uses apply-advanced;
       leaf install-v4-prefixes {
         description "Track IGP metric for IPV4 prefixes";
         type empty;
       }
       leaf install-v6-prefixes {
         description "Track IGP metric for IPV6 prefixes";
         type empty;
       }
     }
     list container-label-switched-path {
       key name;
       ordered-by user;
       leaf name {
         description "Name of container-lsp";
         junos:must "(!(\".. .. label-switched-path $$\"))";
         junos:must-message "The Container LSP name is the same as an existing LSP name";
         type string {
           junos:posix-pattern "^.{1,64}$";
           junos:pattern-message "Must be a string of 64 characters or less";
         }
       }
       uses apply-advanced;
       choice enable-disable {
         case case_1 {
           leaf disable {
             description "Disable MPLS container-label-switched path";
             type empty;
           }
         }
       }
       leaf description {
         description "Text description of label-switched path";
         type string {
           length "1 .. 80";
         }
       }
       container label-switched-path-template {
         description "Template for dynamic point-to-point LSP parameters";
         uses apply-advanced;
         choice dynamic-template {
           case case_1 {
             leaf template-name {
               description "Name of point-to-point LSP template";
               junos:must "(!(\"protocols mpls label-switched-path $$ egress-protection\"))";
               junos:must-message "Referenced point-to-point LSP template cannot have egress-protection";
               junos:must "(!(\"protocols mpls label-switched-path $$ p2mp\"))";
               junos:must-message "Referenced point-to-point LSP template cannot be p2mp sub LSP";
               junos:must "(!(\"protocols mpls label-switched-path $$ bandwidth\"))";
               junos:must-message "Referenced point-to-point LSP template cannot have static bandwidth";
               junos:must "(!(\"protocols mpls label-swithced-path $$ policing\"))";
               junos:must-message "Referenced point-to-point LSP template cannot have policing";
               junos:must "((\"protocols mpls label-switched-path $$\" && (\"protocols mpls label-switched-path $$ template\" && !(\"protocols mpls label-switched-path $$ no-cspf\"))))";
               junos:must-message "Referenced point-to-point LSP template cannot have no-cspf";
               junos:must "((\"protocols mpls label-switched-path $$\" && \"protocols mpls label-switched-path $$ template\"))";
               junos:must-message "Referenced point-to-point LSP template does not exist";
               type string {
                 length "1 .. 64";
                 junos:posix-pattern "![*<>]";
                 junos:pattern-message "Template name should not contain '*' and angle brackets";
               }
             }
           }
           case case_2 {
             leaf default-template {
               description "Use default parameters";
               type empty;
             }
           }
         }
       }
       leaf to {
         description "Address of egress router";
         type jt:ipv4addr;
       }
       leaf suffix {
         description "Suffix to generate names of members of container LSP";
         type string {
           length "1 .. 64";
         }
       }
       container splitting-merging {
         description "Do splitting and merging";
         uses apply-advanced;
         leaf maximum-member-lsps {
           description "Maximum number of LSPs";
           type union {
             type string {
               pattern "<.*>|$.*";
             }
             type int32 {
               range "1 .. 64";
             }
           }
         }
         leaf minimum-member-lsps {
           description "Minimum number of LSPs";
           type union {
             type string {
               pattern "<.*>|$.*";
             }
             type int32 {
               range "1 .. 64";
             }
           }
         }
         leaf splitting-bandwidth {
           description "Maximum bandwidth threshold for splitting";
           units "bps";
           type string;
         }
         leaf merging-bandwidth {
           description "Minimum bandwidth threshold for merging";
           units "bps";
           type string;
         }
         leaf maximum-signaling-bandwidth {
           description "Maximum bandwidth for signaling during normalization";
           units "bps";
           type string;
         }
         leaf minimum-signaling-bandwidth {
           description "Minimum bandwidth for signaling during normalization";
           units "bps";
           type string;
         }
         leaf splitting-merging-threshold {
           description "Change in aggregate LSP utilization to trigger splitting or merging";
           default "10";
           units "percent";
           type union {
             type string {
               pattern "<.*>|$.*";
             }
             type uint32 {
               range "0 .. 100";
             }
           }
         }
         container normalization {
           description "Do normalization";
           uses apply-advanced;
           leaf normalize-interval {
             description "Time to normalize container LSP";
             default "86400";
             units "seconds";
             type union {
               type string {
                 pattern "<.*>|$.*";
               }
               type uint32 {
                 range "300 .. 315360000";
               }
             }
           }
           leaf failover-normalization {
             description "Do pre-mature normalization in case some LSPs go down before next normalization";
             type empty;
           }
           leaf no-incremental-normalize {
             description "Do not normalize unless all LSPs are successfully signaled";
             type empty;
           }
           leaf normalization-retry-duration {
             description "Time before retrying the container LSP normalization";
             units "seconds";
             type union {
               type string {
                 pattern "<.*>|$.*";
               }
               type uint32 {
                 range "1 .. 86400";
               }
             }
           }
           leaf normalization-retry-limits {
             description "Maximum number of times to retry container LSP normalization";
             type union {
               type string {
                 pattern "<.*>|$.*";
               }
               type uint32 {
                 range "1 .. 1000";
               }
             }
           }
           leaf no-normalize-same-members {
             description "Do not normalize when we are not splitting or merging member LSPs";
             type empty;
           }
         }
         container sampling {
           description "Sampling information";
           uses apply-advanced;
           leaf cut-off-threshold {
             description "Cut-off percentile to remove outliers from aggregate samples";
             default "0";
             type union {
               type string {
                 pattern "<.*>|$.*";
               }
               type uint32 {
                 range "0 .. 100";
               }
             }
           }
           choice sampling-mode {
             case case_1 {
               leaf use-average-aggregate {
                 description "Use average of the samples";
                 type empty;
               }
             }
             case case_2 {
               leaf use-percentile {
                 description "Use a percentile of the samples";
                 default "100";
                 type union {
                   type string {
                     pattern "<.*>|$.*";
                   }
                   type uint32 {
                     range "0 .. 100";
                   }
                 }
               }
             }
           }
         }
       }
       leaf lsp-external-controller {
         description "Name of the external path computing entity";
         junos:must "(\"protocols mpls lsp-external-controller $$\")";
         junos:must-message "Referenced lsp-external-controller is not defined";
         type string {
           junos:posix-pattern "^.{1,64}$";
           junos:pattern-message "Must be a string of less than 64 characters";
         }
       }
     }
     list transit-lsp-association {
       key name;
       ordered-by user;
       description "Transit label switch path assoication";
       leaf name {
         description "Name of transit assocation LSP group";
         type string {
           junos:posix-pattern "^.{1,64}$";
           junos:pattern-message "Must be a string of 64 characters or less";
         }
       }
       uses apply-advanced;
       leaf lsp-name-1 {
         description "Name of assocation LSP 1";
         type string {
           junos:posix-pattern "^.{1,64}$";
           junos:pattern-message "Must be a string of 64 characters or less";
         }
       }
       leaf from-1 {
         description "Address of associated LSP 1";
         type jt:ipv4addr;
       }
       leaf lsp-name-2 {
         description "Name of assocation LSP 2";
         type string {
           junos:posix-pattern "^.{1,64}$";
           junos:pattern-message "Must be a string of 64 characters or less";
         }
       }
       leaf from-2 {
         description "Address of associated LSP 2";
         type jt:ipv4addr;
       }
     }
     list path {
       key name;
       ordered-by user;
       description "Route of a label-switched path";
       leaf name {
         description "Name of label-switched path";
         type string {
           junos:posix-pattern "^.{1,64}$";
           junos:pattern-message "Must be a string of less than 64 characters";
         }
       }
       uses apply-advanced;
       list path-list {
         key name;
         ordered-by user;
         description "List of routers in the label-switched path";
         leaf name {
           description "Address of next system in path";
           type string {
             junos:posix-pattern "^.{1,64}$";
             junos:pattern-message "Must be a string of less than 64 characters";
           }
         }
         leaf abstract {
           description "Next system in path is abstract";
           junos:must "(\".. .. .. abstract-hop ${path-list}\")";
           junos:must-message "Referenced abstart hop must be configured";
           type empty;
         }
         choice loose_strict_none {
           case case_1 {
             leaf loose {
               description "Next hop might not be adjacent";
               type empty;
             }
           }
           case case_2 {
             leaf loose-link {
               description "Next hop link might not be adjacent";
               type empty;
             }
           }
           case case_3 {
             leaf strict {
               description "Next hop must be adjacent";
               type empty;
             }
           }
         }
       }
     }
     list constituent-list {
       key name;
       ordered-by user;
       description "MPLS constituent list for abstract hops";
       leaf name {
         description "Constituent list name";
         type string {
           junos:posix-pattern "^.{1,64}$";
           junos:pattern-message "Must be a string of 64 characters or less";
         }
       }
       uses apply-advanced;
       leaf-list srlg {
         ordered-by user;
         description "SRLG Name";
         type string;
         max-elements 16;
       }
       leaf-list admin-group {
         ordered-by user;
         description "Administrative groups";
         type string;
         max-elements 16;
       }
       leaf-list admin-group-extended {
         ordered-by user;
         description "Extended administrative groups";
         type string;
         max-elements 16;
       }
     }
     list abstract-hop {
       key name;
       ordered-by user;
       description "MPLS abstract hop";
       leaf name {
         description "Abstract hop name";
         type string {
           junos:posix-pattern "^.{1,64}$";
           junos:pattern-message "Must be a string of 64 characters or less";
         }
       }
       uses apply-advanced;
       leaf operator {
         description "Operation among constituent lists";
         type enumeration {
           enum "AND" {
             description "AND";
           }
           enum "OR" {
             description "OR";
           }
         }
       }
       list constituent-list {
         key name;
         ordered-by user;
         description "Building abstract hop using constituent lists";
         leaf name {
           description "Constituent list name";
           junos:must "(\"protocols mpls constituent-list $$\")";
           junos:must-message "Referenced constituent list does not exist";
           type string {
             length "1 .. 64";
           }
         }
         uses apply-advanced;
         choice list-type {
           case case_1 {
             leaf include-any-list {
               description "Include any";
               type empty;
             }
           }
           case case_2 {
             leaf include-all-list {
               description "Include all";
               type empty;
             }
           }
           case case_3 {
             leaf exclude-any-list {
               description "Exclude any";
               type empty;
             }
           }
           case case_4 {
             leaf exclude-all-list {
               description "Exclude all";
               type empty;
             }
           }
         }
       }
     }
     container egress-protection {
       description "Egress router protection";
       uses apply-advanced;
       list context-identifier {
         key name;
         description "Context identifier";
         leaf name {
           description "IP address";
           type jt:ipv4addr;
         }
         uses apply-advanced;
         choice context-type {
           case case_1 {
             leaf primary {
               description "Primary";
               type empty;
             }
           }
           case case_2 {
             leaf protector {
               description "Protector";
               type empty;
             }
           }
         }
         leaf metric {
           description "IGP metric";
           junos:must "(!(\" .. advertise-mode stub-alias\"))";
           junos:must-message "Metric configuration is not supported with stub-alias mode";
           junos:must "(\".. protector\")";
           junos:must-message "Configurable only for protector context identifiers";
           type union {
             type string {
               pattern "<.*>|$.*";
             }
             type uint32 {
               range "2 .. 16777215";
             }
           }
         }
         leaf advertise-mode {
           description "Advertise mode";
           type enumeration {
             enum "stub-proxy" {
               description "Proxy";
             }
             enum "stub-alias" {
               description "Alias";
             }
           }
         }
         leaf-list admin-group {
           ordered-by user;
           description "Administrative groups";
           junos:must "((\".. protector\" && \".. advertise-mode stub-proxy\"))";
           junos:must-message "Configurable only for protector with proxy mode";
           type string;
         }
       }
       container traceoptions {
         description "Trace options for egress-protection";
         uses apply-advanced;
         container file {
           description "Trace file options";
           leaf filename {
             description "Name of file in which to write trace information";
             type string {
               length "1 .. 1024";
               junos:posix-pattern "![/ %]";
               junos:pattern-message "Must not contain '/', % or a space";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "state" {
                 description "Trace state transitions";
               }
               enum "route" {
                 description "Trace route transitions";
               }
               enum "error" {
                 description "Trace error conditions";
               }
               enum "all" {
                 description "Trace everything";
               }
             }
           }
         }
       }
     }
     container label-range {
       description "MPLS labels ranges";
       uses apply-advanced;
       list lsi-label-range {
         key name;
         ordered-by user;
         description "LSI-label-range";
         leaf name {
           description "Label_range_start";
           type union {
             type string {
               pattern "<.*>|$.*";
             }
             type uint32 {
               range "16 .. 1048575";
             }
           }
         }
         leaf range-end {
           description "Label_range_end";
           type union {
             type string {
               pattern "<.*>|$.*";
             }
             type uint32 {
               range "16 .. 1048575";
             }
           }
         }
       }
       list dynamic-label-range {
         key name;
         ordered-by user;
         description "Dynamic-label-range";
         leaf name {
           description "Label_range_start";
           type union {
             type string {
               pattern "<.*>|$.*";
             }
             type uint32 {
               range "16 .. 1048575";
             }
           }
         }
         leaf range-end {
           description "Label_range_end";
           type union {
             type string {
               pattern "<.*>|$.*";
             }
             type uint32 {
               range "16 .. 1048575";
             }
           }
         }
       }
       list block-label-range {
         key name;
         ordered-by user;
         description "Block-label-range";
         leaf name {
           description "Label_range_start";
           type union {
             type string {
               pattern "<.*>|$.*";
             }
             type uint32 {
               range "16 .. 1048575";
             }
           }
         }
         leaf range-end {
           description "Label_range_end";
           type union {
             type string {
               pattern "<.*>|$.*";
             }
             type uint32 {
               range "16 .. 1048575";
             }
           }
         }
       }
       list srgb-label-range {
         key name;
         ordered-by user;
         description "SRGB-label-range";
         max-elements 1;
         leaf name {
           description "Label_range_start";
           type union {
             type string {
               pattern "<.*>|$.*";
             }
             type uint32 {
               range "16 .. 1048575";
             }
           }
         }
         leaf range-end {
           description "Label_range_end";
           type union {
             type string {
               pattern "<.*>|$.*";
             }
             type uint32 {
               range "16 .. 1048575";
             }
           }
         }
       }
       leaf label-limit {
         description "Limit for the number of concurrent active labels";
         type union {
           type string {
             pattern "<.*>|$.*";
           }
           type uint32;
         }
       }
       list static-label-range {
         key name;
         ordered-by user;
         description "Static-label-range";
         leaf name {
           description "Label_range_start";
           type union {
             type string {
               pattern "<.*>|$.*";
             }
             type uint32 {
               range "16 .. 1048575";
             }
           }
         }
         leaf range-end {
           description "Label_range_end";
           type union {
             type string {
               pattern "<.*>|$.*";
             }
             type uint32 {
               range "16 .. 1048575";
             }
           }
         }
       }
     }
     choice enable-disable {
       case case_1 {
         leaf disable {
           description "Disable MPLS";
           type empty;
         }
       }
     }
     container label-history {
       presence "enable label-history";
       description "MPLS label history recording";
       uses apply-advanced;
       leaf max-entries {
         description "Limit for the number of history entry per label";
         type union {
           type string {
             pattern "<.*>|$.*";
           }
           type uint32;
         }
       }
     }
     container traceoptions {
       description "Trace options for MPLS";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "connection" {
               description "Trace CCC activity";
             }
             enum "connection-detail" {
               description "Trace CCC activity in detail";
             }
             enum "cspf" {
               description "Trace CSPF computation";
             }
             enum "cspf-node" {
               description "Trace nodes visited during CSPF";
             }
             enum "cspf-link" {
               description "Trace links visited during CSPF";
             }
             enum "cspf-abstract" {
               description "Trace abstract hop based CSPF details";
             }
             enum "state" {
               description "Trace state transitions";
             }
             enum "error" {
               description "Trace error conditions";
             }
             enum "lsping" {
               description "Trace LSP ping packets received";
             }
             enum "graceful-restart" {
               description "Trace graceful-restart-related events";
             }
             enum "nsr-synchronization" {
               description "Trace NSR synchronization events";
             }
             enum "nsr-synchronization-detail" {
               description "Trace NSR synchronization events in detail";
             }
             enum "static" {
               description "Trace static label-switched path";
             }
             enum "egress-protection" {
               description "Trace egress protection events";
             }
             enum "all" {
               description "Trace everything";
             }
             enum "autobw-state" {
               description "Trace autobandwidth events in mpls trace";
             }
             enum "externally-controlled-lsp" {
               description "Trace externally controlled LSP events in mpls trace";
             }
             enum "ted-import" {
               description "Trace leaking TED entries into lsdist.0 table";
             }
             enum "ted-export" {
               description "Trace leaking of entries from lsdist.0 table into TED";
             }
             enum "lsp-history" {
               description "Trace LSP history events";
             }
             enum "abstract-hop" {
               description "Trace abstract hop related events";
             }
             enum "remote-pce" {
               description "Trace cPCE events in mpls trace";
             }
           }
         }
       }
     }
     leaf ipv6-tunneling {
       description "Allow MPLS LSPs to be used for tunneling IPv6 traffic";
       type empty;
     }
     list interface {
       key name;
       ordered-by user;
       description "MPLS interface options";
       uses juniper-protocols-mpls-interface;
     }
     list static-label-switched-path {
       key name;
       ordered-by user;
       description "Static label-switched path";
       leaf name {
         description "Name of path";
         type string {
           length "1 .. 64";
         }
       }
       uses apply-advanced;
       choice lsp-type {
         case case_1 {
           container bypass {
             description "Bypass ingress label-switched path";
             uses apply-advanced;
             leaf bandwidth {
               description "Bandwidth to reserve";
               units "bps";
               type string;
             }
             leaf description {
               description "Text description of label-switched path";
               type string {
                 length "1 .. 80";
               }
             }
             leaf next-hop {
               description "IPv4 or IPv6 address or interface of next-hop router";
               type union {
                 type jt:ipaddr-or-interface;
                 type string {
                   pattern "<.*>|$.*";
                 }
               }
             }
             leaf next-table {
               description "Next-table for lookup";
               type string;
             }
             leaf push {
               description "Label to push";
               type union {
                 type string {
                   pattern "<.*>|$.*";
                 }
                 type uint32 {
                   range "0 .. 1048575";
                 }
               }
             }
             leaf to {
               description "Address of egress router";
               type jt:ipaddr;
             }
           }
         }
         case case_2 {
           list transit {
             key name;
             ordered-by user;
             description "Transit label-switched path";
             leaf name {
               description "Incoming label value";
               type union {
                 type string {
                   pattern "<.*>|$.*";
                 }
                 type uint32 {
                   range "16 .. 1048575";
                 }
               }
             }
             uses apply-advanced;
             leaf bandwidth {
               description "Bandwidth to reserve";
               units "bps";
               type string;
             }
             leaf description {
               description "Text description of label-switched path";
               type string {
                 length "1 .. 80";
               }
             }
             container link-protection {
               description "Bypass link protection";
               leaf bypass-name {
                 description "Bypass label-switched path name";
                 type string {
                   length "1 .. 64";
                 }
               }
             }
             leaf next-hop {
               description "IPv4 or IPv6 address or interface of next-hop router";
               type union {
                 type jt:ipaddr-or-interface;
                 type string {
                   pattern "<.*>|$.*";
                 }
               }
             }
             leaf member-interface {
               description "AE member interface name";
               type union {
                 type jt:interface-unit;
                 type string {
                   pattern "<.*>|$.*";
                 }
               }
             }
             container node-protection {
               description "Bypass node protection";
               leaf bypass-name {
                 description "Bypass label-switched path name";
                 type string {
                   length "1 .. 64";
                 }
               }
               leaf next-next-label {
                 description "Label expected by next-next-hop";
                 type union {
                   type string {
                     pattern "<.*>|$.*";
                   }
                   type uint32 {
                     range "0 .. 1048575";
                   }
                 }
               }
             }
             choice label-action {
               case case_1 {
                 leaf swap {
                   description "Swap top label with this label";
                   type union {
                     type string {
                       pattern "<.*>|$.*";
                     }
                     type uint32 {
                       range "0 .. 1048575";
                     }
                   }
                 }
               }
               case case_2 {
                 leaf pop {
                   description "Pop the top label";
                   type empty;
                 }
               }
               case case_3 {
                 leaf stitch {
                   description "Swap top label with the resolved LSP";
                   junos:must "(!((\".. link-protection\" || \".. node-protection\")))";
                   junos:must-message "Link-protection and node-protection are invalid for LSP stitching";
                   type empty;
                 }
               }
             }
           }
         }
         case case_3 {
           container ingress {
             description "Ingress LSR configuration for a static LSP";
             uses apply-advanced;
             leaf bandwidth {
               description "Bandwidth to reserve";
               units "bps";
               type string;
             }
             leaf class-of-service {
               description "Class-of-service value";
               type union {
                 type string {
                   pattern "<.*>|$.*";
                 }
                 type int32 {
                   range "0 .. 7";
                 }
               }
             }
             leaf description {
               description "Text description of label-switched path";
               type string {
                 length "1 .. 80";
               }
             }
             list install {
               key name;
               ordered-by user;
               description "Install prefix";
               leaf name {
                 description "Destination prefix";
                 type jt:ipv4prefix;
               }
               leaf active {
                 description "Install prefix into forwarding table";
                 type empty;
               }
             }
             leaf metric {
               description "Metric value";
               type union {
                 type string {
                   pattern "<.*>|$.*";
                 }
                 type uint32 {
                   range "1 .. 16777215";
                 }
               }
             }
             leaf next-hop {
               description "IPv4 address or interface of next-hop router";
               type union {
                 type jt:ipv4addr-or-interface;
                 type string {
                   pattern "<.*>|$.*";
                 }
               }
             }
             container link-protection {
               description "Bypass link protection";
               leaf bypass-name {
                 description "Bypass label-switched path name";
                 type string {
                   length "1 .. 64";
                 }
               }
             }
             container node-protection {
               description "Bypass node protection";
               leaf bypass-name {
                 description "Bypass label-switched path name";
                 type string {
                   length "1 .. 64";
                 }
               }
               leaf next-next-label {
                 description "Label expected by next-next-hop";
                 type union {
                   type string {
                     pattern "<.*>|$.*";
                   }
                   type uint32 {
                     range "0 .. 1048575";
                   }
                 }
               }
             }
             leaf no-install-to-address {
               description "Don't install host route 'to' address into routing tables";
               type empty;
             }
             container policing {
               description "Traffic policing for this LSP";
               leaf filter {
                 description "Name of filter to use for policing LSP traffic";
                 junos:must "(!(\"firewall family any filter $$ interface-specific\"))";
                 junos:must-message "LSP policing filter must not be interface-specific";
                 junos:must "((\"firewall family any filter $$\" || (!(\"firewall\") && \".. .. .. .. .. .. .. .. firewall family any filter $$\")))";
                 junos:must-message "referenced filter must be defined under firewall family any";
                 type string {
                   junos:posix-pattern "!^((__.*)|(.{65,}))$";
                   junos:pattern-message "Must be a non-reserved string of 64 characters or less";
                 }
               }
               leaf no-auto-policing {
                 description "Turn off automatic policing for this LSP";
                 type empty;
               }
             }
             leaf preference {
               description "Preference value";
               type union {
                 type uint32;
                 type string {
                   pattern "<.*>|$.*";
                 }
               }
             }
             leaf to {
               description "Address of egress router";
               type jt:ipv4addr;
             }
             leaf push {
               description "Label to push";
               type union {
                 type string {
                   pattern "<.*>|$.*";
                 }
                 type uint32 {
                   range "0 .. 1048575";
                 }
               }
             }
             leaf entropy-label {
               description "Enable entropy label";
               type empty;
             }
           }
         }
         case case_4 {
           container segment {
             description "Segment for segment routing";
             uses apply-advanced;
             leaf sid-label {
               description "Segment identifier (SID) label";
               type union {
                 type string {
                   pattern "<.*>|$.*";
                 }
                 type uint32 {
                   range "16 .. 1048575";
                 }
               }
             }
             leaf description {
               description "Text description of label-switched path";
               type string {
                 length "1 .. 80";
               }
             }
             leaf next-hop {
               description "IPv4 address or interface of next-hop router";
               type union {
                 type jt:ipv4addr-or-interface;
                 type string {
                   pattern "<.*>|$.*";
                 }
               }
             }
             choice label-action {
               case case_1 {
                 leaf swap {
                   description "Swap the SID label to this label";
                   type union {
                     type string {
                       pattern "<.*>|$.*";
                     }
                     type uint32 {
                       range "0 .. 1048575";
                     }
                   }
                 }
               }
               case case_2 {
                 leaf pop {
                   description "Pop the SID label";
                   type empty;
                 }
               }
             }
           }
         }
       }
     }
   }
   grouping juniper-protocols-mpls-interface {
     leaf name {
       description "Interface name";
       type union {
         type jt:interface-name;
         type string {
           pattern "<.*>|$.*";
         }
       }
     }
     uses apply-advanced;
     choice enable-disable {
       case case_1 {
         leaf disable {
           description "Disable MPLS on this interface";
           type empty;
         }
       }
     }
     leaf-list srlg {
       ordered-by user;
       description "SRLG Name";
       type string;
       max-elements 64;
     }
     leaf always-mark-connection-protection-tlv {
       description "Mark connection protection tlv on this interface";
       type empty;
     }
     leaf switch-away-lsps {
       description "Switch away protected LSPs to their bypass LSPs";
       type empty;
     }
     leaf-list admin-group {
       ordered-by user;
       description "Administrative groups";
       type string;
     }
     leaf-list admin-group-extended {
       ordered-by user;
       description "Extended administrative groups";
       type string;
     }
     container static {
       description "Static label-switch path related configurations";
       uses apply-advanced;
       leaf protection-revert-time {
         description "FRR revert wait time, 0 means disable";
         units "seconds";
         type union {
           type string {
             pattern "<.*>|$.*";
           }
           type uint32 {
             range "0 .. 65535";
           }
         }
       }
     }
   }
   grouping juniper-protocols-msdp {
     uses apply-advanced;
     leaf data-encapsulation {
       description "Set encapsulation of data packets";
       type enumeration {
         enum "disable" {
           description "Disable data encapsulation";
         }
         enum "enable" {
           description "Enable data encapsulation";
         }
       }
     }
     container rib-group {
       description "Routing table group";
       uses rib_group_inet_type;
     }
     container active-source-limit {
       description "Limit the number of active sources accepted";
       uses apply-advanced;
       leaf maximum {
         description "Maximum number of active sources accepted";
         default "25000";
         type union {
           type string {
             pattern "<.*>|$.*";
           }
           type uint32 {
             range "1 .. 1000000";
           }
         }
       }
       leaf threshold {
         description "RED threshold for active source acceptance";
         default "24000";
         type union {
           type string {
             pattern "<.*>|$.*";
           }
           type uint32 {
             range "1 .. 1000000";
           }
         }
       }
       leaf log-warning {
         description "Percentage of maximum at which to start generating warnings";
         default "100";
         junos:must "(\".. maximum\")";
         junos:must-message "Maximum must be configured to configure log-warning";
         type union {
           type string {
             pattern "<.*>|$.*";
           }
           type uint32 {
             range "1 .. 100";
           }
         }
       }
       leaf log-interval {
         description "Time between log messages";
         junos:must "(\".. maximum\")";
         junos:must-message "Maximum must be configured to configure log-interval";
         type union {
           type string {
             pattern "<.*>|$.*";
           }
           type uint32 {
             range "6 .. 32767";
           }
         }
       }
     }
     choice enable-disable {
       case case_1 {
         leaf disable {
           description "Disable MSDP";
           type empty;
         }
       }
     }
     leaf-list export {
       ordered-by user;
       description "Export policy";
       type jt:policy-algebra;
     }
     leaf-list import {
       ordered-by user;
       description "Import policy";
       type jt:policy-algebra;
     }
     leaf local-address {
       description "Local address";
       type jt:ipv4addr;
     }
     container traceoptions {
       description "Trace options for MSDP";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "packets" {
               description "Trace all MSDP packets";
             }
             enum "route" {
               description "Trace routing information";
             }
             enum "nsr-synchronization" {
               description "Trace NSR synchronization events";
             }
             enum "source-active" {
               description "Trace source-active messages";
             }
             enum "source-active-request" {
               description "Trace source-active request messages";
             }
             enum "source-active-response" {
               description "Trace source-active response messages";
             }
             enum "keepalive" {
               description "Trace keepalive messages";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     list peer {
       key name;
       ordered-by user;
       description "Configure an MSDP peer";
       leaf name {
         description "Peer address";
         type jt:ipv4addr;
       }
       uses apply-advanced;
       choice enable-disable {
         case case_1 {
           leaf disable {
             description "Disable MSDP";
             type empty;
           }
         }
       }
       leaf-list export {
         ordered-by user;
         description "Export policy";
         type jt:policy-algebra;
       }
       leaf-list import {
         ordered-by user;
         description "Import policy";
         type jt:policy-algebra;
       }
       leaf local-address {
         description "Local address";
         type jt:ipv4addr;
       }
       container traceoptions {
         description "Trace options for MSDP";
         uses apply-advanced;
         container file {
           description "Trace file options";
           leaf filename {
             description "Name of file in which to write trace information";
             type string {
               length "1 .. 1024";
               junos:posix-pattern "![/ %]";
               junos:pattern-message "Must not contain '/', % or a space";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "packets" {
                 description "Trace all MSDP packets";
               }
               enum "route" {
                 description "Trace routing information";
               }
               enum "nsr-synchronization" {
                 description "Trace NSR synchronization events";
               }
               enum "source-active" {
                 description "Trace source-active messages";
               }
               enum "source-active-request" {
                 description "Trace source-active request messages";
               }
               enum "source-active-response" {
                 description "Trace source-active response messages";
               }
               enum "keepalive" {
                 description "Trace keepalive messages";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       container active-source-limit {
         description "Limit the number of active sources accepted";
         uses apply-advanced;
         leaf maximum {
           description "Maximum number of active sources accepted";
           default "25000";
           type union {
             type string {
               pattern "<.*>|$.*";
             }
             type uint32 {
               range "1 .. 1000000";
             }
           }
         }
         leaf threshold {
           description "RED threshold for active source acceptance";
           default "24000";
           type union {
             type string {
               pattern "<.*>|$.*";
             }
             type uint32 {
               range "1 .. 1000000";
             }
           }
         }
         leaf log-warning {
           description "Percentage of maximum at which to start generating warnings";
           default "100";
           junos:must "(\".. maximum\")";
           junos:must-message "Maximum must be configured to configure log-warning";
           type union {
             type string {
               pattern "<.*>|$.*";
             }
             type uint32 {
               range "1 .. 100";
             }
           }
         }
         leaf log-interval {
           description "Time between log messages";
           junos:must "(\".. maximum\")";
           junos:must-message "Maximum must be configured to configure log-interval";
           type union {
             type string {
               pattern "<.*>|$.*";
             }
             type uint32 {
               range "6 .. 32767";
             }
           }
         }
       }
       leaf keep-alive {
         description "Time limit for sending out periodic keep alive to peer";
         units "seconds";
         type union {
           type string {
             pattern "<.*>|$.*";
           }
           type uint32 {
             range "10 .. 60";
           }
         }
       }
       leaf hold-time {
         description "Max time to terminating a peer for having not received any message from ";
         units "seconds";
         type union {
           type string {
             pattern "<.*>|$.*";
           }
           type uint32 {
             range "15 .. 150";
           }
         }
       }
       leaf sa-hold-time {
         description "Max time for holding a sa message before timing out";
         units "seconds";
         type union {
           type string {
             pattern "<.*>|$.*";
           }
           type uint32 {
             range "75 .. 300";
           }
         }
       }
       leaf default-peer {
         description "Default RPF peer";
         type empty;
       }
       leaf authentication-key {
         description "MD5 authentication key";
         type string {
           length "1 .. 126";
         }
       }
     }
     leaf keep-alive {
       description "Time limit for sending out periodic keep alive to peer";
       units "seconds";
       type union {
         type string {
           pattern "<.*>|$.*";
         }
         type uint32 {
           range "10 .. 60";
         }
       }
     }
     leaf hold-time {
       description "Max time to terminating a peer for having not received any message from ";
       units "seconds";
       type union {
         type string {
           pattern "<.*>|$.*";
         }
         type uint32 {
           range "15 .. 150";
         }
       }
     }
     leaf sa-hold-time {
       description "Max time for holding a sa message before timing out";
       units "seconds";
       type union {
         type string {
           pattern "<.*>|$.*";
         }
         type uint32 {
           range "75 .. 300";
         }
       }
     }
     list source {
       key name;
       ordered-by user;
       description "Configure parameters for each source";
       leaf name {
         description "Source address or prefix";
         type jt:ipprefix;
       }
       uses apply-advanced;
       container active-source-limit {
         description "Limit the number of active sources accepted";
         uses apply-advanced;
         leaf maximum {
           description "Maximum number of active sources accepted";
           default "25000";
           type union {
             type string {
               pattern "<.*>|$.*";
             }
             type uint32 {
               range "1 .. 1000000";
             }
           }
         }
         leaf threshold {
           description "RED threshold for active source acceptance";
           default "24000";
           type union {
             type string {
               pattern "<.*>|$.*";
             }
             type uint32 {
               range "1 .. 1000000";
             }
           }
         }
         leaf log-warning {
           description "Percentage of maximum at which to start generating warnings";
           default "100";
           junos:must "(\".. maximum\")";
           junos:must-message "Maximum must be configured to configure log-warning";
           type union {
             type string {
               pattern "<.*>|$.*";
             }
             type uint32 {
               range "1 .. 100";
             }
           }
         }
         leaf log-interval {
           description "Time between log messages";
           junos:must "(\".. maximum\")";
           junos:must-message "Maximum must be configured to configure log-interval";
           type union {
             type string {
               pattern "<.*>|$.*";
             }
             type uint32 {
               range "6 .. 32767";
             }
           }
         }
       }
     }
     list group {
       key name;
       ordered-by user;
       description "Configure MSDP peer groups";
       leaf name {
         description "MSDP peer group name";
         type string;
       }
       uses apply-advanced;
       leaf mode {
         description "MSDP group source-active flooding mode";
         default "standard";
         type enumeration {
           enum "standard" {
             description "Use standard MSDP source-active flooding rules";
           }
           enum "mesh-group" {
             description "Group peers are mesh group members";
           }
         }
       }
       choice enable-disable {
         case case_1 {
           leaf disable {
             description "Disable MSDP";
             type empty;
           }
         }
       }
       leaf-list export {
         ordered-by user;
         description "Export policy";
         type jt:policy-algebra;
       }
       leaf-list import {
         ordered-by user;
         description "Import policy";
         type jt:policy-algebra;
       }
       leaf local-address {
         description "Local address";
         type jt:ipv4addr;
       }
       container traceoptions {
         description "Trace options for MSDP";
         uses apply-advanced;
         container file {
           description "Trace file options";
           leaf filename {
             description "Name of file in which to write trace information";
             type string {
               length "1 .. 1024";
               junos:posix-pattern "![/ %]";
               junos:pattern-message "Must not contain '/', % or a space";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "packets" {
                 description "Trace all MSDP packets";
               }
               enum "route" {
                 description "Trace routing information";
               }
               enum "nsr-synchronization" {
                 description "Trace NSR synchronization events";
               }
               enum "source-active" {
                 description "Trace source-active messages";
               }
               enum "source-active-request" {
                 description "Trace source-active request messages";
               }
               enum "source-active-response" {
                 description "Trace source-active response messages";
               }
               enum "keepalive" {
                 description "Trace keepalive messages";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       list peer {
         key name;
         ordered-by user;
         description "Configure an MSDP peer";
         leaf name {
           description "Peer address";
           type jt:ipv4addr;
         }
         uses apply-advanced;
         choice enable-disable {
           case case_1 {
             leaf disable {
               description "Disable MSDP";
               type empty;
             }
           }
         }
         leaf-list export {
           ordered-by user;
           description "Export policy";
           type jt:policy-algebra;
         }
         leaf-list import {
           ordered-by user;
           description "Import policy";
           type jt:policy-algebra;
         }
         leaf local-address {
           description "Local address";
           type jt:ipv4addr;
         }
         container traceoptions {
           description "Trace options for MSDP";
           uses apply-advanced;
           container file {
             description "Trace file options";
             leaf filename {
               description "Name of file in which to write trace information";
               type string {
                 length "1 .. 1024";
                 junos:posix-pattern "![/ %]";
                 junos:pattern-message "Must not contain '/', % or a space";
               }
             }
             leaf replace {
               description "Replace trace file rather than appending to it";
               status deprecated;
               type empty;
             }
             leaf size {
               description "Maximum trace file size";
               type string;
             }
             leaf files {
               description "Maximum number of trace files";
               default "10";
               type union {
                 type string {
                   pattern "<.*>|$.*";
                 }
                 type uint32 {
                   range "2 .. 1000";
                 }
               }
             }
             leaf no-stamp {
               description "Do not timestamp trace file";
               status deprecated;
               type empty;
             }
             choice world-readable-choice {
               leaf world-readable {
                 description "Allow any user to read the log file";
                 type empty;
               }
               leaf no-world-readable {
                 description "Don't allow any user to read the log file";
                 type empty;
               }
             }
           }
           list flag {
             key name;
             ordered-by user;
             description "Tracing parameters";
             leaf name {
               type enumeration {
                 enum "packets" {
                   description "Trace all MSDP packets";
                 }
                 enum "route" {
                   description "Trace routing information";
                 }
                 enum "nsr-synchronization" {
                   description "Trace NSR synchronization events";
                 }
                 enum "source-active" {
                   description "Trace source-active messages";
                 }
                 enum "source-active-request" {
                   description "Trace source-active request messages";
                 }
                 enum "source-active-response" {
                   description "Trace source-active response messages";
                 }
                 enum "keepalive" {
                   description "Trace keepalive messages";
                 }
                 enum "normal" {
                   description "Trace normal events";
                 }
                 enum "general" {
                   description "Trace general events";
                 }
                 enum "state" {
                   description "Trace state transitions";
                 }
                 enum "policy" {
                   description "Trace policy processing";
                 }
                 enum "task" {
                   description "Trace routing protocol task processing";
                 }
                 enum "timer" {
                   description "Trace routing protocol timer processing";
                 }
                 enum "all" {
                   description "Trace everything";
                 }
               }
             }
             leaf send {
               description "Trace transmitted packets";
               type empty;
             }
             leaf receive {
               description "Trace received packets";
               type empty;
             }
             leaf detail {
               description "Trace detailed information";
               type empty;
             }
             leaf disable {
               description "Disable this trace flag";
               type empty;
             }
           }
         }
         container active-source-limit {
           description "Limit the number of active sources accepted";
           uses apply-advanced;
           leaf maximum {
             description "Maximum number of active sources accepted";
             default "25000";
             type union {
               type string {
                 pattern "<.*>|$.*";
               }
               type uint32 {
                 range "1 .. 1000000";
               }
             }
           }
           leaf threshold {
             description "RED threshold for active source acceptance";
             default "24000";
             type union {
               type string {
                 pattern "<.*>|$.*";
               }
               type uint32 {
                 range "1 .. 1000000";
               }
             }
           }
           leaf log-warning {
             description "Percentage of maximum at which to start generating warnings";
             default "100";
             junos:must "(\".. maximum\")";
             junos:must-message "Maximum must be configured to configure log-warning";
             type union {
               type string {
                 pattern "<.*>|$.*";
               }
               type uint32 {
                 range "1 .. 100";
               }
             }
           }
           leaf log-interval {
             description "Time between log messages";
             junos:must "(\".. maximum\")";
             junos:must-message "Maximum must be configured to configure log-interval";
             type union {
               type string {
                 pattern "<.*>|$.*";
               }
               type uint32 {
                 range "6 .. 32767";
               }
             }
           }
         }
         leaf keep-alive {
           description "Time limit for sending out periodic keep alive to peer";
           units "seconds";
           type union {
             type string {
               pattern "<.*>|$.*";
             }
             type uint32 {
               range "10 .. 60";
             }
           }
         }
         leaf hold-time {
           description "Max time to terminating a peer for having not received any message from ";
           units "seconds";
           type union {
             type string {
               pattern "<.*>|$.*";
             }
             type uint32 {
               range "15 .. 150";
             }
           }
         }
         leaf sa-hold-time {
           description "Max time for holding a sa message before timing out";
           units "seconds";
           type union {
             type string {
               pattern "<.*>|$.*";
             }
             type uint32 {
               range "75 .. 300";
             }
           }
         }
         leaf default-peer {
           description "Default RPF peer";
           type empty;
         }
         leaf authentication-key {
           description "MD5 authentication key";
           type string {
             length "1 .. 126";
           }
         }
       }
     }
   }
   grouping juniper-protocols-mstp {
     uses apply-advanced;
     choice enable-disable {
       case case_1 {
         leaf disable {
           description "Disable MSTP";
           type empty;
         }
       }
     }
     leaf bpdu-destination-mac-address {
       description "Destination MAC address in the spanning tree BPDUs";
       type enumeration {
         enum "provider-bridge-group" {
           description "802.1ad provider bridge group address";
         }
       }
     }
     leaf configuration-name {
       description "Configuration name (part of MST configuration identifier)";
       type string {
         length "1 .. 32";
       }
     }
     leaf revision-level {
       description "Revision level (part of MST configuration identifier)";
       type union {
         type uint16;
         type string {
           pattern "<.*>|$.*";
         }
       }
     }
     leaf max-hops {
       description "Maximum number of hops";
       type union {
         type string {
           pattern "<.*>|$.*";
         }
         type uint16 {
           range "1 .. 255";
         }
       }
     }
     leaf max-age {
       description "Maximum age of received protocol bpdu";
       units "seconds";
       type union {
         type string {
           pattern "<.*>|$.*";
         }
         type uint16 {
           range "6 .. 40";
         }
       }
     }
     leaf hello-time {
       description "Time interval between configuration BPDUs";
       units "seconds";
       type union {
         type string {
           pattern "<.*>|$.*";
         }
         type uint16 {
           range "1 .. 10";
         }
       }
     }
     leaf forward-delay {
       description "Time spent in listening or learning state";
       units "seconds";
       type union {
         type string {
           pattern "<.*>|$.*";
         }
         type uint16 {
           range "4 .. 30";
         }
       }
     }
     leaf system-identifier {
       description "Sytem identifier to represent this node";
       type jt:mac-unicast;
     }
     container traceoptions {
       description "Tracing options for debugging protocol operation";
       uses stp-trace-options;
     }
     leaf bridge-priority {
       description "Priority of the bridge (in increments of 4k - 0,4k,8k,..60k)";
       type string {
         junos:posix-pattern "^(0|4k|4096|8k|8192|12k|12288|16k|16384|20k|20480|24k|24576|28k|28672|32k|32768|36k|36864|40k|40960|44k|45056|48k|49512|52k|53248|56k|57344|60k|61440)$";
         junos:pattern-message "Must be a multiple of 4096";
       }
     }
     leaf backup-bridge-priority {
       description "Priority of the bridge (in increments of 4k - 4k,8k,..60k)";
       type string {
         junos:posix-pattern "^(4k|4096|8k|8192|12k|12288|16k|16384|20k|20480|24k|24576|28k|28672|32k|32768|36k|36864|40k|40960|44k|45056|48k|49512|52k|53248|56k|57344|60k|61440)$";
         junos:pattern-message "Must be a multiple of 4096";
       }
     }
     leaf bpdu-block-on-edge {
       description "Block BPDU on all interfaces configured as edge (BPDU Protect)";
       type empty;
     }
     leaf vpls-flush-on-topology-change {
       description "Enable VPLS MAC flush on root protected CE interface receving topology change";
       type empty;
     }
     leaf priority-hold-time {
       description "Hold time before switching to primary priority when core domain becomes up";
       units "seconds";
       type union {
         type string {
           pattern "<.*>|$.*";
         }
         type uint16 {
           range "1 .. 255";
         }
       }
     }
     list system-id {
       key name;
       ordered-by user;
       description "System ID to IP mapping";
       uses system-id-ip-map;
     }
     list interface {
       key name;
       description "Interface options";
       uses mstp-interface;
     }
     list msti {
       key name;
       description "Per-MSTI options";
       leaf name {
         type union {
           type string {
             pattern "<.*>|$.*";
           }
           type int32 {
             range "1 .. 4094";
           }
         }
       }
       uses apply-advanced;
       leaf bridge-priority {
         description "Priority of the bridge (in increments of 4k - 0,4k,8k,..60k)";
         type string {
           junos:posix-pattern "^(0|4k|4096|8k|8192|12k|12288|16k|16384|20k|20480|24k|24576|28k|28672|32k|32768|36k|36864|40k|40960|44k|45056|48k|49512|52k|53248|56k|57344|60k|61440)$";
           junos:pattern-message "Must be a multiple of 4096";
         }
       }
       leaf backup-bridge-priority {
         description "Priority of the bridge (in increments of 4k - 4k,8k,..60k)";
         type string {
           junos:posix-pattern "^(4k|4096|8k|8192|12k|12288|16k|16384|20k|20480|24k|24576|28k|28672|32k|32768|36k|36864|40k|40960|44k|45056|48k|49512|52k|53248|56k|57344|60k|61440)$";
           junos:pattern-message "Must be a multiple of 4096";
         }
       }
       leaf-list vlan {
         ordered-by user;
         description "VLAN ID or VLAN ID range [1..4094]";
         type string;
       }
       list interface {
         key name;
         description "Interface options";
         uses mstp-interface;
       }
     }
   }
   grouping juniper-protocols-mvpn {
     description "BGP-MVPN configuration";
     uses apply-advanced;
     container traceoptions {
       description "Trace options for BGP-MVPN";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "error" {
               description "Trace errors";
             }
             enum "nlri" {
               description "Trace MVPN advertisements";
             }
             enum "topology" {
               description "Trace MVPN topology changes";
             }
             enum "tunnel" {
               description "Trace provider tunnel events";
             }
             enum "umh" {
               description "Trace Upstream Multicast Hop (UMH) events";
             }
             enum "intra-as-ad" {
               description "Trace MVPN intra-AS auto discovery routes";
             }
             enum "inter-as-ad" {
               description "Trace MVPN inter-AS auto discovery routes";
             }
             enum "spmsi-ad" {
               description "Trace MVPN SPMSI auto discovery routes";
             }
             enum "leaf-ad" {
               description "Trace MVPN leaf auto discovery routes";
             }
             enum "source-active" {
               description "Trace MVPN source active routes";
             }
             enum "cmcast-join" {
               description "Trace MVPN c-multicast join routes";
             }
             enum "mdt-safi-ad" {
               description "Trace MVPN MDT SAFI auto discovery routes";
             }
             enum "mvpn-limit" {
               description "Trace MVPN spmsi and cmcast limit events";
             }
             enum "nsr-synchronization" {
               description "Trace NSR synchronization events";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     container autodiscovery-only {
       junos:must "(!(\".. route-target\"))";
       junos:must-message "MVPN autodiscovery-only mode cannot be used with route-target";
       junos:must "(!(\".. sender-site\"))";
       junos:must-message "MVPN autodiscovery-only mode cannot be used with sender-site";
       junos:must "(!(\".. receiver-site\"))";
       junos:must-message "MVPN autodiscovery-only mode cannot be used with receiver-site";
       junos:must "(\".. .. .. protocols pim mvpn\")";
       junos:must-message "MVPN autodiscovery-only mode requires protocols pim mvpn configuration for the instance.";
       junos:must "(!(\".. .. .. provider-tunnel family inet pim-asm\"))";
       junos:must-message "MVPN autodiscovery-only mode requires a PIM-SSM provider-tunnel root address.";
       junos:must "((\".. .. .. provider-tunnel pim-ssm\" || \".. .. .. provider-tunnel family inet pim-ssm\"))";
       junos:must-message "MVPN autodiscovery-only mode requires a PIM-SSM provider-tunnel root address.";
       description "Use MVPN exclusively for PE router autodiscovery";
       status deprecated;
       uses apply-advanced;
       container intra-as {
         description "Intra-AS autodiscovery options";
         uses apply-advanced;
         leaf inclusive {
           description "Inclusive provider tunnel autodiscovery";
           type empty;
         }
       }
     }
     container family {
       description "BGP-MVPN address family";
       uses apply-advanced;
       container any {
         presence "enable any";
         description "BGP-MVPN properties for all families";
         uses apply-advanced;
         leaf disable {
           description "Disable all families";
           type empty;
         }
       }
       container inet {
         description "IPv4 BGP-MVPN properties";
         uses apply-advanced;
         container autodiscovery-only {
           junos:must "(!(\".. .. .. route-target\"))";
           junos:must-message "MVPN autodiscovery-only mode cannot be used with route-target";
           junos:must "(!(\".. .. .. sender-site\"))";
           junos:must-message "MVPN autodiscovery-only mode cannot be used with sender-site";
           junos:must "(!(\".. .. .. receiver-site\"))";
           junos:must-message "MVPN autodiscovery-only mode cannot be used with receiver-site";
           junos:must "(\".. .. .. .. .. protocols pim mvpn\")";
           junos:must-message "MVPN autodiscovery-only mode requires protocols pim mvpn configuration for the instance.";
           junos:must "(!(\".. .. .. .. .. provider-tunnel family inet pim-asm\"))";
           junos:must-message "MVPN autodiscovery-only mode requires a PIM-SSM provider-tunnel root address.";
           junos:must "((\".. .. .. .. .. provider-tunnel pim-ssm\" || \".. .. .. .. .. provider-tunnel family inet pim-ssm\"))";
           junos:must-message "MVPN autodiscovery-only mode requires a PIM-SSM provider-tunnel root address.";
           description "Use MVPN exclusively for PE router autodiscovery";
           uses apply-advanced;
           container intra-as {
             description "Intra-AS autodiscovery options";
             uses apply-advanced;
             leaf inclusive {
               description "Inclusive provider tunnel autodiscovery";
               type empty;
             }
           }
         }
         leaf disable {
           description "Disable family IPv4";
           type empty;
         }
       }
       container inet6 {
         presence "enable inet6";
         description "IPv6 BGP-MVPN properties";
         uses apply-advanced;
         container autodiscovery-only {
           junos:must "(!(\".. .. .. route-target\"))";
           junos:must-message "MVPN autodiscovery-only mode cannot be used with route-target";
           junos:must "(!(\".. .. .. sender-site\"))";
           junos:must-message "MVPN autodiscovery-only mode cannot be used with sender-site";
           junos:must "(!(\".. .. .. receiver-site\"))";
           junos:must-message "MVPN autodiscovery-only mode cannot be used with receiver-site";
           junos:must "(\".. .. .. .. .. protocols pim mvpn\")";
           junos:must-message "MVPN autodiscovery-only mode requires protocols pim mvpn configuration for the instance.";
           junos:must "(!(\".. .. .. .. .. provider-tunnel family inet pim-asm\"))";
           junos:must-message "MVPN autodiscovery-only mode requires a PIM-SSM provider-tunnel root address.";
           junos:must "((\".. .. .. .. .. provider-tunnel pim-ssm\" || \".. .. .. .. .. provider-tunnel family inet pim-ssm\"))";
           junos:must-message "MVPN autodiscovery-only mode requires a PIM-SSM provider-tunnel root address.";
           description "Use MVPN exclusively for PE router autodiscovery";
           uses apply-advanced;
           container intra-as {
             description "Intra-AS autodiscovery options";
             uses apply-advanced;
             leaf inclusive {
               description "Inclusive provider tunnel autodiscovery";
               type empty;
             }
           }
         }
         leaf disable {
           description "Disable family IPv6";
           type empty;
         }
       }
     }
     choice sender-receiver-site-choice {
       case case_1 {
         leaf receiver-site {
           description "MVPN instance has sites only with multicast receivers";
           junos:must "(!(\".. .. .. provider-tunnel\"))";
           junos:must-message "MVPN instance with only receiver sites cannot be the root of a provider-tunnel";
           type empty;
         }
       }
       case case_2 {
         leaf sender-site {
           description "MVPN instance has sites only with multicast sources";
           junos:must "(\".. .. .. provider-tunnel\")";
           junos:must-message "MVPN instance with sources must be the root of a provider-tunnel";
           type empty;
         }
       }
     }
     leaf unicast-umh-election {
       description "Upstream Multicast Hop election based on unicast route preference";
       junos:must "(!(\".. mvpn-join-load-balance\"))";
       junos:must-message "UMH election based on unicast route cannot be configured with mvpn-join-load-balance";
       junos:must "(!(\".. .. .. .. .. protocols bgp path-selection cisco-non-deterministic\"))";
       junos:must-message "Upstream Multicast Hop election cannot be used with 'protocols bgp path-selection cisco-non-deterministic'";
       type empty;
     }
     container static-umh {
       description "Upstream Multicast Hop election based on static configuration";
       uses apply-advanced;
       leaf primary {
         description "Primary Upstream Multicast Hop";
         type jt:ipv4addr;
       }
       leaf backup {
         description "Secondary Upstream Multicast Hop";
         type jt:ipv4addr;
       }
       choice source-tree_choice {
         case case_1 {
           leaf source-tree {
             description "Mandatory attribute - static-umh applies only to MVPN source-tree c-multicast joins";
             type empty;
           }
         }
       }
     }
     leaf cmcast-joins-limit-inet {
       description "Maximum number of cmcast entries for v4";
       junos:must "(\".. mvpn-mode rpt-spt\")";
       junos:must-message "Cmcast limit can only be configured for MVPN rpt-spt mode";
       type union {
         type string {
           pattern "<.*>|$.*";
         }
         type uint32 {
           range "0 .. 15000";
         }
       }
     }
     leaf cmcast-joins-limit-inet6 {
       description "Maximum number of cmcast entries for v6";
       junos:must "(\".. mvpn-mode rpt-spt\")";
       junos:must-message "Cmcastv6 limit can only be configured for MVPN rpt-spt mode";
       type union {
         type string {
           pattern "<.*>|$.*";
         }
         type uint32 {
           range "0 .. 15000";
         }
       }
     }
     container mvpn-mode {
       description "MVPN mode of operation";
       uses apply-advanced;
       choice mode {
         case case_1 {
           container rpt-spt {
             presence "enable rpt-spt";
             description "MVPN works in multicast RPT and SPT mode";
             uses apply-advanced;
             leaf spt-switch-timer {
               description "Timeout before a PE router switches between RPT and SPT";
               units "seconds";
               type union {
                 type string {
                   pattern "<.*>|$.*";
                 }
                 type uint32 {
                   range "0 .. 60";
                 }
               }
             }
           }
         }
         case case_2 {
           container spt-only {
             presence "enable spt-only";
             description "MVPN works in multicast SPT only mode (default mode)";
             uses apply-advanced;
             container source-active-advertisement {
               description "Attributes associated with advertising Source-Active A-D routes";
               uses apply-advanced;
               leaf dampen {
                 description "Time to wait before re-advertising source-active route";
                 units "minutes";
                 type union {
                   type string {
                     pattern "<.*>|$.*";
                   }
                   type uint32 {
                     range "1 .. 30";
                   }
                 }
               }
               leaf min-rate {
                 description "Minimum traffic rate required to advertise Source-Active route";
                 units "bits per second";
                 type string;
               }
             }
             leaf convert-sa-to-msdp {
               description "Turn on MVPN SA route to MSDP SA conversion";
               type empty;
             }
           }
         }
       }
     }
     container route-target {
       description "Configure route-targets for MVPN routes";
       uses apply-advanced;
       container import-target {
         description "Target communities used when importing routes";
         uses apply-advanced;
         container unicast {
           presence "enable unicast";
           description "Use the same target community as configured for unicast";
           choice receiver-sender-target-choice {
             case case_1 {
               leaf receiver {
                 description "Target community used when importing receiver site routes";
                 junos:must "(!(\".. .. .. .. receiver-site\"))";
                 junos:must-message "MVPN instance with only receivers must not import routes from other receiver only sites";
                 type empty;
               }
             }
             case case_2 {
               leaf sender {
                 description "Target community used when importing sender site routes";
                 junos:must "(!(\".. .. .. .. sender-site\"))";
                 junos:must-message "MVPN instance with only sources must not import routes from other sender only sites";
                 type empty;
               }
             }
           }
         }
         container target {
           presence "enable target";
           description "Target community";
           leaf target-value {
             type string {
               junos:posix-pattern "^[a-z]+:[0-9.]+L?:[0-9]+$";
               junos:pattern-message "Use format 'target:x:y' where 'x' is an AS number followed by an optional 'L' (To indicate 4 byte AS), or an IP address and 'y' is a number. e.g. target:123456L:100";
             }
           }
           choice receiver-sender-target-choice {
             case case_1 {
               leaf receiver {
                 description "Target community used when importing receiver site routes";
                 junos:must "(!(\".. .. .. .. receiver-site\"))";
                 junos:must-message "MVPN instance with only receivers must not import routes from other receiver only sites";
                 type empty;
               }
             }
             case case_2 {
               leaf sender {
                 description "Target community used when importing sender site routes";
                 junos:must "(!(\".. .. .. .. sender-site\"))";
                 junos:must-message "MVPN instance with only sources must not import routes from other sender only sites";
                 type empty;
               }
             }
           }
         }
       }
       container export-target {
         description "Target communities used when exporting routes";
         uses apply-advanced;
         leaf unicast {
           description "Use the same target community as configured for unicast";
           type empty;
         }
         leaf target {
           description "Target community";
           type string {
             junos:posix-pattern "^[a-z]+:[0-9.]+L?:[0-9]+$";
             junos:pattern-message "Use format 'target:x:y' where 'x' is an AS number followed by an optional 'L' (To indicate 4 byte AS), or an IP address and 'y' is a number. e.g. target:123456L:100";
           }
         }
       }
     }
     container mvpn-join-load-balance {
       junos:must "(!(\".. unicast-umh-election\"))";
       junos:must-message "MVPN join load balancing cannot be configured with unicast-umh-election";
       description "MVPN Join Load Balancing Algorithm";
       uses apply-advanced;
       choice algorithm {
         case case_1 {
           container bytewise-xor-hash {
             presence "enable bytewise-xor-hash";
             description "Upstream selection using bytewise XOR hash";
           }
         }
       }
     }
     container hot-root-standby {
       junos:must "(!(\".. .. .. instance-type mpls-internet-multicast\"))";
       junos:must-message "MVPN live-live - hot-root-standby cannot be configured in mpls-internet-multicast vrf";
       junos:must "(\".. sender-based-rpf\")";
       junos:must-message "MVPN live-live - hot-root-standby configuration needs sender-based-rpf configuration";
       description "MVPN live-live - hot root standby";
       uses apply-advanced;
       choice tree {
         case case_1 {
           container source-tree {
             presence "enable source-tree";
             description "MVPN live-live - hot root standby for source tree";
           }
         }
       }
       container min-rate {
         junos:must "(\".. .. hot-root-standby source-tree\")";
         junos:must-message "MVPN live-live - min-rate can be configured only if hot-root-standby source-tree is configured";
         description "Minimum traffic rate for the provider tunnel below which switchover is initiated (in bps)";
         uses apply-advanced;
         leaf rate {
           description "Minium traffic rate for the provider tunnel below which switchover is initiated (in bps)";
           units "bits per second";
           type string;
         }
         leaf revert-delay {
           description "Time to delay updating of multicast routes to allow for multicast convergence";
           units "seconds";
           type union {
             type string {
               pattern "<.*>|$.*";
             }
             type uint32 {
               range "0 .. 20";
             }
           }
         }
       }
     }
     container inter-region-template {
       description "MVPN inter-region tunnel mapping template";
       uses apply-advanced;
       list template {
         key name;
         ordered-by user;
         description "Define a inter-region template";
         leaf name {
           description "MVPN Template Name";
           type string;
         }
         uses apply-advanced;
         list region {
           key name;
           ordered-by user;
           description "BGP peer group names used as region";
           leaf name {
             description "Region name";
             junos:must "(\"protocols bgp group $$\")";
             junos:must-message "BGP group must be present";
             type string;
           }
           uses apply-advanced;
           choice tunnel-type {
             case case_1 {
               container rsvp-te {
                 junos:must "(\"protocols rsvp\")";
                 junos:must-message "RSVP must be configured in the master instance";
                 description "RSVP-TE point-to-multipoint LSP for flooding";
                 uses apply-advanced;
                 choice static-or-dynamic {
                   case case_1 {
                     leaf static-lsp {
                       description "Name of point-to-multipoint LSP";
                       type string {
                         junos:posix-pattern "^.{1,32}$";
                         junos:pattern-message "Must be a string of 32 characters or less";
                       }
                     }
                   }
                   case case_2 {
                     container label-switched-path-template {
                       description "Template for dynamic point-to-multipoint LSP parameters";
                       uses apply-advanced;
                       choice dynamic-template {
                         case case_1 {
                           leaf template-name {
                             description "Name of point-to-multipoint LSP template";
                             junos:must "((\"protocols mpls label-switched-path $$\" && (\"protocols mpls label-switched-path $$ template\" && \"protocols mpls label-switched-path $$ p2mp\")))";
                             junos:must-message "Referenced point-to-multipoint LSP template does not exist";
                             type string {
                               junos:posix-pattern "^.{1,32}$";
                               junos:pattern-message "Must be a string of 32 characters or less";
                             }
                           }
                         }
                         case case_2 {
                           leaf default-template {
                             description "Use default parameters";
                             type empty;
                           }
                         }
                       }
                     }
                   }
                 }
               }
             }
             case case_2 {
               container ldp-p2mp {
                 presence "enable ldp-p2mp";
                 junos:must "(\"protocols ldp p2mp\")";
                 junos:must-message "LDP P2MP must be configured in the master instance";
                 description "LDP point-to-multipoint LSP for flooding";
               }
             }
             case case_3 {
               container ingress-replication {
                 description "Ingress replication tunnel";
                 uses apply-advanced;
                 leaf create-new-ucast-tunnel {
                   description "Create new unicast tunnel for ingress replication";
                   junos:must "(\".. label-switched-path label-switched-path-template\")";
                   junos:must-message "label-switched-path-template must be defined";
                   type empty;
                 }
                 container label-switched-path {
                   presence "enable label-switched-path";
                   description "Point-to-point LSP unicast tunnel";
                   uses apply-advanced;
                   container label-switched-path-template {
                     junos:must "(\".. .. create-new-ucast-tunnel\")";
                     junos:must-message "Templates must be specified when and only when create-new-ucast-tunnel is defined";
                     description "Template for dynamic point-to-point LSP parameters";
                     uses apply-advanced;
                     choice dynamic-template {
                       case case_1 {
                         leaf template-name {
                           description "Name of point-to-point LSP template";
                           junos:must "((\"protocols mpls label-switched-path $$\" && (\"protocols mpls label-switched-path $$ template\" && !(\"protocols mpls label-switched-path $$ p2mp\"))))";
                           junos:must-message "Referenced point-to-point LSP template does not exist";
                           type string {
                             junos:posix-pattern "^.{1,32}$";
                             junos:pattern-message "Must be a string of 32 characters or less";
                           }
                         }
                       }
                       case case_2 {
                         leaf default-template {
                           description "Use default parameters";
                           type empty;
                         }
                       }
                     }
                   }
                 }
               }
             }
             case case_4 {
               leaf incoming {
                 description "Same as incoming provider tunnel";
                 type empty;
               }
             }
           }
         }
         container all-regions {
           description "Used for all regions not specified";
           uses apply-advanced;
           choice tunnel-type {
             case case_1 {
               container rsvp-te {
                 junos:must "(\"protocols rsvp\")";
                 junos:must-message "RSVP must be configured in the master instance";
                 description "RSVP-TE point-to-multipoint LSP for flooding";
                 uses apply-advanced;
                 choice static-or-dynamic {
                   case case_1 {
                     leaf static-lsp {
                       description "Name of point-to-multipoint LSP";
                       type string {
                         junos:posix-pattern "^.{1,32}$";
                         junos:pattern-message "Must be a string of 32 characters or less";
                       }
                     }
                   }
                   case case_2 {
                     container label-switched-path-template {
                       description "Template for dynamic point-to-multipoint LSP parameters";
                       uses apply-advanced;
                       choice dynamic-template {
                         case case_1 {
                           leaf template-name {
                             description "Name of point-to-multipoint LSP template";
                             junos:must "((\"protocols mpls label-switched-path $$\" && (\"protocols mpls label-switched-path $$ template\" && \"protocols mpls label-switched-path $$ p2mp\")))";
                             junos:must-message "Referenced point-to-multipoint LSP template does not exist";
                             type string {
                               junos:posix-pattern "^.{1,32}$";
                               junos:pattern-message "Must be a string of 32 characters or less";
                             }
                           }
                         }
                         case case_2 {
                           leaf default-template {
                             description "Use default parameters";
                             type empty;
                           }
                         }
                       }
                     }
                   }
                 }
               }
             }
             case case_2 {
               container ldp-p2mp {
                 presence "enable ldp-p2mp";
                 junos:must "(\"protocols ldp p2mp\")";
                 junos:must-message "LDP P2MP must be configured in the master instance";
                 description "LDP point-to-multipoint LSP for flooding";
               }
             }
             case case_3 {
               container ingress-replication {
                 description "Ingress replication tunnel";
                 uses apply-advanced;
                 leaf create-new-ucast-tunnel {
                   description "Create new unicast tunnel for ingress replication";
                   junos:must "(\".. label-switched-path label-switched-path-template\")";
                   junos:must-message "label-switched-path-template must be defined";
                   type empty;
                 }
                 container label-switched-path {
                   presence "enable label-switched-path";
                   description "Point-to-point LSP unicast tunnel";
                   uses apply-advanced;
                   container label-switched-path-template {
                     junos:must "(\".. .. create-new-ucast-tunnel\")";
                     junos:must-message "Templates must be specified when and only when create-new-ucast-tunnel is defined";
                     description "Template for dynamic point-to-point LSP parameters";
                     uses apply-advanced;
                     choice dynamic-template {
                       case case_1 {
                         leaf template-name {
                           description "Name of point-to-point LSP template";
                           junos:must "((\"protocols mpls label-switched-path $$\" && (\"protocols mpls label-switched-path $$ template\" && !(\"protocols mpls label-switched-path $$ p2mp\"))))";
                           junos:must-message "Referenced point-to-point LSP template does not exist";
                           type string {
                             junos:posix-pattern "^.{1,32}$";
                             junos:pattern-message "Must be a string of 32 characters or less";
                           }
                         }
                       }
                       case case_2 {
                         leaf default-template {
                           description "Use default parameters";
                           type empty;
                         }
                       }
                     }
                   }
                 }
               }
             }
             case case_4 {
               leaf incoming {
                 description "Same as incoming provider tunnel";
                 type empty;
               }
             }
           }
         }
       }
     }
     leaf source-redundancy {
       description "Assume all the sources for a particular group is sending same data";
       type empty;
     }
     container umh-selection-additional-input {
       description "Additional parameters to consider during UMH";
       uses apply-advanced;
       leaf source-active-preference {
         description "Use the preference set in the source active route";
         junos:must "(!(\".. .. mvpn-mode rpt-spt\"))";
         junos:must-message "Source active preference can be configured only for spt only mode";
         type empty;
       }
       leaf tunnel-status {
         description "Use the RSVP tunnel status";
         type empty;
       }
     }
   }
   grouping juniper-protocols-mvrp {
     description "MVRP Configuration";
     uses apply-advanced;
     container traceoptions {
       description "Tracing options for MVRP";
       uses mrp-trace-options;
     }
     leaf join-timer {
       description "Join timer interval";
       default "200";
       units "milliseconds";
       type union {
         type string {
           pattern "<.*>|$.*";
         }
         type uint16 {
           range "100 .. 500";
         }
       }
     }
     leaf leave-timer {
       description "Leave timer interval";
       default "800";
       units "milliseconds";
       type union {
         type string {
           pattern "<.*>|$.*";
         }
         type uint16 {
           range "300 .. 1000";
         }
       }
     }
     leaf leaveall-timer {
       description "Leaveall timer interval";
       default "10";
       units "seconds";
       type union {
         type string {
           pattern "<.*>|$.*";
         }
         type uint16 {
           range "10 .. 60";
         }
       }
     }
     leaf no-dynamic-vlan {
       description "Disable dynamic VLAN creation";
       type empty;
     }
     leaf no-attribute-length-in-pdu {
       description "No attribute length while sending pdu ";
       type empty;
     }
     leaf bpdu-destination-mac-address {
       description "Destination MAC address in the MVRP BPDUs";
       type enumeration {
         enum "provider-bridge-group" {
           description "802.1ad provider bridge group address";
         }
       }
     }
     list interface {
       key name;
       ordered-by user;
       description "Configure interface options";
       leaf name {
         description "Interface name";
         junos:must "((((\".. .. .. rstp interface $$\" || \".. .. .. rstp interface all\") && !(\".. .. .. rstp interface $$ disable\")) || ((\".. .. .. mstp interface $$\" || \".. .. .. mstp interface all\") && !(\".. .. .. mstp interface $$ disable\"))))";
         junos:must-message "rstp/mstp is not enabled on the interface, mvrp is not allowed";
         junos:must "((!(\"interfaces $$ flexible-vlan-tagging\") && (!(\"interfaces $$ vlan-tagging\") && !(\"interfaces $$ stacked-vlan-tagging\"))))";
         junos:must-message "mvrp is not supported on interfaces if flexible-vlan-tagging/vlan-tagging/stacked-vlan-tagging enabled";
         junos:must "((\"interfaces $$ unit $$={0} family ethernet-switching interface-mode trunk\" || \"interfaces $$ unit $$={0} family bridge interface-mode trunk\"))";
         junos:must-message "mvrp can be enabled only on interfaces with interface-mode trunk";
         type union {
           type jt:interface-device;
           type string {
             pattern "<.*>|$.*";
           }
         }
       }
       uses apply-advanced;
       leaf join-timer {
         description "Join timer interval";
         units "milliseconds";
         type union {
           type string {
             pattern "<.*>|$.*";
           }
           type uint16 {
             range "100 .. 500";
           }
         }
       }
       leaf leave-timer {
         description "Leave timer interval";
         units "milliseconds";
         type union {
           type string {
             pattern "<.*>|$.*";
           }
           type uint16 {
             range "300 .. 1000";
           }
         }
       }
       leaf leaveall-timer {
         description "Leaveall timer interval";
         units "seconds";
         type union {
           type string {
             pattern "<.*>|$.*";
           }
           type uint16 {
             range "10 .. 60";
           }
         }
       }
       leaf point-to-point {
         description "Port is point to point";
         type empty;
       }
       leaf registration {
         description "Registration mode";
         default "normal";
         type enumeration {
           enum "normal" {
             description "Normal registration mode";
           }
           enum "restricted" {
             description "Restricted registration mode";
           }
           enum "forbidden" {
             description "Forbidden registration mode";
           }
         }
       }
     }
   }
   grouping juniper-protocols-openflow {
     uses apply-advanced;
     list switch {
       key name;
       ordered-by user;
       description "OpenFlow switch";
       max-elements 1;
       leaf name {
         description "Switch name";
         type string {
           length "1 .. 64";
           junos:posix-pattern "^[[:alnum:]._-]+$";
           junos:pattern-message "Must be a string of alphanumericals, dashes or underscores";
         }
       }
       uses apply-advanced;
       container default-action {
         description "Action for packets that not have a matching flow entry";
         uses apply-advanced;
         choice drop-pktin {
           case case_1 {
             leaf drop {
               description "Drop all packets that do not have a matching flow entry";
               type empty;
             }
           }
           case case_2 {
             leaf packet-in {
               description "Send packets to client if no matching flow entry";
               type empty;
             }
           }
         }
       }
       list interfaces {
         key name;
         ordered-by user;
         description "Interfaces configured for use with Openflow";
         leaf name {
           description "Interface name";
           junos:must "(\"interfaces $$-IFL\")";
           junos:must-message "Interface does not exist";
           type union {
             type jt:interface-name;
             type string {
               pattern "<.*>|$.*";
             }
           }
         }
         leaf port-id {
           description "Openflow port ID";
           type union {
             type string {
               pattern "<.*>|$.*";
             }
             type int32 {
               range "1 .. 32640";
             }
           }
         }
       }
       leaf purge-flow-timer {
         description "Purge timer value for invalid flows";
         units "seconds";
         type union {
           type string {
             pattern "<.*>|$.*";
           }
           type uint32 {
             range "0 .. 300";
           }
         }
       }
       container controller {
         description "OpenFlow controller's IP address, port and protocol";
         uses apply-advanced;
         container protocol {
           description "Protocol type for controller connection";
           uses apply-advanced;
           container tcp {
             description "Set protocol type to 'TCP' (default)";
             uses apply-advanced;
             leaf port {
               description "Controller's port number (default 6633)";
               type union {
                 type string {
                   pattern "<.*>|$.*";
                 }
                 type int32 {
                   range "1024 .. 65535";
                 }
               }
             }
           }
         }
         leaf role {
           description "Controller role";
           type enumeration {
             enum "equal" {
               description "Set role to 'equal'";
             }
           }
         }
         leaf address {
           description "Controller's IPv4 address";
           type jt:ipaddr;
         }
         leaf id {
           description "Controller id";
           type union {
             type uint32;
             type string {
               pattern "<.*>|$.*";
             }
           }
         }
       }
     }
     container traceoptions {
       description "OpenFlow switch daemon trace options";
       uses apply-advanced;
       leaf no-remote-trace {
         description "Disable remote tracing";
         junos:must "(\"system tracing\")";
         junos:must-message "'no-remote-trace' is valid only when [system tracing] is configured";
         type empty;
       }
       container file {
         description "Trace file information";
         leaf filename {
           description "Name of file in which to write trace information";
           type string {
             length "1 .. 1024";
             junos:posix-pattern "![/ %]";
             junos:pattern-message "Must not contain '/', % or a space";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing flag parameters";
         leaf name {
           type enumeration {
             enum "switch" {
               description "Trace openflow switch events";
             }
             enum "configuration" {
               description "Trace openflow configuration events";
             }
             enum "flow" {
               description "Trace openflow flow events";
             }
             enum "filter" {
               description "Trace openflow filter events";
             }
             enum "function" {
               description "Trace openflow function entry/exit events";
             }
             enum "packet-io" {
               description "Trace openflow packet in/out events";
             }
             enum "statistics" {
               description "Trace openflow statistics events";
             }
             enum "interface" {
               description "Trace openflow interface events";
             }
             enum "packets" {
               description "Trace openflow packets";
             }
             enum "barrier" {
               description "Trace openflow barrier events";
             }
             enum "nh" {
               description "Trace openflow next-hop events";
             }
             enum "group" {
               description "Trace openflow group events";
             }
             enum "all" {
               description "Trace everything";
             }
           }
         }
       }
     }
   }
   grouping juniper-protocols-ospf {
     uses apply-advanced;
     list topology {
       key name;
       ordered-by user;
       description "Topology parameters";
       leaf name {
         description "Topology name";
         type string;
       }
       uses apply-advanced;
       leaf disable {
         description "Disable this topology";
         type empty;
       }
       leaf topology-id {
         description "Topology identifier";
         type union {
           type string {
             pattern "<.*>|$.*";
           }
           type uint8 {
             range "32 .. 127";
           }
         }
       }
       leaf overload {
         description "Set the overload mode (repel transit traffic)";
         type empty;
       }
       leaf rib-group {
         description "Routing table group for importing routes";
         junos:must "(\"routing-options rib-groups $$\")";
         junos:must-message "Referenced rib-group must be defined";
         type string;
       }
       container spf-options {
         description "Configure options for SPF";
         uses apply-advanced;
         container microloop-avoidance {
           junos:must "(\"protocols ospf source-packet-routing\")";
           junos:must-message "Configuration of 'protocols ospf source-packet-routing' is required";
           description "Configure microloop avoidance mechanism";
           uses apply-advanced;
           container post-convergence-path {
             presence "enable post-convergence-path";
             description "Temporarily install post-convergence path for routes potentially affected by microloops";
             uses apply-advanced;
             leaf delay {
               description "Time after which temporary post-convergence paths are removed";
               units "milliseconds";
               type union {
                 type string {
                   pattern "<.*>|$.*";
                 }
                 type uint32 {
                   range "500 .. 60000";
                 }
               }
             }
             leaf maximum-labels {
               description "Maximum number of labels installed for post-convergence paths";
               type union {
                 type string {
                   pattern "<.*>|$.*";
                 }
                 type uint32 {
                   range "2 .. 8";
                 }
               }
             }
           }
         }
         leaf delay {
           description "Time to wait before running an SPF";
           units "milliseconds";
           type union {
             type string {
               pattern "<.*>|$.*";
             }
             type uint32 {
               range "50 .. 8000";
             }
           }
         }
         leaf holddown {
           description "Time to hold down before running an SPF";
           units "milliseconds";
           type union {
             type string {
               pattern "<.*>|$.*";
             }
             type uint32 {
               range "2000 .. 20000";
             }
           }
         }
         leaf rapid-runs {
           description "Number of maximum rapid SPF runs before holddown";
           type union {
             type string {
               pattern "<.*>|$.*";
             }
             type uint32 {
               range "1 .. 10";
             }
           }
         }
         leaf no-ignore-our-externals {
           description "Do not ignore self-generated external and NSSA LSAs";
           type empty;
         }
       }
       container backup-spf-options {
         description "Configure options for backup SPF";
         uses apply-advanced;
         container remote-backup-calculation {
           presence "enable remote-backup-calculation";
           junos:must "(!(\"protocols ospf backup-spf-options use-post-convergence-lfa\"))";
           junos:must-message "Not allowed with 'protocols ospf backup-spf-options use-post-convergence-lfa'";
           description "Calculate Remote LFA backup nexthops";
           uses apply-advanced;
           container pq-nodes-nearest-to-source {
             description "PQ nodes selection based upon nearest to source";
             uses apply-advanced;
             leaf percent {
               description "Selection percentage for nearest to source";
               type union {
                 type string {
                   pattern "<.*>|$.*";
                 }
                 type uint32 {
                   range "10 .. 100";
                 }
               }
             }
           }
         }
         container use-post-convergence-lfa {
           presence "enable use-post-convergence-lfa";
           junos:must "(\"protocols ospf source-packet-routing\")";
           junos:must-message "Configuration of 'protocols ospf source-packet-routing' is required";
           description "Calculate post-convergence backup paths";
           uses apply-advanced;
           leaf maximum-labels {
             description "Maximum number of labels installed for post-convergence paths";
             type union {
               type string {
                 pattern "<.*>|$.*";
               }
               type uint32 {
                 range "2 .. 8";
               }
             }
           }
           leaf maximum-backup-paths {
             description "Maximum number of equal-cost post-convergence paths installed";
             type union {
               type string {
                 pattern "<.*>|$.*";
               }
               type uint32 {
                 range "1 .. 8";
               }
             }
           }
         }
         leaf use-source-packet-routing {
           description "Use spring backup paths for inet.0 routes";
           junos:must "(\".. .. source-packet-routing\")";
           junos:must-message "Configuration of 'protocols ospf source-packet-routing' is required";
           junos:must "(!(\".. remote-backup-calculation\"))";
           junos:must-message "Not allowed with 'protocols ospf backup-spf-options remote-backup-calculation'";
           type empty;
         }
         leaf disable {
           description "Do not run backup SPF";
           junos:must "(!(\"protocols ospf backup-spf-options use-post-convergence-lfa\"))";
           junos:must-message "Not allowed with 'protocols ospf backup-spf-options use-post-convergence-lfa'";
           type empty;
         }
         leaf no-install {
           description "Do not install backup nexthops into the RIB";
           type empty;
         }
         leaf downstream-paths-only {
           description "Use only downstream backup paths";
           junos:must "(!(\"protocols ospf backup-spf-options use-post-convergence-lfa\"))";
           junos:must-message "Not allowed with 'protocols ospf backup-spf-options use-post-convergence-lfa'";
           type empty;
         }
         container per-prefix-calculation {
           junos:must "(!(\"protocols ospf backup-spf-options use-post-convergence-lfa\"))";
           junos:must-message "Not allowed with 'protocols ospf backup-spf-options use-post-convergence-lfa'";
           description "Calculate backup nexthops for non-best prefix originators";
           uses apply-advanced;
           leaf stubs {
             description "Per prefix calculation for stubs only";
             type empty;
           }
           leaf summary {
             description "Per prefix calculation for summary originators only";
             type empty;
           }
           leaf externals {
             description "Per prefix calculation for externals";
             type empty;
           }
           leaf all {
             description "Per prefix calculation for all";
             type empty;
           }
         }
         leaf node-link-degradation {
           description "Degrade to link protection when nodelink protection not available";
           junos:must "(!(\"protocols ospf backup-spf-options use-post-convergence-lfa\"))";
           junos:must-message "Not allowed with 'protocols ospf backup-spf-options use-post-convergence-lfa'";
           type empty;
         }
       }
       leaf prefix-export-limit {
         description "Maximum number of prefixes that can be exported";
         type union {
           type string {
             pattern "<.*>|$.*";
           }
           type uint32 {
             range "0 .. 4294967295";
           }
         }
       }
     }
     container spf-options {
       description "Configure options for SPF";
       uses apply-advanced;
       container microloop-avoidance {
         junos:must "(\"protocols ospf source-packet-routing\")";
         junos:must-message "Configuration of 'protocols ospf source-packet-routing' is required";
         description "Configure microloop avoidance mechanism";
         uses apply-advanced;
         container post-convergence-path {
           presence "enable post-convergence-path";
           description "Temporarily install post-convergence path for routes potentially affected by microloops";
           uses apply-advanced;
           leaf delay {
             description "Time after which temporary post-convergence paths are removed";
             units "milliseconds";
             type union {
               type string {
                 pattern "<.*>|$.*";
               }
               type uint32 {
                 range "500 .. 60000";
               }
             }
           }
           leaf maximum-labels {
             description "Maximum number of labels installed for post-convergence paths";
             type union {
               type string {
                 pattern "<.*>|$.*";
               }
               type uint32 {
                 range "2 .. 8";
               }
             }
           }
         }
       }
       leaf delay {
         description "Time to wait before running an SPF";
         units "milliseconds";
         type union {
           type string {
             pattern "<.*>|$.*";
           }
           type uint32 {
             range "50 .. 8000";
           }
         }
       }
       leaf holddown {
         description "Time to hold down before running an SPF";
         units "milliseconds";
         type union {
           type string {
             pattern "<.*>|$.*";
           }
           type uint32 {
             range "2000 .. 20000";
           }
         }
       }
       leaf rapid-runs {
         description "Number of maximum rapid SPF runs before holddown";
         type union {
           type string {
             pattern "<.*>|$.*";
           }
           type uint32 {
             range "1 .. 10";
           }
         }
       }
       leaf no-ignore-our-externals {
         description "Do not ignore self-generated external and NSSA LSAs";
         type empty;
       }
     }
     container backup-spf-options {
       description "Configure options for backup SPF";
       uses apply-advanced;
       container remote-backup-calculation {
         presence "enable remote-backup-calculation";
         junos:must "(!(\"protocols ospf backup-spf-options use-post-convergence-lfa\"))";
         junos:must-message "Not allowed with 'protocols ospf backup-spf-options use-post-convergence-lfa'";
         description "Calculate Remote LFA backup nexthops";
         uses apply-advanced;
         container pq-nodes-nearest-to-source {
           description "PQ nodes selection based upon nearest to source";
           uses apply-advanced;
           leaf percent {
             description "Selection percentage for nearest to source";
             type union {
               type string {
                 pattern "<.*>|$.*";
               }
               type uint32 {
                 range "10 .. 100";
               }
             }
           }
         }
       }
       container use-post-convergence-lfa {
         presence "enable use-post-convergence-lfa";
         junos:must "(\"protocols ospf source-packet-routing\")";
         junos:must-message "Configuration of 'protocols ospf source-packet-routing' is required";
         description "Calculate post-convergence backup paths";
         uses apply-advanced;
         leaf maximum-labels {
           description "Maximum number of labels installed for post-convergence paths";
           type union {
             type string {
               pattern "<.*>|$.*";
             }
             type uint32 {
               range "2 .. 8";
             }
           }
         }
         leaf maximum-backup-paths {
           description "Maximum number of equal-cost post-convergence paths installed";
           type union {
             type string {
               pattern "<.*>|$.*";
             }
             type uint32 {
               range "1 .. 8";
             }
           }
         }
       }
       leaf use-source-packet-routing {
         description "Use spring backup paths for inet.0 routes";
         junos:must "(\".. .. source-packet-routing\")";
         junos:must-message "Configuration of 'protocols ospf source-packet-routing' is required";
         junos:must "(!(\".. remote-backup-calculation\"))";
         junos:must-message "Not allowed with 'protocols ospf backup-spf-options remote-backup-calculation'";
         type empty;
       }
       leaf disable {
         description "Do not run backup SPF";
         junos:must "(!(\"protocols ospf backup-spf-options use-post-convergence-lfa\"))";
         junos:must-message "Not allowed with 'protocols ospf backup-spf-options use-post-convergence-lfa'";
         type empty;
       }
       leaf no-install {
         description "Do not install backup nexthops into the RIB";
         type empty;
       }
       leaf downstream-paths-only {
         description "Use only downstream backup paths";
         junos:must "(!(\"protocols ospf backup-spf-options use-post-convergence-lfa\"))";
         junos:must-message "Not allowed with 'protocols ospf backup-spf-options use-post-convergence-lfa'";
         type empty;
       }
       container per-prefix-calculation {
         junos:must "(!(\"protocols ospf backup-spf-options use-post-convergence-lfa\"))";
         junos:must-message "Not allowed with 'protocols ospf backup-spf-options use-post-convergence-lfa'";
         description "Calculate backup nexthops for non-best prefix originators";
         uses apply-advanced;
         leaf stubs {
           description "Per prefix calculation for stubs only";
           type empty;
         }
         leaf summary {
           description "Per prefix calculation for summary originators only";
           type empty;
         }
         leaf externals {
           description "Per prefix calculation for externals";
           type empty;
         }
         leaf all {
           description "Per prefix calculation for all";
           type empty;
         }
       }
       leaf node-link-degradation {
         description "Degrade to link protection when nodelink protection not available";
         junos:must "(!(\"protocols ospf backup-spf-options use-post-convergence-lfa\"))";
         junos:must-message "Not allowed with 'protocols ospf backup-spf-options use-post-convergence-lfa'";
         type empty;
       }
     }
     container traffic-engineering {
       presence "enable traffic-engineering";
       description "Configure traffic engineering attributes";
       uses apply-advanced;
       leaf no-topology {
         description "Disable dissemination of TE link-state topology information";
         type empty;
       }
       leaf multicast-rpf-routes {
         description "Install routes for multicast RPF checks into inet.2";
         junos:must "(!(\".. .. topology $$={ipv4-multicast}\"))";
         junos:must-message "multicast-rpf-routes cannot be used with topology ipv4-multicast";
         junos:must "(\".. shortcuts\")";
         junos:must-message "multicast-rpf-routes cannot be used without shortcuts";
         type empty;
       }
       leaf l3-unicast-topology {
         description "Download IGP topology into TED";
         type empty;
       }
       container ignore-lsp-metrics {
         presence "enable ignore-lsp-metrics";
         description "Ignore label-switched path metrics when doing shortcuts";
         uses apply-advanced;
         leaf unconfigured-only {
           description "Ignore lsp metrics for unconfigured only";
           type empty;
         }
       }
       container shortcuts {
         presence "enable shortcuts";
         description "Use label-switched paths as next hops, if possible";
         uses apply-advanced;
         leaf ignore-lsp-metrics {
           description "Ignore label-switched path metrics when doing shortcuts";
           status deprecated;
           type empty;
         }
         leaf lsp-metric-into-summary {
           description "Advertise LSP metric into summary LSAs";
           type empty;
         }
         list family {
           key name;
           ordered-by user;
           description "Address family specific traffic-engineering attributes";
           leaf name {
             type enumeration {
               enum "inet" {
                 description "IPv4 family";
               }
               enum "inet-mpls" {
                 description "IPv4-MPLS family";
               }
             }
           }
           uses apply-advanced;
         }
       }
       leaf advertise-unnumbered-interfaces {
         description "Advertise unnumbered interfaces";
         type empty;
       }
       leaf credibility-protocol-preference {
         description "TED protocol credibility follows protocol preference";
         type empty;
       }
       container advertisement {
         description "Advertise TE parameters even if RSVP is not turned on";
         uses apply-advanced;
         leaf always {
           description "Advertise TE parameters in TE LSAs";
           type empty;
         }
       }
     }
     container source-packet-routing {
       presence "enable source-packet-routing";
       junos:must "(!(\".. .. .. protocols mpls disable\"))";
       junos:must-message "SPRING configuration is not allowed with 'protocols mpls disable'";
       junos:must "(\".. .. .. protocols mpls \")";
       junos:must-message "SPRING configuration is not allowed without 'protocols mpls'";
       description "Enable source packet routing (SPRING)";
       uses apply-advanced;
       container adjacency-segment {
         description "Attributes for adjacency segments in spring";
         uses apply-advanced;
         leaf hold-time {
           description "Retain time of Adjacency segment after isolating from an interface";
           type union {
             type string {
               pattern "<.*>|$.*";
             }
             type uint32 {
               range "180000 .. 900000";
             }
           }
         }
       }
       leaf-list prefix-segment {
         ordered-by user;
         description "Prefix Segment policy";
         type jt:policy-algebra;
       }
       leaf explicit-null {
         description "Set E and P bits in all Prefix SID advertisements";
         type empty;
       }
       container node-segment {
         presence "enable node-segment";
         description "Enable support for Node segments in SPRING";
         uses apply-advanced;
         leaf ipv4-index {
           description "Set ipv4 node segment index";
           type union {
             type string {
               pattern "<.*>|$.*";
             }
             type uint32 {
               range "0 .. 199999";
             }
           }
         }
         leaf index-range {
           description "Set range of node segment indices allowed";
           type union {
             type string {
               pattern "<.*>|$.*";
             }
             type uint32 {
               range "32 .. 16385";
             }
           }
         }
       }
       container srgb {
         junos:must "(!(\".. node-segment index-range\"))";
         junos:must-message "Can not be configured with node-segment index-range";
         description "Set the SRGB global block in SPRING";
         leaf start-label {
           description "Start range for SRGB label block";
           type union {
             type string {
               pattern "<.*>|$.*";
             }
             type uint32;
           }
         }
         leaf index-range {
           description "Index to the SRGB start label block";
           type union {
             type string {
               pattern "<.*>|$.*";
             }
             type uint32;
           }
         }
       }
       leaf mapping-server {
         description "Mapping server name";
         junos:must "(\".. node-segment\")";
         junos:must-message "protocols ospf source-packet-routing node-segment must be defined";
         junos:must "(\"routing-options source-packet-routing mapping-server-entry $$\")";
         junos:must-message "Referenced source-packet-routing mapping-server-entry must be defined";
         type string;
       }
       leaf install-prefix-sid-for-best-route {
         description "For best route install a exact prefix sid route";
         type empty;
       }
       leaf ldp-stitching {
         description "Enable SR to LDP stitching";
         type empty;
       }
       leaf-list flex-algorithm {
         description "Flex-algorithms we would like to participate in";
         type union {
           type string {
             pattern "<.*>|$.*";
           }
           type uint32 {
             range "128 .. 255";
           }
         }
         max-elements 16;
       }
       leaf strict-asla-based-flex-algorithm {
         description "Flex-Algorithm to ignore links not having ASLA sub-TLVs";
         type empty;
       }
     }
     list area {
       key name;
       ordered-by user;
       description "Configure an OSPF area";
       leaf name {
         description "Area ID";
         type jt:areaid;
       }
       uses apply-advanced;
       choice stub-option {
         case case_1 {
           container stub {
             presence "enable stub";
             description "Configure a stub area";
             leaf default-metric {
               description "Metric for the default route in this stub area";
               type union {
                 type string {
                   pattern "<.*>|$.*";
                 }
                 type uint32 {
                   range "1 .. 16777215";
                 }
               }
             }
             choice summaries-choice {
               leaf summaries {
                 description "Flood summary LSAs into this stub area";
                 type empty;
               }
               leaf no-summaries {
                 description "Don't flood summary LSAs into this stub area";
                 type empty;
               }
             }
           }
         }
         case case_2 {
           container nssa {
             presence "enable nssa";
             description "Configure a not-so-stubby area";
             uses apply-advanced;
             container default-lsa {
               presence "enable default-lsa";
               description "Configure a default LSA";
               uses apply-advanced;
               leaf default-metric {
                 description "Metric for the default route in this area";
                 type union {
                   type string {
                     pattern "<.*>|$.*";
                   }
                   type uint32 {
                     range "1 .. 16777215";
                   }
                 }
               }
               leaf metric-type {
                 description "External metric type for the default type 7 LSA";
                 type union {
                   type string {
                     pattern "<.*>|$.*";
                   }
                   type uint32 {
                     range "1 .. 2";
                   }
                 }
               }
               leaf type-7 {
                 description "Flood type 7 default LSA if no-summaries is configured";
                 type empty;
               }
             }
             leaf default-metric {
               description "Metric for the default route in this area";
               status deprecated;
               type union {
                 type string {
                   pattern "<.*>|$.*";
                 }
                 type uint32 {
                   range "1 .. 16777215";
                 }
               }
             }
             leaf metric-type {
               description "External metric type for the default type 7 LSA";
               status deprecated;
               type union {
                 type string {
                   pattern "<.*>|$.*";
                 }
                 type uint32 {
                   range "1 .. 2";
                 }
               }
             }
             choice summaries-choice {
               leaf summaries {
                 description "Flood summary LSAs into this NSSA area";
                 type empty;
               }
               leaf no-summaries {
                 description "Don't flood summary LSAs into this NSSA area";
                 type empty;
               }
             }
             list area-range {
               key name;
               ordered-by user;
               description "Configure NSSA area ranges";
               leaf name {
                 description "Range to summarize NSSA routes in this area";
                 type jt:ipprefix;
               }
               uses apply-advanced;
               leaf restrict {
                 description "Restrict advertisement of this area range";
                 type empty;
               }
               leaf exact {
                 description "Enforce exact match for advertisement of this area range";
                 type empty;
               }
               container override-metric {
                 presence "enable override-metric";
                 description "Override the dynamic metric for this area-range";
                 uses apply-advanced;
                 leaf metric {
                   description "Metric value";
                   type union {
                     type string {
                       pattern "<.*>|$.*";
                     }
                     type uint32 {
                       range "1 .. 16777215";
                     }
                   }
                 }
                 leaf metric-type {
                   description "Set the metric type for the override metric";
                   default "1";
                   type union {
                     type string {
                       pattern "<.*>|$.*";
                     }
                     type uint32 {
                       range "1 .. 2";
                     }
                   }
                 }
               }
             }
           }
         }
       }
       list area-range {
         key name;
         ordered-by user;
         description "Configure area ranges";
         leaf name {
           description "Range to summarize routes in this area";
           type jt:ipprefix;
         }
         uses apply-advanced;
         leaf restrict {
           description "Restrict advertisement of this area range";
           type empty;
         }
         leaf exact {
           description "Enforce exact match for advertisement of this area range";
           type empty;
         }
         leaf override-metric {
           description "Override the dynamic metric for this area-range";
           type union {
             type string {
               pattern "<.*>|$.*";
             }
             type uint32 {
               range "1 .. 16777215";
             }
           }
         }
       }
       leaf-list network-summary-export {
         ordered-by user;
         description "Export policy for Type 3 Summary LSAs";
         type jt:policy-algebra;
       }
       leaf-list network-summary-import {
         ordered-by user;
         description "Import policy for Type 3 Summary LSAs";
         type jt:policy-algebra;
       }
       leaf-list inter-area-prefix-export {
         ordered-by user;
         description "Export policy for Inter Area Prefix LSAs";
         type jt:policy-algebra;
       }
       leaf-list inter-area-prefix-import {
         ordered-by user;
         description "Import policy for Inter Area Prefix LSAs";
         type jt:policy-algebra;
       }
       leaf authentication-type {
         description "Authentication type";
         status deprecated;
         type enumeration {
           enum "none" {
             description "No authentication";
             status deprecated;
           }
           enum "simple" {
             description "Simple password authentication";
             status deprecated;
           }
           enum "md5" {
             description "MD5 authentication";
             status deprecated;
           }
         }
       }
       list virtual-link {
         key "neighbor-id transit-area";
         ordered-by user;
         description "Configure virtual links";
         junos:must "(\".. .. area $$={0.0.0.0}\")";
         junos:must-message "virtual link can be configured only under backbone area";
         leaf neighbor-id {
           description "Router ID of a virtual neighbor";
           type jt:ipv4addr;
         }
         leaf transit-area {
           description "Transit area in common with virtual neighbor";
           type jt:areaid;
         }
         uses apply-advanced;
         choice enable-disable {
           case case_1 {
             leaf disable {
               description "Disable this virtual link";
               type empty;
             }
           }
         }
         leaf retransmit-interval {
           description "Retransmission interval (seconds)";
           type union {
             type string {
               pattern "<.*>|$.*";
             }
             type uint32 {
               range "1 .. 65535";
             }
           }
         }
         leaf transit-delay {
           description "Transit delay (seconds)";
           type union {
             type string {
               pattern "<.*>|$.*";
             }
             type uint32 {
               range "1 .. 65535";
             }
           }
         }
         leaf hello-interval {
           description "Hello interval (seconds)";
           type union {
             type string {
               pattern "<.*>|$.*";
             }
             type uint32 {
               range "1 .. 255";
             }
           }
         }
         leaf dead-interval {
           description "Dead interval (seconds)";
           type union {
             type string {
               pattern "<.*>|$.*";
             }
             type uint32 {
               range "1 .. 65535";
             }
           }
         }
         leaf mtu {
           description "Maximum OSPF packet size";
           type union {
             type string {
               pattern "<.*>|$.*";
             }
             type uint32 {
               range "128 .. 65535";
             }
           }
         }
         choice auth {
           case case_1 {
             container authentication {
               uses juniper-ospf-authentication;
             }
           }
           case case_2 {
             container authentication-key {
               description "Authentication key";
               status deprecated;
               leaf keyname {
                 description "Authentication key value";
                 type jt:unreadable;
               }
               leaf key-id {
                 description "Key ID for MD5 authentication";
                 type union {
                   type string {
                     pattern "<.*>|$.*";
                   }
                   type uint32 {
                     range "0 .. 255";
                   }
                 }
               }
             }
           }
         }
         leaf demand-circuit {
           description "Interface functions as a demand circuit";
           type empty;
         }
         leaf flood-reduction {
           description "Enable flood reduction";
           type empty;
         }
         leaf no-neighbor-down-notification {
           description "Don't inform other protocols about neighbor down events";
           type empty;
         }
         leaf ipsec-sa {
           description "IPSec security association name";
           junos:must "(!(any \".. .. interface <st*> ipsec-sa $$\"))";
           junos:must-message "Must not configure ipsec-sa for st0 interface";
           junos:must "(\"security ipsec security-association $$ manual\")";
           junos:must-message "Referenced IPSec security association must be a manual SA";
           junos:must "(\"security ipsec security-association $$ mode transport\")";
           junos:must-message "Referenced IPSec security association must be in transport mode";
           junos:must "(\"security ipsec security-association $$\")";
           junos:must-message "Referenced IPSec security association must be defined";
           type string {
             length "1 .. 32";
           }
         }
         list topology {
           key name;
           ordered-by user;
           description "Topology specific attributes";
           leaf name {
             description "Topology name";
             type string;
           }
           uses apply-advanced;
           leaf disable {
             description "Disable this topology";
             type empty;
           }
           leaf metric {
             description "Topology metric";
             type union {
               type string {
                 pattern "<.*>|$.*";
               }
               type uint16 {
                 range "1 .. 65535";
               }
             }
           }
           container bandwidth-based-metrics {
             junos:must "(\".. metric\")";
             junos:must-message "Metric must be configured";
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint16 {
                     range "1 .. 65535";
                   }
                 }
               }
             }
           }
         }
       }
       list sham-link-remote {
         key name;
         ordered-by user;
         description "Configure parameters for remote sham link endpoint";
         leaf name {
           description "Remote sham link endpoint address";
           junos:must "(!(\".. .. .. sham-link local $$\"))";
           junos:must-message "Local and remote sham link endpoint addresses must be different";
           junos:must "(\".. .. .. sham-link local\")";
           junos:must-message "Local sham link endpoint must be configured";
           type jt:ipaddr;
         }
         uses apply-advanced;
         leaf metric {
           description "Sham link metric";
           type union {
             type string {
               pattern "<.*>|$.*";
             }
             type uint16 {
               range "1 .. 65535";
             }
           }
         }
         leaf ipsec-sa {
           description "IPSec security association name";
           junos:must "(!(any \".. .. interface <st*> ipsec-sa $$\"))";
           junos:must-message "Must not configure ipsec-sa for st0 interface";
           junos:must "(\"security ipsec security-association $$ manual\")";
           junos:must-message "Referenced IPSec security association must be a manual SA";
           junos:must "(\"security ipsec security-association $$ mode transport\")";
           junos:must-message "Referenced IPSec security association must be in transport mode";
           junos:must "(\"security ipsec security-association $$\")";
           junos:must-message "Referenced IPSec security association must be defined";
           type string {
             length "1 .. 32";
           }
         }
         leaf demand-circuit {
           description "Interface functions as a demand circuit";
           type empty;
         }
         leaf flood-reduction {
           description "Enable flood reduction";
           type empty;
         }
         list topology {
           key name;
           ordered-by user;
           description "Topology specific attributes";
           leaf name {
             description "Topology name";
             type string;
           }
           uses apply-advanced;
           leaf disable {
             description "Disable this topology";
             type empty;
           }
           leaf metric {
             description "Topology metric";
             type union {
               type string {
                 pattern "<.*>|$.*";
               }
               type uint16 {
                 range "1 .. 65535";
               }
             }
           }
           container bandwidth-based-metrics {
             junos:must "(\".. metric\")";
             junos:must-message "Metric must be configured";
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint16 {
                     range "1 .. 65535";
                   }
                 }
               }
             }
           }
         }
       }
       list interface {
         key name;
         ordered-by user;
         description "Include an interface in this area";
         leaf name {
           description "Interface name";
           junos:must "((!(\".. interface-type nbma\") || (!((\"interfaces $$\" || any \"logical-systems <*> interfaces $$\")) || (any \"interfaces $$-IFL family inet address <*>\" || any \"logical-systems <*> interfaces $$-IFL family inet address <*>\"))))";
           junos:must-message "IPv4 address must be configured on the interface for nbma mode";
           type union {
             type jt:ipv4addr-or-interface;
             type string {
               pattern "<.*>|$.*";
             }
           }
         }
         uses apply-advanced;
         choice enable-disable {
           case case_1 {
             leaf disable {
               description "Disable OSPF on this interface";
               type empty;
             }
           }
         }
         leaf interface-type {
           description "Type of interface";
           type enumeration {
             enum "nbma" {
               description "Nonbroadcast multiaccess";
             }
             enum "p2mp" {
               description "Point-to-multipoint NBMA";
             }
             enum "p2p" {
               description "Point-to-point";
             }
             enum "p2mp-over-lan" {
               description "Point-to-multipoint over LAN mode";
             }
           }
         }
         choice protection-type {
           case case_1 {
             leaf link-protection {
               description "Protect interface from link faults only";
               type empty;
             }
           }
           case case_2 {
             leaf node-link-protection {
               description "Protect interface from both link and node faults";
               type empty;
             }
           }
         }
         leaf no-eligible-backup {
           description "Not eligible to backup traffic from protected interfaces";
           type empty;
         }
         leaf no-eligible-remote-backup {
           description "Not eligible for Remote-LFA backup traffic from protected interfaces";
           type empty;
         }
         container passive {
           presence "enable passive";
           description "Do not run OSPF, but advertise it";
           uses apply-advanced;
           container traffic-engineering {
             description "Advertise TE link information";
             uses apply-advanced;
             leaf remote-node-id {
               description "Remote address of the link";
               type jt:ipaddr;
             }
             leaf remote-node-router-id {
               description "TE Router-ID of the remote node";
               junos:must "(\".. remote-node-id\")";
               junos:must-message "remote-node-id must be configured";
               type jt:ipv4addr;
             }
           }
         }
         leaf secondary {
           description "Treat interface as secondary";
           junos:must "(!(\" .. ipsec-sa\"))";
           junos:must-message "secondary interface cannot have ipsec-sa configured";
           junos:must "(!(\" .. dynamic-neighbors\"))";
           junos:must-message "secondary interface cannot have dynamic-neighbors configured";
           junos:must "(!(\" .. neighbor\"))";
           junos:must-message "secondary interface cannot have configured neighbors";
           junos:must "(!(\" .. interface-type p2mp\"))";
           junos:must-message "secondary interface cannot be set as type p2mp";
           junos:must "(!(\" .. interface-type nbma\"))";
           junos:must-message "secondary interface cannot be set as type nbma";
           junos:must "(!(\" .. passive\"))";
           junos:must-message "secondary interface cannot be configured passive";
           type empty;
         }
         leaf own-router-lsa {
           description "Generate a separate router LSA for this interface";
           type empty;
         }
         container bandwidth-based-metrics {
           junos:must "(\".. metric\")";
           junos:must-message "Metric must be configured";
           description "Configure bandwidth based metrics";
           uses apply-advanced;
           list bandwidth {
             key name;
             description "Bandwidth threshold";
             leaf name {
               type string;
             }
             leaf metric {
               description "Metric associated with specified bandwidth";
               type union {
                 type string {
                   pattern "<.*>|$.*";
                 }
                 type uint16 {
                   range "1 .. 65535";
                 }
               }
             }
           }
         }
         leaf metric {
           description "Interface metric";
           type union {
             type string {
               pattern "<.*>|$.*";
             }
             type uint16 {
               range "1 .. 65535";
             }
           }
         }
         leaf priority {
           description "Designated router priority";
           type union {
             type string {
               pattern "<.*>|$.*";
             }
             type uint32 {
               range "0 .. 255";
             }
           }
         }
         leaf retransmit-interval {
           description "Retransmission interval (seconds)";
           type union {
             type string {
               pattern "<.*>|$.*";
             }
             type uint32 {
               range "1 .. 65535";
             }
           }
         }
         leaf transit-delay {
           description "Transit delay (seconds)";
           type union {
             type string {
               pattern "<.*>|$.*";
             }
             type uint32 {
               range "1 .. 65535";
             }
           }
         }
         leaf hello-interval {
           description "Hello interval (seconds)";
           type union {
             type string {
               pattern "<.*>|$.*";
             }
             type uint32 {
               range "1 .. 255";
             }
           }
         }
         leaf dead-interval {
           description "Dead interval (seconds)";
           type union {
             type string {
               pattern "<.*>|$.*";
             }
             type uint32 {
               range "1 .. 65535";
             }
           }
         }
         leaf mtu {
           description "Maximum OSPF packet size";
           type union {
             type string {
               pattern "<.*>|$.*";
             }
             type uint32 {
               range "128 .. 65535";
             }
           }
         }
         choice auth {
           case case_1 {
             container authentication {
               uses juniper-ospf-authentication;
             }
           }
           case case_2 {
             container authentication-key {
               description "Authentication key";
               status deprecated;
               leaf keyname {
                 description "Authentication key value";
                 type jt:unreadable;
               }
               leaf key-id {
                 description "Key ID for MD5 authentication";
                 type union {
                   type string {
                     pattern "<.*>|$.*";
                   }
                   type uint32 {
                     range "0 .. 255";
                   }
                 }
               }
             }
           }
         }
         leaf demand-circuit {
           description "Interface functions as a demand circuit";
           type empty;
         }
         leaf flood-reduction {
           description "Enable flood reduction";
           type empty;
         }
         leaf no-neighbor-down-notification {
           description "Don't inform other protocols about neighbor down events";
           type empty;
         }
         leaf ipsec-sa {
           description "IPSec security association name";
           junos:must "(!(any \".. .. interface <st*> ipsec-sa $$\"))";
           junos:must-message "Must not configure ipsec-sa for st0 interface";
           junos:must "(\"security ipsec security-association $$ manual\")";
           junos:must-message "Referenced IPSec security association must be a manual SA";
           junos:must "(\"security ipsec security-association $$ mode transport\")";
           junos:must-message "Referenced IPSec security association must be in transport mode";
           junos:must "(\"security ipsec security-association $$\")";
           junos:must-message "Referenced IPSec security association must be defined";
           type string {
             length "1 .. 32";
           }
         }
         list topology {
           key name;
           ordered-by user;
           description "Topology specific attributes";
           leaf name {
             description "Topology name";
             type string;
           }
           uses apply-advanced;
           leaf disable {
             description "Disable this topology";
             type empty;
           }
           leaf metric {
             description "Topology metric";
             type union {
               type string {
                 pattern "<.*>|$.*";
               }
               type uint16 {
                 range "1 .. 65535";
               }
             }
           }
           container bandwidth-based-metrics {
             junos:must "(\".. metric\")";
             junos:must-message "Metric must be configured";
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint16 {
                     range "1 .. 65535";
                   }
                 }
               }
             }
           }
         }
         leaf transmit-interval {
           description "OSPF packet transmit interval (milliseconds)";
           status deprecated;
           type union {
             type string {
               pattern "<.*>|$.*";
             }
             type uint32 {
               range "1 .. 4294967295";
             }
           }
         }
         container bfd-liveness-detection {
           description "Bidirectional Forwarding Detection options";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
           container authentication {
             description "Authentication options";
             uses apply-advanced;
             leaf key-chain {
               description "Key chain name";
               junos:must "(\".. algorithm\")";
               junos:must-message "May not be configured without algorithm";
               junos:must "(\"security authentication-key-chains key-chain $$\")";
               junos:must-message "Referenced key-chain must be defined";
               type string;
             }
             leaf algorithm {
               description "Algorithm name";
               junos:must "(\".. key-chain\")";
               junos:must-message "May not be configured without key-chain";
               type enumeration {
                 enum "simple-password" {
                   description "Simple password";
                 }
                 enum "keyed-md5" {
                   description "Keyed message Digest 5";
                 }
                 enum "meticulous-keyed-md5" {
                   description "Meticulous keyed message Digest 5";
                 }
                 enum "keyed-sha-1" {
                   description "Keyed secure hash algorithm (SHA1) ";
                 }
                 enum "meticulous-keyed-sha-1" {
                   description "Meticulous keyed secure hash algorithm (SHA1) ";
                 }
               }
             }
             leaf loose-check {
               description "Verify authentication only if authentication is negotiated";
               type empty;
             }
           }
           leaf full-neighbors-only {
             description "Setup BFD sessions only to Full neighbors";
             type empty;
           }
           leaf holddown-interval {
             description "Time to hold the session-UP notification to the client";
             units "milliseconds";
             type union {
               type string {
                 pattern "<.*>|$.*";
               }
               type uint32 {
                 range "0 .. 255000";
               }
             }
           }
         }
         leaf dynamic-neighbors {
           description "Learn neighbors dynamically on a p2mp interface";
           junos:must "(\" .. interface-type p2mp\")";
           junos:must-message "dynamic-neighbors option can be set only if the interface type is p2mp";
           type empty;
         }
         leaf no-advertise-adjacency-segment {
           description "Do not advertise an adjacency segment for this interface";
           type empty;
         }
         list neighbor {
           key name;
           ordered-by user;
           description "NBMA neighbor";
           junos:must "(!(\" .. dynamic-neighbors\"))";
           junos:must-message "Neighbors cannot be specified manually if dynamic-neighbors is set";
           leaf name {
             description "Address of neighbor";
             type jt:ipaddr;
           }
           leaf eligible {
             description "Eligible to be DR on an NBMA network";
             type empty;
           }
         }
         leaf poll-interval {
           description "Poll interval for NBMA interfaces";
           type union {
             type string {
               pattern "<.*>|$.*";
             }
             type uint32 {
               range "1 .. 65535";
             }
           }
         }
         leaf no-interface-state-traps {
           description "Do not send interface state change traps";
           type empty;
         }
         leaf strict-bfd {
           description "Enable strict bfd over this interface";
           junos:must "(\" .. bfd-liveness-detection\")";
           junos:must-message "strict bfd cannot be configured without bfd.";
           junos:must "(!(\" .. bfd-liveness-detection full-neighbors-only\"))";
           junos:must-message "full-neighbors-only and strict-bfd cannot be configured together";
           type empty;
         }
         container post-convergence-lfa {
           presence "enable post-convergence-lfa";
           junos:must "(\"protocols ospf backup-spf-options use-post-convergence-lfa\")";
           junos:must-message "Not allowed without 'protocols ospf backup-spf-options use-post-convergence-lfa'";
           description "Protect interface using post-convergence backup path";
           uses apply-advanced;
           container node-protection {
             presence "enable node-protection";
             description "Compute backup path assuming node failure";
             uses apply-advanced;
             leaf cost {
               description "Cost for node protection";
               type union {
                 type string {
                   pattern "<.*>|$.*";
                 }
                 type uint16 {
                   range "1 .. 65535";
                 }
               }
             }
           }
           leaf srlg-protection {
             description "Compute backup path assuming SRLG failure";
             type empty;
           }
           leaf fate-sharing-protection {
             description "Compute backup path assuming fate-sharing group failure";
             type empty;
           }
         }
         leaf te-metric {
           description "Traffic engineering metric";
           type union {
             type string {
               pattern "<.*>|$.*";
             }
             type uint32 {
               range "1 .. 4294967295";
             }
           }
         }
         container ldp-synchronization {
           description "Advertise maximum metric until LDP is operational";
           presence "enable ldp-synchronization";
           uses ldp-sync-obj;
         }
         container ipv4-adjacency-segment {
           junos:must "(!(\".. no-advertise-adjacency-segment\"))";
           junos:must-message "ipv4-adjacency-segment can't be configured if no-advertise-adjacency-segment is configured in the same interface";
           description "Configure ipv4 adjacency segment";
           uses apply-advanced;
           container protected {
             description "Adjacency SID is eligible for protection";
             choice adjsid-type {
               case case_1 {
                 container index {
                   description "Adjacency SID indexed from SRGB";
                   leaf index-number {
                     type union {
                       type string {
                         pattern "<.*>|$.*";
                       }
                       type uint32 {
                         range "0 .. 199999";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
           container unprotected {
             description "Adjacency SID uneligible for protection";
             choice adjsid-type {
               case case_1 {
                 container index {
                   description "Adjacency SID indexed from SRGB";
                   leaf index-number {
                     type union {
                       type string {
                         pattern "<.*>|$.*";
                       }
                       type uint32 {
                         range "0 .. 199999";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
         }
         list lan-neighbor {
           key name;
           ordered-by user;
           description "Configuration specific to a LAN neighbor";
           junos:must "(!(\".. ipv4-adjacency-segment\"))";
           junos:must-message "lan-neighbor can't be configured if ipv4-adjacency-segment is configured in the same interface";
           junos:must "(!(\".. no-advertise-adjacency-segment\"))";
           junos:must-message "lan-neighbor can't be configured if no-advertise-adjacency-segment is configured in the same interface ";
           junos:must "(!(\".. interface-type p2p\"))";
           junos:must-message "lan-neighbor can't be configured for point-to-point interfaces";
           leaf name {
             description "Address of neighbor";
             type jt:ipaddr;
           }
           uses apply-advanced;
           container ipv4-adjacency-segment {
             junos:must "(!(\".. no-advertise-adjacency-segment\"))";
             junos:must-message "ipv4-adjacency-segment can't be configured if no-advertise-adjacency-segment is configured in the same interface";
             description "Configure ipv4 adjacency segment";
             uses apply-advanced;
             container protected {
               description "Adjacency SID is eligible for protection";
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
             container unprotected {
               description "Adjacency SID uneligible for protection";
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
           }
         }
         leaf delay-metric {
           description "Delay metric";
           units "microseconds";
           type union {
             type string {
               pattern "<.*>|$.*";
             }
             type uint32 {
               range "0 .. 16777215";
             }
           }
         }
         container delay-measurement {
           presence "enable delay-measurement";
           description "Enable delay measurement";
           uses apply-advanced;
           leaf probe-interval {
             description "Probe interval";
             units "seconds";
             type union {
               type string {
                 pattern "<.*>|$.*";
               }
               type uint32 {
                 range "1 .. 255";
               }
             }
           }
           leaf probe-count {
             description "Probe count";
             type union {
               type string {
                 pattern "<.*>|$.*";
               }
               type uint32 {
                 range "1 .. 15";
               }
             }
           }
           container advertisement {
             description "Delay advertisement";
             uses apply-advanced;
             container periodic {
               description "Periodic advertisement parameters";
               uses apply-advanced;
               leaf threshold {
                 description "Threshold";
                 units "percentage";
                 type union {
                   type string {
                     pattern "<.*>|$.*";
                   }
                   type uint32 {
                     range "0 .. 100";
                   }
                 }
               }
               leaf interval {
                 description "Interval";
                 units "seconds";
                 type union {
                   type string {
                     pattern "<.*>|$.*";
                   }
                   type uint32 {
                     range "30 .. 3600";
                   }
                 }
               }
             }
             container accelerated {
               presence "enable accelerated";
               description "Accelerated advertisement parameters";
               uses apply-advanced;
               leaf threshold {
                 description "Threshold";
                 units "percentage";
                 type union {
                   type string {
                     pattern "<.*>|$.*";
                   }
                   type uint32 {
                     range "0 .. 100";
                   }
                 }
               }
             }
           }
         }
         container application-specific {
           description "Advertise application-specific TE attributes";
           uses apply-advanced;
           list attribute-group {
             key name;
             ordered-by user;
             description "Link attribute group name";
             max-elements 1;
             leaf name {
               description "Link attribute group name";
               type string;
             }
             uses apply-advanced;
             leaf te-metric {
               description "Traffic engineering metric for this attribute group";
               junos:must "(\".. application\")";
               junos:must-message "Atleast one application is must";
               type union {
                 type string {
                   pattern "<.*>|$.*";
                 }
                 type uint32 {
                   range "1 .. 4294967295";
                 }
               }
             }
             leaf-list admin-group {
               ordered-by user;
               description "Administrative groups for this attribute-group";
               junos:must "(\".. application\")";
               junos:must-message "Atleast one application is must";
               type string;
               max-elements 16;
             }
             leaf delay-metric {
               description "Delay metric for this attribute-group";
               units "microseconds";
               junos:must "(!(\".. advertise-interface-delay\"))";
               junos:must-message "ASLA delay-metric can't be configured with ASLA advertise interface delay knob";
               junos:must "(\".. application\")";
               junos:must-message "Atleast one application is must";
               type union {
                 type string {
                   pattern "<.*>|$.*";
                 }
                 type uint32 {
                   range "0 .. 16777215";
                 }
               }
             }
             leaf advertise-interface-delay {
               description "Use interface specific static/dynamic delay values as applicable in ASLA Sub-TLVs";
               junos:must "((\".. .. .. delay-metric\" || \".. .. .. delay-measurement\"))";
               junos:must-message "Interface specific delay values must be configured for advertise interface delay knob";
               junos:must "(\".. application\")";
               junos:must-message "Atleast one application is must";
               type empty;
             }
             container application {
               junos:must "((\".. delay-metric\" || (\".. admin-group\" || (\".. te-metric\" || \".. advertise-interface-delay\"))))";
               junos:must-message "Atleast one attribute must be configured";
               description "Standard Applications part of this attribute-group";
               uses apply-advanced;
               leaf flex-algorithm {
                 description "Set X flag in standard application bit mask";
                 type empty;
               }
             }
           }
         }
       }
       leaf no-context-identifier-advertisement {
         description "Disable context identifier advertisments in this area";
         junos:must "(!(\".. context-identifier\"))";
         junos:must-message "no-context-identifier-advertisement and context-identifier attributes are mutually exclusive";
         type empty;
       }
       list peer-interface {
         key name;
         ordered-by user;
         description "Configuration for peer interface";
         leaf name {
           description "Name of peer interface";
           type string;
         }
         uses apply-advanced;
         choice enable-disable {
           case case_1 {
             leaf disable {
               description "Disable OSPF on this control peer";
               type empty;
             }
           }
         }
         leaf retransmit-interval {
           description "Retransmission interval (seconds)";
           type union {
             type string {
               pattern "<.*>|$.*";
             }
             type uint32 {
               range "1 .. 65535";
             }
           }
         }
         leaf transit-delay {
           description "Transit delay (seconds)";
           type union {
             type string {
               pattern "<.*>|$.*";
             }
             type uint32 {
               range "1 .. 65535";
             }
           }
         }
         leaf hello-interval {
           description "Hello interval (seconds)";
           type union {
             type string {
               pattern "<.*>|$.*";
             }
             type uint32 {
               range "1 .. 255";
             }
           }
         }
         leaf dead-interval {
           description "Dead interval (seconds)";
           type union {
             type string {
               pattern "<.*>|$.*";
             }
             type uint32 {
               range "1 .. 65535";
             }
           }
         }
         leaf mtu {
           description "Maximum OSPF packet size";
           type union {
             type string {
               pattern "<.*>|$.*";
             }
             type uint32 {
               range "128 .. 65535";
             }
           }
         }
         choice auth {
           case case_1 {
             container authentication {
               uses juniper-ospf-authentication;
             }
           }
           case case_2 {
             container authentication-key {
               description "Authentication key";
               status deprecated;
               leaf keyname {
                 description "Authentication key value";
                 type jt:unreadable;
               }
               leaf key-id {
                 description "Key ID for MD5 authentication";
                 type union {
                   type string {
                     pattern "<.*>|$.*";
                   }
                   type uint32 {
                     range "0 .. 255";
                   }
                 }
               }
             }
           }
         }
         leaf demand-circuit {
           description "Interface functions as a demand circuit";
           type empty;
         }
         leaf flood-reduction {
           description "Enable flood reduction";
           type empty;
         }
         leaf no-neighbor-down-notification {
           description "Don't inform other protocols about neighbor down events";
           type empty;
         }
       }
       leaf no-source-packet-routing {
         description "Disable SPRING in this area";
         type empty;
       }
       list context-identifier {
         key name;
         ordered-by user;
         description "Configure context identifier in support of edge protection";
         junos:must "(!(\".. no-context-identifier-advertisement\"))";
         junos:must-message "no-context-identifier-advertisement and context-identifier attributes are mutually exclusive";
         leaf name {
           description "Context identifier";
           type jt:ipv4addr;
         }
         uses apply-advanced;
       }
       list label-switched-path {
         key name;
         ordered-by user;
         description "Configuration for advertisement of a label-switched path";
         junos:must "(!(\".. .. traffic-engineering multicast-rpf-routes\"))";
         junos:must-message "cannot advertise LSPs when using multicast-rpf-routes";
         leaf name {
           description "Name of label-switched path to be advertised";
           type string {
             length "1 .. 64";
           }
         }
         uses apply-advanced;
         choice enable-disable {
           case case_1 {
             leaf disable {
               description "Disable OSPF on this label-switched path";
               type empty;
             }
           }
         }
         leaf metric {
           description "Interface metric";
           type union {
             type string {
               pattern "<.*>|$.*";
             }
             type uint16 {
               range "1 .. 65535";
             }
           }
         }
         list topology {
           key name;
           ordered-by user;
           description "Topology specific attributes";
           leaf name {
             description "Topology name";
             type string;
           }
           uses apply-advanced;
           leaf disable {
             description "Disable this topology";
             type empty;
           }
           leaf metric {
             description "Topology metric";
             type union {
               type string {
                 pattern "<.*>|$.*";
               }
               type uint16 {
                 range "1 .. 65535";
               }
             }
           }
           container bandwidth-based-metrics {
             junos:must "(\".. metric\")";
             junos:must-message "Metric must be configured";
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint16 {
                     range "1 .. 65535";
                   }
                 }
               }
             }
           }
         }
       }
     }
     choice enable-disable {
       case case_1 {
         leaf disable {
           description "Disable OSPF";
           type empty;
         }
       }
     }
     container traceoptions {
       description "Trace options for OSPF";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "spf" {
               description "Trace SPF calculations";
             }
             enum "error" {
               description "Trace errored packets";
             }
             enum "event" {
               description "Trace OSPF state machine events";
             }
             enum "packet-dump" {
               description "Dump the contents of selected packet types";
             }
             enum "flooding" {
               description "Trace LSA flooding";
             }
             enum "lsa-analysis" {
               description "Trace LSA analysis";
             }
             enum "packets" {
               description "Trace all OSPF packets";
             }
             enum "hello" {
               description "Trace hello packets";
             }
             enum "database-description" {
               description "Trace database description packets";
             }
             enum "lsa-request" {
               description "Trace LSA request packets";
             }
             enum "lsa-update" {
               description "Trace LSA update packets";
             }
             enum "lsa-ack" {
               description "Trace LSA acknowledgment packets";
             }
             enum "ldp-synchronization" {
               description "Trace synchronization between OSPF and LDP";
             }
             enum "on-demand" {
               description "Trace demand circuit extensions";
             }
             enum "nsr-synchronization" {
               description "Trace NSR synchronization events";
             }
             enum "graceful-restart" {
               description "Trace graceful restart";
             }
             enum "restart-signaling" {
               description "Trace restart signaling";
             }
             enum "backup-spf" {
               description "Trace backup SPF (LFA) specific events";
             }
             enum "source-packet-routing" {
               description "Trace source packet routing (SPRING) events";
             }
             enum "post-convergence-lfa" {
               description "Trace post-convergence-lfa related events";
             }
             enum "flex-algorithm" {
               description "Trace flex-algorithm related events";
             }
             enum "rmopd" {
               description "Trace rmopd interactions";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     leaf prefix-export-limit {
       description "Maximum number of prefixes that can be exported";
       type union {
         type string {
           pattern "<.*>|$.*";
         }
         type uint32 {
           range "0 .. 4294967295";
         }
       }
     }
     container rib-groups {
       description "Routing table groups for importing OSPF routes";
       uses apply-advanced;
       leaf inet {
         description "Name of the IPv4/v6 routing table group";
         junos:must "(\"routing-options rib-groups $$\")";
         junos:must-message "Referenced rib-groups must be defined";
         junos:must "(!(\".. topology $$={default} rib-group\"))";
         junos:must-message "rib-group cannot be used with topology default rib-group";
         type string;
       }
       leaf inet3 {
         description "Name of the IPv4/v6 inet.3 routing table group";
         junos:must "(\"routing-options rib-groups $$\")";
         junos:must-message "Referenced rib-groups must be defined";
         junos:must "(!(\".. topology $$={default} rib-group\"))";
         junos:must-message "rib-group cannot be used with topology default rib-group";
         type string;
       }
     }
     leaf job-stats {
       description "Collect job statistics";
       type empty;
     }
     container overload {
       presence "enable overload";
       description "Set the overload mode (repel transit traffic)";
       uses apply-advanced;
       leaf timeout {
         description "Time after which overload mode is reset";
         units "seconds";
         type union {
           type string {
             pattern "<.*>|$.*";
           }
           type uint32 {
             range "60 .. 3600";
           }
         }
       }
       leaf allow-route-leaking {
         description "Allow routes to be leaked when overload is configured";
         type empty;
       }
       leaf stub-network {
         description "Advertise Stub Network with maximum metric";
         type empty;
       }
       leaf intra-area-prefix {
         description "Advertise Intra Area Prefix with maximum metric";
         type empty;
       }
       leaf as-external {
         description "Advertise As External with maximum usable metric";
         type empty;
       }
     }
     container database-protection {
       presence "enable database-protection";
       description "Configure database protection attributes";
       uses apply-advanced;
       leaf maximum-lsa {
         description "Maximum allowed non self-generated LSAs";
         type union {
           type string {
             pattern "<.*>|$.*";
           }
           type uint32 {
             range "1 .. 1000000";
           }
         }
       }
       leaf warning-only {
         description "Emit only a warning when LSA maximum limit is exceeded";
         type empty;
       }
       leaf warning-threshold {
         description "Percentage of LSA maximum above which to trigger warning";
         units "percent";
         type union {
           type string {
             pattern "<.*>|$.*";
           }
           type uint8 {
             range "30 .. 100";
           }
         }
       }
       leaf ignore-count {
         description "Maximum number of times to go into ignore state";
         type union {
           type string {
             pattern "<.*>|$.*";
           }
           type uint8 {
             range "1 .. 32";
           }
         }
       }
       leaf ignore-time {
         description "Time to stay in ignore state and ignore all neighbors";
         units "seconds";
         type union {
           type string {
             pattern "<.*>|$.*";
           }
           type uint16 {
             range "30 .. 3600";
           }
         }
       }
       leaf reset-time {
         description "Time after which the ignore count gets reset to zero";
         units "seconds";
         type union {
           type string {
             pattern "<.*>|$.*";
           }
           type uint32 {
             range "60 .. 86400";
           }
         }
       }
     }
     container graceful-restart {
       description "Configure graceful restart attributes";
       uses apply-advanced;
       choice enable-disable {
         case case_1 {
           leaf disable {
             description "Disable OSPF graceful restart capability";
             type empty;
           }
         }
       }
       leaf restart-duration {
         description "Time for all neighbors to become full";
         units "seconds";
         type union {
           type string {
             pattern "<.*>|$.*";
           }
           type uint32 {
             range "1 .. 3600";
           }
         }
       }
       leaf notify-duration {
         description "Time to send all max-aged grace LSAs";
         units "seconds";
         type union {
           type string {
             pattern "<.*>|$.*";
           }
           type uint32 {
             range "1 .. 3600";
           }
         }
       }
       container helper-disable {
         presence "enable helper-disable";
         description "Disable graceful restart helper capability";
         uses apply-advanced;
         choice disable-choices {
           case case_1 {
             leaf standard {
               description "Disable helper-mode for rfc3623 based GR";
               type empty;
             }
           }
           case case_2 {
             leaf restart-signaling {
               description "Disable helper mode for restart-signaling ";
               type empty;
             }
           }
           case case_3 {
             leaf both {
               description "Disable helper mode for both the types of GR";
               type empty;
             }
           }
         }
       }
       leaf no-strict-lsa-checking {
         description "Do not abort graceful helper mode upon LSA changes";
         junos:must "(!(\".. helper-disable\"))";
         junos:must-message "To configure no-strict-lsa-checking, helper-disable must not be set";
         type empty;
       }
     }
     leaf route-type-community {
       description "Specify BGP extended community value to encode OSPF route type";
       type enumeration {
         enum "iana" {
           description "BGP extended community value used is 0x0306";
         }
         enum "vendor" {
           description "Vendor BGP extended community value used is 0x8000";
         }
       }
     }
     container domain-id {
       description "Configure domain ID";
       choice domain_id_or_disable {
         case case_1 {
           leaf domain-id {
             description "Domain ID";
             type string;
           }
         }
         case case_2 {
           leaf disable {
             description "Disable domain ID";
             type empty;
           }
         }
       }
     }
     choice domain_vpn_tag_or_disable {
       case case_1 {
         leaf domain-vpn-tag {
           description "Domain VPN tag for external LSA";
           type union {
             type string {
               pattern "<.*>|$.*";
             }
             type uint32 {
               range "0 .. 4294967295";
             }
           }
         }
       }
       case case_2 {
         leaf no-domain-vpn-tag {
           description "Disable domain VPN tag";
           type empty;
         }
       }
     }
     leaf preference {
       description "Preference of internal routes";
       type union {
         type uint32;
         type string {
           pattern "<.*>|$.*";
         }
       }
     }
     leaf external-preference {
       description "Preference of external routes";
       type union {
         type uint32;
         type string {
           pattern "<.*>|$.*";
         }
       }
     }
     leaf labeled-preference {
       description "Preference of labeled routes";
       type union {
         type uint32;
         type string {
           pattern "<.*>|$.*";
         }
       }
     }
     leaf-list export {
       ordered-by user;
       description "Export policy";
       type jt:policy-algebra;
     }
     leaf-list import {
       ordered-by user;
       description "Import policy (for external routes or setting priority)";
       type jt:policy-algebra;
     }
     leaf reference-bandwidth {
       description "Bandwidth for calculating metric defaults";
       type string;
     }
     leaf lsa-refresh-interval {
       description "LSA refresh interval (minutes)";
       default "50";
       type union {
         type string {
           pattern "<.*>|$.*";
         }
         type uint32 {
           range "25 .. 50";
         }
       }
     }
     leaf spf-delay {
       description "Time to wait before running an SPF";
       status deprecated;
       units "milliseconds";
       junos:must "(!(\".. spf-options delay\"))";
       junos:must-message "You can only configure either spf-delay or delay under spf-options";
       type union {
         type string {
           pattern "<.*>|$.*";
         }
         type uint32 {
           range "50 .. 8000";
         }
       }
     }
     leaf no-rfc-1583 {
       description "Disable RFC1583 compatibility";
       type empty;
     }
     leaf forwarding-address-to-broadcast {
       description "Set forwarding address in Type 5 LSA in broadcast network";
       type empty;
     }
     choice nssa-abr-option {
       case case_1 {
         leaf no-nssa-abr {
           description "Disable full NSSA functionality at ABR";
           type empty;
         }
       }
     }
     container sham-link {
       presence "enable sham-link";
       description "Configure parameters for sham links";
       uses apply-advanced;
       leaf local {
         description "Local sham link endpoint address";
         type jt:ipaddr;
       }
       leaf no-advertise-local {
         description "Don't advertise local sham link endpoint as stub in router LSA";
         status deprecated;
         type empty;
       }
     }
   }
   grouping juniper-ospf-authentication {
     description "Authentication information";
     uses apply-advanced;
     choice authentication-type {
       case case_1 {
         leaf simple-password {
           description "Authentication key";
           type jt:unreadable;
         }
       }
       case case_2 {
         list md5 {
           key name;
           ordered-by user;
           description "MD5 authentication key";
           leaf name {
             description "Key ID for MD5 authentication";
             type union {
               type string {
                 pattern "<.*>|$.*";
               }
               type uint32 {
                 range "0 .. 255";
               }
             }
           }
           leaf key {
             description "MD5 authentication key value";
             type jt:unreadable;
           }
           leaf start-time {
             description "Start time for key transmission (YYYY-MM-DD.HH:MM)";
             type jt:time;
           }
         }
       }
     }
   }
   grouping juniper-protocols-ospf3 {
     list realm {
       key name;
       ordered-by user;
       description "OSPFv3 realm configuration";
       leaf name {
         description "OSPFv3 realm name";
         type enumeration {
           enum "ipv6-unicast" {
             description "IPv6 unicast realm";
           }
           enum "ipv6-multicast" {
             description "IPv6 multicast realm";
           }
           enum "ipv4-unicast" {
             description "IPv4 unicast realm";
           }
           enum "ipv4-multicast" {
             description "IPv4 multicast realm";
           }
         }
       }
       uses apply-advanced;
       list topology {
         key name;
         ordered-by user;
         description "Topology parameters";
         leaf name {
           description "Topology name";
           type string;
         }
         uses apply-advanced;
         leaf disable {
           description "Disable this topology";
           type empty;
         }
         leaf topology-id {
           description "Topology identifier";
           type union {
             type string {
               pattern "<.*>|$.*";
             }
             type uint8 {
               range "32 .. 127";
             }
           }
         }
         leaf overload {
           description "Set the overload mode (repel transit traffic)";
           type empty;
         }
         leaf rib-group {
           description "Routing table group for importing routes";
           junos:must "(\"routing-options rib-groups $$\")";
           junos:must-message "Referenced rib-group must be defined";
           type string;
         }
         container spf-options {
           description "Configure options for SPF";
           uses apply-advanced;
           container microloop-avoidance {
             junos:must "(\"protocols ospf source-packet-routing\")";
             junos:must-message "Configuration of 'protocols ospf source-packet-routing' is required";
             description "Configure microloop avoidance mechanism";
             uses apply-advanced;
             container post-convergence-path {
               presence "enable post-convergence-path";
               description "Temporarily install post-convergence path for routes potentially affected by microloops";
               uses apply-advanced;
               leaf delay {
                 description "Time after which temporary post-convergence paths are removed";
                 units "milliseconds";
                 type union {
                   type string {
                     pattern "<.*>|$.*";
                   }
                   type uint32 {
                     range "500 .. 60000";
                   }
                 }
               }
               leaf maximum-labels {
                 description "Maximum number of labels installed for post-convergence paths";
                 type union {
                   type string {
                     pattern "<.*>|$.*";
                   }
                   type uint32 {
                     range "2 .. 8";
                   }
                 }
               }
             }
           }
           leaf delay {
             description "Time to wait before running an SPF";
             units "milliseconds";
             type union {
               type string {
                 pattern "<.*>|$.*";
               }
               type uint32 {
                 range "50 .. 8000";
               }
             }
           }
           leaf holddown {
             description "Time to hold down before running an SPF";
             units "milliseconds";
             type union {
               type string {
                 pattern "<.*>|$.*";
               }
               type uint32 {
                 range "2000 .. 20000";
               }
             }
           }
           leaf rapid-runs {
             description "Number of maximum rapid SPF runs before holddown";
             type union {
               type string {
                 pattern "<.*>|$.*";
               }
               type uint32 {
                 range "1 .. 10";
               }
             }
           }
           leaf no-ignore-our-externals {
             description "Do not ignore self-generated external and NSSA LSAs";
             type empty;
           }
         }
         container backup-spf-options {
           description "Configure options for backup SPF";
           uses apply-advanced;
           container remote-backup-calculation {
             presence "enable remote-backup-calculation";
             junos:must "(!(\"protocols ospf backup-spf-options use-post-convergence-lfa\"))";
             junos:must-message "Not allowed with 'protocols ospf backup-spf-options use-post-convergence-lfa'";
             description "Calculate Remote LFA backup nexthops";
             uses apply-advanced;
             container pq-nodes-nearest-to-source {
               description "PQ nodes selection based upon nearest to source";
               uses apply-advanced;
               leaf percent {
                 description "Selection percentage for nearest to source";
                 type union {
                   type string {
                     pattern "<.*>|$.*";
                   }
                   type uint32 {
                     range "10 .. 100";
                   }
                 }
               }
             }
           }
           container use-post-convergence-lfa {
             presence "enable use-post-convergence-lfa";
             junos:must "(\"protocols ospf source-packet-routing\")";
             junos:must-message "Configuration of 'protocols ospf source-packet-routing' is required";
             description "Calculate post-convergence backup paths";
             uses apply-advanced;
             leaf maximum-labels {
               description "Maximum number of labels installed for post-convergence paths";
               type union {
                 type string {
                   pattern "<.*>|$.*";
                 }
                 type uint32 {
                   range "2 .. 8";
                 }
               }
             }
             leaf maximum-backup-paths {
               description "Maximum number of equal-cost post-convergence paths installed";
               type union {
                 type string {
                   pattern "<.*>|$.*";
                 }
                 type uint32 {
                   range "1 .. 8";
                 }
               }
             }
           }
           leaf use-source-packet-routing {
             description "Use spring backup paths for inet.0 routes";
             junos:must "(\".. .. source-packet-routing\")";
             junos:must-message "Configuration of 'protocols ospf source-packet-routing' is required";
             junos:must "(!(\".. remote-backup-calculation\"))";
             junos:must-message "Not allowed with 'protocols ospf backup-spf-options remote-backup-calculation'";
             type empty;
           }
           leaf disable {
             description "Do not run backup SPF";
             junos:must "(!(\"protocols ospf backup-spf-options use-post-convergence-lfa\"))";
             junos:must-message "Not allowed with 'protocols ospf backup-spf-options use-post-convergence-lfa'";
             type empty;
           }
           leaf no-install {
             description "Do not install backup nexthops into the RIB";
             type empty;
           }
           leaf downstream-paths-only {
             description "Use only downstream backup paths";
             junos:must "(!(\"protocols ospf backup-spf-options use-post-convergence-lfa\"))";
             junos:must-message "Not allowed with 'protocols ospf backup-spf-options use-post-convergence-lfa'";
             type empty;
           }
           container per-prefix-calculation {
             junos:must "(!(\"protocols ospf backup-spf-options use-post-convergence-lfa\"))";
             junos:must-message "Not allowed with 'protocols ospf backup-spf-options use-post-convergence-lfa'";
             description "Calculate backup nexthops for non-best prefix originators";
             uses apply-advanced;
             leaf stubs {
               description "Per prefix calculation for stubs only";
               type empty;
             }
             leaf summary {
               description "Per prefix calculation for summary originators only";
               type empty;
             }
             leaf externals {
               description "Per prefix calculation for externals";
               type empty;
             }
             leaf all {
               description "Per prefix calculation for all";
               type empty;
             }
           }
           leaf node-link-degradation {
             description "Degrade to link protection when nodelink protection not available";
             junos:must "(!(\"protocols ospf backup-spf-options use-post-convergence-lfa\"))";
             junos:must-message "Not allowed with 'protocols ospf backup-spf-options use-post-convergence-lfa'";
             type empty;
           }
         }
         leaf prefix-export-limit {
           description "Maximum number of prefixes that can be exported";
           type union {
             type string {
               pattern "<.*>|$.*";
             }
             type uint32 {
               range "0 .. 4294967295";
             }
           }
         }
       }
       container spf-options {
         description "Configure options for SPF";
         uses apply-advanced;
         container microloop-avoidance {
           junos:must "(\"protocols ospf source-packet-routing\")";
           junos:must-message "Configuration of 'protocols ospf source-packet-routing' is required";
           description "Configure microloop avoidance mechanism";
           uses apply-advanced;
           container post-convergence-path {
             presence "enable post-convergence-path";
             description "Temporarily install post-convergence path for routes potentially affected by microloops";
             uses apply-advanced;
             leaf delay {
               description "Time after which temporary post-convergence paths are removed";
               units "milliseconds";
               type union {
                 type string {
                   pattern "<.*>|$.*";
                 }
                 type uint32 {
                   range "500 .. 60000";
                 }
               }
             }
             leaf maximum-labels {
               description "Maximum number of labels installed for post-convergence paths";
               type union {
                 type string {
                   pattern "<.*>|$.*";
                 }
                 type uint32 {
                   range "2 .. 8";
                 }
               }
             }
           }
         }
         leaf delay {
           description "Time to wait before running an SPF";
           units "milliseconds";
           type union {
             type string {
               pattern "<.*>|$.*";
             }
             type uint32 {
               range "50 .. 8000";
             }
           }
         }
         leaf holddown {
           description "Time to hold down before running an SPF";
           units "milliseconds";
           type union {
             type string {
               pattern "<.*>|$.*";
             }
             type uint32 {
               range "2000 .. 20000";
             }
           }
         }
         leaf rapid-runs {
           description "Number of maximum rapid SPF runs before holddown";
           type union {
             type string {
               pattern "<.*>|$.*";
             }
             type uint32 {
               range "1 .. 10";
             }
           }
         }
         leaf no-ignore-our-externals {
           description "Do not ignore self-generated external and NSSA LSAs";
           type empty;
         }
       }
       container backup-spf-options {
         description "Configure options for backup SPF";
         uses apply-advanced;
         container remote-backup-calculation {
           presence "enable remote-backup-calculation";
           junos:must "(!(\"protocols ospf backup-spf-options use-post-convergence-lfa\"))";
           junos:must-message "Not allowed with 'protocols ospf backup-spf-options use-post-convergence-lfa'";
           description "Calculate Remote LFA backup nexthops";
           uses apply-advanced;
           container pq-nodes-nearest-to-source {
             description "PQ nodes selection based upon nearest to source";
             uses apply-advanced;
             leaf percent {
               description "Selection percentage for nearest to source";
               type union {
                 type string {
                   pattern "<.*>|$.*";
                 }
                 type uint32 {
                   range "10 .. 100";
                 }
               }
             }
           }
         }
         container use-post-convergence-lfa {
           presence "enable use-post-convergence-lfa";
           junos:must "(\"protocols ospf source-packet-routing\")";
           junos:must-message "Configuration of 'protocols ospf source-packet-routing' is required";
           description "Calculate post-convergence backup paths";
           uses apply-advanced;
           leaf maximum-labels {
             description "Maximum number of labels installed for post-convergence paths";
             type union {
               type string {
                 pattern "<.*>|$.*";
               }
               type uint32 {
                 range "2 .. 8";
               }
             }
           }
           leaf maximum-backup-paths {
             description "Maximum number of equal-cost post-convergence paths installed";
             type union {
               type string {
                 pattern "<.*>|$.*";
               }
               type uint32 {
                 range "1 .. 8";
               }
             }
           }
         }
         leaf use-source-packet-routing {
           description "Use spring backup paths for inet.0 routes";
           junos:must "(\".. .. source-packet-routing\")";
           junos:must-message "Configuration of 'protocols ospf source-packet-routing' is required";
           junos:must "(!(\".. remote-backup-calculation\"))";
           junos:must-message "Not allowed with 'protocols ospf backup-spf-options remote-backup-calculation'";
           type empty;
         }
         leaf disable {
           description "Do not run backup SPF";
           junos:must "(!(\"protocols ospf backup-spf-options use-post-convergence-lfa\"))";
           junos:must-message "Not allowed with 'protocols ospf backup-spf-options use-post-convergence-lfa'";
           type empty;
         }
         leaf no-install {
           description "Do not install backup nexthops into the RIB";
           type empty;
         }
         leaf downstream-paths-only {
           description "Use only downstream backup paths";
           junos:must "(!(\"protocols ospf backup-spf-options use-post-convergence-lfa\"))";
           junos:must-message "Not allowed with 'protocols ospf backup-spf-options use-post-convergence-lfa'";
           type empty;
         }
         container per-prefix-calculation {
           junos:must "(!(\"protocols ospf backup-spf-options use-post-convergence-lfa\"))";
           junos:must-message "Not allowed with 'protocols ospf backup-spf-options use-post-convergence-lfa'";
           description "Calculate backup nexthops for non-best prefix originators";
           uses apply-advanced;
           leaf stubs {
             description "Per prefix calculation for stubs only";
             type empty;
           }
           leaf summary {
             description "Per prefix calculation for summary originators only";
             type empty;
           }
           leaf externals {
             description "Per prefix calculation for externals";
             type empty;
           }
           leaf all {
             description "Per prefix calculation for all";
             type empty;
           }
         }
         leaf node-link-degradation {
           description "Degrade to link protection when nodelink protection not available";
           junos:must "(!(\"protocols ospf backup-spf-options use-post-convergence-lfa\"))";
           junos:must-message "Not allowed with 'protocols ospf backup-spf-options use-post-convergence-lfa'";
           type empty;
         }
       }
       container traffic-engineering {
         presence "enable traffic-engineering";
         description "Configure traffic engineering attributes";
         uses apply-advanced;
         leaf no-topology {
           description "Disable dissemination of TE link-state topology information";
           type empty;
         }
         leaf multicast-rpf-routes {
           description "Install routes for multicast RPF checks into inet.2";
           junos:must "(!(\".. .. topology $$={ipv4-multicast}\"))";
           junos:must-message "multicast-rpf-routes cannot be used with topology ipv4-multicast";
           junos:must "(\".. shortcuts\")";
           junos:must-message "multicast-rpf-routes cannot be used without shortcuts";
           type empty;
         }
         leaf l3-unicast-topology {
           description "Download IGP topology into TED";
           type empty;
         }
         container ignore-lsp-metrics {
           presence "enable ignore-lsp-metrics";
           description "Ignore label-switched path metrics when doing shortcuts";
           uses apply-advanced;
           leaf unconfigured-only {
             description "Ignore lsp metrics for unconfigured only";
             type empty;
           }
         }
         container shortcuts {
           presence "enable shortcuts";
           description "Use label-switched paths as next hops, if possible";
           uses apply-advanced;
           leaf ignore-lsp-metrics {
             description "Ignore label-switched path metrics when doing shortcuts";
             status deprecated;
             type empty;
           }
           leaf lsp-metric-into-summary {
             description "Advertise LSP metric into summary LSAs";
             type empty;
           }
           list family {
             key name;
             ordered-by user;
             description "Address family specific traffic-engineering attributes";
             leaf name {
               type enumeration {
                 enum "inet" {
                   description "IPv4 family";
                 }
                 enum "inet-mpls" {
                   description "IPv4-MPLS family";
                 }
               }
             }
             uses apply-advanced;
           }
         }
         leaf advertise-unnumbered-interfaces {
           description "Advertise unnumbered interfaces";
           type empty;
         }
         leaf credibility-protocol-preference {
           description "TED protocol credibility follows protocol preference";
           type empty;
         }
         container advertisement {
           description "Advertise TE parameters even if RSVP is not turned on";
           uses apply-advanced;
           leaf always {
             description "Advertise TE parameters in TE LSAs";
             type empty;
           }
         }
       }
       container source-packet-routing {
         presence "enable source-packet-routing";
         junos:must "(!(\".. .. .. protocols mpls disable\"))";
         junos:must-message "SPRING configuration is not allowed with 'protocols mpls disable'";
         junos:must "(\".. .. .. protocols mpls \")";
         junos:must-message "SPRING configuration is not allowed without 'protocols mpls'";
         description "Enable source packet routing (SPRING)";
         uses apply-advanced;
         container adjacency-segment {
           description "Attributes for adjacency segments in spring";
           uses apply-advanced;
           leaf hold-time {
             description "Retain time of Adjacency segment after isolating from an interface";
             type union {
               type string {
                 pattern "<.*>|$.*";
               }
               type uint32 {
                 range "180000 .. 900000";
               }
             }
           }
         }
         leaf-list prefix-segment {
           ordered-by user;
           description "Prefix Segment policy";
           type jt:policy-algebra;
         }
         leaf explicit-null {
           description "Set E and P bits in all Prefix SID advertisements";
           type empty;
         }
         container node-segment {
           presence "enable node-segment";
           description "Enable support for Node segments in SPRING";
           uses apply-advanced;
           leaf ipv4-index {
             description "Set ipv4 node segment index";
             type union {
               type string {
                 pattern "<.*>|$.*";
               }
               type uint32 {
                 range "0 .. 199999";
               }
             }
           }
           leaf index-range {
             description "Set range of node segment indices allowed";
             type union {
               type string {
                 pattern "<.*>|$.*";
               }
               type uint32 {
                 range "32 .. 16385";
               }
             }
           }
         }
         container srgb {
           junos:must "(!(\".. node-segment index-range\"))";
           junos:must-message "Can not be configured with node-segment index-range";
           description "Set the SRGB global block in SPRING";
           leaf start-label {
             description "Start range for SRGB label block";
             type union {
               type string {
                 pattern "<.*>|$.*";
               }
               type uint32;
             }
           }
           leaf index-range {
             description "Index to the SRGB start label block";
             type union {
               type string {
                 pattern "<.*>|$.*";
               }
               type uint32;
             }
           }
         }
         leaf mapping-server {
           description "Mapping server name";
           junos:must "(\".. node-segment\")";
           junos:must-message "protocols ospf source-packet-routing node-segment must be defined";
           junos:must "(\"routing-options source-packet-routing mapping-server-entry $$\")";
           junos:must-message "Referenced source-packet-routing mapping-server-entry must be defined";
           type string;
         }
         leaf install-prefix-sid-for-best-route {
           description "For best route install a exact prefix sid route";
           type empty;
         }
         leaf ldp-stitching {
           description "Enable SR to LDP stitching";
           type empty;
         }
         leaf-list flex-algorithm {
           description "Flex-algorithms we would like to participate in";
           type union {
             type string {
               pattern "<.*>|$.*";
             }
             type uint32 {
               range "128 .. 255";
             }
           }
           max-elements 16;
         }
         leaf strict-asla-based-flex-algorithm {
           description "Flex-Algorithm to ignore links not having ASLA sub-TLVs";
           type empty;
         }
       }
       list area {
         key name;
         ordered-by user;
         description "Configure an OSPF area";
         leaf name {
           description "Area ID";
           type jt:areaid;
         }
         uses apply-advanced;
         choice stub-option {
           case case_1 {
             container stub {
               presence "enable stub";
               description "Configure a stub area";
               leaf default-metric {
                 description "Metric for the default route in this stub area";
                 type union {
                   type string {
                     pattern "<.*>|$.*";
                   }
                   type uint32 {
                     range "1 .. 16777215";
                   }
                 }
               }
               choice summaries-choice {
                 leaf summaries {
                   description "Flood summary LSAs into this stub area";
                   type empty;
                 }
                 leaf no-summaries {
                   description "Don't flood summary LSAs into this stub area";
                   type empty;
                 }
               }
             }
           }
           case case_2 {
             container nssa {
               presence "enable nssa";
               description "Configure a not-so-stubby area";
               uses apply-advanced;
               container default-lsa {
                 presence "enable default-lsa";
                 description "Configure a default LSA";
                 uses apply-advanced;
                 leaf default-metric {
                   description "Metric for the default route in this area";
                   type union {
                     type string {
                       pattern "<.*>|$.*";
                     }
                     type uint32 {
                       range "1 .. 16777215";
                     }
                   }
                 }
                 leaf metric-type {
                   description "External metric type for the default type 7 LSA";
                   type union {
                     type string {
                       pattern "<.*>|$.*";
                     }
                     type uint32 {
                       range "1 .. 2";
                     }
                   }
                 }
                 leaf type-7 {
                   description "Flood type 7 default LSA if no-summaries is configured";
                   type empty;
                 }
               }
               leaf default-metric {
                 description "Metric for the default route in this area";
                 status deprecated;
                 type union {
                   type string {
                     pattern "<.*>|$.*";
                   }
                   type uint32 {
                     range "1 .. 16777215";
                   }
                 }
               }
               leaf metric-type {
                 description "External metric type for the default type 7 LSA";
                 status deprecated;
                 type union {
                   type string {
                     pattern "<.*>|$.*";
                   }
                   type uint32 {
                     range "1 .. 2";
                   }
                 }
               }
               choice summaries-choice {
                 leaf summaries {
                   description "Flood summary LSAs into this NSSA area";
                   type empty;
                 }
                 leaf no-summaries {
                   description "Don't flood summary LSAs into this NSSA area";
                   type empty;
                 }
               }
               list area-range {
                 key name;
                 ordered-by user;
                 description "Configure NSSA area ranges";
                 leaf name {
                   description "Range to summarize NSSA routes in this area";
                   type jt:ipprefix;
                 }
                 uses apply-advanced;
                 leaf restrict {
                   description "Restrict advertisement of this area range";
                   type empty;
                 }
                 leaf exact {
                   description "Enforce exact match for advertisement of this area range";
                   type empty;
                 }
                 container override-metric {
                   presence "enable override-metric";
                   description "Override the dynamic metric for this area-range";
                   uses apply-advanced;
                   leaf metric {
                     description "Metric value";
                     type union {
                       type string {
                         pattern "<.*>|$.*";
                       }
                       type uint32 {
                         range "1 .. 16777215";
                       }
                     }
                   }
                   leaf metric-type {
                     description "Set the metric type for the override metric";
                     default "1";
                     type union {
                       type string {
                         pattern "<.*>|$.*";
                       }
                       type uint32 {
                         range "1 .. 2";
                       }
                     }
                   }
                 }
               }
             }
           }
         }
         list area-range {
           key name;
           ordered-by user;
           description "Configure area ranges";
           leaf name {
             description "Range to summarize routes in this area";
             type jt:ipprefix;
           }
           uses apply-advanced;
           leaf restrict {
             description "Restrict advertisement of this area range";
             type empty;
           }
           leaf exact {
             description "Enforce exact match for advertisement of this area range";
             type empty;
           }
           leaf override-metric {
             description "Override the dynamic metric for this area-range";
             type union {
               type string {
                 pattern "<.*>|$.*";
               }
               type uint32 {
                 range "1 .. 16777215";
               }
             }
           }
         }
         leaf-list network-summary-export {
           ordered-by user;
           description "Export policy for Type 3 Summary LSAs";
           type jt:policy-algebra;
         }
         leaf-list network-summary-import {
           ordered-by user;
           description "Import policy for Type 3 Summary LSAs";
           type jt:policy-algebra;
         }
         leaf-list inter-area-prefix-export {
           ordered-by user;
           description "Export policy for Inter Area Prefix LSAs";
           type jt:policy-algebra;
         }
         leaf-list inter-area-prefix-import {
           ordered-by user;
           description "Import policy for Inter Area Prefix LSAs";
           type jt:policy-algebra;
         }
         leaf authentication-type {
           description "Authentication type";
           status deprecated;
           type enumeration {
             enum "none" {
               description "No authentication";
               status deprecated;
             }
             enum "simple" {
               description "Simple password authentication";
               status deprecated;
             }
             enum "md5" {
               description "MD5 authentication";
               status deprecated;
             }
           }
         }
         list virtual-link {
           key "neighbor-id transit-area";
           ordered-by user;
           description "Configure virtual links";
           junos:must "(\".. .. area $$={0.0.0.0}\")";
           junos:must-message "virtual link can be configured only under backbone area";
           leaf neighbor-id {
             description "Router ID of a virtual neighbor";
             type jt:ipv4addr;
           }
           leaf transit-area {
             description "Transit area in common with virtual neighbor";
             type jt:areaid;
           }
           uses apply-advanced;
           choice enable-disable {
             case case_1 {
               leaf disable {
                 description "Disable this virtual link";
                 type empty;
               }
             }
           }
           leaf retransmit-interval {
             description "Retransmission interval (seconds)";
             type union {
               type string {
                 pattern "<.*>|$.*";
               }
               type uint32 {
                 range "1 .. 65535";
               }
             }
           }
           leaf transit-delay {
             description "Transit delay (seconds)";
             type union {
               type string {
                 pattern "<.*>|$.*";
               }
               type uint32 {
                 range "1 .. 65535";
               }
             }
           }
           leaf hello-interval {
             description "Hello interval (seconds)";
             type union {
               type string {
                 pattern "<.*>|$.*";
               }
               type uint32 {
                 range "1 .. 255";
               }
             }
           }
           leaf dead-interval {
             description "Dead interval (seconds)";
             type union {
               type string {
                 pattern "<.*>|$.*";
               }
               type uint32 {
                 range "1 .. 65535";
               }
             }
           }
           leaf mtu {
             description "Maximum OSPF packet size";
             type union {
               type string {
                 pattern "<.*>|$.*";
               }
               type uint32 {
                 range "128 .. 65535";
               }
             }
           }
           choice auth {
             case case_1 {
               container authentication {
                 uses juniper-ospf-authentication;
               }
             }
             case case_2 {
               container authentication-key {
                 description "Authentication key";
                 status deprecated;
                 leaf keyname {
                   description "Authentication key value";
                   type jt:unreadable;
                 }
                 leaf key-id {
                   description "Key ID for MD5 authentication";
                   type union {
                     type string {
                       pattern "<.*>|$.*";
                     }
                     type uint32 {
                       range "0 .. 255";
                     }
                   }
                 }
               }
             }
           }
           leaf demand-circuit {
             description "Interface functions as a demand circuit";
             type empty;
           }
           leaf flood-reduction {
             description "Enable flood reduction";
             type empty;
           }
           leaf no-neighbor-down-notification {
             description "Don't inform other protocols about neighbor down events";
             type empty;
           }
           leaf ipsec-sa {
             description "IPSec security association name";
             junos:must "(!(any \".. .. interface <st*> ipsec-sa $$\"))";
             junos:must-message "Must not configure ipsec-sa for st0 interface";
             junos:must "(\"security ipsec security-association $$ manual\")";
             junos:must-message "Referenced IPSec security association must be a manual SA";
             junos:must "(\"security ipsec security-association $$ mode transport\")";
             junos:must-message "Referenced IPSec security association must be in transport mode";
             junos:must "(\"security ipsec security-association $$\")";
             junos:must-message "Referenced IPSec security association must be defined";
             type string {
               length "1 .. 32";
             }
           }
           list topology {
             key name;
             ordered-by user;
             description "Topology specific attributes";
             leaf name {
               description "Topology name";
               type string;
             }
             uses apply-advanced;
             leaf disable {
               description "Disable this topology";
               type empty;
             }
             leaf metric {
               description "Topology metric";
               type union {
                 type string {
                   pattern "<.*>|$.*";
                 }
                 type uint16 {
                   range "1 .. 65535";
                 }
               }
             }
             container bandwidth-based-metrics {
               junos:must "(\".. metric\")";
               junos:must-message "Metric must be configured";
               description "Configure bandwidth based metrics";
               uses apply-advanced;
               list bandwidth {
                 key name;
                 description "Bandwidth threshold";
                 leaf name {
                   type string;
                 }
                 leaf metric {
                   description "Metric associated with specified bandwidth";
                   type union {
                     type string {
                       pattern "<.*>|$.*";
                     }
                     type uint16 {
                       range "1 .. 65535";
                     }
                   }
                 }
               }
             }
           }
         }
         list sham-link-remote {
           key name;
           ordered-by user;
           description "Configure parameters for remote sham link endpoint";
           leaf name {
             description "Remote sham link endpoint address";
             junos:must "(!(\".. .. .. sham-link local $$\"))";
             junos:must-message "Local and remote sham link endpoint addresses must be different";
             junos:must "(\".. .. .. sham-link local\")";
             junos:must-message "Local sham link endpoint must be configured";
             type jt:ipaddr;
           }
           uses apply-advanced;
           leaf metric {
             description "Sham link metric";
             type union {
               type string {
                 pattern "<.*>|$.*";
               }
               type uint16 {
                 range "1 .. 65535";
               }
             }
           }
           leaf ipsec-sa {
             description "IPSec security association name";
             junos:must "(!(any \".. .. interface <st*> ipsec-sa $$\"))";
             junos:must-message "Must not configure ipsec-sa for st0 interface";
             junos:must "(\"security ipsec security-association $$ manual\")";
             junos:must-message "Referenced IPSec security association must be a manual SA";
             junos:must "(\"security ipsec security-association $$ mode transport\")";
             junos:must-message "Referenced IPSec security association must be in transport mode";
             junos:must "(\"security ipsec security-association $$\")";
             junos:must-message "Referenced IPSec security association must be defined";
             type string {
               length "1 .. 32";
             }
           }
           leaf demand-circuit {
             description "Interface functions as a demand circuit";
             type empty;
           }
           leaf flood-reduction {
             description "Enable flood reduction";
             type empty;
           }
           list topology {
             key name;
             ordered-by user;
             description "Topology specific attributes";
             leaf name {
               description "Topology name";
               type string;
             }
             uses apply-advanced;
             leaf disable {
               description "Disable this topology";
               type empty;
             }
             leaf metric {
               description "Topology metric";
               type union {
                 type string {
                   pattern "<.*>|$.*";
                 }
                 type uint16 {
                   range "1 .. 65535";
                 }
               }
             }
             container bandwidth-based-metrics {
               junos:must "(\".. metric\")";
               junos:must-message "Metric must be configured";
               description "Configure bandwidth based metrics";
               uses apply-advanced;
               list bandwidth {
                 key name;
                 description "Bandwidth threshold";
                 leaf name {
                   type string;
                 }
                 leaf metric {
                   description "Metric associated with specified bandwidth";
                   type union {
                     type string {
                       pattern "<.*>|$.*";
                     }
                     type uint16 {
                       range "1 .. 65535";
                     }
                   }
                 }
               }
             }
           }
         }
         list interface {
           key name;
           ordered-by user;
           description "Include an interface in this area";
           leaf name {
             description "Interface name";
             junos:must "((!(\".. interface-type nbma\") || (!((\"interfaces $$\" || any \"logical-systems <*> interfaces $$\")) || (any \"interfaces $$-IFL family inet address <*>\" || any \"logical-systems <*> interfaces $$-IFL family inet address <*>\"))))";
             junos:must-message "IPv4 address must be configured on the interface for nbma mode";
             type union {
               type jt:ipv4addr-or-interface;
               type string {
                 pattern "<.*>|$.*";
               }
             }
           }
           uses apply-advanced;
           choice enable-disable {
             case case_1 {
               leaf disable {
                 description "Disable OSPF on this interface";
                 type empty;
               }
             }
           }
           leaf interface-type {
             description "Type of interface";
             type enumeration {
               enum "nbma" {
                 description "Nonbroadcast multiaccess";
               }
               enum "p2mp" {
                 description "Point-to-multipoint NBMA";
               }
               enum "p2p" {
                 description "Point-to-point";
               }
               enum "p2mp-over-lan" {
                 description "Point-to-multipoint over LAN mode";
               }
             }
           }
           choice protection-type {
             case case_1 {
               leaf link-protection {
                 description "Protect interface from link faults only";
                 type empty;
               }
             }
             case case_2 {
               leaf node-link-protection {
                 description "Protect interface from both link and node faults";
                 type empty;
               }
             }
           }
           leaf no-eligible-backup {
             description "Not eligible to backup traffic from protected interfaces";
             type empty;
           }
           leaf no-eligible-remote-backup {
             description "Not eligible for Remote-LFA backup traffic from protected interfaces";
             type empty;
           }
           container passive {
             presence "enable passive";
             description "Do not run OSPF, but advertise it";
             uses apply-advanced;
             container traffic-engineering {
               description "Advertise TE link information";
               uses apply-advanced;
               leaf remote-node-id {
                 description "Remote address of the link";
                 type jt:ipaddr;
               }
               leaf remote-node-router-id {
                 description "TE Router-ID of the remote node";
                 junos:must "(\".. remote-node-id\")";
                 junos:must-message "remote-node-id must be configured";
                 type jt:ipv4addr;
               }
             }
           }
           leaf secondary {
             description "Treat interface as secondary";
             junos:must "(!(\" .. ipsec-sa\"))";
             junos:must-message "secondary interface cannot have ipsec-sa configured";
             junos:must "(!(\" .. dynamic-neighbors\"))";
             junos:must-message "secondary interface cannot have dynamic-neighbors configured";
             junos:must "(!(\" .. neighbor\"))";
             junos:must-message "secondary interface cannot have configured neighbors";
             junos:must "(!(\" .. interface-type p2mp\"))";
             junos:must-message "secondary interface cannot be set as type p2mp";
             junos:must "(!(\" .. interface-type nbma\"))";
             junos:must-message "secondary interface cannot be set as type nbma";
             junos:must "(!(\" .. passive\"))";
             junos:must-message "secondary interface cannot be configured passive";
             type empty;
           }
           leaf own-router-lsa {
             description "Generate a separate router LSA for this interface";
             type empty;
           }
           container bandwidth-based-metrics {
             junos:must "(\".. metric\")";
             junos:must-message "Metric must be configured";
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint16 {
                     range "1 .. 65535";
                   }
                 }
               }
             }
           }
           leaf metric {
             description "Interface metric";
             type union {
               type string {
                 pattern "<.*>|$.*";
               }
               type uint16 {
                 range "1 .. 65535";
               }
             }
           }
           leaf priority {
             description "Designated router priority";
             type union {
               type string {
                 pattern "<.*>|$.*";
               }
               type uint32 {
                 range "0 .. 255";
               }
             }
           }
           leaf retransmit-interval {
             description "Retransmission interval (seconds)";
             type union {
               type string {
                 pattern "<.*>|$.*";
               }
               type uint32 {
                 range "1 .. 65535";
               }
             }
           }
           leaf transit-delay {
             description "Transit delay (seconds)";
             type union {
               type string {
                 pattern "<.*>|$.*";
               }
               type uint32 {
                 range "1 .. 65535";
               }
             }
           }
           leaf hello-interval {
             description "Hello interval (seconds)";
             type union {
               type string {
                 pattern "<.*>|$.*";
               }
               type uint32 {
                 range "1 .. 255";
               }
             }
           }
           leaf dead-interval {
             description "Dead interval (seconds)";
             type union {
               type string {
                 pattern "<.*>|$.*";
               }
               type uint32 {
                 range "1 .. 65535";
               }
             }
           }
           leaf mtu {
             description "Maximum OSPF packet size";
             type union {
               type string {
                 pattern "<.*>|$.*";
               }
               type uint32 {
                 range "128 .. 65535";
               }
             }
           }
           choice auth {
             case case_1 {
               container authentication {
                 uses juniper-ospf-authentication;
               }
             }
             case case_2 {
               container authentication-key {
                 description "Authentication key";
                 status deprecated;
                 leaf keyname {
                   description "Authentication key value";
                   type jt:unreadable;
                 }
                 leaf key-id {
                   description "Key ID for MD5 authentication";
                   type union {
                     type string {
                       pattern "<.*>|$.*";
                     }
                     type uint32 {
                       range "0 .. 255";
                     }
                   }
                 }
               }
             }
           }
           leaf demand-circuit {
             description "Interface functions as a demand circuit";
             type empty;
           }
           leaf flood-reduction {
             description "Enable flood reduction";
             type empty;
           }
           leaf no-neighbor-down-notification {
             description "Don't inform other protocols about neighbor down events";
             type empty;
           }
           leaf ipsec-sa {
             description "IPSec security association name";
             junos:must "(!(any \".. .. interface <st*> ipsec-sa $$\"))";
             junos:must-message "Must not configure ipsec-sa for st0 interface";
             junos:must "(\"security ipsec security-association $$ manual\")";
             junos:must-message "Referenced IPSec security association must be a manual SA";
             junos:must "(\"security ipsec security-association $$ mode transport\")";
             junos:must-message "Referenced IPSec security association must be in transport mode";
             junos:must "(\"security ipsec security-association $$\")";
             junos:must-message "Referenced IPSec security association must be defined";
             type string {
               length "1 .. 32";
             }
           }
           list topology {
             key name;
             ordered-by user;
             description "Topology specific attributes";
             leaf name {
               description "Topology name";
               type string;
             }
             uses apply-advanced;
             leaf disable {
               description "Disable this topology";
               type empty;
             }
             leaf metric {
               description "Topology metric";
               type union {
                 type string {
                   pattern "<.*>|$.*";
                 }
                 type uint16 {
                   range "1 .. 65535";
                 }
               }
             }
             container bandwidth-based-metrics {
               junos:must "(\".. metric\")";
               junos:must-message "Metric must be configured";
               description "Configure bandwidth based metrics";
               uses apply-advanced;
               list bandwidth {
                 key name;
                 description "Bandwidth threshold";
                 leaf name {
                   type string;
                 }
                 leaf metric {
                   description "Metric associated with specified bandwidth";
                   type union {
                     type string {
                       pattern "<.*>|$.*";
                     }
                     type uint16 {
                       range "1 .. 65535";
                     }
                   }
                 }
               }
             }
           }
           leaf transmit-interval {
             description "OSPF packet transmit interval (milliseconds)";
             status deprecated;
             type union {
               type string {
                 pattern "<.*>|$.*";
               }
               type uint32 {
                 range "1 .. 4294967295";
               }
             }
           }
           container bfd-liveness-detection {
             description "Bidirectional Forwarding Detection options";
             uses apply-advanced;
             leaf version {
               description "BFD protocol version number";
               default "automatic";
               type enumeration {
                 enum "0" {
                   description "BFD version 0 (deprecated)";
                 }
                 enum "1" {
                   description "BFD version 1";
                 }
                 enum "automatic" {
                   description "Choose BFD version automatically";
                 }
               }
             }
             leaf minimum-interval {
               description "Minimum transmit and receive interval";
               units "milliseconds";
               type union {
                 type string {
                   pattern "<.*>|$.*";
                 }
                 type uint32 {
                   range "1 .. 255000";
                 }
               }
             }
             leaf minimum-transmit-interval {
               description "Minimum transmit interval";
               status deprecated;
               units "milliseconds";
               type union {
                 type string {
                   pattern "<.*>|$.*";
                 }
                 type uint32 {
                   range "1 .. 255000";
                 }
               }
             }
             leaf minimum-receive-interval {
               description "Minimum receive interval";
               units "milliseconds";
               type union {
                 type string {
                   pattern "<.*>|$.*";
                 }
                 type uint32 {
                   range "1 .. 255000";
                 }
               }
             }
             leaf multiplier {
               description "Detection time multiplier";
               default "3";
               type union {
                 type string {
                   pattern "<.*>|$.*";
                 }
                 type uint32 {
                   range "1 .. 255";
                 }
               }
             }
             choice adaptation-choice {
               case case_1 {
                 leaf no-adaptation {
                   description "Disable adaptation";
                   type empty;
                 }
               }
             }
             container transmit-interval {
               description "Transmit-interval options";
               uses apply-advanced;
               leaf minimum-interval {
                 description "Minimum transmit interval";
                 units "milliseconds";
                 type union {
                   type string {
                     pattern "<.*>|$.*";
                   }
                   type uint32 {
                     range "1 .. 255000";
                   }
                 }
               }
               leaf threshold {
                 description "High transmit interval triggering a trap";
                 units "milliseconds";
                 type union {
                   type uint32;
                   type string {
                     pattern "<.*>|$.*";
                   }
                 }
               }
             }
             container detection-time {
               description "Detection-time options";
               uses apply-advanced;
               leaf threshold {
                 description "High detection-time triggering a trap";
                 units "milliseconds";
                 type union {
                   type uint32;
                   type string {
                     pattern "<.*>|$.*";
                   }
                 }
               }
             }
             container authentication {
               description "Authentication options";
               uses apply-advanced;
               leaf key-chain {
                 description "Key chain name";
                 junos:must "(\".. algorithm\")";
                 junos:must-message "May not be configured without algorithm";
                 junos:must "(\"security authentication-key-chains key-chain $$\")";
                 junos:must-message "Referenced key-chain must be defined";
                 type string;
               }
               leaf algorithm {
                 description "Algorithm name";
                 junos:must "(\".. key-chain\")";
                 junos:must-message "May not be configured without key-chain";
                 type enumeration {
                   enum "simple-password" {
                     description "Simple password";
                   }
                   enum "keyed-md5" {
                     description "Keyed message Digest 5";
                   }
                   enum "meticulous-keyed-md5" {
                     description "Meticulous keyed message Digest 5";
                   }
                   enum "keyed-sha-1" {
                     description "Keyed secure hash algorithm (SHA1) ";
                   }
                   enum "meticulous-keyed-sha-1" {
                     description "Meticulous keyed secure hash algorithm (SHA1) ";
                   }
                 }
               }
               leaf loose-check {
                 description "Verify authentication only if authentication is negotiated";
                 type empty;
               }
             }
             leaf full-neighbors-only {
               description "Setup BFD sessions only to Full neighbors";
               type empty;
             }
             leaf holddown-interval {
               description "Time to hold the session-UP notification to the client";
               units "milliseconds";
               type union {
                 type string {
                   pattern "<.*>|$.*";
                 }
                 type uint32 {
                   range "0 .. 255000";
                 }
               }
             }
           }
           leaf dynamic-neighbors {
             description "Learn neighbors dynamically on a p2mp interface";
             junos:must "(\" .. interface-type p2mp\")";
             junos:must-message "dynamic-neighbors option can be set only if the interface type is p2mp";
             type empty;
           }
           leaf no-advertise-adjacency-segment {
             description "Do not advertise an adjacency segment for this interface";
             type empty;
           }
           list neighbor {
             key name;
             ordered-by user;
             description "NBMA neighbor";
             junos:must "(!(\" .. dynamic-neighbors\"))";
             junos:must-message "Neighbors cannot be specified manually if dynamic-neighbors is set";
             leaf name {
               description "Address of neighbor";
               type jt:ipaddr;
             }
             leaf eligible {
               description "Eligible to be DR on an NBMA network";
               type empty;
             }
           }
           leaf poll-interval {
             description "Poll interval for NBMA interfaces";
             type union {
               type string {
                 pattern "<.*>|$.*";
               }
               type uint32 {
                 range "1 .. 65535";
               }
             }
           }
           leaf no-interface-state-traps {
             description "Do not send interface state change traps";
             type empty;
           }
           leaf strict-bfd {
             description "Enable strict bfd over this interface";
             junos:must "(\" .. bfd-liveness-detection\")";
             junos:must-message "strict bfd cannot be configured without bfd.";
             junos:must "(!(\" .. bfd-liveness-detection full-neighbors-only\"))";
             junos:must-message "full-neighbors-only and strict-bfd cannot be configured together";
             type empty;
           }
           container post-convergence-lfa {
             presence "enable post-convergence-lfa";
             junos:must "(\"protocols ospf backup-spf-options use-post-convergence-lfa\")";
             junos:must-message "Not allowed without 'protocols ospf backup-spf-options use-post-convergence-lfa'";
             description "Protect interface using post-convergence backup path";
             uses apply-advanced;
             container node-protection {
               presence "enable node-protection";
               description "Compute backup path assuming node failure";
               uses apply-advanced;
               leaf cost {
                 description "Cost for node protection";
                 type union {
                   type string {
                     pattern "<.*>|$.*";
                   }
                   type uint16 {
                     range "1 .. 65535";
                   }
                 }
               }
             }
             leaf srlg-protection {
               description "Compute backup path assuming SRLG failure";
               type empty;
             }
             leaf fate-sharing-protection {
               description "Compute backup path assuming fate-sharing group failure";
               type empty;
             }
           }
           leaf te-metric {
             description "Traffic engineering metric";
             type union {
               type string {
                 pattern "<.*>|$.*";
               }
               type uint32 {
                 range "1 .. 4294967295";
               }
             }
           }
           container ldp-synchronization {
             description "Advertise maximum metric until LDP is operational";
             presence "enable ldp-synchronization";
             uses ldp-sync-obj;
           }
           container ipv4-adjacency-segment {
             junos:must "(!(\".. no-advertise-adjacency-segment\"))";
             junos:must-message "ipv4-adjacency-segment can't be configured if no-advertise-adjacency-segment is configured in the same interface";
             description "Configure ipv4 adjacency segment";
             uses apply-advanced;
             container protected {
               description "Adjacency SID is eligible for protection";
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
             container unprotected {
               description "Adjacency SID uneligible for protection";
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
           }
           list lan-neighbor {
             key name;
             ordered-by user;
             description "Configuration specific to a LAN neighbor";
             junos:must "(!(\".. ipv4-adjacency-segment\"))";
             junos:must-message "lan-neighbor can't be configured if ipv4-adjacency-segment is configured in the same interface";
             junos:must "(!(\".. no-advertise-adjacency-segment\"))";
             junos:must-message "lan-neighbor can't be configured if no-advertise-adjacency-segment is configured in the same interface ";
             junos:must "(!(\".. interface-type p2p\"))";
             junos:must-message "lan-neighbor can't be configured for point-to-point interfaces";
             leaf name {
               description "Address of neighbor";
               type jt:ipaddr;
             }
             uses apply-advanced;
             container ipv4-adjacency-segment {
               junos:must "(!(\".. no-advertise-adjacency-segment\"))";
               junos:must-message "ipv4-adjacency-segment can't be configured if no-advertise-adjacency-segment is configured in the same interface";
               description "Configure ipv4 adjacency segment";
               uses apply-advanced;
               container protected {
                 description "Adjacency SID is eligible for protection";
                 choice adjsid-type {
                   case case_1 {
                     container index {
                       description "Adjacency SID indexed from SRGB";
                       leaf index-number {
                         type union {
                           type string {
                             pattern "<.*>|$.*";
                           }
                           type uint32 {
                             range "0 .. 199999";
                           }
                         }
                       }
                     }
                   }
                   case case_2 {
                     leaf label {
                       description "Adjacency SID from static label pool";
                       type union {
                         type string {
                           pattern "<.*>|$.*";
                         }
                         type uint32 {
                           range "16 .. 1048575";
                         }
                       }
                     }
                   }
                   case case_3 {
                     leaf dynamic {
                       description "Dynamically allocate an adjacency segment";
                       type empty;
                     }
                   }
                 }
               }
               container unprotected {
                 description "Adjacency SID uneligible for protection";
                 choice adjsid-type {
                   case case_1 {
                     container index {
                       description "Adjacency SID indexed from SRGB";
                       leaf index-number {
                         type union {
                           type string {
                             pattern "<.*>|$.*";
                           }
                           type uint32 {
                             range "0 .. 199999";
                           }
                         }
                       }
                     }
                   }
                   case case_2 {
                     leaf label {
                       description "Adjacency SID from static label pool";
                       type union {
                         type string {
                           pattern "<.*>|$.*";
                         }
                         type uint32 {
                           range "16 .. 1048575";
                         }
                       }
                     }
                   }
                   case case_3 {
                     leaf dynamic {
                       description "Dynamically allocate an adjacency segment";
                       type empty;
                     }
                   }
                 }
               }
             }
           }
           leaf delay-metric {
             description "Delay metric";
             units "microseconds";
             type union {
               type string {
                 pattern "<.*>|$.*";
               }
               type uint32 {
                 range "0 .. 16777215";
               }
             }
           }
           container delay-measurement {
             presence "enable delay-measurement";
             description "Enable delay measurement";
             uses apply-advanced;
             leaf probe-interval {
               description "Probe interval";
               units "seconds";
               type union {
                 type string {
                   pattern "<.*>|$.*";
                 }
                 type uint32 {
                   range "1 .. 255";
                 }
               }
             }
             leaf probe-count {
               description "Probe count";
               type union {
                 type string {
                   pattern "<.*>|$.*";
                 }
                 type uint32 {
                   range "1 .. 15";
                 }
               }
             }
             container advertisement {
               description "Delay advertisement";
               uses apply-advanced;
               container periodic {
                 description "Periodic advertisement parameters";
                 uses apply-advanced;
                 leaf threshold {
                   description "Threshold";
                   units "percentage";
                   type union {
                     type string {
                       pattern "<.*>|$.*";
                     }
                     type uint32 {
                       range "0 .. 100";
                     }
                   }
                 }
                 leaf interval {
                   description "Interval";
                   units "seconds";
                   type union {
                     type string {
                       pattern "<.*>|$.*";
                     }
                     type uint32 {
                       range "30 .. 3600";
                     }
                   }
                 }
               }
               container accelerated {
                 presence "enable accelerated";
                 description "Accelerated advertisement parameters";
                 uses apply-advanced;
                 leaf threshold {
                   description "Threshold";
                   units "percentage";
                   type union {
                     type string {
                       pattern "<.*>|$.*";
                     }
                     type uint32 {
                       range "0 .. 100";
                     }
                   }
                 }
               }
             }
           }
           container application-specific {
             description "Advertise application-specific TE attributes";
             uses apply-advanced;
             list attribute-group {
               key name;
               ordered-by user;
               description "Link attribute group name";
               max-elements 1;
               leaf name {
                 description "Link attribute group name";
                 type string;
               }
               uses apply-advanced;
               leaf te-metric {
                 description "Traffic engineering metric for this attribute group";
                 junos:must "(\".. application\")";
                 junos:must-message "Atleast one application is must";
                 type union {
                   type string {
                     pattern "<.*>|$.*";
                   }
                   type uint32 {
                     range "1 .. 4294967295";
                   }
                 }
               }
               leaf-list admin-group {
                 ordered-by user;
                 description "Administrative groups for this attribute-group";
                 junos:must "(\".. application\")";
                 junos:must-message "Atleast one application is must";
                 type string;
                 max-elements 16;
               }
               leaf delay-metric {
                 description "Delay metric for this attribute-group";
                 units "microseconds";
                 junos:must "(!(\".. advertise-interface-delay\"))";
                 junos:must-message "ASLA delay-metric can't be configured with ASLA advertise interface delay knob";
                 junos:must "(\".. application\")";
                 junos:must-message "Atleast one application is must";
                 type union {
                   type string {
                     pattern "<.*>|$.*";
                   }
                   type uint32 {
                     range "0 .. 16777215";
                   }
                 }
               }
               leaf advertise-interface-delay {
                 description "Use interface specific static/dynamic delay values as applicable in ASLA Sub-TLVs";
                 junos:must "((\".. .. .. delay-metric\" || \".. .. .. delay-measurement\"))";
                 junos:must-message "Interface specific delay values must be configured for advertise interface delay knob";
                 junos:must "(\".. application\")";
                 junos:must-message "Atleast one application is must";
                 type empty;
               }
               container application {
                 junos:must "((\".. delay-metric\" || (\".. admin-group\" || (\".. te-metric\" || \".. advertise-interface-delay\"))))";
                 junos:must-message "Atleast one attribute must be configured";
                 description "Standard Applications part of this attribute-group";
                 uses apply-advanced;
                 leaf flex-algorithm {
                   description "Set X flag in standard application bit mask";
                   type empty;
                 }
               }
             }
           }
         }
         leaf no-context-identifier-advertisement {
           description "Disable context identifier advertisments in this area";
           junos:must "(!(\".. context-identifier\"))";
           junos:must-message "no-context-identifier-advertisement and context-identifier attributes are mutually exclusive";
           type empty;
         }
         list peer-interface {
           key name;
           ordered-by user;
           description "Configuration for peer interface";
           leaf name {
             description "Name of peer interface";
             type string;
           }
           uses apply-advanced;
           choice enable-disable {
             case case_1 {
               leaf disable {
                 description "Disable OSPF on this control peer";
                 type empty;
               }
             }
           }
           leaf retransmit-interval {
             description "Retransmission interval (seconds)";
             type union {
               type string {
                 pattern "<.*>|$.*";
               }
               type uint32 {
                 range "1 .. 65535";
               }
             }
           }
           leaf transit-delay {
             description "Transit delay (seconds)";
             type union {
               type string {
                 pattern "<.*>|$.*";
               }
               type uint32 {
                 range "1 .. 65535";
               }
             }
           }
           leaf hello-interval {
             description "Hello interval (seconds)";
             type union {
               type string {
                 pattern "<.*>|$.*";
               }
               type uint32 {
                 range "1 .. 255";
               }
             }
           }
           leaf dead-interval {
             description "Dead interval (seconds)";
             type union {
               type string {
                 pattern "<.*>|$.*";
               }
               type uint32 {
                 range "1 .. 65535";
               }
             }
           }
           leaf mtu {
             description "Maximum OSPF packet size";
             type union {
               type string {
                 pattern "<.*>|$.*";
               }
               type uint32 {
                 range "128 .. 65535";
               }
             }
           }
           choice auth {
             case case_1 {
               container authentication {
                 uses juniper-ospf-authentication;
               }
             }
             case case_2 {
               container authentication-key {
                 description "Authentication key";
                 status deprecated;
                 leaf keyname {
                   description "Authentication key value";
                   type jt:unreadable;
                 }
                 leaf key-id {
                   description "Key ID for MD5 authentication";
                   type union {
                     type string {
                       pattern "<.*>|$.*";
                     }
                     type uint32 {
                       range "0 .. 255";
                     }
                   }
                 }
               }
             }
           }
           leaf demand-circuit {
             description "Interface functions as a demand circuit";
             type empty;
           }
           leaf flood-reduction {
             description "Enable flood reduction";
             type empty;
           }
           leaf no-neighbor-down-notification {
             description "Don't inform other protocols about neighbor down events";
             type empty;
           }
         }
         leaf no-source-packet-routing {
           description "Disable SPRING in this area";
           type empty;
         }
         list context-identifier {
           key name;
           ordered-by user;
           description "Configure context identifier in support of edge protection";
           junos:must "(!(\".. no-context-identifier-advertisement\"))";
           junos:must-message "no-context-identifier-advertisement and context-identifier attributes are mutually exclusive";
           leaf name {
             description "Context identifier";
             type jt:ipv4addr;
           }
           uses apply-advanced;
         }
         list label-switched-path {
           key name;
           ordered-by user;
           description "Configuration for advertisement of a label-switched path";
           junos:must "(!(\".. .. traffic-engineering multicast-rpf-routes\"))";
           junos:must-message "cannot advertise LSPs when using multicast-rpf-routes";
           leaf name {
             description "Name of label-switched path to be advertised";
             type string {
               length "1 .. 64";
             }
           }
           uses apply-advanced;
           choice enable-disable {
             case case_1 {
               leaf disable {
                 description "Disable OSPF on this label-switched path";
                 type empty;
               }
             }
           }
           leaf metric {
             description "Interface metric";
             type union {
               type string {
                 pattern "<.*>|$.*";
               }
               type uint16 {
                 range "1 .. 65535";
               }
             }
           }
           list topology {
             key name;
             ordered-by user;
             description "Topology specific attributes";
             leaf name {
               description "Topology name";
               type string;
             }
             uses apply-advanced;
             leaf disable {
               description "Disable this topology";
               type empty;
             }
             leaf metric {
               description "Topology metric";
               type union {
                 type string {
                   pattern "<.*>|$.*";
                 }
                 type uint16 {
                   range "1 .. 65535";
                 }
               }
             }
             container bandwidth-based-metrics {
               junos:must "(\".. metric\")";
               junos:must-message "Metric must be configured";
               description "Configure bandwidth based metrics";
               uses apply-advanced;
               list bandwidth {
                 key name;
                 description "Bandwidth threshold";
                 leaf name {
                   type string;
                 }
                 leaf metric {
                   description "Metric associated with specified bandwidth";
                   type union {
                     type string {
                       pattern "<.*>|$.*";
                     }
                     type uint16 {
                       range "1 .. 65535";
                     }
                   }
                 }
               }
             }
           }
         }
       }
       choice enable-disable {
         case case_1 {
           leaf disable {
             description "Disable OSPF";
             type empty;
           }
         }
       }
       container traceoptions {
         description "Trace options for OSPF";
         uses apply-advanced;
         container file {
           description "Trace file options";
           leaf filename {
             description "Name of file in which to write trace information";
             type string {
               length "1 .. 1024";
               junos:posix-pattern "![/ %]";
               junos:pattern-message "Must not contain '/', % or a space";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "spf" {
                 description "Trace SPF calculations";
               }
               enum "error" {
                 description "Trace errored packets";
               }
               enum "event" {
                 description "Trace OSPF state machine events";
               }
               enum "packet-dump" {
                 description "Dump the contents of selected packet types";
               }
               enum "flooding" {
                 description "Trace LSA flooding";
               }
               enum "lsa-analysis" {
                 description "Trace LSA analysis";
               }
               enum "packets" {
                 description "Trace all OSPF packets";
               }
               enum "hello" {
                 description "Trace hello packets";
               }
               enum "database-description" {
                 description "Trace database description packets";
               }
               enum "lsa-request" {
                 description "Trace LSA request packets";
               }
               enum "lsa-update" {
                 description "Trace LSA update packets";
               }
               enum "lsa-ack" {
                 description "Trace LSA acknowledgment packets";
               }
               enum "ldp-synchronization" {
                 description "Trace synchronization between OSPF and LDP";
               }
               enum "on-demand" {
                 description "Trace demand circuit extensions";
               }
               enum "nsr-synchronization" {
                 description "Trace NSR synchronization events";
               }
               enum "graceful-restart" {
                 description "Trace graceful restart";
               }
               enum "restart-signaling" {
                 description "Trace restart signaling";
               }
               enum "backup-spf" {
                 description "Trace backup SPF (LFA) specific events";
               }
               enum "source-packet-routing" {
                 description "Trace source packet routing (SPRING) events";
               }
               enum "post-convergence-lfa" {
                 description "Trace post-convergence-lfa related events";
               }
               enum "flex-algorithm" {
                 description "Trace flex-algorithm related events";
               }
               enum "rmopd" {
                 description "Trace rmopd interactions";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
       leaf prefix-export-limit {
         description "Maximum number of prefixes that can be exported";
         type union {
           type string {
             pattern "<.*>|$.*";
           }
           type uint32 {
             range "0 .. 4294967295";
           }
         }
       }
       container rib-groups {
         description "Routing table groups for importing OSPF routes";
         uses apply-advanced;
         leaf inet {
           description "Name of the IPv4/v6 routing table group";
           junos:must "(\"routing-options rib-groups $$\")";
           junos:must-message "Referenced rib-groups must be defined";
           junos:must "(!(\".. topology $$={default} rib-group\"))";
           junos:must-message "rib-group cannot be used with topology default rib-group";
           type string;
         }
         leaf inet3 {
           description "Name of the IPv4/v6 inet.3 routing table group";
           junos:must "(\"routing-options rib-groups $$\")";
           junos:must-message "Referenced rib-groups must be defined";
           junos:must "(!(\".. topology $$={default} rib-group\"))";
           junos:must-message "rib-group cannot be used with topology default rib-group";
           type string;
         }
       }
       leaf job-stats {
         description "Collect job statistics";
         type empty;
       }
       container overload {
         presence "enable overload";
         description "Set the overload mode (repel transit traffic)";
         uses apply-advanced;
         leaf timeout {
           description "Time after which overload mode is reset";
           units "seconds";
           type union {
             type string {
               pattern "<.*>|$.*";
             }
             type uint32 {
               range "60 .. 3600";
             }
           }
         }
         leaf allow-route-leaking {
           description "Allow routes to be leaked when overload is configured";
           type empty;
         }
         leaf stub-network {
           description "Advertise Stub Network with maximum metric";
           type empty;
         }
         leaf intra-area-prefix {
           description "Advertise Intra Area Prefix with maximum metric";
           type empty;
         }
         leaf as-external {
           description "Advertise As External with maximum usable metric";
           type empty;
         }
       }
       container database-protection {
         presence "enable database-protection";
         description "Configure database protection attributes";
         uses apply-advanced;
         leaf maximum-lsa {
           description "Maximum allowed non self-generated LSAs";
           type union {
             type string {
               pattern "<.*>|$.*";
             }
             type uint32 {
               range "1 .. 1000000";
             }
           }
         }
         leaf warning-only {
           description "Emit only a warning when LSA maximum limit is exceeded";
           type empty;
         }
         leaf warning-threshold {
           description "Percentage of LSA maximum above which to trigger warning";
           units "percent";
           type union {
             type string {
               pattern "<.*>|$.*";
             }
             type uint8 {
               range "30 .. 100";
             }
           }
         }
         leaf ignore-count {
           description "Maximum number of times to go into ignore state";
           type union {
             type string {
               pattern "<.*>|$.*";
             }
             type uint8 {
               range "1 .. 32";
             }
           }
         }
         leaf ignore-time {
           description "Time to stay in ignore state and ignore all neighbors";
           units "seconds";
           type union {
             type string {
               pattern "<.*>|$.*";
             }
             type uint16 {
               range "30 .. 3600";
             }
           }
         }
         leaf reset-time {
           description "Time after which the ignore count gets reset to zero";
           units "seconds";
           type union {
             type string {
               pattern "<.*>|$.*";
             }
             type uint32 {
               range "60 .. 86400";
             }
           }
         }
       }
       container graceful-restart {
         description "Configure graceful restart attributes";
         uses apply-advanced;
         choice enable-disable {
           case case_1 {
             leaf disable {
               description "Disable OSPF graceful restart capability";
               type empty;
             }
           }
         }
         leaf restart-duration {
           description "Time for all neighbors to become full";
           units "seconds";
           type union {
             type string {
               pattern "<.*>|$.*";
             }
             type uint32 {
               range "1 .. 3600";
             }
           }
         }
         leaf notify-duration {
           description "Time to send all max-aged grace LSAs";
           units "seconds";
           type union {
             type string {
               pattern "<.*>|$.*";
             }
             type uint32 {
               range "1 .. 3600";
             }
           }
         }
         container helper-disable {
           presence "enable helper-disable";
           description "Disable graceful restart helper capability";
           uses apply-advanced;
           choice disable-choices {
             case case_1 {
               leaf standard {
                 description "Disable helper-mode for rfc3623 based GR";
                 type empty;
               }
             }
             case case_2 {
               leaf restart-signaling {
                 description "Disable helper mode for restart-signaling ";
                 type empty;
               }
             }
             case case_3 {
               leaf both {
                 description "Disable helper mode for both the types of GR";
                 type empty;
               }
             }
           }
         }
         leaf no-strict-lsa-checking {
           description "Do not abort graceful helper mode upon LSA changes";
           junos:must "(!(\".. helper-disable\"))";
           junos:must-message "To configure no-strict-lsa-checking, helper-disable must not be set";
           type empty;
         }
       }
       leaf route-type-community {
         description "Specify BGP extended community value to encode OSPF route type";
         type enumeration {
           enum "iana" {
             description "BGP extended community value used is 0x0306";
           }
           enum "vendor" {
             description "Vendor BGP extended community value used is 0x8000";
           }
         }
       }
       container domain-id {
         description "Configure domain ID";
         choice domain_id_or_disable {
           case case_1 {
             leaf domain-id {
               description "Domain ID";
               type string;
             }
           }
           case case_2 {
             leaf disable {
               description "Disable domain ID";
               type empty;
             }
           }
         }
       }
       choice domain_vpn_tag_or_disable {
         case case_1 {
           leaf domain-vpn-tag {
             description "Domain VPN tag for external LSA";
             type union {
               type string {
                 pattern "<.*>|$.*";
               }
               type uint32 {
                 range "0 .. 4294967295";
               }
             }
           }
         }
         case case_2 {
           leaf no-domain-vpn-tag {
             description "Disable domain VPN tag";
             type empty;
           }
         }
       }
       leaf preference {
         description "Preference of internal routes";
         type union {
           type uint32;
           type string {
             pattern "<.*>|$.*";
           }
         }
       }
       leaf external-preference {
         description "Preference of external routes";
         type union {
           type uint32;
           type string {
             pattern "<.*>|$.*";
           }
         }
       }
       leaf labeled-preference {
         description "Preference of labeled routes";
         type union {
           type uint32;
           type string {
             pattern "<.*>|$.*";
           }
         }
       }
       leaf-list export {
         ordered-by user;
         description "Export policy";
         type jt:policy-algebra;
       }
       leaf-list import {
         ordered-by user;
         description "Import policy (for external routes or setting priority)";
         type jt:policy-algebra;
       }
       leaf reference-bandwidth {
         description "Bandwidth for calculating metric defaults";
         type string;
       }
       leaf lsa-refresh-interval {
         description "LSA refresh interval (minutes)";
         default "50";
         type union {
           type string {
             pattern "<.*>|$.*";
           }
           type uint32 {
             range "25 .. 50";
           }
         }
       }
       leaf spf-delay {
         description "Time to wait before running an SPF";
         status deprecated;
         units "milliseconds";
         junos:must "(!(\".. spf-options delay\"))";
         junos:must-message "You can only configure either spf-delay or delay under spf-options";
         type union {
           type string {
             pattern "<.*>|$.*";
           }
           type uint32 {
             range "50 .. 8000";
           }
         }
       }
       leaf no-rfc-1583 {
         description "Disable RFC1583 compatibility";
         type empty;
       }
       leaf forwarding-address-to-broadcast {
         description "Set forwarding address in Type 5 LSA in broadcast network";
         type empty;
       }
       choice nssa-abr-option {
         case case_1 {
           leaf no-nssa-abr {
             description "Disable full NSSA functionality at ABR";
             type empty;
           }
         }
       }
       container sham-link {
         presence "enable sham-link";
         description "Configure parameters for sham links";
         uses apply-advanced;
         leaf local {
           description "Local sham link endpoint address";
           type jt:ipaddr;
         }
         leaf no-advertise-local {
           description "Don't advertise local sham link endpoint as stub in router LSA";
           status deprecated;
           type empty;
         }
       }
     }
     uses apply-advanced;
     list topology {
       key name;
       ordered-by user;
       description "Topology parameters";
       leaf name {
         description "Topology name";
         type string;
       }
       uses apply-advanced;
       leaf disable {
         description "Disable this topology";
         type empty;
       }
       leaf topology-id {
         description "Topology identifier";
         type union {
           type string {
             pattern "<.*>|$.*";
           }
           type uint8 {
             range "32 .. 127";
           }
         }
       }
       leaf overload {
         description "Set the overload mode (repel transit traffic)";
         type empty;
       }
       leaf rib-group {
         description "Routing table group for importing routes";
         junos:must "(\"routing-options rib-groups $$\")";
         junos:must-message "Referenced rib-group must be defined";
         type string;
       }
       container spf-options {
         description "Configure options for SPF";
         uses apply-advanced;
         container microloop-avoidance {
           junos:must "(\"protocols ospf source-packet-routing\")";
           junos:must-message "Configuration of 'protocols ospf source-packet-routing' is required";
           description "Configure microloop avoidance mechanism";
           uses apply-advanced;
           container post-convergence-path {
             presence "enable post-convergence-path";
             description "Temporarily install post-convergence path for routes potentially affected by microloops";
             uses apply-advanced;
             leaf delay {
               description "Time after which temporary post-convergence paths are removed";
               units "milliseconds";
               type union {
                 type string {
                   pattern "<.*>|$.*";
                 }
                 type uint32 {
                   range "500 .. 60000";
                 }
               }
             }
             leaf maximum-labels {
               description "Maximum number of labels installed for post-convergence paths";
               type union {
                 type string {
                   pattern "<.*>|$.*";
                 }
                 type uint32 {
                   range "2 .. 8";
                 }
               }
             }
           }
         }
         leaf delay {
           description "Time to wait before running an SPF";
           units "milliseconds";
           type union {
             type string {
               pattern "<.*>|$.*";
             }
             type uint32 {
               range "50 .. 8000";
             }
           }
         }
         leaf holddown {
           description "Time to hold down before running an SPF";
           units "milliseconds";
           type union {
             type string {
               pattern "<.*>|$.*";
             }
             type uint32 {
               range "2000 .. 20000";
             }
           }
         }
         leaf rapid-runs {
           description "Number of maximum rapid SPF runs before holddown";
           type union {
             type string {
               pattern "<.*>|$.*";
             }
             type uint32 {
               range "1 .. 10";
             }
           }
         }
         leaf no-ignore-our-externals {
           description "Do not ignore self-generated external and NSSA LSAs";
           type empty;
         }
       }
       container backup-spf-options {
         description "Configure options for backup SPF";
         uses apply-advanced;
         container remote-backup-calculation {
           presence "enable remote-backup-calculation";
           junos:must "(!(\"protocols ospf backup-spf-options use-post-convergence-lfa\"))";
           junos:must-message "Not allowed with 'protocols ospf backup-spf-options use-post-convergence-lfa'";
           description "Calculate Remote LFA backup nexthops";
           uses apply-advanced;
           container pq-nodes-nearest-to-source {
             description "PQ nodes selection based upon nearest to source";
             uses apply-advanced;
             leaf percent {
               description "Selection percentage for nearest to source";
               type union {
                 type string {
                   pattern "<.*>|$.*";
                 }
                 type uint32 {
                   range "10 .. 100";
                 }
               }
             }
           }
         }
         container use-post-convergence-lfa {
           presence "enable use-post-convergence-lfa";
           junos:must "(\"protocols ospf source-packet-routing\")";
           junos:must-message "Configuration of 'protocols ospf source-packet-routing' is required";
           description "Calculate post-convergence backup paths";
           uses apply-advanced;
           leaf maximum-labels {
             description "Maximum number of labels installed for post-convergence paths";
             type union {
               type string {
                 pattern "<.*>|$.*";
               }
               type uint32 {
                 range "2 .. 8";
               }
             }
           }
           leaf maximum-backup-paths {
             description "Maximum number of equal-cost post-convergence paths installed";
             type union {
               type string {
                 pattern "<.*>|$.*";
               }
               type uint32 {
                 range "1 .. 8";
               }
             }
           }
         }
         leaf use-source-packet-routing {
           description "Use spring backup paths for inet.0 routes";
           junos:must "(\".. .. source-packet-routing\")";
           junos:must-message "Configuration of 'protocols ospf source-packet-routing' is required";
           junos:must "(!(\".. remote-backup-calculation\"))";
           junos:must-message "Not allowed with 'protocols ospf backup-spf-options remote-backup-calculation'";
           type empty;
         }
         leaf disable {
           description "Do not run backup SPF";
           junos:must "(!(\"protocols ospf backup-spf-options use-post-convergence-lfa\"))";
           junos:must-message "Not allowed with 'protocols ospf backup-spf-options use-post-convergence-lfa'";
           type empty;
         }
         leaf no-install {
           description "Do not install backup nexthops into the RIB";
           type empty;
         }
         leaf downstream-paths-only {
           description "Use only downstream backup paths";
           junos:must "(!(\"protocols ospf backup-spf-options use-post-convergence-lfa\"))";
           junos:must-message "Not allowed with 'protocols ospf backup-spf-options use-post-convergence-lfa'";
           type empty;
         }
         container per-prefix-calculation {
           junos:must "(!(\"protocols ospf backup-spf-options use-post-convergence-lfa\"))";
           junos:must-message "Not allowed with 'protocols ospf backup-spf-options use-post-convergence-lfa'";
           description "Calculate backup nexthops for non-best prefix originators";
           uses apply-advanced;
           leaf stubs {
             description "Per prefix calculation for stubs only";
             type empty;
           }
           leaf summary {
             description "Per prefix calculation for summary originators only";
             type empty;
           }
           leaf externals {
             description "Per prefix calculation for externals";
             type empty;
           }
           leaf all {
             description "Per prefix calculation for all";
             type empty;
           }
         }
         leaf node-link-degradation {
           description "Degrade to link protection when nodelink protection not available";
           junos:must "(!(\"protocols ospf backup-spf-options use-post-convergence-lfa\"))";
           junos:must-message "Not allowed with 'protocols ospf backup-spf-options use-post-convergence-lfa'";
           type empty;
         }
       }
       leaf prefix-export-limit {
         description "Maximum number of prefixes that can be exported";
         type union {
           type string {
             pattern "<.*>|$.*";
           }
           type uint32 {
             range "0 .. 4294967295";
           }
         }
       }
     }
     container spf-options {
       description "Configure options for SPF";
       uses apply-advanced;
       container microloop-avoidance {
         junos:must "(\"protocols ospf source-packet-routing\")";
         junos:must-message "Configuration of 'protocols ospf source-packet-routing' is required";
         description "Configure microloop avoidance mechanism";
         uses apply-advanced;
         container post-convergence-path {
           presence "enable post-convergence-path";
           description "Temporarily install post-convergence path for routes potentially affected by microloops";
           uses apply-advanced;
           leaf delay {
             description "Time after which temporary post-convergence paths are removed";
             units "milliseconds";
             type union {
               type string {
                 pattern "<.*>|$.*";
               }
               type uint32 {
                 range "500 .. 60000";
               }
             }
           }
           leaf maximum-labels {
             description "Maximum number of labels installed for post-convergence paths";
             type union {
               type string {
                 pattern "<.*>|$.*";
               }
               type uint32 {
                 range "2 .. 8";
               }
             }
           }
         }
       }
       leaf delay {
         description "Time to wait before running an SPF";
         units "milliseconds";
         type union {
           type string {
             pattern "<.*>|$.*";
           }
           type uint32 {
             range "50 .. 8000";
           }
         }
       }
       leaf holddown {
         description "Time to hold down before running an SPF";
         units "milliseconds";
         type union {
           type string {
             pattern "<.*>|$.*";
           }
           type uint32 {
             range "2000 .. 20000";
           }
         }
       }
       leaf rapid-runs {
         description "Number of maximum rapid SPF runs before holddown";
         type union {
           type string {
             pattern "<.*>|$.*";
           }
           type uint32 {
             range "1 .. 10";
           }
         }
       }
       leaf no-ignore-our-externals {
         description "Do not ignore self-generated external and NSSA LSAs";
         type empty;
       }
     }
     container backup-spf-options {
       description "Configure options for backup SPF";
       uses apply-advanced;
       container remote-backup-calculation {
         presence "enable remote-backup-calculation";
         junos:must "(!(\"protocols ospf backup-spf-options use-post-convergence-lfa\"))";
         junos:must-message "Not allowed with 'protocols ospf backup-spf-options use-post-convergence-lfa'";
         description "Calculate Remote LFA backup nexthops";
         uses apply-advanced;
         container pq-nodes-nearest-to-source {
           description "PQ nodes selection based upon nearest to source";
           uses apply-advanced;
           leaf percent {
             description "Selection percentage for nearest to source";
             type union {
               type string {
                 pattern "<.*>|$.*";
               }
               type uint32 {
                 range "10 .. 100";
               }
             }
           }
         }
       }
       container use-post-convergence-lfa {
         presence "enable use-post-convergence-lfa";
         junos:must "(\"protocols ospf source-packet-routing\")";
         junos:must-message "Configuration of 'protocols ospf source-packet-routing' is required";
         description "Calculate post-convergence backup paths";
         uses apply-advanced;
         leaf maximum-labels {
           description "Maximum number of labels installed for post-convergence paths";
           type union {
             type string {
               pattern "<.*>|$.*";
             }
             type uint32 {
               range "2 .. 8";
             }
           }
         }
         leaf maximum-backup-paths {
           description "Maximum number of equal-cost post-convergence paths installed";
           type union {
             type string {
               pattern "<.*>|$.*";
             }
             type uint32 {
               range "1 .. 8";
             }
           }
         }
       }
       leaf use-source-packet-routing {
         description "Use spring backup paths for inet.0 routes";
         junos:must "(\".. .. source-packet-routing\")";
         junos:must-message "Configuration of 'protocols ospf source-packet-routing' is required";
         junos:must "(!(\".. remote-backup-calculation\"))";
         junos:must-message "Not allowed with 'protocols ospf backup-spf-options remote-backup-calculation'";
         type empty;
       }
       leaf disable {
         description "Do not run backup SPF";
         junos:must "(!(\"protocols ospf backup-spf-options use-post-convergence-lfa\"))";
         junos:must-message "Not allowed with 'protocols ospf backup-spf-options use-post-convergence-lfa'";
         type empty;
       }
       leaf no-install {
         description "Do not install backup nexthops into the RIB";
         type empty;
       }
       leaf downstream-paths-only {
         description "Use only downstream backup paths";
         junos:must "(!(\"protocols ospf backup-spf-options use-post-convergence-lfa\"))";
         junos:must-message "Not allowed with 'protocols ospf backup-spf-options use-post-convergence-lfa'";
         type empty;
       }
       container per-prefix-calculation {
         junos:must "(!(\"protocols ospf backup-spf-options use-post-convergence-lfa\"))";
         junos:must-message "Not allowed with 'protocols ospf backup-spf-options use-post-convergence-lfa'";
         description "Calculate backup nexthops for non-best prefix originators";
         uses apply-advanced;
         leaf stubs {
           description "Per prefix calculation for stubs only";
           type empty;
         }
         leaf summary {
           description "Per prefix calculation for summary originators only";
           type empty;
         }
         leaf externals {
           description "Per prefix calculation for externals";
           type empty;
         }
         leaf all {
           description "Per prefix calculation for all";
           type empty;
         }
       }
       leaf node-link-degradation {
         description "Degrade to link protection when nodelink protection not available";
         junos:must "(!(\"protocols ospf backup-spf-options use-post-convergence-lfa\"))";
         junos:must-message "Not allowed with 'protocols ospf backup-spf-options use-post-convergence-lfa'";
         type empty;
       }
     }
     container traffic-engineering {
       presence "enable traffic-engineering";
       description "Configure traffic engineering attributes";
       uses apply-advanced;
       leaf no-topology {
         description "Disable dissemination of TE link-state topology information";
         type empty;
       }
       leaf multicast-rpf-routes {
         description "Install routes for multicast RPF checks into inet.2";
         junos:must "(!(\".. .. topology $$={ipv4-multicast}\"))";
         junos:must-message "multicast-rpf-routes cannot be used with topology ipv4-multicast";
         junos:must "(\".. shortcuts\")";
         junos:must-message "multicast-rpf-routes cannot be used without shortcuts";
         type empty;
       }
       leaf l3-unicast-topology {
         description "Download IGP topology into TED";
         type empty;
       }
       container ignore-lsp-metrics {
         presence "enable ignore-lsp-metrics";
         description "Ignore label-switched path metrics when doing shortcuts";
         uses apply-advanced;
         leaf unconfigured-only {
           description "Ignore lsp metrics for unconfigured only";
           type empty;
         }
       }
       container shortcuts {
         presence "enable shortcuts";
         description "Use label-switched paths as next hops, if possible";
         uses apply-advanced;
         leaf ignore-lsp-metrics {
           description "Ignore label-switched path metrics when doing shortcuts";
           status deprecated;
           type empty;
         }
         leaf lsp-metric-into-summary {
           description "Advertise LSP metric into summary LSAs";
           type empty;
         }
         list family {
           key name;
           ordered-by user;
           description "Address family specific traffic-engineering attributes";
           leaf name {
             type enumeration {
               enum "inet" {
                 description "IPv4 family";
               }
               enum "inet-mpls" {
                 description "IPv4-MPLS family";
               }
             }
           }
           uses apply-advanced;
         }
       }
       leaf advertise-unnumbered-interfaces {
         description "Advertise unnumbered interfaces";
         type empty;
       }
       leaf credibility-protocol-preference {
         description "TED protocol credibility follows protocol preference";
         type empty;
       }
       container advertisement {
         description "Advertise TE parameters even if RSVP is not turned on";
         uses apply-advanced;
         leaf always {
           description "Advertise TE parameters in TE LSAs";
           type empty;
         }
       }
     }
     container source-packet-routing {
       presence "enable source-packet-routing";
       junos:must "(!(\".. .. .. protocols mpls disable\"))";
       junos:must-message "SPRING configuration is not allowed with 'protocols mpls disable'";
       junos:must "(\".. .. .. protocols mpls \")";
       junos:must-message "SPRING configuration is not allowed without 'protocols mpls'";
       description "Enable source packet routing (SPRING)";
       uses apply-advanced;
       container adjacency-segment {
         description "Attributes for adjacency segments in spring";
         uses apply-advanced;
         leaf hold-time {
           description "Retain time of Adjacency segment after isolating from an interface";
           type union {
             type string {
               pattern "<.*>|$.*";
             }
             type uint32 {
               range "180000 .. 900000";
             }
           }
         }
       }
       leaf-list prefix-segment {
         ordered-by user;
         description "Prefix Segment policy";
         type jt:policy-algebra;
       }
       leaf explicit-null {
         description "Set E and P bits in all Prefix SID advertisements";
         type empty;
       }
       container node-segment {
         presence "enable node-segment";
         description "Enable support for Node segments in SPRING";
         uses apply-advanced;
         leaf ipv4-index {
           description "Set ipv4 node segment index";
           type union {
             type string {
               pattern "<.*>|$.*";
             }
             type uint32 {
               range "0 .. 199999";
             }
           }
         }
         leaf index-range {
           description "Set range of node segment indices allowed";
           type union {
             type string {
               pattern "<.*>|$.*";
             }
             type uint32 {
               range "32 .. 16385";
             }
           }
         }
       }
       container srgb {
         junos:must "(!(\".. node-segment index-range\"))";
         junos:must-message "Can not be configured with node-segment index-range";
         description "Set the SRGB global block in SPRING";
         leaf start-label {
           description "Start range for SRGB label block";
           type union {
             type string {
               pattern "<.*>|$.*";
             }
             type uint32;
           }
         }
         leaf index-range {
           description "Index to the SRGB start label block";
           type union {
             type string {
               pattern "<.*>|$.*";
             }
             type uint32;
           }
         }
       }
       leaf mapping-server {
         description "Mapping server name";
         junos:must "(\".. node-segment\")";
         junos:must-message "protocols ospf source-packet-routing node-segment must be defined";
         junos:must "(\"routing-options source-packet-routing mapping-server-entry $$\")";
         junos:must-message "Referenced source-packet-routing mapping-server-entry must be defined";
         type string;
       }
       leaf install-prefix-sid-for-best-route {
         description "For best route install a exact prefix sid route";
         type empty;
       }
       leaf ldp-stitching {
         description "Enable SR to LDP stitching";
         type empty;
       }
       leaf-list flex-algorithm {
         description "Flex-algorithms we would like to participate in";
         type union {
           type string {
             pattern "<.*>|$.*";
           }
           type uint32 {
             range "128 .. 255";
           }
         }
         max-elements 16;
       }
       leaf strict-asla-based-flex-algorithm {
         description "Flex-Algorithm to ignore links not having ASLA sub-TLVs";
         type empty;
       }
     }
     list area {
       key name;
       ordered-by user;
       description "Configure an OSPF area";
       leaf name {
         description "Area ID";
         type jt:areaid;
       }
       uses apply-advanced;
       choice stub-option {
         case case_1 {
           container stub {
             presence "enable stub";
             description "Configure a stub area";
             leaf default-metric {
               description "Metric for the default route in this stub area";
               type union {
                 type string {
                   pattern "<.*>|$.*";
                 }
                 type uint32 {
                   range "1 .. 16777215";
                 }
               }
             }
             choice summaries-choice {
               leaf summaries {
                 description "Flood summary LSAs into this stub area";
                 type empty;
               }
               leaf no-summaries {
                 description "Don't flood summary LSAs into this stub area";
                 type empty;
               }
             }
           }
         }
         case case_2 {
           container nssa {
             presence "enable nssa";
             description "Configure a not-so-stubby area";
             uses apply-advanced;
             container default-lsa {
               presence "enable default-lsa";
               description "Configure a default LSA";
               uses apply-advanced;
               leaf default-metric {
                 description "Metric for the default route in this area";
                 type union {
                   type string {
                     pattern "<.*>|$.*";
                   }
                   type uint32 {
                     range "1 .. 16777215";
                   }
                 }
               }
               leaf metric-type {
                 description "External metric type for the default type 7 LSA";
                 type union {
                   type string {
                     pattern "<.*>|$.*";
                   }
                   type uint32 {
                     range "1 .. 2";
                   }
                 }
               }
               leaf type-7 {
                 description "Flood type 7 default LSA if no-summaries is configured";
                 type empty;
               }
             }
             leaf default-metric {
               description "Metric for the default route in this area";
               status deprecated;
               type union {
                 type string {
                   pattern "<.*>|$.*";
                 }
                 type uint32 {
                   range "1 .. 16777215";
                 }
               }
             }
             leaf metric-type {
               description "External metric type for the default type 7 LSA";
               status deprecated;
               type union {
                 type string {
                   pattern "<.*>|$.*";
                 }
                 type uint32 {
                   range "1 .. 2";
                 }
               }
             }
             choice summaries-choice {
               leaf summaries {
                 description "Flood summary LSAs into this NSSA area";
                 type empty;
               }
               leaf no-summaries {
                 description "Don't flood summary LSAs into this NSSA area";
                 type empty;
               }
             }
             list area-range {
               key name;
               ordered-by user;
               description "Configure NSSA area ranges";
               leaf name {
                 description "Range to summarize NSSA routes in this area";
                 type jt:ipprefix;
               }
               uses apply-advanced;
               leaf restrict {
                 description "Restrict advertisement of this area range";
                 type empty;
               }
               leaf exact {
                 description "Enforce exact match for advertisement of this area range";
                 type empty;
               }
               container override-metric {
                 presence "enable override-metric";
                 description "Override the dynamic metric for this area-range";
                 uses apply-advanced;
                 leaf metric {
                   description "Metric value";
                   type union {
                     type string {
                       pattern "<.*>|$.*";
                     }
                     type uint32 {
                       range "1 .. 16777215";
                     }
                   }
                 }
                 leaf metric-type {
                   description "Set the metric type for the override metric";
                   default "1";
                   type union {
                     type string {
                       pattern "<.*>|$.*";
                     }
                     type uint32 {
                       range "1 .. 2";
                     }
                   }
                 }
               }
             }
           }
         }
       }
       list area-range {
         key name;
         ordered-by user;
         description "Configure area ranges";
         leaf name {
           description "Range to summarize routes in this area";
           type jt:ipprefix;
         }
         uses apply-advanced;
         leaf restrict {
           description "Restrict advertisement of this area range";
           type empty;
         }
         leaf exact {
           description "Enforce exact match for advertisement of this area range";
           type empty;
         }
         leaf override-metric {
           description "Override the dynamic metric for this area-range";
           type union {
             type string {
               pattern "<.*>|$.*";
             }
             type uint32 {
               range "1 .. 16777215";
             }
           }
         }
       }
       leaf-list network-summary-export {
         ordered-by user;
         description "Export policy for Type 3 Summary LSAs";
         type jt:policy-algebra;
       }
       leaf-list network-summary-import {
         ordered-by user;
         description "Import policy for Type 3 Summary LSAs";
         type jt:policy-algebra;
       }
       leaf-list inter-area-prefix-export {
         ordered-by user;
         description "Export policy for Inter Area Prefix LSAs";
         type jt:policy-algebra;
       }
       leaf-list inter-area-prefix-import {
         ordered-by user;
         description "Import policy for Inter Area Prefix LSAs";
         type jt:policy-algebra;
       }
       leaf authentication-type {
         description "Authentication type";
         status deprecated;
         type enumeration {
           enum "none" {
             description "No authentication";
             status deprecated;
           }
           enum "simple" {
             description "Simple password authentication";
             status deprecated;
           }
           enum "md5" {
             description "MD5 authentication";
             status deprecated;
           }
         }
       }
       list virtual-link {
         key "neighbor-id transit-area";
         ordered-by user;
         description "Configure virtual links";
         junos:must "(\".. .. area $$={0.0.0.0}\")";
         junos:must-message "virtual link can be configured only under backbone area";
         leaf neighbor-id {
           description "Router ID of a virtual neighbor";
           type jt:ipv4addr;
         }
         leaf transit-area {
           description "Transit area in common with virtual neighbor";
           type jt:areaid;
         }
         uses apply-advanced;
         choice enable-disable {
           case case_1 {
             leaf disable {
               description "Disable this virtual link";
               type empty;
             }
           }
         }
         leaf retransmit-interval {
           description "Retransmission interval (seconds)";
           type union {
             type string {
               pattern "<.*>|$.*";
             }
             type uint32 {
               range "1 .. 65535";
             }
           }
         }
         leaf transit-delay {
           description "Transit delay (seconds)";
           type union {
             type string {
               pattern "<.*>|$.*";
             }
             type uint32 {
               range "1 .. 65535";
             }
           }
         }
         leaf hello-interval {
           description "Hello interval (seconds)";
           type union {
             type string {
               pattern "<.*>|$.*";
             }
             type uint32 {
               range "1 .. 255";
             }
           }
         }
         leaf dead-interval {
           description "Dead interval (seconds)";
           type union {
             type string {
               pattern "<.*>|$.*";
             }
             type uint32 {
               range "1 .. 65535";
             }
           }
         }
         leaf mtu {
           description "Maximum OSPF packet size";
           type union {
             type string {
               pattern "<.*>|$.*";
             }
             type uint32 {
               range "128 .. 65535";
             }
           }
         }
         choice auth {
           case case_1 {
             container authentication {
               uses juniper-ospf-authentication;
             }
           }
           case case_2 {
             container authentication-key {
               description "Authentication key";
               status deprecated;
               leaf keyname {
                 description "Authentication key value";
                 type jt:unreadable;
               }
               leaf key-id {
                 description "Key ID for MD5 authentication";
                 type union {
                   type string {
                     pattern "<.*>|$.*";
                   }
                   type uint32 {
                     range "0 .. 255";
                   }
                 }
               }
             }
           }
         }
         leaf demand-circuit {
           description "Interface functions as a demand circuit";
           type empty;
         }
         leaf flood-reduction {
           description "Enable flood reduction";
           type empty;
         }
         leaf no-neighbor-down-notification {
           description "Don't inform other protocols about neighbor down events";
           type empty;
         }
         leaf ipsec-sa {
           description "IPSec security association name";
           junos:must "(!(any \".. .. interface <st*> ipsec-sa $$\"))";
           junos:must-message "Must not configure ipsec-sa for st0 interface";
           junos:must "(\"security ipsec security-association $$ manual\")";
           junos:must-message "Referenced IPSec security association must be a manual SA";
           junos:must "(\"security ipsec security-association $$ mode transport\")";
           junos:must-message "Referenced IPSec security association must be in transport mode";
           junos:must "(\"security ipsec security-association $$\")";
           junos:must-message "Referenced IPSec security association must be defined";
           type string {
             length "1 .. 32";
           }
         }
         list topology {
           key name;
           ordered-by user;
           description "Topology specific attributes";
           leaf name {
             description "Topology name";
             type string;
           }
           uses apply-advanced;
           leaf disable {
             description "Disable this topology";
             type empty;
           }
           leaf metric {
             description "Topology metric";
             type union {
               type string {
                 pattern "<.*>|$.*";
               }
               type uint16 {
                 range "1 .. 65535";
               }
             }
           }
           container bandwidth-based-metrics {
             junos:must "(\".. metric\")";
             junos:must-message "Metric must be configured";
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint16 {
                     range "1 .. 65535";
                   }
                 }
               }
             }
           }
         }
       }
       list sham-link-remote {
         key name;
         ordered-by user;
         description "Configure parameters for remote sham link endpoint";
         leaf name {
           description "Remote sham link endpoint address";
           junos:must "(!(\".. .. .. sham-link local $$\"))";
           junos:must-message "Local and remote sham link endpoint addresses must be different";
           junos:must "(\".. .. .. sham-link local\")";
           junos:must-message "Local sham link endpoint must be configured";
           type jt:ipaddr;
         }
         uses apply-advanced;
         leaf metric {
           description "Sham link metric";
           type union {
             type string {
               pattern "<.*>|$.*";
             }
             type uint16 {
               range "1 .. 65535";
             }
           }
         }
         leaf ipsec-sa {
           description "IPSec security association name";
           junos:must "(!(any \".. .. interface <st*> ipsec-sa $$\"))";
           junos:must-message "Must not configure ipsec-sa for st0 interface";
           junos:must "(\"security ipsec security-association $$ manual\")";
           junos:must-message "Referenced IPSec security association must be a manual SA";
           junos:must "(\"security ipsec security-association $$ mode transport\")";
           junos:must-message "Referenced IPSec security association must be in transport mode";
           junos:must "(\"security ipsec security-association $$\")";
           junos:must-message "Referenced IPSec security association must be defined";
           type string {
             length "1 .. 32";
           }
         }
         leaf demand-circuit {
           description "Interface functions as a demand circuit";
           type empty;
         }
         leaf flood-reduction {
           description "Enable flood reduction";
           type empty;
         }
         list topology {
           key name;
           ordered-by user;
           description "Topology specific attributes";
           leaf name {
             description "Topology name";
             type string;
           }
           uses apply-advanced;
           leaf disable {
             description "Disable this topology";
             type empty;
           }
           leaf metric {
             description "Topology metric";
             type union {
               type string {
                 pattern "<.*>|$.*";
               }
               type uint16 {
                 range "1 .. 65535";
               }
             }
           }
           container bandwidth-based-metrics {
             junos:must "(\".. metric\")";
             junos:must-message "Metric must be configured";
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint16 {
                     range "1 .. 65535";
                   }
                 }
               }
             }
           }
         }
       }
       list interface {
         key name;
         ordered-by user;
         description "Include an interface in this area";
         leaf name {
           description "Interface name";
           junos:must "((!(\".. interface-type nbma\") || (!((\"interfaces $$\" || any \"logical-systems <*> interfaces $$\")) || (any \"interfaces $$-IFL family inet address <*>\" || any \"logical-systems <*> interfaces $$-IFL family inet address <*>\"))))";
           junos:must-message "IPv4 address must be configured on the interface for nbma mode";
           type union {
             type jt:ipv4addr-or-interface;
             type string {
               pattern "<.*>|$.*";
             }
           }
         }
         uses apply-advanced;
         choice enable-disable {
           case case_1 {
             leaf disable {
               description "Disable OSPF on this interface";
               type empty;
             }
           }
         }
         leaf interface-type {
           description "Type of interface";
           type enumeration {
             enum "nbma" {
               description "Nonbroadcast multiaccess";
             }
             enum "p2mp" {
               description "Point-to-multipoint NBMA";
             }
             enum "p2p" {
               description "Point-to-point";
             }
             enum "p2mp-over-lan" {
               description "Point-to-multipoint over LAN mode";
             }
           }
         }
         choice protection-type {
           case case_1 {
             leaf link-protection {
               description "Protect interface from link faults only";
               type empty;
             }
           }
           case case_2 {
             leaf node-link-protection {
               description "Protect interface from both link and node faults";
               type empty;
             }
           }
         }
         leaf no-eligible-backup {
           description "Not eligible to backup traffic from protected interfaces";
           type empty;
         }
         leaf no-eligible-remote-backup {
           description "Not eligible for Remote-LFA backup traffic from protected interfaces";
           type empty;
         }
         container passive {
           presence "enable passive";
           description "Do not run OSPF, but advertise it";
           uses apply-advanced;
           container traffic-engineering {
             description "Advertise TE link information";
             uses apply-advanced;
             leaf remote-node-id {
               description "Remote address of the link";
               type jt:ipaddr;
             }
             leaf remote-node-router-id {
               description "TE Router-ID of the remote node";
               junos:must "(\".. remote-node-id\")";
               junos:must-message "remote-node-id must be configured";
               type jt:ipv4addr;
             }
           }
         }
         leaf secondary {
           description "Treat interface as secondary";
           junos:must "(!(\" .. ipsec-sa\"))";
           junos:must-message "secondary interface cannot have ipsec-sa configured";
           junos:must "(!(\" .. dynamic-neighbors\"))";
           junos:must-message "secondary interface cannot have dynamic-neighbors configured";
           junos:must "(!(\" .. neighbor\"))";
           junos:must-message "secondary interface cannot have configured neighbors";
           junos:must "(!(\" .. interface-type p2mp\"))";
           junos:must-message "secondary interface cannot be set as type p2mp";
           junos:must "(!(\" .. interface-type nbma\"))";
           junos:must-message "secondary interface cannot be set as type nbma";
           junos:must "(!(\" .. passive\"))";
           junos:must-message "secondary interface cannot be configured passive";
           type empty;
         }
         leaf own-router-lsa {
           description "Generate a separate router LSA for this interface";
           type empty;
         }
         container bandwidth-based-metrics {
           junos:must "(\".. metric\")";
           junos:must-message "Metric must be configured";
           description "Configure bandwidth based metrics";
           uses apply-advanced;
           list bandwidth {
             key name;
             description "Bandwidth threshold";
             leaf name {
               type string;
             }
             leaf metric {
               description "Metric associated with specified bandwidth";
               type union {
                 type string {
                   pattern "<.*>|$.*";
                 }
                 type uint16 {
                   range "1 .. 65535";
                 }
               }
             }
           }
         }
         leaf metric {
           description "Interface metric";
           type union {
             type string {
               pattern "<.*>|$.*";
             }
             type uint16 {
               range "1 .. 65535";
             }
           }
         }
         leaf priority {
           description "Designated router priority";
           type union {
             type string {
               pattern "<.*>|$.*";
             }
             type uint32 {
               range "0 .. 255";
             }
           }
         }
         leaf retransmit-interval {
           description "Retransmission interval (seconds)";
           type union {
             type string {
               pattern "<.*>|$.*";
             }
             type uint32 {
               range "1 .. 65535";
             }
           }
         }
         leaf transit-delay {
           description "Transit delay (seconds)";
           type union {
             type string {
               pattern "<.*>|$.*";
             }
             type uint32 {
               range "1 .. 65535";
             }
           }
         }
         leaf hello-interval {
           description "Hello interval (seconds)";
           type union {
             type string {
               pattern "<.*>|$.*";
             }
             type uint32 {
               range "1 .. 255";
             }
           }
         }
         leaf dead-interval {
           description "Dead interval (seconds)";
           type union {
             type string {
               pattern "<.*>|$.*";
             }
             type uint32 {
               range "1 .. 65535";
             }
           }
         }
         leaf mtu {
           description "Maximum OSPF packet size";
           type union {
             type string {
               pattern "<.*>|$.*";
             }
             type uint32 {
               range "128 .. 65535";
             }
           }
         }
         choice auth {
           case case_1 {
             container authentication {
               uses juniper-ospf-authentication;
             }
           }
           case case_2 {
             container authentication-key {
               description "Authentication key";
               status deprecated;
               leaf keyname {
                 description "Authentication key value";
                 type jt:unreadable;
               }
               leaf key-id {
                 description "Key ID for MD5 authentication";
                 type union {
                   type string {
                     pattern "<.*>|$.*";
                   }
                   type uint32 {
                     range "0 .. 255";
                   }
                 }
               }
             }
           }
         }
         leaf demand-circuit {
           description "Interface functions as a demand circuit";
           type empty;
         }
         leaf flood-reduction {
           description "Enable flood reduction";
           type empty;
         }
         leaf no-neighbor-down-notification {
           description "Don't inform other protocols about neighbor down events";
           type empty;
         }
         leaf ipsec-sa {
           description "IPSec security association name";
           junos:must "(!(any \".. .. interface <st*> ipsec-sa $$\"))";
           junos:must-message "Must not configure ipsec-sa for st0 interface";
           junos:must "(\"security ipsec security-association $$ manual\")";
           junos:must-message "Referenced IPSec security association must be a manual SA";
           junos:must "(\"security ipsec security-association $$ mode transport\")";
           junos:must-message "Referenced IPSec security association must be in transport mode";
           junos:must "(\"security ipsec security-association $$\")";
           junos:must-message "Referenced IPSec security association must be defined";
           type string {
             length "1 .. 32";
           }
         }
         list topology {
           key name;
           ordered-by user;
           description "Topology specific attributes";
           leaf name {
             description "Topology name";
             type string;
           }
           uses apply-advanced;
           leaf disable {
             description "Disable this topology";
             type empty;
           }
           leaf metric {
             description "Topology metric";
             type union {
               type string {
                 pattern "<.*>|$.*";
               }
               type uint16 {
                 range "1 .. 65535";
               }
             }
           }
           container bandwidth-based-metrics {
             junos:must "(\".. metric\")";
             junos:must-message "Metric must be configured";
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint16 {
                     range "1 .. 65535";
                   }
                 }
               }
             }
           }
         }
         leaf transmit-interval {
           description "OSPF packet transmit interval (milliseconds)";
           status deprecated;
           type union {
             type string {
               pattern "<.*>|$.*";
             }
             type uint32 {
               range "1 .. 4294967295";
             }
           }
         }
         container bfd-liveness-detection {
           description "Bidirectional Forwarding Detection options";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
           container authentication {
             description "Authentication options";
             uses apply-advanced;
             leaf key-chain {
               description "Key chain name";
               junos:must "(\".. algorithm\")";
               junos:must-message "May not be configured without algorithm";
               junos:must "(\"security authentication-key-chains key-chain $$\")";
               junos:must-message "Referenced key-chain must be defined";
               type string;
             }
             leaf algorithm {
               description "Algorithm name";
               junos:must "(\".. key-chain\")";
               junos:must-message "May not be configured without key-chain";
               type enumeration {
                 enum "simple-password" {
                   description "Simple password";
                 }
                 enum "keyed-md5" {
                   description "Keyed message Digest 5";
                 }
                 enum "meticulous-keyed-md5" {
                   description "Meticulous keyed message Digest 5";
                 }
                 enum "keyed-sha-1" {
                   description "Keyed secure hash algorithm (SHA1) ";
                 }
                 enum "meticulous-keyed-sha-1" {
                   description "Meticulous keyed secure hash algorithm (SHA1) ";
                 }
               }
             }
             leaf loose-check {
               description "Verify authentication only if authentication is negotiated";
               type empty;
             }
           }
           leaf full-neighbors-only {
             description "Setup BFD sessions only to Full neighbors";
             type empty;
           }
           leaf holddown-interval {
             description "Time to hold the session-UP notification to the client";
             units "milliseconds";
             type union {
               type string {
                 pattern "<.*>|$.*";
               }
               type uint32 {
                 range "0 .. 255000";
               }
             }
           }
         }
         leaf dynamic-neighbors {
           description "Learn neighbors dynamically on a p2mp interface";
           junos:must "(\" .. interface-type p2mp\")";
           junos:must-message "dynamic-neighbors option can be set only if the interface type is p2mp";
           type empty;
         }
         leaf no-advertise-adjacency-segment {
           description "Do not advertise an adjacency segment for this interface";
           type empty;
         }
         list neighbor {
           key name;
           ordered-by user;
           description "NBMA neighbor";
           junos:must "(!(\" .. dynamic-neighbors\"))";
           junos:must-message "Neighbors cannot be specified manually if dynamic-neighbors is set";
           leaf name {
             description "Address of neighbor";
             type jt:ipaddr;
           }
           leaf eligible {
             description "Eligible to be DR on an NBMA network";
             type empty;
           }
         }
         leaf poll-interval {
           description "Poll interval for NBMA interfaces";
           type union {
             type string {
               pattern "<.*>|$.*";
             }
             type uint32 {
               range "1 .. 65535";
             }
           }
         }
         leaf no-interface-state-traps {
           description "Do not send interface state change traps";
           type empty;
         }
         leaf strict-bfd {
           description "Enable strict bfd over this interface";
           junos:must "(\" .. bfd-liveness-detection\")";
           junos:must-message "strict bfd cannot be configured without bfd.";
           junos:must "(!(\" .. bfd-liveness-detection full-neighbors-only\"))";
           junos:must-message "full-neighbors-only and strict-bfd cannot be configured together";
           type empty;
         }
         container post-convergence-lfa {
           presence "enable post-convergence-lfa";
           junos:must "(\"protocols ospf backup-spf-options use-post-convergence-lfa\")";
           junos:must-message "Not allowed without 'protocols ospf backup-spf-options use-post-convergence-lfa'";
           description "Protect interface using post-convergence backup path";
           uses apply-advanced;
           container node-protection {
             presence "enable node-protection";
             description "Compute backup path assuming node failure";
             uses apply-advanced;
             leaf cost {
               description "Cost for node protection";
               type union {
                 type string {
                   pattern "<.*>|$.*";
                 }
                 type uint16 {
                   range "1 .. 65535";
                 }
               }
             }
           }
           leaf srlg-protection {
             description "Compute backup path assuming SRLG failure";
             type empty;
           }
           leaf fate-sharing-protection {
             description "Compute backup path assuming fate-sharing group failure";
             type empty;
           }
         }
         leaf te-metric {
           description "Traffic engineering metric";
           type union {
             type string {
               pattern "<.*>|$.*";
             }
             type uint32 {
               range "1 .. 4294967295";
             }
           }
         }
         container ldp-synchronization {
           description "Advertise maximum metric until LDP is operational";
           presence "enable ldp-synchronization";
           uses ldp-sync-obj;
         }
         container ipv4-adjacency-segment {
           junos:must "(!(\".. no-advertise-adjacency-segment\"))";
           junos:must-message "ipv4-adjacency-segment can't be configured if no-advertise-adjacency-segment is configured in the same interface";
           description "Configure ipv4 adjacency segment";
           uses apply-advanced;
           container protected {
             description "Adjacency SID is eligible for protection";
             choice adjsid-type {
               case case_1 {
                 container index {
                   description "Adjacency SID indexed from SRGB";
                   leaf index-number {
                     type union {
                       type string {
                         pattern "<.*>|$.*";
                       }
                       type uint32 {
                         range "0 .. 199999";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
           container unprotected {
             description "Adjacency SID uneligible for protection";
             choice adjsid-type {
               case case_1 {
                 container index {
                   description "Adjacency SID indexed from SRGB";
                   leaf index-number {
                     type union {
                       type string {
                         pattern "<.*>|$.*";
                       }
                       type uint32 {
                         range "0 .. 199999";
                       }
                     }
                   }
                 }
               }
               case case_2 {
                 leaf label {
                   description "Adjacency SID from static label pool";
                   type union {
                     type string {
                       pattern "<.*>|$.*";
                     }
                     type uint32 {
                       range "16 .. 1048575";
                     }
                   }
                 }
               }
               case case_3 {
                 leaf dynamic {
                   description "Dynamically allocate an adjacency segment";
                   type empty;
                 }
               }
             }
           }
         }
         list lan-neighbor {
           key name;
           ordered-by user;
           description "Configuration specific to a LAN neighbor";
           junos:must "(!(\".. ipv4-adjacency-segment\"))";
           junos:must-message "lan-neighbor can't be configured if ipv4-adjacency-segment is configured in the same interface";
           junos:must "(!(\".. no-advertise-adjacency-segment\"))";
           junos:must-message "lan-neighbor can't be configured if no-advertise-adjacency-segment is configured in the same interface ";
           junos:must "(!(\".. interface-type p2p\"))";
           junos:must-message "lan-neighbor can't be configured for point-to-point interfaces";
           leaf name {
             description "Address of neighbor";
             type jt:ipaddr;
           }
           uses apply-advanced;
           container ipv4-adjacency-segment {
             junos:must "(!(\".. no-advertise-adjacency-segment\"))";
             junos:must-message "ipv4-adjacency-segment can't be configured if no-advertise-adjacency-segment is configured in the same interface";
             description "Configure ipv4 adjacency segment";
             uses apply-advanced;
             container protected {
               description "Adjacency SID is eligible for protection";
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
             container unprotected {
               description "Adjacency SID uneligible for protection";
               choice adjsid-type {
                 case case_1 {
                   container index {
                     description "Adjacency SID indexed from SRGB";
                     leaf index-number {
                       type union {
                         type string {
                           pattern "<.*>|$.*";
                         }
                         type uint32 {
                           range "0 .. 199999";
                         }
                       }
                     }
                   }
                 }
                 case case_2 {
                   leaf label {
                     description "Adjacency SID from static label pool";
                     type union {
                       type string {
                         pattern "<.*>|$.*";
                       }
                       type uint32 {
                         range "16 .. 1048575";
                       }
                     }
                   }
                 }
                 case case_3 {
                   leaf dynamic {
                     description "Dynamically allocate an adjacency segment";
                     type empty;
                   }
                 }
               }
             }
           }
         }
         leaf delay-metric {
           description "Delay metric";
           units "microseconds";
           type union {
             type string {
               pattern "<.*>|$.*";
             }
             type uint32 {
               range "0 .. 16777215";
             }
           }
         }
         container delay-measurement {
           presence "enable delay-measurement";
           description "Enable delay measurement";
           uses apply-advanced;
           leaf probe-interval {
             description "Probe interval";
             units "seconds";
             type union {
               type string {
                 pattern "<.*>|$.*";
               }
               type uint32 {
                 range "1 .. 255";
               }
             }
           }
           leaf probe-count {
             description "Probe count";
             type union {
               type string {
                 pattern "<.*>|$.*";
               }
               type uint32 {
                 range "1 .. 15";
               }
             }
           }
           container advertisement {
             description "Delay advertisement";
             uses apply-advanced;
             container periodic {
               description "Periodic advertisement parameters";
               uses apply-advanced;
               leaf threshold {
                 description "Threshold";
                 units "percentage";
                 type union {
                   type string {
                     pattern "<.*>|$.*";
                   }
                   type uint32 {
                     range "0 .. 100";
                   }
                 }
               }
               leaf interval {
                 description "Interval";
                 units "seconds";
                 type union {
                   type string {
                     pattern "<.*>|$.*";
                   }
                   type uint32 {
                     range "30 .. 3600";
                   }
                 }
               }
             }
             container accelerated {
               presence "enable accelerated";
               description "Accelerated advertisement parameters";
               uses apply-advanced;
               leaf threshold {
                 description "Threshold";
                 units "percentage";
                 type union {
                   type string {
                     pattern "<.*>|$.*";
                   }
                   type uint32 {
                     range "0 .. 100";
                   }
                 }
               }
             }
           }
         }
         container application-specific {
           description "Advertise application-specific TE attributes";
           uses apply-advanced;
           list attribute-group {
             key name;
             ordered-by user;
             description "Link attribute group name";
             max-elements 1;
             leaf name {
               description "Link attribute group name";
               type string;
             }
             uses apply-advanced;
             leaf te-metric {
               description "Traffic engineering metric for this attribute group";
               junos:must "(\".. application\")";
               junos:must-message "Atleast one application is must";
               type union {
                 type string {
                   pattern "<.*>|$.*";
                 }
                 type uint32 {
                   range "1 .. 4294967295";
                 }
               }
             }
             leaf-list admin-group {
               ordered-by user;
               description "Administrative groups for this attribute-group";
               junos:must "(\".. application\")";
               junos:must-message "Atleast one application is must";
               type string;
               max-elements 16;
             }
             leaf delay-metric {
               description "Delay metric for this attribute-group";
               units "microseconds";
               junos:must "(!(\".. advertise-interface-delay\"))";
               junos:must-message "ASLA delay-metric can't be configured with ASLA advertise interface delay knob";
               junos:must "(\".. application\")";
               junos:must-message "Atleast one application is must";
               type union {
                 type string {
                   pattern "<.*>|$.*";
                 }
                 type uint32 {
                   range "0 .. 16777215";
                 }
               }
             }
             leaf advertise-interface-delay {
               description "Use interface specific static/dynamic delay values as applicable in ASLA Sub-TLVs";
               junos:must "((\".. .. .. delay-metric\" || \".. .. .. delay-measurement\"))";
               junos:must-message "Interface specific delay values must be configured for advertise interface delay knob";
               junos:must "(\".. application\")";
               junos:must-message "Atleast one application is must";
               type empty;
             }
             container application {
               junos:must "((\".. delay-metric\" || (\".. admin-group\" || (\".. te-metric\" || \".. advertise-interface-delay\"))))";
               junos:must-message "Atleast one attribute must be configured";
               description "Standard Applications part of this attribute-group";
               uses apply-advanced;
               leaf flex-algorithm {
                 description "Set X flag in standard application bit mask";
                 type empty;
               }
             }
           }
         }
       }
       leaf no-context-identifier-advertisement {
         description "Disable context identifier advertisments in this area";
         junos:must "(!(\".. context-identifier\"))";
         junos:must-message "no-context-identifier-advertisement and context-identifier attributes are mutually exclusive";
         type empty;
       }
       list peer-interface {
         key name;
         ordered-by user;
         description "Configuration for peer interface";
         leaf name {
           description "Name of peer interface";
           type string;
         }
         uses apply-advanced;
         choice enable-disable {
           case case_1 {
             leaf disable {
               description "Disable OSPF on this control peer";
               type empty;
             }
           }
         }
         leaf retransmit-interval {
           description "Retransmission interval (seconds)";
           type union {
             type string {
               pattern "<.*>|$.*";
             }
             type uint32 {
               range "1 .. 65535";
             }
           }
         }
         leaf transit-delay {
           description "Transit delay (seconds)";
           type union {
             type string {
               pattern "<.*>|$.*";
             }
             type uint32 {
               range "1 .. 65535";
             }
           }
         }
         leaf hello-interval {
           description "Hello interval (seconds)";
           type union {
             type string {
               pattern "<.*>|$.*";
             }
             type uint32 {
               range "1 .. 255";
             }
           }
         }
         leaf dead-interval {
           description "Dead interval (seconds)";
           type union {
             type string {
               pattern "<.*>|$.*";
             }
             type uint32 {
               range "1 .. 65535";
             }
           }
         }
         leaf mtu {
           description "Maximum OSPF packet size";
           type union {
             type string {
               pattern "<.*>|$.*";
             }
             type uint32 {
               range "128 .. 65535";
             }
           }
         }
         choice auth {
           case case_1 {
             container authentication {
               uses juniper-ospf-authentication;
             }
           }
           case case_2 {
             container authentication-key {
               description "Authentication key";
               status deprecated;
               leaf keyname {
                 description "Authentication key value";
                 type jt:unreadable;
               }
               leaf key-id {
                 description "Key ID for MD5 authentication";
                 type union {
                   type string {
                     pattern "<.*>|$.*";
                   }
                   type uint32 {
                     range "0 .. 255";
                   }
                 }
               }
             }
           }
         }
         leaf demand-circuit {
           description "Interface functions as a demand circuit";
           type empty;
         }
         leaf flood-reduction {
           description "Enable flood reduction";
           type empty;
         }
         leaf no-neighbor-down-notification {
           description "Don't inform other protocols about neighbor down events";
           type empty;
         }
       }
       leaf no-source-packet-routing {
         description "Disable SPRING in this area";
         type empty;
       }
       list context-identifier {
         key name;
         ordered-by user;
         description "Configure context identifier in support of edge protection";
         junos:must "(!(\".. no-context-identifier-advertisement\"))";
         junos:must-message "no-context-identifier-advertisement and context-identifier attributes are mutually exclusive";
         leaf name {
           description "Context identifier";
           type jt:ipv4addr;
         }
         uses apply-advanced;
       }
       list label-switched-path {
         key name;
         ordered-by user;
         description "Configuration for advertisement of a label-switched path";
         junos:must "(!(\".. .. traffic-engineering multicast-rpf-routes\"))";
         junos:must-message "cannot advertise LSPs when using multicast-rpf-routes";
         leaf name {
           description "Name of label-switched path to be advertised";
           type string {
             length "1 .. 64";
           }
         }
         uses apply-advanced;
         choice enable-disable {
           case case_1 {
             leaf disable {
               description "Disable OSPF on this label-switched path";
               type empty;
             }
           }
         }
         leaf metric {
           description "Interface metric";
           type union {
             type string {
               pattern "<.*>|$.*";
             }
             type uint16 {
               range "1 .. 65535";
             }
           }
         }
         list topology {
           key name;
           ordered-by user;
           description "Topology specific attributes";
           leaf name {
             description "Topology name";
             type string;
           }
           uses apply-advanced;
           leaf disable {
             description "Disable this topology";
             type empty;
           }
           leaf metric {
             description "Topology metric";
             type union {
               type string {
                 pattern "<.*>|$.*";
               }
               type uint16 {
                 range "1 .. 65535";
               }
             }
           }
           container bandwidth-based-metrics {
             junos:must "(\".. metric\")";
             junos:must-message "Metric must be configured";
             description "Configure bandwidth based metrics";
             uses apply-advanced;
             list bandwidth {
               key name;
               description "Bandwidth threshold";
               leaf name {
                 type string;
               }
               leaf metric {
                 description "Metric associated with specified bandwidth";
                 type union {
                   type string {
                     pattern "<.*>|$.*";
                   }
                   type uint16 {
                     range "1 .. 65535";
                   }
                 }
               }
             }
           }
         }
       }
     }
     choice enable-disable {
       case case_1 {
         leaf disable {
           description "Disable OSPF";
           type empty;
         }
       }
     }
     container traceoptions {
       description "Trace options for OSPF";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "spf" {
               description "Trace SPF calculations";
             }
             enum "error" {
               description "Trace errored packets";
             }
             enum "event" {
               description "Trace OSPF state machine events";
             }
             enum "packet-dump" {
               description "Dump the contents of selected packet types";
             }
             enum "flooding" {
               description "Trace LSA flooding";
             }
             enum "lsa-analysis" {
               description "Trace LSA analysis";
             }
             enum "packets" {
               description "Trace all OSPF packets";
             }
             enum "hello" {
               description "Trace hello packets";
             }
             enum "database-description" {
               description "Trace database description packets";
             }
             enum "lsa-request" {
               description "Trace LSA request packets";
             }
             enum "lsa-update" {
               description "Trace LSA update packets";
             }
             enum "lsa-ack" {
               description "Trace LSA acknowledgment packets";
             }
             enum "ldp-synchronization" {
               description "Trace synchronization between OSPF and LDP";
             }
             enum "on-demand" {
               description "Trace demand circuit extensions";
             }
             enum "nsr-synchronization" {
               description "Trace NSR synchronization events";
             }
             enum "graceful-restart" {
               description "Trace graceful restart";
             }
             enum "restart-signaling" {
               description "Trace restart signaling";
             }
             enum "backup-spf" {
               description "Trace backup SPF (LFA) specific events";
             }
             enum "source-packet-routing" {
               description "Trace source packet routing (SPRING) events";
             }
             enum "post-convergence-lfa" {
               description "Trace post-convergence-lfa related events";
             }
             enum "flex-algorithm" {
               description "Trace flex-algorithm related events";
             }
             enum "rmopd" {
               description "Trace rmopd interactions";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     leaf prefix-export-limit {
       description "Maximum number of prefixes that can be exported";
       type union {
         type string {
           pattern "<.*>|$.*";
         }
         type uint32 {
           range "0 .. 4294967295";
         }
       }
     }
     container rib-groups {
       description "Routing table groups for importing OSPF routes";
       uses apply-advanced;
       leaf inet {
         description "Name of the IPv4/v6 routing table group";
         junos:must "(\"routing-options rib-groups $$\")";
         junos:must-message "Referenced rib-groups must be defined";
         junos:must "(!(\".. topology $$={default} rib-group\"))";
         junos:must-message "rib-group cannot be used with topology default rib-group";
         type string;
       }
       leaf inet3 {
         description "Name of the IPv4/v6 inet.3 routing table group";
         junos:must "(\"routing-options rib-groups $$\")";
         junos:must-message "Referenced rib-groups must be defined";
         junos:must "(!(\".. topology $$={default} rib-group\"))";
         junos:must-message "rib-group cannot be used with topology default rib-group";
         type string;
       }
     }
     leaf job-stats {
       description "Collect job statistics";
       type empty;
     }
     container overload {
       presence "enable overload";
       description "Set the overload mode (repel transit traffic)";
       uses apply-advanced;
       leaf timeout {
         description "Time after which overload mode is reset";
         units "seconds";
         type union {
           type string {
             pattern "<.*>|$.*";
           }
           type uint32 {
             range "60 .. 3600";
           }
         }
       }
       leaf allow-route-leaking {
         description "Allow routes to be leaked when overload is configured";
         type empty;
       }
       leaf stub-network {
         description "Advertise Stub Network with maximum metric";
         type empty;
       }
       leaf intra-area-prefix {
         description "Advertise Intra Area Prefix with maximum metric";
         type empty;
       }
       leaf as-external {
         description "Advertise As External with maximum usable metric";
         type empty;
       }
     }
     container database-protection {
       presence "enable database-protection";
       description "Configure database protection attributes";
       uses apply-advanced;
       leaf maximum-lsa {
         description "Maximum allowed non self-generated LSAs";
         type union {
           type string {
             pattern "<.*>|$.*";
           }
           type uint32 {
             range "1 .. 1000000";
           }
         }
       }
       leaf warning-only {
         description "Emit only a warning when LSA maximum limit is exceeded";
         type empty;
       }
       leaf warning-threshold {
         description "Percentage of LSA maximum above which to trigger warning";
         units "percent";
         type union {
           type string {
             pattern "<.*>|$.*";
           }
           type uint8 {
             range "30 .. 100";
           }
         }
       }
       leaf ignore-count {
         description "Maximum number of times to go into ignore state";
         type union {
           type string {
             pattern "<.*>|$.*";
           }
           type uint8 {
             range "1 .. 32";
           }
         }
       }
       leaf ignore-time {
         description "Time to stay in ignore state and ignore all neighbors";
         units "seconds";
         type union {
           type string {
             pattern "<.*>|$.*";
           }
           type uint16 {
             range "30 .. 3600";
           }
         }
       }
       leaf reset-time {
         description "Time after which the ignore count gets reset to zero";
         units "seconds";
         type union {
           type string {
             pattern "<.*>|$.*";
           }
           type uint32 {
             range "60 .. 86400";
           }
         }
       }
     }
     container graceful-restart {
       description "Configure graceful restart attributes";
       uses apply-advanced;
       choice enable-disable {
         case case_1 {
           leaf disable {
             description "Disable OSPF graceful restart capability";
             type empty;
           }
         }
       }
       leaf restart-duration {
         description "Time for all neighbors to become full";
         units "seconds";
         type union {
           type string {
             pattern "<.*>|$.*";
           }
           type uint32 {
             range "1 .. 3600";
           }
         }
       }
       leaf notify-duration {
         description "Time to send all max-aged grace LSAs";
         units "seconds";
         type union {
           type string {
             pattern "<.*>|$.*";
           }
           type uint32 {
             range "1 .. 3600";
           }
         }
       }
       container helper-disable {
         presence "enable helper-disable";
         description "Disable graceful restart helper capability";
         uses apply-advanced;
         choice disable-choices {
           case case_1 {
             leaf standard {
               description "Disable helper-mode for rfc3623 based GR";
               type empty;
             }
           }
           case case_2 {
             leaf restart-signaling {
               description "Disable helper mode for restart-signaling ";
               type empty;
             }
           }
           case case_3 {
             leaf both {
               description "Disable helper mode for both the types of GR";
               type empty;
             }
           }
         }
       }
       leaf no-strict-lsa-checking {
         description "Do not abort graceful helper mode upon LSA changes";
         junos:must "(!(\".. helper-disable\"))";
         junos:must-message "To configure no-strict-lsa-checking, helper-disable must not be set";
         type empty;
       }
     }
     leaf route-type-community {
       description "Specify BGP extended community value to encode OSPF route type";
       type enumeration {
         enum "iana" {
           description "BGP extended community value used is 0x0306";
         }
         enum "vendor" {
           description "Vendor BGP extended community value used is 0x8000";
         }
       }
     }
     container domain-id {
       description "Configure domain ID";
       choice domain_id_or_disable {
         case case_1 {
           leaf domain-id {
             description "Domain ID";
             type string;
           }
         }
         case case_2 {
           leaf disable {
             description "Disable domain ID";
             type empty;
           }
         }
       }
     }
     choice domain_vpn_tag_or_disable {
       case case_1 {
         leaf domain-vpn-tag {
           description "Domain VPN tag for external LSA";
           type union {
             type string {
               pattern "<.*>|$.*";
             }
             type uint32 {
               range "0 .. 4294967295";
             }
           }
         }
       }
       case case_2 {
         leaf no-domain-vpn-tag {
           description "Disable domain VPN tag";
           type empty;
         }
       }
     }
     leaf preference {
       description "Preference of internal routes";
       type union {
         type uint32;
         type string {
           pattern "<.*>|$.*";
         }
       }
     }
     leaf external-preference {
       description "Preference of external routes";
       type union {
         type uint32;
         type string {
           pattern "<.*>|$.*";
         }
       }
     }
     leaf labeled-preference {
       description "Preference of labeled routes";
       type union {
         type uint32;
         type string {
           pattern "<.*>|$.*";
         }
       }
     }
     leaf-list export {
       ordered-by user;
       description "Export policy";
       type jt:policy-algebra;
     }
     leaf-list import {
       ordered-by user;
       description "Import policy (for external routes or setting priority)";
       type jt:policy-algebra;
     }
     leaf reference-bandwidth {
       description "Bandwidth for calculating metric defaults";
       type string;
     }
     leaf lsa-refresh-interval {
       description "LSA refresh interval (minutes)";
       default "50";
       type union {
         type string {
           pattern "<.*>|$.*";
         }
         type uint32 {
           range "25 .. 50";
         }
       }
     }
     leaf spf-delay {
       description "Time to wait before running an SPF";
       status deprecated;
       units "milliseconds";
       junos:must "(!(\".. spf-options delay\"))";
       junos:must-message "You can only configure either spf-delay or delay under spf-options";
       type union {
         type string {
           pattern "<.*>|$.*";
         }
         type uint32 {
           range "50 .. 8000";
         }
       }
     }
     leaf no-rfc-1583 {
       description "Disable RFC1583 compatibility";
       type empty;
     }
     leaf forwarding-address-to-broadcast {
       description "Set forwarding address in Type 5 LSA in broadcast network";
       type empty;
     }
     choice nssa-abr-option {
       case case_1 {
         leaf no-nssa-abr {
           description "Disable full NSSA functionality at ABR";
           type empty;
         }
       }
     }
     container sham-link {
       presence "enable sham-link";
       description "Configure parameters for sham links";
       uses apply-advanced;
       leaf local {
         description "Local sham link endpoint address";
         type jt:ipaddr;
       }
       leaf no-advertise-local {
         description "Don't advertise local sham link endpoint as stub in router LSA";
         status deprecated;
         type empty;
       }
     }
   }
   grouping juniper-protocols-overlayd {
     uses apply-advanced;
     container traceoptions {
       description "Overlayd trace options";
       uses apply-advanced;
       leaf no-remote-trace {
         description "Disable remote tracing";
         junos:must "(\"system tracing\")";
         junos:must-message "'no-remote-trace' is valid only when [system tracing] is configured";
         type empty;
       }
       container file {
         description "Trace file information";
         leaf filename {
           description "Name of file in which to write trace information";
           type string {
             length "1 .. 1024";
             junos:posix-pattern "![/ %]";
             junos:pattern-message "Must not contain '/', % or a space";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing flag parameters";
         leaf name {
           type enumeration {
             enum "socket" {
               description "Trace overlay daemon socket events";
             }
             enum "rtsock" {
               description "Trace overlay daemon rtsock events";
             }
             enum "config" {
               description "Trace overlay daemon config events";
             }
             enum "all" {
               description "Trace everything";
             }
           }
         }
       }
     }
   }
   grouping juniper-protocols-pgm {
     uses apply-advanced;
     container traceoptions {
       description "PGM trace options";
       uses apply-advanced;
       list flag {
         key name;
         ordered-by user;
         description "Tracing parameters";
         leaf name {
           type enumeration {
             enum "init" {
               description "Trace initialization events";
             }
             enum "show" {
               description "Trace show command servicing";
             }
             enum "route-socket" {
               description "Trace route-socket events";
             }
             enum "parse" {
               description "Trace parser processing";
             }
             enum "state" {
               description "Trace state transitions";
             }
             enum "packets" {
               description "Trace packet processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
   }
   grouping juniper-protocols-pim {
     uses apply-advanced;
     container family {
       description "Local address family";
       container any {
         presence "enable any";
         description "Default properties for all address families";
         uses apply-advanced;
         leaf disable {
           description "Disable all families";
           type empty;
         }
       }
       container inet {
         presence "enable inet";
         description "IPv4 specific properties";
         uses apply-advanced;
         choice enable-disable {
           case case_1 {
             leaf disable {
               description "Disable PIMv4 on all interfaces";
               type empty;
             }
           }
         }
       }
       container inet6 {
         presence "enable inet6";
         description "IPv6 specific properties";
         uses apply-advanced;
         choice enable-disable {
           case case_1 {
             leaf disable {
               description "Disable PIMv6 on all interfaces";
               type empty;
             }
           }
         }
       }
     }
     choice enable-disable {
       case case_1 {
         leaf disable {
           description "Disable PIM";
           type empty;
         }
       }
     }
     container nonstop-routing {
       junos:must "(\"routing-options nonstop-routing\")";
       junos:must-message "To disable PIM nonstop-routing, non-stop routing must be globally enabled.";
       description "Configure PIM nonstop-routing attributes";
       uses apply-advanced;
       choice enable-disable {
         case case_1 {
           leaf disable {
             description "Disable non-stop routing for PIM";
             type empty;
           }
         }
       }
     }
     container traceoptions {
       description "Trace options for PIM";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "route" {
               description "Trace routing information";
             }
             enum "packets" {
               description "Trace all PIM packets";
             }
             enum "hello" {
               description "Trace hello packets";
             }
             enum "register" {
               description "Trace register/register-stop messages";
             }
             enum "join" {
               description "Trace join/prune/graft/graft-ack messages";
             }
             enum "prune" {
               description "Trace join/prune/graft/graft-ack messages";
             }
             enum "graft" {
               description "Trace join/prune/graft/graft-ack messages";
             }
             enum "bootstrap" {
               description "Trace bootstrap/RP/auto-RP messages";
             }
             enum "rp" {
               description "Trace bootstrap/RP/auto-RP messages";
             }
             enum "autorp" {
               description "Trace bootstrap/RP/auto-RP messages";
             }
             enum "assert" {
               description "Trace assert messages";
             }
             enum "mdt" {
               description "Trace messages related to multicast data tunnels";
             }
             enum "nsr-synchronization" {
               description "Trace NSR synchronization events";
             }
             enum "bidirectional-df-election" {
               description "Trace bidirectional PIM DF election events";
             }
             enum "mofrr" {
               description "Trace Multicast only Fast Re-Route messages";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
         container filter {
           description "Filter to apply to this flag";
           presence "enable filter";
           uses pim_filter_obj;
         }
       }
     }
     container dense-groups {
       description "Dense mode groups for sparse-dense mode";
       uses apply-advanced;
       leaf dynamic-reject {
         description "Reject dynamic autorp negative dense-mode prefixes learnt from network";
         type empty;
       }
       list pim-dense-group-type {
         key name;
         ordered-by user;
         leaf name {
           description "Group address or range to forward in dense mode";
           type jt:ipprefix;
         }
         choice dense-group-flags {
           case case_1 {
             leaf reject {
               description "Do not include prefix as dense mode; force sparse mode";
               type empty;
             }
           }
           case case_2 {
             leaf announce {
               description "Advertise as negative prefix in auto-RP announce messages";
               type empty;
             }
           }
         }
       }
     }
     leaf vpn-tunnel-source {
       description "Source address for the provider space mGRE tunnel";
       status deprecated;
       type jt:ipv4addr;
     }
     leaf vpn-group-address {
       description "Group address for the VPN in provider space";
       status deprecated;
       junos:must "(!(\".. .. .. provider-tunnel pim-ssm\"))";
       junos:must-message "'provider-tunnel pim-ssm' can not be configured with 'pim vpn-group-address'. Please disable one of them.";
       junos:must "((!(\".. .. .. provider-tunnel pim-asm\") || \".. .. .. provider-tunnel pim-asm group-address $$\"))";
       junos:must-message "MVPN inclusive provider-tunnel group-address must be same as 'vpn-group-address'";
       type jt:ipv4addr;
     }
     leaf-list tunnel-devices {
       ordered-by user;
       description "Tunnel devices to be used for creating mt interfaces";
       type union {
         type jt:interface-device;
         type string {
           pattern "<.*>|$.*";
         }
       }
     }
     container rpf-selection {
       description "Select RPF neighbor";
       uses apply-advanced;
       list group {
         key name;
         ordered-by user;
         description "IP prefix of multicast group";
         leaf name {
           description "IP prefix of group";
           type jt:ipprefix;
         }
         uses apply-advanced;
         container wildcard-source {
           presence "enable wildcard-source";
           description "Select RPF for (*,g) and unspecified (s,g) joins";
           uses apply-advanced;
           leaf next-hop {
             description "Next-hop address";
             type jt:ipaddr;
           }
         }
         list source {
           key name;
           ordered-by user;
           description "IP prefix of one or more multicast sources";
           leaf name {
             description "IP prefix of source";
             type jt:ipprefix;
           }
           uses apply-advanced;
           leaf next-hop {
             description "Next-hop address";
             type jt:ipaddr;
           }
         }
       }
       list prefix-list {
         key name;
         ordered-by user;
         description "Multicast group prefix list";
         leaf name {
           description "Name of prefix list to match against";
           junos:must "(\"policy-options prefix-list $$\")";
           junos:must-message "This prefix-list must be configured in policy-options.";
           type string;
         }
         uses apply-advanced;
         container wildcard-source {
           presence "enable wildcard-source";
           description "Select RPF for (*,g) and unspecified (s,g) joins";
           uses apply-advanced;
           leaf next-hop {
             description "Next-hop address";
             type jt:ipaddr;
           }
         }
         list source {
           key name;
           ordered-by user;
           description "IP prefix of one or more multicast sources";
           leaf name {
             description "IP prefix of source";
             type jt:ipprefix;
           }
           uses apply-advanced;
           leaf next-hop {
             description "Next-hop address";
             type jt:ipaddr;
           }
         }
       }
     }
     container mvpn {
       presence "enable mvpn";
       description "PIM MVPN control-plane options";
       uses apply-advanced;
       container autodiscovery {
         junos:must "(!(\".. .. vpn-group-address\"))";
         junos:must-message "PIM MVPN autodiscovery options cannot be configured with 'vpn-group-address'";
         junos:must "(\".. .. .. mvpn\")";
         junos:must-message "Autodiscovery for PIM MVPNs requires 'protocols mvpn'";
         junos:must "(!(\".. .. mdt\"))";
         junos:must-message "PIM MVPN auto-discovery cannot be configured with 'pim mdt'";
         description "PE router autodiscovery options for SSM MDTs";
         status deprecated;
         uses apply-advanced;
         leaf inet-mdt {
           description "MDT-SAFI PE autodiscovery for SSM MDTs";
           type empty;
         }
       }
       container family {
         description "PIM MVPN address family";
         uses apply-advanced;
         container inet {
           description "IPv4 PIM MVPN specific properties";
           uses apply-advanced;
           leaf rosen-mvpn {
             status deprecated;
             type empty;
           }
           leaf ngen-mvpn {
             status deprecated;
             junos:must "(\".. .. .. .. .. mvpn\")";
             junos:must-message "Requires 'protocols mvpn'";
             type empty;
           }
           container autodiscovery {
             junos:must "(!(\".. .. .. .. vpn-group-address\"))";
             junos:must-message "PIM MVPN autodiscovery options cannot be configured with 'vpn-group-address'";
             junos:must "(\".. .. .. .. .. mvpn\")";
             junos:must-message "Autodiscovery for PIM MVPNs requires 'protocols mvpn'";
             junos:must "(!(\".. .. .. .. mdt\"))";
             junos:must-message "PIM MVPN auto-discovery cannot be configured with 'pim mdt'";
             description "PE router autodiscovery options for SSM MDTs";
             uses apply-advanced;
             leaf inet-mdt {
               description "MDT-SAFI PE autodiscovery for SSM MDTs";
               type empty;
             }
           }
           leaf disable {
             description "Disable family IPv4";
             type empty;
           }
         }
         container inet6 {
           description "IPv6 PIM MVPN specific properties";
           uses apply-advanced;
           leaf rosen-mvpn {
             status deprecated;
             type empty;
           }
           leaf ngen-mvpn {
             status deprecated;
             junos:must "(\".. .. .. .. .. mvpn\")";
             junos:must-message "Requires 'protocols mvpn'";
             type empty;
           }
           container autodiscovery {
             junos:must "(!(\".. .. .. .. vpn-group-address\"))";
             junos:must-message "PIM MVPN autodiscovery options cannot be configured with 'vpn-group-address'";
             junos:must "(\".. .. .. .. .. mvpn\")";
             junos:must-message "Autodiscovery for PIM MVPNs requires 'protocols mvpn'";
             junos:must "(!(\".. .. .. .. mdt\"))";
             junos:must-message "PIM MVPN auto-discovery cannot be configured with 'pim mdt'";
             description "PE router autodiscovery options for SSM MDTs";
             uses apply-advanced;
             leaf inet-mdt {
               description "MDT-SAFI PE autodiscovery for SSM MDTs";
               type empty;
             }
           }
           leaf disable {
             description "Disable family IPv6";
             type empty;
           }
         }
       }
     }
     container rib-group {
       description "Routing table group";
       uses rib_group_type;
     }
     leaf-list import {
       ordered-by user;
       description "PIM sparse import join policy";
       type jt:policy-algebra;
     }
     leaf-list export {
       ordered-by user;
       description "PIM sparse export join policy";
       type jt:policy-algebra;
     }
     container mldp-inband-signalling {
       presence "enable mldp-inband-signalling";
       junos:must "(!(\"system processes routing bgp rib-sharding\"))";
       junos:must-message "Can't be configured together with rib-sharding";
       uses apply-advanced;
       leaf-list policy {
         ordered-by user;
         description "PIM MLDP join translation filter policy";
         type jt:policy-algebra;
       }
     }
     container rpf-vector {
       description "RPF vector TLV";
       uses apply-advanced;
       leaf-list policy {
         ordered-by user;
         description "RPF vector TLV include policy";
         type jt:policy-algebra;
       }
     }
     leaf assert-timeout {
       description "Set assert timeout";
       default "180";
       type union {
         type string {
           pattern "<.*>|$.*";
         }
         type uint32 {
           range "5 .. 210";
         }
       }
     }
     leaf assert-robust-count {
       description "Number of assert messages an assert winner sends in one cycle";
       default "2";
       type union {
         type string {
           pattern "<.*>|$.*";
         }
         type uint32 {
           range "1 .. 5";
         }
       }
     }
     leaf join-prune-timeout {
       description "Set join/prune timeout";
       default "210";
       type union {
         type string {
           pattern "<.*>|$.*";
         }
         type uint32 {
           range "210 .. 420";
         }
       }
     }
     container spt-threshold {
       description "Set shortest-path-tree threshold policy";
       uses apply-advanced;
       leaf-list infinity {
         ordered-by user;
         description "Apply policy to always remain on shared tree";
         type jt:policy-algebra;
       }
     }
     container sglimit {
       description "Set limit on number of (S,G) states ";
       uses apply-advanced;
       list family {
         key name;
         ordered-by user;
         description "Protocol family";
         junos:must "(!(\".. maximum\"))";
         junos:must-message "Family wise threshold cannot be configuredif global threshold is already configured";
         leaf name {
           type enumeration {
             enum "inet" {
               description "IPv4 family";
             }
             enum "inet6" {
               description "IPv6 family";
             }
           }
         }
         uses apply-advanced;
         leaf maximum {
           description "Maximum limit above which additional entries are not accepted";
           type union {
             type string {
               pattern "<.*>|$.*";
             }
             type uint32 {
               range "1 .. 65535";
             }
           }
         }
         leaf threshold {
           description "Percentage of maximum at which to start generating warnings";
           junos:must "(\".. maximum\")";
           junos:must-message "To configure threshold, maximum must be configured";
           type union {
             type string {
               pattern "<.*>|$.*";
             }
             type uint32 {
               range "1 .. 100";
             }
           }
         }
         leaf log-interval {
           description "Time between successive log messages";
           junos:must "(\".. maximum\")";
           junos:must-message "To configure log-interval, maximum must be configured";
           type union {
             type string {
               pattern "<.*>|$.*";
             }
             type uint32 {
               range "1 .. 65535";
             }
           }
         }
       }
       leaf maximum {
         description "Maximum limit above which additional entries are not accepted";
         type union {
           type string {
             pattern "<.*>|$.*";
           }
           type uint32 {
             range "1 .. 65535";
           }
         }
       }
       leaf threshold {
         description "Percentage of maximum at which to start generating warnings";
         junos:must "(\".. maximum\")";
         junos:must-message "To configure threshold, maximum must be configured";
         type union {
           type string {
             pattern "<.*>|$.*";
           }
           type uint32 {
             range "1 .. 100";
           }
         }
       }
       leaf log-interval {
         description "Time between successive log messages";
         junos:must "(\".. maximum\")";
         junos:must-message "To configure log-interval, maximum must be configured";
         type union {
           type string {
             pattern "<.*>|$.*";
           }
           type uint32 {
             range "1 .. 65535";
           }
         }
       }
     }
     container rp {
       junos:must "(!(\" .. passive\"))";
       junos:must-message "pim rp cannot be configured with pim passive";
       description "Router's rendezvous point properties";
       uses apply-advanced;
       leaf bootstrap-priority {
         description "Eligibility to be the bootstrap router (IPv4 only)";
         type union {
           type string {
             pattern "<.*>|$.*";
           }
           type uint32 {
             range "0 .. 255";
           }
         }
       }
       leaf-list bootstrap-import {
         ordered-by user;
         description "Bootstrap import policy (IPv4 only)";
         type jt:policy-algebra;
       }
       leaf-list bootstrap-export {
         ordered-by user;
         description "Bootstrap export policy (IPv4 only)";
         type jt:policy-algebra;
       }
       container bootstrap {
         description "Bootstrap properties";
         uses apply-advanced;
         container family {
           description "Bootstrap address family";
           container inet {
             description "IPv4 bootstrap properties";
             junos:must "(!((\".. .. .. bootstrap-priority\" || (\".. .. .. bootstrap-import\" || \".. .. .. bootstrap-export\"))))";
             junos:must-message "Duplicate IPv4 bootstrap configuration";
             uses pim_bootstrap_options_type;
           }
           container inet6 {
             description "IPv6 bootstrap properties";
             uses pim_bootstrap_options_type;
           }
         }
       }
       container register-limit {
         description "Set limit on incoming registers that create (S,G) state";
         uses apply-advanced;
         list family {
           key name;
           ordered-by user;
           description "Protocol family";
           junos:must "(!(\".. maximum\"))";
           junos:must-message "Family wise threshold cannot be configuredif global threshold is already configured";
           leaf name {
             type enumeration {
               enum "inet" {
                 description "IPv4 family";
               }
               enum "inet6" {
                 description "IPv6 family";
               }
             }
           }
           uses apply-advanced;
           leaf maximum {
             description "Maximum limit above which additional entries are not accepted";
             type union {
               type string {
                 pattern "<.*>|$.*";
               }
               type uint32 {
                 range "1 .. 65535";
               }
             }
           }
           leaf threshold {
             description "Percentage of maximum at which to start generating warnings";
             junos:must "(\".. maximum\")";
             junos:must-message "To configure threshold, maximum must be configured";
             type union {
               type string {
                 pattern "<.*>|$.*";
               }
               type uint32 {
                 range "1 .. 100";
               }
             }
           }
           leaf log-interval {
             description "Time between successive log messages";
             junos:must "(\".. maximum\")";
             junos:must-message "To configure log-interval, maximum must be configured";
             type union {
               type string {
                 pattern "<.*>|$.*";
               }
               type uint32 {
                 range "1 .. 65535";
               }
             }
           }
         }
         leaf maximum {
           description "Maximum limit above which additional entries are not accepted";
           type union {
             type string {
               pattern "<.*>|$.*";
             }
             type uint32 {
               range "1 .. 65535";
             }
           }
         }
         leaf threshold {
           description "Percentage of maximum at which to start generating warnings";
           junos:must "(\".. maximum\")";
           junos:must-message "To configure threshold, maximum must be configured";
           type union {
             type string {
               pattern "<.*>|$.*";
             }
             type uint32 {
               range "1 .. 100";
             }
           }
         }
         leaf log-interval {
           description "Time between successive log messages";
           junos:must "(\".. maximum\")";
           junos:must-message "To configure log-interval, maximum must be configured";
           type union {
             type string {
               pattern "<.*>|$.*";
             }
             type uint32 {
               range "1 .. 65535";
             }
           }
         }
       }
       container group-rp-mapping {
         description "Group-rp-mapping";
         uses apply-advanced;
         list family {
           key name;
           ordered-by user;
           description "Protocol family";
           junos:must "(!(\".. maximum\"))";
           junos:must-message "Family wise threshold cannot be configuredif global threshold is already configured";
           leaf name {
             type enumeration {
               enum "inet" {
                 description "IPv4 family";
               }
               enum "inet6" {
                 description "IPv6 family";
               }
             }
           }
           uses apply-advanced;
           leaf maximum {
             description "Maximum limit above which additional entries are not accepted";
             type union {
               type string {
                 pattern "<.*>|$.*";
               }
               type uint32 {
                 range "1 .. 65535";
               }
             }
           }
           leaf threshold {
             description "Percentage of maximum at which to start generating warnings";
             junos:must "(\".. maximum\")";
             junos:must-message "To configure threshold, maximum must be configured";
             type union {
               type string {
                 pattern "<.*>|$.*";
               }
               type uint32 {
                 range "1 .. 100";
               }
             }
           }
           leaf log-interval {
             description "Time between successive log messages";
             junos:must "(\".. maximum\")";
             junos:must-message "To configure log-interval, maximum must be configured";
             type union {
               type string {
                 pattern "<.*>|$.*";
               }
               type uint32 {
                 range "1 .. 65535";
               }
             }
           }
         }
         leaf maximum {
           description "Maximum limit above which additional entries are not accepted";
           type union {
             type string {
               pattern "<.*>|$.*";
             }
             type uint32 {
               range "1 .. 65535";
             }
           }
         }
         leaf threshold {
           description "Percentage of maximum at which to start generating warnings";
           junos:must "(\".. maximum\")";
           junos:must-message "To configure threshold, maximum must be configured";
           type union {
             type string {
               pattern "<.*>|$.*";
             }
             type uint32 {
               range "1 .. 100";
             }
           }
         }
         leaf log-interval {
           description "Time between successive log messages";
           junos:must "(\".. maximum\")";
           junos:must-message "To configure log-interval, maximum must be configured";
           type union {
             type string {
               pattern "<.*>|$.*";
             }
             type uint32 {
               range "1 .. 65535";
             }
           }
         }
       }
       leaf-list rp-register-policy {
         ordered-by user;
         description "RP policy applied to incoming register messages";
         type jt:policy-algebra;
       }
       leaf-list dr-register-policy {
         ordered-by user;
         description "DR policy applied to outgoing register messages";
         type jt:policy-algebra;
       }
       container local {
         description "Router's local RP properties";
         uses apply-advanced;
         leaf address {
           description "Local RP address (IPv4 only)";
           type jt:ipv4addr;
         }
         choice enable-disable {
           case case_1 {
             leaf disable {
               description "Disable this RP (IPv4 only)";
               type empty;
             }
           }
         }
         leaf priority {
           description "Router's priority for becoming an RP (IPv4 only)";
           type union {
             type string {
               pattern "<.*>|$.*";
             }
             type uint32 {
               range "0 .. 255";
             }
           }
         }
         leaf hold-time {
           description "How long neighbor considers this router to be up, in seconds (IPv4 only)";
           type union {
             type string {
               pattern "<.*>|$.*";
             }
             type uint32 {
               range "1 .. 65535";
             }
           }
         }
         list group-ranges {
           key name;
           ordered-by user;
           description "Group address range for which this router can be an RP (IPv4 only)";
           leaf name {
             type jt:ipv4prefix;
           }
           uses apply-advanced;
         }
         leaf override {
           description "Static RP mapping will take precedence over dynamic";
           type empty;
         }
         leaf process-non-null-as-null-register {
           description "Process incoming non null registers as null registers";
           type empty;
         }
         container family {
           description "Local RP address family";
           container inet {
             description "IPv4 local RP properties";
             uses apply-advanced;
             leaf address {
               description "Local RP address";
               type jt:ipv4addr;
             }
             choice enable-disable {
               case case_1 {
                 leaf disable {
                   description "Disable this RP";
                   type empty;
                 }
               }
             }
             leaf priority {
               description "Router's priority for becoming an RP";
               type union {
                 type string {
                   pattern "<.*>|$.*";
                 }
                 type uint32 {
                   range "0 .. 255";
                 }
               }
             }
             leaf hold-time {
               description "How long neighbor considers this router to be up, in seconds";
               type union {
                 type string {
                   pattern "<.*>|$.*";
                 }
                 type uint32 {
                   range "1 .. 65535";
                 }
               }
             }
             list group-ranges {
               key name;
               ordered-by user;
               description "Group address range for which this router can be an RP";
               leaf name {
                 type jt:ipv4prefix;
               }
               uses apply-advanced;
             }
             leaf override {
               description "Static RP mapping will take precedence over dynamic";
               type empty;
             }
             container anycast-pim {
               description "Attributes for IPv4 anycast PIM";
               uses apply-advanced;
               container rp-set {
                 description "Rendezvous points belonging to anycast RP set";
                 uses apply-advanced;
                 list address {
                   key name;
                   ordered-by user;
                   description "IPv4 address of one or more remote anycast RPs";
                   leaf name {
                     description "IPv4 address of remote anycast RP";
                     type jt:ipaddr;
                   }
                   uses apply-advanced;
                   leaf forward-msdp-sa {
                     description "Forward SAs learned from MSDP to this RP";
                     type empty;
                   }
                 }
               }
               leaf local-address {
                 description "Local address for replicating register messages to other RPs";
                 type jt:ipaddr;
               }
             }
           }
           container inet6 {
             description "IPv6 local RP properties";
             uses apply-advanced;
             leaf address {
               description "Local RP address";
               type jt:ipv6addr;
             }
             choice enable-disable {
               case case_1 {
                 leaf disable {
                   description "Disable this RP";
                   type empty;
                 }
               }
             }
             leaf priority {
               description "Router's priority for becoming an RP";
               type union {
                 type string {
                   pattern "<.*>|$.*";
                 }
                 type uint32 {
                   range "0 .. 255";
                 }
               }
             }
             leaf hold-time {
               description "How long neighbor considers this router to be up, in seconds";
               type union {
                 type string {
                   pattern "<.*>|$.*";
                 }
                 type uint32 {
                   range "1 .. 65535";
                 }
               }
             }
             list group-ranges {
               key name;
               ordered-by user;
               description "Group address range for which this router can be an RP";
               leaf name {
                 type jt:ipv6prefix;
               }
               uses apply-advanced;
             }
             leaf override {
               description "Static RP mapping will take precedence over dynamic";
               type empty;
             }
             container anycast-pim {
               description "Attributes for IPv6 anycast PIM";
               uses apply-advanced;
               container rp-set {
                 description "Rendezvous points belonging to anycast RP set";
                 uses apply-advanced;
                 list address {
                   key name;
                   ordered-by user;
                   description "IPv6 address of one or more remote anycast RPs";
                   leaf name {
                     description "IPv6 address of remote anycast RP";
                     type jt:ipv6addr;
                   }
                   uses apply-advanced;
                 }
               }
               leaf local-address {
                 description "Local address for replicating register messages to other RPs";
                 type jt:ipv6addr;
               }
             }
           }
         }
       }
       container embedded-rp {
         presence "enable embedded-rp";
         description "Set embedded-RP mode (IPv6 only)";
         uses apply-advanced;
         list group-ranges {
           key name;
           ordered-by user;
           description "Group address range of RP";
           uses pim_rp_group_range_type;
         }
         leaf maximum-rps {
           description "Maximum number of embedded RPs";
           default "100";
           type union {
             type string {
               pattern "<.*>|$.*";
             }
             type uint32 {
               range "1 .. 500";
             }
           }
         }
       }
       container auto-rp {
         description "Set auto-RP mode (IPv4 only)";
         uses apply-advanced;
         choice autorp-mode {
           case case_1 {
             leaf discovery {
               description "Listen for auto-RP discovery messages";
               type empty;
             }
           }
           case case_2 {
             leaf announce {
               description "Transmit auto-RP announcement messages";
               type empty;
             }
           }
           case case_3 {
             leaf mapping {
               description "Transmit auto-RP mapping messages";
               type empty;
             }
           }
         }
         choice mapping-agent-election-choice {
           leaf mapping-agent-election {
             description "Consider higher-addressed mapping agents as authoritative";
             type empty;
           }
           leaf no-mapping-agent-election {
             description "Don't consider higher-addressed mapping agents as authoritative";
             type empty;
           }
         }
       }
       container static {
         description "Configure static PIM RPs";
         uses apply-advanced;
         list address {
           key name;
           ordered-by user;
           description "RP address";
           leaf name {
             description "IP address of RP";
             type jt:ipaddr;
           }
           uses apply-advanced;
           leaf version {
             description "PIM version of RP";
             status deprecated;
             type union {
               type string {
                 pattern "<.*>|$.*";
               }
               type uint32 {
                 range "1 .. 2";
               }
             }
           }
           list group-ranges {
             key name;
             ordered-by user;
             description "Group address range of RP";
             uses pim_rp_group_range_type;
           }
           leaf override {
             description "Static RP mapping will take precedence over dynamic";
             type empty;
           }
         }
       }
       leaf register-probe-time {
         description "Register probe time";
         default "5";
         units "seconds";
         type union {
           type string {
             pattern "<.*>|$.*";
           }
           type uint32 {
             range "5 .. 60";
           }
         }
       }
     }
     leaf passive {
       description "Configure PIM protocol in passive mode";
       junos:must "(!(any \".. interface <*> distributed-dr\"))";
       junos:must-message "pim passive cannot be configured with pim distributed-dr";
       junos:must "(!(\" .. rp\"))";
       junos:must-message "pim passive cannot be configured with pim rp";
       type empty;
     }
     list interface {
       key name;
       ordered-by user;
       description "PIM interface options";
       leaf name {
         description "Interface name";
         junos:must "((((\"routing-options multicast interface $$ disable\" || (\"routing-options multicast interface $$ maximum-bandwidth\" || (\"routing-options multicast interface $$ nexthop-unicast-address\" || (\"routing-options multicast interface $$ reverse-oif-mapping\" || (\"routing-options multicast interface $$ subscriber-leave-timer\" || \"routing-options multicast interface $$ no-qos-adjust\"))))) && !(\"routing-options multicast interface $$ enable\")) || (\"protocols pim interface $$ disable\" || !((\"routing-options multicast interface $$\" || \"routing-options multicast interface $$ enable\")))))";
         junos:must-message "Multicast cannot be enabled on the same interface in the [edit routing-options] hierarchy";
         type string;
       }
       uses apply-advanced;
       container family {
         description "Local address family";
         container any {
           presence "enable any";
           description "Default properties for all families";
           uses apply-advanced;
           leaf disable {
             description "Disable all families";
             type empty;
           }
         }
         container inet {
           presence "enable inet";
           description "IPv4 specific properties";
           uses apply-advanced;
           container bfd-liveness-detection {
             description "Bidirectional Forwarding Detection options";
             uses apply-advanced;
             leaf version {
               description "BFD protocol version number";
               default "automatic";
               type enumeration {
                 enum "0" {
                   description "BFD version 0 (deprecated)";
                 }
                 enum "1" {
                   description "BFD version 1";
                 }
                 enum "automatic" {
                   description "Choose BFD version automatically";
                 }
               }
             }
             leaf minimum-interval {
               description "Minimum transmit and receive interval";
               units "milliseconds";
               type union {
                 type string {
                   pattern "<.*>|$.*";
                 }
                 type uint32 {
                   range "1 .. 255000";
                 }
               }
             }
             leaf minimum-transmit-interval {
               description "Minimum transmit interval";
               status deprecated;
               units "milliseconds";
               type union {
                 type string {
                   pattern "<.*>|$.*";
                 }
                 type uint32 {
                   range "1 .. 255000";
                 }
               }
             }
             leaf minimum-receive-interval {
               description "Minimum receive interval";
               units "milliseconds";
               type union {
                 type string {
                   pattern "<.*>|$.*";
                 }
                 type uint32 {
                   range "1 .. 255000";
                 }
               }
             }
             leaf multiplier {
               description "Detection time multiplier";
               default "3";
               type union {
                 type string {
                   pattern "<.*>|$.*";
                 }
                 type uint32 {
                   range "1 .. 255";
                 }
               }
             }
             choice adaptation-choice {
               case case_1 {
                 leaf no-adaptation {
                   description "Disable adaptation";
                   type empty;
                 }
               }
             }
             container transmit-interval {
               description "Transmit-interval options";
               uses apply-advanced;
               leaf minimum-interval {
                 description "Minimum transmit interval";
                 units "milliseconds";
                 type union {
                   type string {
                     pattern "<.*>|$.*";
                   }
                   type uint32 {
                     range "1 .. 255000";
                   }
                 }
               }
               leaf threshold {
                 description "High transmit interval triggering a trap";
                 units "milliseconds";
                 type union {
                   type uint32;
                   type string {
                     pattern "<.*>|$.*";
                   }
                 }
               }
             }
             container detection-time {
               description "Detection-time options";
               uses apply-advanced;
               leaf threshold {
                 description "High detection-time triggering a trap";
                 units "milliseconds";
                 type union {
                   type uint32;
                   type string {
                     pattern "<.*>|$.*";
                   }
                 }
               }
             }
             container authentication {
               description "Authentication options";
               uses apply-advanced;
               leaf key-chain {
                 description "Key chain name";
                 junos:must "(\".. algorithm\")";
                 junos:must-message "May not be configured without algorithm";
                 junos:must "(\"security authentication-key-chains key-chain $$\")";
                 junos:must-message "Referenced key-chain must be defined";
                 type string;
               }
               leaf algorithm {
                 description "Algorithm name";
                 junos:must "(\".. key-chain\")";
                 junos:must-message "May not be configured without key-chain";
                 type enumeration {
                   enum "simple-password" {
                     description "Simple password";
                   }
                   enum "keyed-md5" {
                     description "Keyed message Digest 5";
                   }
                   enum "meticulous-keyed-md5" {
                     description "Meticulous keyed message Digest 5";
                   }
                   enum "keyed-sha-1" {
                     description "Keyed secure hash algorithm (SHA1) ";
                   }
                   enum "meticulous-keyed-sha-1" {
                     description "Meticulous keyed secure hash algorithm (SHA1) ";
                   }
                 }
               }
               leaf loose-check {
                 description "Verify authentication only if authentication is negotiated";
                 type empty;
               }
             }
           }
           leaf mcae-mac-synchronize {
             description "Mclag mac synchronization";
             type empty;
           }
           choice enable-disable {
             case case_1 {
               leaf disable {
                 description "Disable PIMv4 on this interface";
                 type empty;
               }
             }
           }
         }
         container inet6 {
           presence "enable inet6";
           description "IPv6 specific properties";
           uses apply-advanced;
           container bfd-liveness-detection {
             description "Bidirectional Forwarding Detection options";
             uses apply-advanced;
             leaf version {
               description "BFD protocol version number";
               default "automatic";
               type enumeration {
                 enum "0" {
                   description "BFD version 0 (deprecated)";
                 }
                 enum "1" {
                   description "BFD version 1";
                 }
                 enum "automatic" {
                   description "Choose BFD version automatically";
                 }
               }
             }
             leaf minimum-interval {
               description "Minimum transmit and receive interval";
               units "milliseconds";
               type union {
                 type string {
                   pattern "<.*>|$.*";
                 }
                 type uint32 {
                   range "1 .. 255000";
                 }
               }
             }
             leaf minimum-transmit-interval {
               description "Minimum transmit interval";
               status deprecated;
               units "milliseconds";
               type union {
                 type string {
                   pattern "<.*>|$.*";
                 }
                 type uint32 {
                   range "1 .. 255000";
                 }
               }
             }
             leaf minimum-receive-interval {
               description "Minimum receive interval";
               units "milliseconds";
               type union {
                 type string {
                   pattern "<.*>|$.*";
                 }
                 type uint32 {
                   range "1 .. 255000";
                 }
               }
             }
             leaf multiplier {
               description "Detection time multiplier";
               default "3";
               type union {
                 type string {
                   pattern "<.*>|$.*";
                 }
                 type uint32 {
                   range "1 .. 255";
                 }
               }
             }
             choice adaptation-choice {
               case case_1 {
                 leaf no-adaptation {
                   description "Disable adaptation";
                   type empty;
                 }
               }
             }
             container transmit-interval {
               description "Transmit-interval options";
               uses apply-advanced;
               leaf minimum-interval {
                 description "Minimum transmit interval";
                 units "milliseconds";
                 type union {
                   type string {
                     pattern "<.*>|$.*";
                   }
                   type uint32 {
                     range "1 .. 255000";
                   }
                 }
               }
               leaf threshold {
                 description "High transmit interval triggering a trap";
                 units "milliseconds";
                 type union {
                   type uint32;
                   type string {
                     pattern "<.*>|$.*";
                   }
                 }
               }
             }
             container detection-time {
               description "Detection-time options";
               uses apply-advanced;
               leaf threshold {
                 description "High detection-time triggering a trap";
                 units "milliseconds";
                 type union {
                   type uint32;
                   type string {
                     pattern "<.*>|$.*";
                   }
                 }
               }
             }
             container authentication {
               description "Authentication options";
               uses apply-advanced;
               leaf key-chain {
                 description "Key chain name";
                 junos:must "(\".. algorithm\")";
                 junos:must-message "May not be configured without algorithm";
                 junos:must "(\"security authentication-key-chains key-chain $$\")";
                 junos:must-message "Referenced key-chain must be defined";
                 type string;
               }
               leaf algorithm {
                 description "Algorithm name";
                 junos:must "(\".. key-chain\")";
                 junos:must-message "May not be configured without key-chain";
                 type enumeration {
                   enum "simple-password" {
                     description "Simple password";
                   }
                   enum "keyed-md5" {
                     description "Keyed message Digest 5";
                   }
                   enum "meticulous-keyed-md5" {
                     description "Meticulous keyed message Digest 5";
                   }
                   enum "keyed-sha-1" {
                     description "Keyed secure hash algorithm (SHA1) ";
                   }
                   enum "meticulous-keyed-sha-1" {
                     description "Meticulous keyed secure hash algorithm (SHA1) ";
                   }
                 }
               }
               leaf loose-check {
                 description "Verify authentication only if authentication is negotiated";
                 type empty;
               }
             }
           }
           choice enable-disable {
             case case_1 {
               leaf disable {
                 description "Disable PIMv6 on this interface";
                 type empty;
               }
             }
           }
         }
       }
       choice enable-disable {
         case case_1 {
           leaf disable {
             description "Disable PIM on this interface";
             type empty;
           }
         }
       }
       leaf mode {
         description "Mode of interface";
         type enumeration {
           enum "dense" {
             description "Dense mode";
           }
           enum "sparse" {
             description "Sparse mode";
           }
           enum "sparse-dense" {
             description "Sparse-dense mode";
           }
           enum "bidirectional-sparse" {
             description "Bidirectional-sparse mode";
             junos:must "((!(\".. .. .. .. .. .. routing-instances\") || any \".. .. .. .. .. .. routing-instances <*> instance-type virtual-router\"))";
             junos:must-message "Only master instance and routing-instances of type virtual-router support PIM-BIDIR.";
             junos:must "(!(\".. version $$={1}\"))";
             junos:must-message "PIM Bidirectional is not supported by PIMv1.";
           }
           enum "bidirectional-sparse-dense" {
             description "Bidirectional-sparse-dense mode";
             junos:must "((!(\".. .. .. .. .. .. routing-instances\") || any \".. .. .. .. .. .. routing-instances <*> instance-type virtual-router\"))";
             junos:must-message "Only master instance and routing-instances of type virtual-router support PIM-BIDIR.";
             junos:must "(!(\".. version $$={1}\"))";
             junos:must-message "PIM Bidirectional is not supported by PIMv1.";
           }
         }
       }
       leaf priority {
         description "Hello option DR priority";
         junos:must "((!(\".. mode dense\") || (\".. mode dense\" && \"protocols igmp interface ${interface} version 1\")))";
         junos:must-message "PIM DR Priority cannot be configured in Dense Mode unless IGMP V1 is configured";
         type union {
           type string {
             pattern "<.*>|$.*";
           }
           type uint32 {
             range "0 .. 4294967295";
           }
         }
       }
       container stickydr {
         presence "enable stickydr";
         description "Make DR sticky";
         uses apply-advanced;
       }
       container multiple-triggered-joins {
         presence "enable multiple-triggered-joins";
         description "Send multiple pim triggered joins in quick intervals";
         uses apply-advanced;
         leaf count {
           description "Set number of triggered joins to be sent";
           default "2";
           type union {
             type string {
               pattern "<.*>|$.*";
             }
             type uint16 {
               range "2 .. 15";
             }
           }
         }
         leaf interval {
           description "Set interval between multiple triggered joins to be sent in milliseconds";
           default "100";
           type union {
             type string {
               pattern "<.*>|$.*";
             }
             type uint16 {
               range "100 .. 1000";
             }
           }
         }
       }
       leaf version {
         description "Force PIM version";
         status deprecated;
         type union {
           type string {
             pattern "<.*>|$.*";
           }
           type uint32 {
             range "1 .. 2";
           }
         }
       }
       leaf hello-interval {
         description "Hello interval";
         units "seconds";
         type union {
           type string {
             pattern "<.*>|$.*";
           }
           type uint32 {
             range "0 .. 255";
           }
         }
       }
       leaf-list neighbor-policy {
         ordered-by user;
         description "PIM neighbor policy applied to incoming hello messages";
         type jt:policy-algebra;
       }
       leaf-list accept-join-always-from {
         ordered-by user;
         description "Accept pim join/prune messages based on the policy configured";
         type jt:policy-algebra;
       }
       leaf accept-remote-source {
         description "Accept traffic from remote source";
         type empty;
       }
       container dual-dr {
         presence "enable dual-dr";
         junos:must "(!(\" .. distributed-dr\"))";
         junos:must-message "pim dual-dr cannot be configured with pim distributed-dr";
         description "Configure PIM Dual DR";
         uses apply-advanced;
         leaf enhanced {
           description "Enable enhanced PIM Dual DR";
           type empty;
         }
       }
       leaf distributed-dr {
         description "PIM Distributed DR";
         junos:must "(!(\".. .. .. passive\"))";
         junos:must-message "pim distributed-dr cannot be configured with pim passive";
         junos:must "(!(\" .. dual-dr\"))";
         junos:must-message "pim distributed-dr cannot be configured with pim dual-dr";
         type empty;
       }
       leaf reset-tracking-bit {
         description "Clear tracking-bit in PIM Hello LAN Prune Delay Option";
         type empty;
       }
       leaf propagation-delay {
         description "Propagation delay value";
         default "500";
         units "milliseconds";
         type union {
           type string {
             pattern "<.*>|$.*";
           }
           type uint32 {
             range "250 .. 2000";
           }
         }
       }
       leaf override-interval {
         description "Override interval value";
         default "2000";
         units "milliseconds";
         type union {
           type string {
             pattern "<.*>|$.*";
           }
           type uint32 {
             range "500 .. 6000";
           }
         }
       }
       container bfd-liveness-detection {
         description "Bidirectional Forwarding Detection options (ipv4 only)";
         status deprecated;
         uses apply-advanced;
         leaf version {
           description "BFD protocol version number";
           default "automatic";
           type enumeration {
             enum "0" {
               description "BFD version 0 (deprecated)";
             }
             enum "1" {
               description "BFD version 1";
             }
             enum "automatic" {
               description "Choose BFD version automatically";
             }
           }
         }
         leaf minimum-interval {
           description "Minimum transmit and receive interval";
           units "milliseconds";
           type union {
             type string {
               pattern "<.*>|$.*";
             }
             type uint32 {
               range "1 .. 255000";
             }
           }
         }
         leaf minimum-transmit-interval {
           description "Minimum transmit interval";
           status deprecated;
           units "milliseconds";
           type union {
             type string {
               pattern "<.*>|$.*";
             }
             type uint32 {
               range "1 .. 255000";
             }
           }
         }
         leaf minimum-receive-interval {
           description "Minimum receive interval";
           units "milliseconds";
           type union {
             type string {
               pattern "<.*>|$.*";
             }
             type uint32 {
               range "1 .. 255000";
             }
           }
         }
         leaf multiplier {
           description "Detection time multiplier";
           default "3";
           type union {
             type string {
               pattern "<.*>|$.*";
             }
             type uint32 {
               range "1 .. 255";
             }
           }
         }
         choice adaptation-choice {
           case case_1 {
             leaf no-adaptation {
               description "Disable adaptation";
               type empty;
             }
           }
         }
         container transmit-interval {
           description "Transmit-interval options";
           uses apply-advanced;
           leaf minimum-interval {
             description "Minimum transmit interval";
             units "milliseconds";
             type union {
               type string {
                 pattern "<.*>|$.*";
               }
               type uint32 {
                 range "1 .. 255000";
               }
             }
           }
           leaf threshold {
             description "High transmit interval triggering a trap";
             units "milliseconds";
             type union {
               type uint32;
               type string {
                 pattern "<.*>|$.*";
               }
             }
           }
         }
         container detection-time {
           description "Detection-time options";
           uses apply-advanced;
           leaf threshold {
             description "High detection-time triggering a trap";
             units "milliseconds";
             type union {
               type uint32;
               type string {
                 pattern "<.*>|$.*";
               }
             }
           }
         }
         container authentication {
           description "Authentication options";
           uses apply-advanced;
           leaf key-chain {
             description "Key chain name";
             junos:must "(\".. algorithm\")";
             junos:must-message "May not be configured without algorithm";
             junos:must "(\"security authentication-key-chains key-chain $$\")";
             junos:must-message "Referenced key-chain must be defined";
             type string;
           }
           leaf algorithm {
             description "Algorithm name";
             junos:must "(\".. key-chain\")";
             junos:must-message "May not be configured without key-chain";
             type enumeration {
               enum "simple-password" {
                 description "Simple password";
               }
               enum "keyed-md5" {
                 description "Keyed message Digest 5";
               }
               enum "meticulous-keyed-md5" {
                 description "Meticulous keyed message Digest 5";
               }
               enum "keyed-sha-1" {
                 description "Keyed secure hash algorithm (SHA1) ";
               }
               enum "meticulous-keyed-sha-1" {
                 description "Meticulous keyed secure hash algorithm (SHA1) ";
               }
             }
           }
           leaf loose-check {
             description "Verify authentication only if authentication is negotiated";
             type empty;
           }
         }
       }
     }
     container mdt {
       junos:must "((!(\" .. .. mvpn\") || \".. mvpn family inet rosen-mvpn\"))";
       junos:must-message "Data tunnels cannot be configured with 'protocols mvpn'";
       description "Configure multicast data tunnel parameters";
       status deprecated;
       uses apply-advanced;
       container threshold {
         description "Threshold for creation of multicast tunnels";
         uses apply-advanced;
         list group {
           key name;
           ordered-by user;
           description "IP prefix of multicast group";
           leaf name {
             description "IP prefix of group";
             type jt:ipprefix;
           }
           uses apply-advanced;
           list source {
             key name;
             ordered-by user;
             description "IP prefix of one or more multicast sources ";
             leaf name {
               description "IP prefix of source";
               type jt:ipprefix;
             }
             uses apply-advanced;
             leaf rate {
               description "Data threshold to create new tunnel";
               units "kilobits";
               type union {
                 type string {
                   pattern "<.*>|$.*";
                 }
                 type uint32 {
                   range "10 .. 1000000";
                 }
               }
             }
           }
         }
       }
       leaf data-mdt-reuse {
         description "Allow multiple customer streams to be transmitted over one data tunnel ";
         type empty;
       }
       leaf tunnel-limit {
         description "Maximum multicast data tunnels";
         type union {
           type string {
             pattern "<.*>|$.*";
           }
           type uint32 {
             range "0 .. 8192";
           }
         }
       }
       leaf group-range {
         description "Group address range for multicast data tunnels";
         type jt:ipprefix;
       }
     }
     container graceful-restart {
       description "Configure graceful restart attributes";
       uses apply-advanced;
       choice enable-disable {
         case case_1 {
           leaf disable {
             description "Disable PIM graceful restart capability";
             type empty;
           }
         }
       }
       leaf restart-duration {
         description "Maximum time for graceful restart to finish (seconds)";
         units "seconds";
         type union {
           type string {
             pattern "<.*>|$.*";
           }
           type uint32 {
             range "30 .. 300";
           }
         }
       }
       leaf no-bidirectional-mode {
         description "Disable PIM graceful restart for bidirectional mode";
         type empty;
       }
       leaf restart-complete-duration {
         description "Maximum time for graceful restart to complete (seconds)";
         units "seconds";
         type union {
           type string {
             pattern "<.*>|$.*";
           }
           type uint32 {
             range "5 .. 300";
           }
         }
       }
     }
     container join-load-balance {
       presence "enable join-load-balance";
       description "Configure PIM join load balancing";
       uses apply-advanced;
       leaf automatic {
         description "Enable automatic PIM join load balancing";
         type empty;
       }
     }
     leaf standby-path-creation-delay {
       description "Amount of time to wait before creating standby path";
       units "seconds";
       type union {
         type string {
           pattern "<.*>|$.*";
         }
         type uint32 {
           range "1 .. 300";
         }
       }
     }
     leaf idle-standby-path-switchover-delay {
       description "Amount of time to wait before switching over to idle standby path";
       units "seconds";
       type union {
         type string {
           pattern "<.*>|$.*";
         }
         type uint32 {
           range "1 .. 300";
         }
       }
     }
     leaf dr-election-on-p2p {
       description "Enable DR election on Point-to-Point Interfaces";
       type empty;
     }
     leaf no-wildcard-register-stop {
       description "Disable sending of wildcard register stop message";
       type empty;
     }
     leaf nexthop-hold-time {
       description "Nexthop hold time in milliseconds";
       units "milliseconds";
       type union {
         type string {
           pattern "<.*>|$.*";
         }
         type uint32 {
           range "1 .. 1000";
         }
       }
     }
     leaf mpls-internet-multicast {
       description "Enable support for Internet Multicast over MPLS";
       junos:must "(any \"routing-instances <*> instance-type mpls-internet-multicast\")";
       junos:must-message "The mpls-internet-multicast instance must be configured to support multicast over MPLS";
       type empty;
     }
     container join-make-before-break {
       description "Enable PIM Join Make-Before-Break during RPF neighbor change";
       uses apply-advanced;
       choice enable-disable {
         case case_1 {
           leaf disable {
             description "Disable Make-Before-Break for PIM RPF neighbor change";
             type empty;
           }
         }
       }
     }
     leaf reset-tracking-bit {
       description "Clear tracking-bit in PIM Hello LAN Prune Delay Option";
       type empty;
     }
     leaf propagation-delay {
       description "Propagation delay value";
       default "500";
       units "milliseconds";
       type union {
         type string {
           pattern "<.*>|$.*";
         }
         type uint32 {
           range "250 .. 2000";
         }
       }
     }
     leaf override-interval {
       description "Override interval value";
       default "2000";
       units "milliseconds";
       type union {
         type string {
           pattern "<.*>|$.*";
         }
         type uint32 {
           range "500 .. 6000";
         }
       }
     }
     container default-vpn-source {
       presence "enable default-vpn-source";
       description "Let all VRFs use master loopback address for mt interfaces";
       uses apply-advanced;
       leaf interface-name {
         description "Master loopback interface name";
         junos:must "(\"interfaces $$-IFL family inet address\")";
         junos:must-message "Family inet address should be configured on this loopback interface";
         type union {
           type jt:interface-unit;
           type string {
             pattern "<.*>|$.*";
           }
         }
       }
     }
   }
   grouping juniper-protocols-protection-group {
     uses apply-advanced;
     container ethernet-aps {
       description "Ethernet APS configuration";
       uses juniper-protocols-protection-group-eaps;
     }
     container traceoptions {
       description "Tracing options for debugging protocol operation";
       uses erp-trace-options;
     }
     leaf restore-interval {
       description "Wait to restore interval";
       default "5";
       units "minutes";
       type union {
         type string {
           pattern "<.*>|$.*";
         }
         type uint32 {
           range "1 .. 12";
         }
       }
     }
     leaf guard-interval {
       description "Guard timer interval in 10ms steps";
       default "500";
       units "milliseconds";
       type union {
         type string {
           pattern "<.*>|$.*";
         }
         type uint32 {
           range "10 .. 2000";
         }
       }
     }
     leaf hold-interval {
       description "Hold off timer interval in 100ms steps";
       default "0";
       units "milliseconds";
       type union {
         type string {
           pattern "<.*>|$.*";
         }
         type uint32 {
           range "0 .. 10000";
         }
       }
     }
     list ethernet-ring {
       key name;
       ordered-by user;
       description "Ethernet ring";
       uses juniper-protocols-protection-group-ethernet-ring;
     }
   }
   grouping erp-trace-options {
     description "Trace options for Ethernet Ring Protocol";
     uses apply-advanced;
     list flag {
       key name;
       ordered-by user;
       description "Tracing parameters";
       junos:must "(\".. file\")";
       junos:must-message "Trace file name required to enable tracing";
       leaf name {
         type enumeration {
           enum "events" {
             description "Trace events to the protocol state machine";
           }
           enum "pdu" {
             description "Trace R-APS PDU reception and transmission";
           }
           enum "timers" {
             description "Trace protocol timers";
           }
           enum "state-machine" {
             description "Trace R-APS state machine";
           }
           enum "periodic-packet-management" {
             description "Trace periodic packet management state and events";
           }
           enum "config" {
             description "Trace protocol configuration";
           }
           enum "normal" {
             description "Trace protocol general log messages";
           }
           enum "debug" {
             description "Trace protocol debug log messages";
           }
           enum "all" {
             description "Trace all";
           }
         }
       }
     }
     container file {
       description "Trace file options";
       leaf filename {
         description "Name of file in which to write trace information";
         type string {
           length "1 .. 1024";
           junos:posix-pattern "![/ %]";
           junos:pattern-message "Must not contain '/', % or a space";
         }
       }
       leaf replace {
         description "Replace trace file rather than appending to it";
         status deprecated;
         type empty;
       }
       leaf size {
         description "Maximum trace file size";
         type string;
       }
       leaf files {
         description "Maximum number of trace files";
         default "10";
         type union {
           type string {
             pattern "<.*>|$.*";
           }
           type uint32 {
             range "2 .. 1000";
           }
         }
       }
       leaf no-stamp {
         description "Do not timestamp trace file";
         status deprecated;
         type empty;
       }
       choice world-readable-choice {
         leaf world-readable {
           description "Allow any user to read the log file";
           type empty;
         }
         leaf no-world-readable {
           description "Don't allow any user to read the log file";
           type empty;
         }
       }
     }
   }
   grouping juniper-protocols-protection-group-eaps {
     uses apply-advanced;
     list profile {
       key name;
       uses juniper-protocols-protection-group-eaps-profile;
     }
   }
   grouping juniper-protocols-protection-group-eaps-profile {
     description "Ethernet APS profile";
     leaf name {
       description "Profile name";
       type string {
         length "1 .. 32";
       }
     }
     uses apply-advanced;
     leaf protocol {
       description "Protocol value";
       type enumeration {
         enum "ccm" {
           description "Use CCM packets for protection.";
         }
         enum "G.8031" {
           description "Use G.8031 packets for protection.";
         }
       }
     }
     leaf revert-time {
       description "Reversion time in minutes, 0 would mean no reversion";
       default "4";
       units "minutes";
       type union {
         type string {
           pattern "<.*>|$.*";
         }
         type uint32 {
           range "0 .. 15";
         }
       }
     }
     leaf hold-time {
       description "Hold time in seconds";
       default "0";
       units "milli seconds";
       junos:must "(\".. protocol G.8031\")";
       junos:must-message "hold-time is allowed with G.8031 protocol only";
       type union {
         type string {
           pattern "<.*>|$.*";
         }
         type uint32 {
           range "0 .. 10000";
         }
       }
     }
     leaf local-request {
       description "Local APS request";
       junos:must "(\".. protocol G.8031\")";
       junos:must-message "local-request is allowed with G.8031 protocol only";
       type enumeration {
         enum "lockout" {
           description "Lockout protection";
         }
       }
     }
   }
   grouping juniper-protocols-protection-group-ethernet-ring {
     description "Ethernet Ring protection group configuration";
     leaf name {
       description "Name of Ethernet Ring protection group";
       type string {
         length "1 .. 32";
       }
     }
     uses apply-advanced;
     leaf node-id {
       description "Node ID of the protection group, by default bridge's MAC";
       type jt:mac-unicast;
     }
     leaf ring-protection-link-owner {
       description "Ring protection link owner flag, one ring should have only one node as a ring protection link owner";
       type empty;
     }
     leaf level {
       description "MPG Level value for R-APS PDU";
       type union {
         type string {
           pattern "<.*>|$.*";
         }
         type uint32 {
           range "0 .. 7";
         }
       }
     }
     leaf restore-interval {
       description "Wait to restore interval";
       units "minutes";
       type union {
         type string {
           pattern "<.*>|$.*";
         }
         type uint32 {
           range "1 .. 12";
         }
       }
     }
     leaf guard-interval {
       description "Guard timer interval in 10ms";
       units "milliseconds";
       type union {
         type string {
           pattern "<.*>|$.*";
         }
         type uint32 {
           range "10 .. 2000";
         }
       }
     }
     leaf hold-interval {
       description "Hold off timer interval in 100ms steps";
       units "milliseconds";
       type union {
         type string {
           pattern "<.*>|$.*";
         }
         type uint32 {
           range "0 .. 10000";
         }
       }
     }
     leaf non-revertive {
       description "Non-revertive mode of operation";
       type empty;
     }
     leaf wait-to-block-interval {
       description "Wait to block interval";
       default "5";
       units "seconds";
       type union {
         type string {
           pattern "<.*>|$.*";
         }
         type uint32 {
           range "5 .. 10";
         }
       }
     }
     leaf major-ring-name {
       description "Name of major-ring to which this sub-ring node attached";
       type string {
         length "1 .. 32";
       }
     }
     leaf propagate-tc {
       description "Enable Topology Change Propagation to major-ring from the sub-ring";
       type empty;
     }
     leaf compatibility-version {
       description "G.8032 compatibility version";
       default "2";
       type union {
         type string {
           pattern "<.*>|$.*";
         }
         type uint32 {
           range "1 .. 2";
         }
       }
     }
     leaf ring-id {
       description "Ethernet Ring ID of protection group";
       default "1";
       type union {
         type string {
           pattern "<.*>|$.*";
         }
         type uint32 {
           range "1 .. 239";
         }
       }
     }
     leaf non-vc-mode {
       description "Node is operating in non virtual channel mode";
       type empty;
     }
     leaf dot1p-priority {
       description "IEEE 802.1p priority of transmitted R-APS";
       default "0";
       type union {
         type string {
           pattern "<.*>|$.*";
         }
         type uint32 {
           range "0 .. 7";
         }
       }
     }
     container east-interface {
       description "East interface configuration";
       presence "enable east-interface";
       uses erp-interface;
     }
     container west-interface {
       description "West interface configuration";
       presence "enable west-interface";
       uses erp-interface;
     }
     leaf control-vlan {
       description "Dedicated VLAN identifier - VLAN id or VLAN name";
       type string;
     }
     container data-channel {
       description "Ring instance data channel";
       presence "enable data-channel";
       uses erp-data-channel;
     }
   }
   grouping erp-data-channel {
     uses apply-advanced;
     leaf-list vlan {
       ordered-by user;
       description "VLAN ID or VLAN ID range [1..4094]";
       type string;
     }
   }
   grouping erp-interface {
     uses apply-advanced;
     container control-channel {
       presence "enable control-channel";
       description "Control channel of ring port";
       uses apply-advanced;
       leaf vlan {
         description "Dedicated VLAN identifier";
         type union {
           type string {
             pattern "<.*>|$.*";
           }
           type uint16 {
             range "1 .. 4094";
           }
         }
       }
       leaf control-channel-name {
         type union {
           type jt:interface-name;
           type string {
             pattern "<.*>|$.*";
           }
         }
       }
     }
     leaf ring-protection-link-end {
       description "Port is connecting to ring protection link";
       type empty;
     }
     leaf interface-none {
       description "Port is not used";
       type empty;
     }
   }
   grouping juniper-protocols-rip {
     uses apply-advanced;
     container traceoptions {
       description "Trace options for RIP";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "auth" {
               description "Trace RIP authentication";
             }
             enum "error" {
               description "Trace RIP errors";
             }
             enum "expiration" {
               description "Trace RIP route expiration processing";
             }
             enum "holddown" {
               description "Trace RIP hold-down processing";
             }
             enum "packets" {
               description "Trace all RIP packets";
             }
             enum "request" {
               description "Trace RIP information packets";
             }
             enum "trigger" {
               description "Trace RIP triggered updates";
             }
             enum "update" {
               description "Trace RIP update packets";
             }
             enum "nsr-synchronization" {
               description "Trace NSR synchronization events";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
         container filter {
           description "Filter to apply to this flag";
           presence "enable filter";
           uses rip_filter_obj;
         }
       }
     }
     container rib-group {
       description "Routing table group for importing RIP routes";
       uses rib_group_inet_type;
     }
     leaf metric-in {
       description "Metric value to add to incoming routes";
       type union {
         type string {
           pattern "<.*>|$.*";
         }
         type uint32 {
           range "1 .. 15";
         }
       }
     }
     container send {
       description "Configure RIP send options";
       choice send-opts {
         case case_1 {
           leaf broadcast {
             description "Broadcast RIPv2 packets (RIPv1 compatible)";
             type empty;
           }
         }
         case case_2 {
           leaf multicast {
             description "Multicast RIPv2 packets";
             type empty;
           }
         }
         case case_3 {
           leaf none {
             description "Do not send RIP updates";
             type empty;
           }
         }
         case case_4 {
           leaf version-1 {
             description "Broadcast RIPv1 packets";
             type empty;
           }
         }
       }
     }
     container receive {
       description "Configure RIP receive options";
       choice receive-opts {
         case case_1 {
           leaf both {
             description "Accept both RIPv1 and RIPv2 packets";
             type empty;
           }
         }
         case case_2 {
           leaf none {
             description "Do not receive RIP packets";
             type empty;
           }
         }
         case case_3 {
           leaf version-1 {
             description "Accept RIPv1 packets only";
             type empty;
           }
         }
         case case_4 {
           leaf version-2 {
             description "Accept only RIPv2 packets";
             type empty;
           }
         }
       }
     }
     choice check-zero-choice {
       leaf check-zero {
         description "Check reserved fields on incoming RIPv2 packets";
         type empty;
       }
       leaf no-check-zero {
         description "Don't check reserved fields on incoming RIPv2 packets";
         type empty;
       }
     }
     leaf message-size {
       description "Number of route entries per update message";
       type union {
         type string {
           pattern "<.*>|$.*";
         }
         type uint32 {
           range "25 .. 255";
         }
       }
     }
     leaf-list import {
       ordered-by user;
       description "Import policy";
       type jt:policy-algebra;
     }
     leaf holddown {
       description "Hold-down time";
       units "seconds";
       type union {
         type string {
           pattern "<.*>|$.*";
         }
         type uint32 {
           range "10 .. 180";
         }
       }
     }
     leaf route-timeout {
       description "Delay before routes time out";
       units "seconds";
       type union {
         type string {
           pattern "<.*>|$.*";
         }
         type uint32 {
           range "30 .. 360";
         }
       }
     }
     leaf update-interval {
       description "Interval between regular route updates";
       units "seconds";
       type union {
         type string {
           pattern "<.*>|$.*";
         }
         type uint32 {
           range "10 .. 60";
         }
       }
     }
     choice authentication {
       case case_1 {
         leaf authentication-type {
           type enumeration {
             enum "none" {
               description "No authentication";
             }
             enum "simple" {
               description "Simple password authentication";
             }
             enum "md5" {
               description "MD5 authentication";
             }
           }
         }
       }
       case case_2 {
         list authentication-selective-md5 {
           key name;
           ordered-by user;
           description "MD5 authentication with one or more keys";
           leaf name {
             description "Key ID for MD5 authentication";
             type union {
               type string {
                 pattern "<.*>|$.*";
               }
               type uint32 {
                 range "0 .. 255";
               }
             }
           }
           leaf key {
             description "MD5 authentication key value";
             type jt:unreadable;
           }
           leaf start-time {
             description "Start time for key transmission (YYYY-MM-DD.HH:MM)";
             type jt:time;
           }
         }
       }
     }
     leaf authentication-key {
       description "Authentication key (password)";
       junos:must "(!(\".. authentication-selective-md5\"))";
       junos:must-message "Key already provided for selective-md5";
       type jt:unreadable;
     }
     list group {
       key name;
       ordered-by user;
       description "Instance configuration";
       leaf name {
         description "Group name";
         type string {
           junos:posix-pattern "^.{1,48}$";
           junos:pattern-message "Must be a string of at most 48 characters";
         }
       }
       uses apply-advanced;
       leaf route-timeout {
         description "Delay before routes time out";
         units "seconds";
         type union {
           type string {
             pattern "<.*>|$.*";
           }
           type uint32 {
             range "30 .. 360";
           }
         }
       }
       leaf update-interval {
         description "Interval between regular route updates";
         units "seconds";
         type union {
           type string {
             pattern "<.*>|$.*";
           }
           type uint32 {
             range "10 .. 60";
           }
         }
       }
       leaf preference {
         description "Preference of routes learned by this group";
         type union {
           type uint32;
           type string {
             pattern "<.*>|$.*";
           }
         }
       }
       leaf metric-out {
         description "Default metric of exported routes";
         type union {
           type string {
             pattern "<.*>|$.*";
           }
           type uint32 {
             range "1 .. 15";
           }
         }
       }
       leaf-list export {
         ordered-by user;
         description "Export policy";
         type jt:policy-algebra;
       }
       leaf-list import {
         ordered-by user;
         description "Import policy";
         type jt:policy-algebra;
       }
       leaf demand-circuit {
         description "Enable demand circuit on this interface";
         junos:must "(!(\".. .. authentication-selective-md5\"))";
         junos:must-message "selective-md5 isn't supported with demand-circuit,opt for 'authentication-type md5' instead";
         type empty;
       }
       leaf max-retrans-time {
         description "Maximum time to re-transmit a message in demand-circuit";
         type union {
           type string {
             pattern "<.*>|$.*";
           }
           type uint32 {
             range "5 .. 180";
           }
         }
       }
       container bfd-liveness-detection {
         description "Bidirectional Forwarding Detection options";
         uses apply-advanced;
         leaf version {
           description "BFD protocol version number";
           default "automatic";
           type enumeration {
             enum "0" {
               description "BFD version 0 (deprecated)";
             }
             enum "1" {
               description "BFD version 1";
             }
             enum "automatic" {
               description "Choose BFD version automatically";
             }
           }
         }
         leaf minimum-interval {
           description "Minimum transmit and receive interval";
           units "milliseconds";
           type union {
             type string {
               pattern "<.*>|$.*";
             }
             type uint32 {
               range "1 .. 255000";
             }
           }
         }
         leaf minimum-transmit-interval {
           description "Minimum transmit interval";
           status deprecated;
           units "milliseconds";
           type union {
             type string {
               pattern "<.*>|$.*";
             }
             type uint32 {
               range "1 .. 255000";
             }
           }
         }
         leaf minimum-receive-interval {
           description "Minimum receive interval";
           units "milliseconds";
           type union {
             type string {
               pattern "<.*>|$.*";
             }
             type uint32 {
               range "1 .. 255000";
             }
           }
         }
         leaf multiplier {
           description "Detection time multiplier";
           default "3";
           type union {
             type string {
               pattern "<.*>|$.*";
             }
             type uint32 {
               range "1 .. 255";
             }
           }
         }
         choice adaptation-choice {
           case case_1 {
             leaf no-adaptation {
               description "Disable adaptation";
               type empty;
             }
           }
         }
         container transmit-interval {
           description "Transmit-interval options";
           uses apply-advanced;
           leaf minimum-interval {
             description "Minimum transmit interval";
             units "milliseconds";
             type union {
               type string {
                 pattern "<.*>|$.*";
               }
               type uint32 {
                 range "1 .. 255000";
               }
             }
           }
           leaf threshold {
             description "High transmit interval triggering a trap";
             units "milliseconds";
             type union {
               type uint32;
               type string {
                 pattern "<.*>|$.*";
               }
             }
           }
         }
         container detection-time {
           description "Detection-time options";
           uses apply-advanced;
           leaf threshold {
             description "High detection-time triggering a trap";
             units "milliseconds";
             type union {
               type uint32;
               type string {
                 pattern "<.*>|$.*";
               }
             }
           }
         }
         container authentication {
           description "Authentication options";
           uses apply-advanced;
           leaf key-chain {
             description "Key chain name";
             junos:must "(\".. algorithm\")";
             junos:must-message "May not be configured without algorithm";
             junos:must "(\"security authentication-key-chains key-chain $$\")";
             junos:must-message "Referenced key-chain must be defined";
             type string;
           }
           leaf algorithm {
             description "Algorithm name";
             junos:must "(\".. key-chain\")";
             junos:must-message "May not be configured without key-chain";
             type enumeration {
               enum "simple-password" {
                 description "Simple password";
               }
               enum "keyed-md5" {
                 description "Keyed message Digest 5";
               }
               enum "meticulous-keyed-md5" {
                 description "Meticulous keyed message Digest 5";
               }
               enum "keyed-sha-1" {
                 description "Keyed secure hash algorithm (SHA1) ";
               }
               enum "meticulous-keyed-sha-1" {
                 description "Meticulous keyed secure hash algorithm (SHA1) ";
               }
             }
           }
           leaf loose-check {
             description "Verify authentication only if authentication is negotiated";
             type empty;
           }
         }
       }
       list neighbor {
         key name;
         ordered-by user;
         description "Neighbor configuration";
         leaf name {
           description "Interface name";
           type union {
             type jt:interface-name;
             type string {
               pattern "<.*>|$.*";
             }
           }
         }
         uses apply-advanced;
         leaf route-timeout {
           description "Delay before routes time out";
           units "seconds";
           type union {
             type string {
               pattern "<.*>|$.*";
             }
             type uint32 {
               range "30 .. 360";
             }
           }
         }
         leaf update-interval {
           description "Interval between regular route updates";
           units "seconds";
           type union {
             type string {
               pattern "<.*>|$.*";
             }
             type uint32 {
               range "10 .. 60";
             }
           }
         }
         leaf interface-type {
           description "Interface type for the neighbor";
           type enumeration {
             enum "p2mp" {
               description "Point-to-multipoint link";
               junos:must "(!(\".. .. .. authentication-selective-md5\"))";
               junos:must-message "selective-md5 isn't supported with 'interface-type p2mp', opt for 'authentication-type md5' instead";
             }
           }
         }
         leaf dynamic-peers {
           description "Learn peers dynamically on a p2mp interface";
           junos:must "(\" .. interface-type p2mp\")";
           junos:must-message "dynamic-peers option can be set only if the interface type is p2mp";
           type empty;
         }
         list peer {
           key name;
           ordered-by user;
           description "P2MP peer";
           junos:must "(\" .. interface-type p2mp\")";
           junos:must-message "Peer address can be set only if the interface type is p2mp";
           leaf name {
             description "Address of peer";
             type jt:ipaddr;
           }
         }
         leaf metric-in {
           description "Metric value to add to incoming routes";
           type union {
             type string {
               pattern "<.*>|$.*";
             }
             type uint32 {
               range "1 .. 15";
             }
           }
         }
         container send {
           description "Configure RIP send options";
           choice send-opts {
             case case_1 {
               leaf broadcast {
                 description "Broadcast RIPv2 packets (RIPv1 compatible)";
                 type empty;
               }
             }
             case case_2 {
               leaf multicast {
                 description "Multicast RIPv2 packets";
                 type empty;
               }
             }
             case case_3 {
               leaf none {
                 description "Do not send RIP updates";
                 type empty;
               }
             }
             case case_4 {
               leaf version-1 {
                 description "Broadcast RIPv1 packets";
                 type empty;
               }
             }
           }
         }
         container receive {
           description "Configure RIP receive options";
           choice receive-opts {
             case case_1 {
               leaf both {
                 description "Accept both RIPv1 and RIPv2 packets";
                 type empty;
               }
             }
             case case_2 {
               leaf none {
                 description "Do not receive RIP packets";
                 type empty;
               }
             }
             case case_3 {
               leaf version-1 {
                 description "Accept RIPv1 packets only";
                 type empty;
               }
             }
             case case_4 {
               leaf version-2 {
                 description "Accept only RIPv2 packets";
                 type empty;
               }
             }
           }
         }
         leaf demand-circuit {
           description "Enable demand circuit on this interface";
           junos:must "(!(\".. .. .. authentication-selective-md5\"))";
           junos:must-message "selective-md5 isn't supported with demand-circuit, opt for 'authentication-type md5' instead";
           type empty;
         }
         leaf max-retrans-time {
           description "Maximum time to re-transmit a msg in demand-circuit";
           type union {
             type string {
               pattern "<.*>|$.*";
             }
             type uint32 {
               range "5 .. 180";
             }
           }
         }
         choice check-zero-choice {
           leaf check-zero {
             description "Check reserved fields on incoming RIPv1 packets";
             type empty;
           }
           leaf no-check-zero {
             description "Don't check reserved fields on incoming RIPv1 packets";
             type empty;
           }
         }
         leaf any-sender {
           description "Disable strict checks on sender address";
           type empty;
         }
         leaf message-size {
           description "Number of route entries per update message";
           type union {
             type string {
               pattern "<.*>|$.*";
             }
             type uint32 {
               range "25 .. 255";
             }
           }
         }
         leaf-list import {
           ordered-by user;
           description "Import policy";
           type jt:policy-algebra;
         }
         choice authentication {
           case case_1 {
             leaf authentication-type {
               type enumeration {
                 enum "none" {
                   description "No authentication";
                 }
                 enum "simple" {
                   description "Simple password authentication";
                 }
                 enum "md5" {
                   description "MD5 authentication";
                 }
               }
             }
           }
           case case_2 {
             list authentication-selective-md5 {
               key name;
               ordered-by user;
               description "MD5 authentication with one or more keys";
               junos:must "(!(\"..  interface-type p2mp\"))";
               junos:must-message "selective-md5 isn't supported with '.. neighbor <> interface-type p2mp', opt for 'authentication-type md5' instead";
               junos:must "(!(\"..  demand-circuit\"))";
               junos:must-message "selective-md5 isn't supported with '.. neighbor <> demand-circuit', opt for 'authentication-type md5' instead";
               junos:must "(!(\".. .. demand-circuit\"))";
               junos:must-message "selective-md5 isn't supported with '.. group <> demand-circuit', opt for 'authentication-type md5' instead";
               leaf name {
                 description "Key ID for MD5 authentication";
                 type union {
                   type string {
                     pattern "<.*>|$.*";
                   }
                   type uint32 {
                     range "0 .. 255";
                   }
                 }
               }
               leaf key {
                 description "MD5 authentication key value";
                 type jt:unreadable;
               }
               leaf start-time {
                 description "Start time for key transmission (YYYY-MM-DD.HH:MM)";
                 type jt:time;
               }
             }
           }
         }
         leaf authentication-key {
           description "Authentication key (password)";
           junos:must "(!(\".. authentication-selective-md5\"))";
           junos:must-message "Key already provided for selective-md5";
           type jt:unreadable;
         }
         container bfd-liveness-detection {
           description "Bidirectional Forwarding Detection options";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
           container authentication {
             description "Authentication options";
             uses apply-advanced;
             leaf key-chain {
               description "Key chain name";
               junos:must "(\".. algorithm\")";
               junos:must-message "May not be configured without algorithm";
               junos:must "(\"security authentication-key-chains key-chain $$\")";
               junos:must-message "Referenced key-chain must be defined";
               type string;
             }
             leaf algorithm {
               description "Algorithm name";
               junos:must "(\".. key-chain\")";
               junos:must-message "May not be configured without key-chain";
               type enumeration {
                 enum "simple-password" {
                   description "Simple password";
                 }
                 enum "keyed-md5" {
                   description "Keyed message Digest 5";
                 }
                 enum "meticulous-keyed-md5" {
                   description "Meticulous keyed message Digest 5";
                 }
                 enum "keyed-sha-1" {
                   description "Keyed secure hash algorithm (SHA1) ";
                 }
                 enum "meticulous-keyed-sha-1" {
                   description "Meticulous keyed secure hash algorithm (SHA1) ";
                 }
               }
             }
             leaf loose-check {
               description "Verify authentication only if authentication is negotiated";
               type empty;
             }
           }
         }
       }
     }
     container graceful-restart {
       presence "enable graceful-restart";
       description "RIP graceful restart options";
       uses apply-advanced;
       choice enable-disable {
         case case_1 {
           leaf disable {
             description "Disable graceful restart";
             type empty;
           }
         }
       }
       leaf restart-time {
         description "Time after which RIP is declared out of restart";
         type union {
           type string {
             pattern "<.*>|$.*";
           }
           type uint32 {
             range "1 .. 600";
           }
         }
       }
     }
   }
   grouping juniper-protocols-ripng {
     uses apply-advanced;
     container traceoptions {
       description "Trace options for RIPng";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "error" {
               description "Trace RIPng errors";
             }
             enum "expiration" {
               description "Trace RIPng route expiration processing";
             }
             enum "holddown" {
               description "Trace RIPng hold-down processing";
             }
             enum "packets" {
               description "Trace all RIPng packets";
             }
             enum "request" {
               description "Trace RIPng information packets";
             }
             enum "trigger" {
               description "Trace RIPng triggered updates";
             }
             enum "update" {
               description "Trace RIPng update packets";
             }
             enum "nsr-synchronization" {
               description "Trace NSR synchronization events";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     leaf metric-in {
       description "Metric value to add to incoming routes";
       type union {
         type string {
           pattern "<.*>|$.*";
         }
         type uint32 {
           range "1 .. 15";
         }
       }
     }
     container send {
       description "Configure RIPng send options";
       choice send-opts {
         case case_1 {
           leaf none {
             description "Do not send RIPng updates";
             type empty;
           }
         }
       }
     }
     container receive {
       description "Configure RIPng receive options";
       choice receive-opts {
         case case_1 {
           leaf none {
             description "Do not receive RIPng packets";
             type empty;
           }
         }
       }
     }
     leaf-list import {
       ordered-by user;
       description "Import policy";
       type jt:policy-algebra;
     }
     leaf holddown {
       description "Hold-down time";
       units "seconds";
       type union {
         type string {
           pattern "<.*>|$.*";
         }
         type uint32 {
           range "10 .. 180";
         }
       }
     }
     leaf route-timeout {
       description "Delay before routes time out";
       units "seconds";
       type union {
         type string {
           pattern "<.*>|$.*";
         }
         type uint32 {
           range "30 .. 360";
         }
       }
     }
     leaf update-interval {
       description "Interval between regular route updates";
       units "seconds";
       type union {
         type string {
           pattern "<.*>|$.*";
         }
         type uint32 {
           range "10 .. 60";
         }
       }
     }
     list group {
       key name;
       ordered-by user;
       description "Instance configuration";
       leaf name {
         description "Group name";
         type string {
           junos:posix-pattern "^.{1,48}$";
           junos:pattern-message "Must be a string of at most 48 characters";
         }
       }
       uses apply-advanced;
       leaf route-timeout {
         description "Delay before routes time out";
         units "seconds";
         type union {
           type string {
             pattern "<.*>|$.*";
           }
           type uint32 {
             range "30 .. 360";
           }
         }
       }
       leaf update-interval {
         description "Interval between regular route updates";
         units "seconds";
         type union {
           type string {
             pattern "<.*>|$.*";
           }
           type uint32 {
             range "10 .. 60";
           }
         }
       }
       leaf preference {
         description "Preference of routes learned by this group";
         type union {
           type uint32;
           type string {
             pattern "<.*>|$.*";
           }
         }
       }
       leaf metric-out {
         description "Default metric of exported routes";
         type union {
           type string {
             pattern "<.*>|$.*";
           }
           type uint32 {
             range "1 .. 15";
           }
         }
       }
       leaf-list export {
         ordered-by user;
         description "Export policy";
         type jt:policy-algebra;
       }
       leaf-list import {
         ordered-by user;
         description "Import policy";
         type jt:policy-algebra;
       }
       list neighbor {
         key name;
         ordered-by user;
         description "Neighbor configuration";
         leaf name {
           description "Interface name";
           type union {
             type jt:interface-name;
             type string {
               pattern "<.*>|$.*";
             }
           }
         }
         uses apply-advanced;
         leaf route-timeout {
           description "Delay before routes time out";
           units "seconds";
           type union {
             type string {
               pattern "<.*>|$.*";
             }
             type uint32 {
               range "30 .. 360";
             }
           }
         }
         leaf update-interval {
           description "Interval between regular route updates";
           units "seconds";
           type union {
             type string {
               pattern "<.*>|$.*";
             }
             type uint32 {
               range "10 .. 60";
             }
           }
         }
         leaf metric-in {
           description "Metric value to add to incoming routes";
           type union {
             type string {
               pattern "<.*>|$.*";
             }
             type uint32 {
               range "1 .. 15";
             }
           }
         }
         container send {
           description "Configure RIPng send options";
           choice send-opts {
             case case_1 {
               leaf none {
                 description "Do not send RIPng updates";
                 type empty;
               }
             }
           }
         }
         container receive {
           description "Configure RIPng receive options";
           choice receive-opts {
             case case_1 {
               leaf none {
                 description "Do not receive RIPng packets";
                 type empty;
               }
             }
           }
         }
         leaf-list import {
           ordered-by user;
           description "Import policy";
           type jt:policy-algebra;
         }
       }
     }
     container graceful-restart {
       presence "enable graceful-restart";
       description "RIPng graceful restart options";
       uses apply-advanced;
       choice enable-disable {
         case case_1 {
           leaf disable {
             description "Disable graceful restart";
             type empty;
           }
         }
       }
       leaf restart-time {
         description "Time after which RIPng is declared out of restart";
         type union {
           type string {
             pattern "<.*>|$.*";
           }
           type uint32 {
             range "1 .. 600";
           }
         }
       }
     }
   }
   grouping juniper-protocols-router-discovery {
     uses apply-advanced;
     choice enable-disable {
       case case_1 {
         leaf disable {
           description "Disable router discovery";
           type empty;
         }
       }
     }
     container traceoptions {
       description "Trace options for router discovery";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
       }
     }
     list interface {
       key name;
       ordered-by user;
       description "Interfaces on which to configure router discovery";
       leaf name {
         description "Interface name";
         type union {
           type jt:interface-name;
           type string {
             pattern "<.*>|$.*";
           }
         }
       }
       uses apply-advanced;
       leaf max-advertisement-interval {
         description "Maximum time before sending advertisements";
         units "seconds";
         type union {
           type string {
             pattern "<.*>|$.*";
           }
           type uint32 {
             range "4 .. 1800";
           }
         }
       }
       leaf min-advertisement-interval {
         description "Minimum time before sending advertisements";
         units "seconds";
         type union {
           type string {
             pattern "<.*>|$.*";
           }
           type uint32 {
             range "3 .. 1800";
           }
         }
       }
       leaf lifetime {
         description "How long addresses in advertisements are valid";
         units "seconds";
         type union {
           type string {
             pattern "<.*>|$.*";
           }
           type uint32 {
             range "3 .. 9000";
           }
         }
       }
     }
     list address {
       key name;
       ordered-by user;
       description "IP addresses to include in advertisements";
       leaf name {
         description "IP addresses to include in router advertisements";
         type jt:ipv4addr;
       }
       uses apply-advanced;
       leaf advertise {
         description "Advertise the IP address in advertisements";
         type empty;
       }
       leaf ignore {
         description "Do not advertise the IP address in advertisements";
         type empty;
       }
       leaf broadcast {
         description "Include IP address only in broadcast advertisements";
         type empty;
       }
       leaf multicast {
         description "Include IP address only in multicast advertisements";
         type empty;
       }
       leaf ineligible {
         description "IP address can never become a default router";
         type empty;
       }
       leaf priority {
         description "Preference of the address to become a default router";
         type union {
           type int32;
           type string {
             pattern "<.*>|$.*";
           }
         }
       }
     }
   }
   grouping juniper-protocols-rsvp {
     description "RSVP options";
     uses apply-advanced;
     choice enable-disable {
       case case_1 {
         leaf disable {
           description "Disable RSVP";
           type empty;
         }
       }
     }
     container graceful-restart {
       description "Configure graceful restart attributes";
       uses apply-advanced;
       choice enable-disable {
         case case_1 {
           leaf disable {
             description "Disable RSVP graceful restart capability";
             type empty;
           }
         }
       }
       leaf helper-disable {
         description "Disable graceful restart helper capability";
         type empty;
       }
       leaf maximum-helper-restart-time {
         description "Maximum wait time from down event to neighbor dead";
         default "20";
         units "seconds";
         type union {
           type string {
             pattern "<.*>|$.*";
           }
           type uint32 {
             range "1 .. 1800";
           }
         }
       }
       leaf maximum-helper-recovery-time {
         description "Maximum time restarting neighbor states are kept";
         default "180";
         units "seconds";
         type union {
           type string {
             pattern "<.*>|$.*";
           }
           type uint32 {
             range "1 .. 3600";
           }
         }
       }
     }
     container tunnel-services {
       presence "enable tunnel-services";
       description "Use tunnel services for P2MP LSP ultimate-hop popping";
       uses apply-advanced;
       leaf-list devices {
         ordered-by user;
         description "Tunnel services devices to use for P2MP LSPs";
         type union {
           type jt:interface-device;
           type string {
             pattern "<.*>|$.*";
           }
         }
       }
     }
     leaf no-p2mp-sublsp {
       description "Disable P2MP sub-LSP object generation";
       type empty;
     }
     leaf no-node-id-subobject {
       description "Do not include the node-id sub-object in the RRO";
       type empty;
     }
     leaf no-interface-hello {
       description "Disble interface Hellos on all RSVP interfaces";
       type empty;
     }
     container pop-and-forward {
       description "RSVP pop-and-forward specific global parameters";
       uses apply-advanced;
       container application-label {
         description "Number of application labels under the RSVP transport";
         uses apply-advanced;
         leaf depth {
           description "Application label depth";
           default "1";
           type union {
             type string {
               pattern "<.*>|$.*";
             }
             type uint32 {
               range "0 .. 3";
             }
           }
         }
       }
     }
     leaf hello-acknowledgements {
       description "Acknowledge Hellos on RSVP interfaces not having sessions";
       type empty;
     }
     leaf no-hello-acknowledgements {
       description "Do not ack Hellos on RSVP interfaces not having sessions";
       junos:must "(!(\"protocols rsvp hello-acknowledgements\"))";
       junos:must-message "Config hello-acknowledgements should be removed";
       type empty;
     }
     container node-hello {
       presence "enable node-hello";
       description "Enable node-ID based Hellos on all RSVP interfaces";
       leaf hello-interval {
         description "Hello interval";
         default "9";
         units "seconds";
         type union {
           type string {
             pattern "<.*>|$.*";
           }
           type uint32 {
             range "0 .. 60";
           }
         }
       }
     }
     leaf no-node-hello {
       description "Disable node-ID based Hellos on the router";
       junos:must "(!(\"protocols rsvp node-hello\"))";
       junos:must-message "Config node-hello should be removed";
       type empty;
     }
     leaf allow-bidirectional {
       description "Enable bidirectional support in RSVP";
       status deprecated;
       type empty;
     }
     leaf local-reversion {
       description "Enable local reversion at this Point of Local Repair";
       junos:must "(!(\"protocols rsvp no-local-reversion\"))";
       junos:must-message "Config no-local-reversion should be removed";
       type empty;
     }
     leaf no-local-reversion {
       description "Disable local reversion at this Point of Local Repair";
       type empty;
     }
     leaf rfc6510-lsp-attributes {
       description "Use RFC6510 compliant LSP_ATTRIBUTES";
       type empty;
     }
     container fast-reroute {
       description "One-to-one fast-reroute protection mechanism";
       uses apply-advanced;
       leaf optimize-timer {
         description "Frequency of reoptimization for fast-reroute detour";
         units "seconds";
         type union {
           type string {
             pattern "<.*>|$.*";
           }
           type int32 {
             range "0 .. 65535";
           }
         }
       }
     }
     container load-balance {
       description "Per-packet load-balancing algorithm";
       uses apply-advanced;
       leaf bandwidth {
         description "Per-packet load balancing proportional to LSP bandwidth";
         type empty;
       }
     }
     container traceoptions {
       description "Trace options for RSVP";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "io-event" {
               description "Trace RSVP IO task related events";
             }
             enum "io-packets" {
               description "Trace all RSVP periodic refresh activity";
             }
             enum "packets" {
               description "Trace all RSVP trigger packets";
             }
             enum "path" {
               description "Trace RSVP trigger path messages";
             }
             enum "resv" {
               description "Trace RSVP trigger Resv messages";
             }
             enum "pathtear" {
               description "Trace RSVP PathTear messages";
             }
             enum "resvtear" {
               description "Trace RSVP ResvTear messages";
             }
             enum "state" {
               description "Trace state transitions";
             }
             enum "error" {
               description "Trace error conditions";
             }
             enum "route" {
               description "Trace routing information";
             }
             enum "lmp" {
               description "Trace RSVP-LMP related interactions";
             }
             enum "event" {
               description "Trace RSVP related events";
             }
             enum "nsr-synchronization" {
               description "Trace NSR synchronization events";
             }
             enum "lsp-prefix" {
               description "Prefix the trace messages with LSP information";
             }
             enum "enhanced-frr" {
               description "Enhanced FRR related information";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
       }
     }
     leaf refresh-time {
       description "Refresh time in seconds";
       default "1200";
       type union {
         type string {
           pattern "<.*>|$.*";
         }
         type uint32 {
           range "1 .. 65535";
         }
       }
     }
     leaf keep-multiplier {
       description "Keep multiplier";
       default "3";
       type union {
         type string {
           pattern "<.*>|$.*";
         }
         type uint32 {
           range "1 .. 255";
         }
       }
     }
     leaf graceful-deletion-timeout {
       description "Time to complete graceful deletion signaling";
       default "30";
       units "seconds";
       type union {
         type string {
           pattern "<.*>|$.*";
         }
         type uint32 {
           range "1 .. 300";
         }
       }
     }
     leaf setup-protection {
       description "Enable setup protection";
       type empty;
     }
     leaf no-p2mp-re-merge {
       description "Enable p2mp remerge";
       type empty;
     }
     leaf cross-credibility-cspf {
       description "Compute CSPF paths spanning protocols for bypass LSP, detour LSP and loose hop expansion";
       type empty;
     }
     container preemption {
       description "Set RSVP session preemption attributes";
       uses apply-advanced;
       choice preemption-type {
         case case_1 {
           leaf disabled {
             description "No RSVP session preemption";
             type empty;
           }
         }
         case case_2 {
           leaf normal {
             description "Run RSVP session preemption to accommodate new sessions";
             type empty;
           }
         }
         case case_3 {
           leaf aggressive {
             description "Run RSVP session preemption whenever necessary";
             type empty;
           }
         }
       }
       container soft-preemption {
         description "Options for establishing new path before tearing down a preempted LSP";
         uses apply-advanced;
         leaf cleanup-timer {
           description "Time a soft-preempted LSP will be maintained";
           units "seconds";
           type union {
             type string {
               pattern "<.*>|$.*";
             }
             type int32 {
               range "0 .. 10800";
             }
           }
         }
       }
     }
     leaf authentication-key {
       description "Authentication password";
       type jt:unreadable;
     }
     leaf no-authentication-check {
       description "Skip authentication check for received messages";
       type empty;
     }
     container associated-bidirectional-lsp {
       description "Set associated bidirectional LSP attributes";
       uses apply-advanced;
       leaf single-sided-provisioning {
         description "Enable unidirectional reverse LSP setup for single sided provisioned forward LSP";
         type empty;
       }
     }
     leaf no-enhanced-frr-bypass {
       description "Disable enhanced facility backup FRR";
       type empty;
     }
     leaf no-node-hello-on-bypass {
       description "Do not send NodeID hello over bypass LSP";
       type empty;
     }
     container expand-flood-reflector-hop {
       presence "enable expand-flood-reflector-hop";
       description "Control expansion of flood reflector ERO strict hops";
     }
     list interface {
       key name;
       ordered-by user;
       description "RSVP interface options";
       leaf name {
         description "Interface name";
         type union {
           type jt:interface-name;
           type string {
             pattern "<.*>|$.*";
           }
         }
       }
       uses apply-advanced;
       choice enable-disable {
         case case_1 {
           leaf disable {
             description "Disable RSVP on this interface";
             type empty;
           }
         }
       }
       leaf authentication-key {
         description "Authentication password";
         type jt:unreadable;
       }
       choice aggregate-choice {
         leaf aggregate {
           description "Permit refresh reduction extensions on the interface";
           status deprecated;
           type empty;
         }
         leaf no-aggregate {
           description "Don't permit refresh reduction extensions on the interface";
           status deprecated;
           type empty;
         }
       }
       choice reliable-choice {
         leaf reliable {
           description "Permit reliable message delivery on the interface";
           type empty;
         }
         leaf no-reliable {
           description "Don't permit reliable message delivery on the interface";
           type empty;
         }
       }
       leaf hello-interval {
         description "Hello interval";
         default "9";
         units "seconds";
         type union {
           type string {
             pattern "<.*>|$.*";
           }
           type uint32 {
             range "0 .. 60";
           }
         }
       }
       container subscription {
         description "Link bandwidth percentage for RSVP reservation";
         uses subscription-type;
       }
       leaf bandwidth {
         description "Available bandwidth for the interface units bps";
         type string;
       }
       container update-threshold {
         description "Change in reserved bandwidth to trigger IGP update";
         uses apply-advanced;
         container adaptive {
           junos:must "(!(\".. threshold-value\"))";
           junos:must-message "Cannot be configured with threshold-value";
           junos:must "(!(\".. threshold-percent\"))";
           junos:must-message "Cannot be configured with threshold-percent";
           description "Tune update-threshold dynamically";
           uses apply-advanced;
           list limit {
             key name;
             description "Available Bandwidth threshold limit";
             leaf name {
               description "Upper limit of Available bandwidth for this range";
               type string;
             }
             leaf threshold-percent {
               description "Percentage change in reserved bandwidth to trigger IGP update";
               default "10.0";
               units "percent";
               junos:must "(!(\".. .. limit $$ threshold-value\"))";
               junos:must-message "Cannot be configured with threshold-value";
               type decimal64 {
                 fraction-digits 9;
                 range "0.001 .. 20";
               }
             }
             leaf threshold-value {
               description "Change in reserved bandwidth to trigger IGP update (will be capped at 20% of link BW)";
               junos:must "(!(\".. .. limit $$ threshold-percent\"))";
               junos:must-message "Cannot be configured with threshold-percent";
               type string;
             }
           }
         }
         leaf threshold-percent {
           description "Percentage change in reserved bandwidth to trigger IGP update";
           default "10.0";
           units "percent";
           junos:must "(!(\".. adaptive\"))";
           junos:must-message "Cannot be configured with adaptive";
           type decimal64 {
             fraction-digits 9;
             range "0.001 .. 20";
           }
         }
         leaf threshold-value {
           description "Change in reserved bandwidth to trigger IGP update (will be capped at 20% of link BW)";
           junos:must "(!(\".. adaptive\"))";
           junos:must-message "Cannot be configured with adaptive";
           type string;
         }
       }
       container update-threshold-max-reservable {
         description "Change in non-rsvp bandwidth to trigger IGP update ";
         uses apply-advanced;
         leaf bandwidth {
           description "Change in non-rsvp bandwidth to trigger IGP update units bps";
           type string;
         }
         leaf percent {
           description "Percentage change in max-reservable bandwidth to trigger IGP update";
           units "percent";
           type union {
             type string {
               pattern "<.*>|$.*";
             }
             type uint32 {
               range "1 .. 100";
             }
           }
         }
       }
       container non-rsvp-bandwdith {
         description "Config knobs relating to non-rsvp bandwidth";
         uses apply-advanced;
         leaf local-bw-override-threshold {
           description "Overide threshold and update local bandwidth with non-rsvp bandwidth usage";
           type empty;
         }
       }
       container link-protection {
         presence "enable link-protection";
         description "Protect traffic with a label-stacked LSP";
         uses apply-advanced;
         choice enable-disable {
           case case_1 {
             leaf disable {
               description "Disable link protection on this interface";
               type empty;
             }
           }
         }
         container bandwidth {
           description "Bandwidth for each bypass";
           uses bandwidth-type;
         }
         leaf max-bypasses {
           description "Max number of bypasses permitted for protecting this interface";
           default "1";
           type union {
             type string {
               pattern "<.*>|$.*";
             }
             type uint32 {
               range "0 .. 99";
             }
           }
         }
         leaf subscription {
           description "Percent of bandwidth guaranteed when admitting protected LSPs into bypasses";
           default "100";
           type union {
             type string {
               pattern "<.*>|$.*";
             }
             type uint32 {
               range "1 .. 65535";
             }
           }
         }
         leaf no-node-protection {
           description "Disallow node protection on this interface";
           type empty;
         }
         leaf optimize-timer {
           description "Interval between bypass reoptimizations";
           default "0";
           units "seconds";
           type union {
             type string {
               pattern "<.*>|$.*";
             }
             type uint32 {
               range "0 .. 65535";
             }
           }
         }
         leaf class-of-service {
           description "Class of service for the bypass LSP";
           type union {
             type string {
               pattern "<.*>|$.*";
             }
             type int32 {
               range "0 .. 7";
             }
           }
         }
         leaf hop-limit {
           description "Maximum allowed router hops for bypass";
           type union {
             type string {
               pattern "<.*>|$.*";
             }
             type uint32 {
               range "2 .. 255";
             }
           }
         }
         leaf no-cspf {
           description "Disable automatic path computation";
           junos:must "(\".. path\")";
           junos:must-message "The path of the bypass must be configured when using no-cspf";
           type empty;
         }
         leaf exclude-srlg {
           description "Exclude SRLG links";
           type empty;
         }
         container priority {
           presence "enable priority";
           description "Preemption priorities for the bypass LSP";
         }
         leaf setup-priority {
           description "Set-up priority";
           type union {
             type string {
               pattern "<.*>|$.*";
             }
             type uint32 {
               range "0 .. 7";
             }
           }
         }
         leaf reservation-priority {
           description "Reservation priority";
           type union {
             type string {
               pattern "<.*>|$.*";
             }
             type uint32 {
               range "0 .. 7";
             }
           }
         }
         list path {
           key name;
           ordered-by user;
           description "Explicit route of bypass path";
           leaf name {
             description "Address of next system in path";
             type jt:ipv4addr;
           }
           choice loose_strict_none {
             case case_1 {
               leaf loose {
                 description "Next hop might not be adjacent";
                 type empty;
               }
             }
             case case_2 {
               leaf strict {
                 description "Next hop must be adjacent";
                 type empty;
               }
             }
           }
         }
         container admin-group {
           description "Administrative group policy";
           uses admin_group_include_exclude;
         }
         list bypass {
           key name;
           ordered-by user;
           description "Bypass with specific constraints";
           leaf name {
             description "Name of bypass";
             type string {
               length "1 .. 64";
             }
           }
           uses apply-advanced;
           leaf to {
             description "Address of egress router";
             type jt:ipv4addr;
           }
           container bandwidth {
             description "Bandwidth for each bypass";
             uses bandwidth-type;
           }
           container subscription {
             description "Bandwidth percent available on bypass for protected LSPs";
             presence "enable subscription";
             uses bypass-subscription-type;
           }
           leaf description {
             description "Text description of bypass";
             type string {
               length "1 .. 80";
             }
           }
           container priority {
             presence "enable priority";
             description "Preemption priorities for bypass";
           }
           leaf setup-priority {
             description "Set-up priority";
             type union {
               type string {
                 pattern "<.*>|$.*";
               }
               type uint32 {
                 range "0 .. 7";
               }
             }
           }
           leaf reservation-priority {
             description "Reservation priority";
             type union {
               type string {
                 pattern "<.*>|$.*";
               }
               type uint32 {
                 range "0 .. 7";
               }
             }
           }
           leaf class-of-service {
             description "Class of service for the bypass LSP";
             type union {
               type string {
                 pattern "<.*>|$.*";
               }
               type int32 {
                 range "0 .. 7";
               }
             }
           }
           leaf hop-limit {
             description "Maximum allowed router hops for bypass";
             type union {
               type string {
                 pattern "<.*>|$.*";
               }
               type uint32 {
                 range "2 .. 255";
               }
             }
           }
           leaf no-cspf {
             description "Disable automatic path computation";
             junos:must "(\".. path\")";
             junos:must-message "The path of the bypass must be configured when using no-cspf";
             type empty;
           }
           leaf exclude-srlg {
             description "Exclude SRLG links";
             type empty;
           }
           list path {
             key name;
             ordered-by user;
             description "Explicit route of bypass path";
             leaf name {
               description "Address of next system in path";
               type jt:ipv4addr;
             }
             choice loose_strict_none {
               case case_1 {
                 leaf loose {
                   description "Next hop might not be adjacent";
                   type empty;
                 }
               }
               case case_2 {
                 leaf strict {
                   description "Next hop must be adjacent";
                   type empty;
                 }
               }
             }
           }
           container admin-group {
             description "Administrative group policy";
             uses admin_group_include_exclude;
           }
         }
       }
     }
     list peer-interface {
       key name;
       ordered-by user;
       description "Configuration for peer interface";
       leaf name {
         description "Name of peer interface";
         type string;
       }
       uses apply-advanced;
       choice enable-disable {
         case case_1 {
           leaf disable {
             description "Disable RSVP on this control peer";
             type empty;
           }
         }
       }
       leaf authentication-key {
         description "Authentication password";
         type jt:unreadable;
       }
       choice aggregate-choice {
         leaf aggregate {
           description "Permit refresh reduction extensions on the interface";
           status deprecated;
           type empty;
         }
         leaf no-aggregate {
           description "Don't permit refresh reduction extensions on the interface";
           status deprecated;
           type empty;
         }
       }
       choice reliable-choice {
         leaf reliable {
           description "Permit reliable message delivery on the interface";
           type empty;
         }
         leaf no-reliable {
           description "Don't permit reliable message delivery on the interface";
           type empty;
         }
       }
       leaf hello-interval {
         description "Hello interval";
         default "9";
         units "seconds";
         type union {
           type string {
             pattern "<.*>|$.*";
           }
           type uint32 {
             range "0 .. 60";
           }
         }
       }
       container dynamic-bidirectional-transport {
         presence "enable dynamic-bidirectional-transport";
         description "Enable dynamic setup of bidirectional packet LSP for transporting non-packet GMPLS LSP";
         uses apply-advanced;
         leaf template {
           description "Template for the dynamic bidirectional packet LSP";
           junos:must "(!(\"protocols mpls label-switched-path $$ p2mp\"))";
           junos:must-message "Referenced template cannot be a p2mp template";
           junos:must "((\"protocols mpls label-switched-path $$\" && \"protocols mpls label-switched-path $$ template\"))";
           junos:must-message "Referenced LSP template does not exist";
           type string {
             junos:posix-pattern "^.{1,64}$";
             junos:pattern-message "Must be a string of 64 characters or less";
           }
         }
       }
     }
     list lsp-set {
       key name;
       ordered-by user;
       description "Configuration for lsp set";
       leaf name {
         description "Name of lsp set";
         type string;
       }
       uses apply-advanced;
       choice enable-disable {
         case case_1 {
           leaf disable {
             description "Disable this lsp set";
             type empty;
           }
         }
       }
       container match-criteria {
         description "Match criteria for this lsp set";
         uses lsp-set-match-type;
       }
       container traceoptions {
         description "Trace options for this lsp set";
         uses apply-advanced;
         container file {
           description "Trace file options";
           leaf filename {
             description "Name of file in which to write trace information";
             type string {
               length "1 .. 1024";
               junos:posix-pattern "![/ %]";
               junos:pattern-message "Must not contain '/', % or a space";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "io-event" {
                 description "Trace RSVP IO task related events";
               }
               enum "io-packets" {
                 description "Trace all RSVP periodic refresh activity";
               }
               enum "packets" {
                 description "Trace all RSVP packets";
               }
               enum "path" {
                 description "Trace RSVP path messages";
               }
               enum "resv" {
                 description "Trace RSVP Resv messages";
               }
               enum "pathtear" {
                 description "Trace RSVP PathTear messages";
               }
               enum "resvtear" {
                 description "Trace RSVP ResvTear messages";
               }
               enum "state" {
                 description "Trace state transitions";
               }
               enum "error" {
                 description "Trace error conditions";
               }
               enum "route" {
                 description "Trace routing information";
               }
               enum "lmp" {
                 description "Trace RSVP-LMP related interactions";
               }
               enum "event" {
                 description "Trace RSVP related events";
               }
               enum "nsr-synchronization" {
                 description "Trace NSR synchronization events";
               }
               enum "lsp-prefix" {
                 description "Prefix the trace messages with LSP information";
               }
               enum "enhanced-frr" {
                 description "Enhanced FRR related information";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
         }
       }
     }
   }
   grouping bypass-subscription-type {
     uses apply-advanced;
     leaf subscription {
       description "Subscription percentage for bandwidth protection";
       default "100";
       type string;
     }
   }
   grouping juniper-protocols-stp {
     uses apply-advanced;
     choice enable-disable {
       case case_1 {
         leaf disable {
           description "Disable STP";
           type empty;
         }
       }
     }
     leaf bpdu-destination-mac-address {
       description "Destination MAC address in the spanning tree BPDUs";
       type enumeration {
         enum "provider-bridge-group" {
           description "802.1ad provider bridge group address";
         }
       }
     }
     leaf bridge-priority {
       description "Priority of the bridge (in increments of 4k - 0,4k,8k,..60k)";
       type string {
         junos:posix-pattern "^(0|4k|4096|8k|8192|12k|12288|16k|16384|20k|20480|24k|24576|28k|28672|32k|32768|36k|36864|40k|40960|44k|45056|48k|49512|52k|53248|56k|57344|60k|61440)$";
         junos:pattern-message "Must be a multiple of 4096";
       }
     }
     leaf backup-bridge-priority {
       description "Priority of the bridge (in increments of 4k - 4k,8k,..60k)";
       type string {
         junos:posix-pattern "^(4k|4096|8k|8192|12k|12288|16k|16384|20k|20480|24k|24576|28k|28672|32k|32768|36k|36864|40k|40960|44k|45056|48k|49512|52k|53248|56k|57344|60k|61440)$";
         junos:pattern-message "Must be a multiple of 4096";
       }
     }
     leaf max-age {
       description "Maximum age of received protocol bpdu";
       units "seconds";
       type union {
         type string {
           pattern "<.*>|$.*";
         }
         type uint16 {
           range "6 .. 40";
         }
       }
     }
     leaf hello-time {
       description "Time interval between configuration BPDUs";
       units "seconds";
       type union {
         type string {
           pattern "<.*>|$.*";
         }
         type uint16 {
           range "1 .. 10";
         }
       }
     }
     leaf forward-delay {
       description "Time spent in listening or learning state";
       units "seconds";
       type union {
         type string {
           pattern "<.*>|$.*";
         }
         type uint16 {
           range "4 .. 30";
         }
       }
     }
     leaf system-identifier {
       description "Sytem identifier to represent this node";
       type jt:mac-unicast;
     }
     container traceoptions {
       description "Tracing options for debugging protocol operation";
       uses stp-trace-options;
     }
     leaf vpls-flush-on-topology-change {
       description "Enable VPLS MAC flush on root protected CE interface receving topology change";
       type empty;
     }
     leaf priority-hold-time {
       description "Hold time before switching to primary priority when core domain becomes up";
       units "seconds";
       type union {
         type string {
           pattern "<.*>|$.*";
         }
         type uint16 {
           range "1 .. 255";
         }
       }
     }
     list system-id {
       key name;
       ordered-by user;
       description "System ID to IP mapping";
       uses system-id-ip-map;
     }
     list interface {
       key name;
       description "Interface options";
       uses stp-interface;
     }
     leaf extended-system-id {
       description "Extended system identifier";
       type union {
         type string {
           pattern "<.*>|$.*";
         }
         type uint16 {
           range "0 .. 4095";
         }
       }
     }
     leaf force-version {
       description "Force protocol version";
       type enumeration {
         enum "stp" {
           description "Spanning tree protocol";
         }
       }
     }
     leaf bpdu-block-on-edge {
       description "Block BPDU on all interfaces configured as edge (BPDU Protect)";
       type empty;
     }
   }
   grouping juniper-protocols-vni-options {
     uses apply-advanced;
     list vni {
       key name;
       description "Per-vni options";
       leaf name {
         type union {
           type string {
             pattern "<.*>|$.*";
           }
           type int32 {
             range "1 .. 16777214";
           }
         }
       }
       uses apply-advanced;
       container vrf-target {
         description "VRF target community configuration";
         uses apply-advanced;
         leaf export {
           description "Target community to use when marking routes on export";
           status deprecated;
           type string {
             junos:posix-pattern "^[a-z]+:[0-9.]+L?:[0-9]+$";
             junos:pattern-message "Use format 'target:x:y' where 'x' is an AS number followed by an optional 'L' (To indicate 4 byte AS), or an IP address and 'y' is a number. e.g. target:123456L:100";
           }
         }
         leaf community {
           description "Target community";
           type string {
             junos:posix-pattern "^[a-z]+:[0-9.]+L?:[0-9]+$";
             junos:pattern-message "Use format 'target:x:y' where 'x' is an AS number followed by an optional 'L' (To indicate 4 byte AS), or an IP address and 'y' is a number. e.g. target:123456L:100";
           }
         }
       }
     }
   }
   grouping juniper-protocols-vstp {
     uses apply-advanced;
     choice enable-disable {
       case case_1 {
         leaf disable {
           description "Disable VSTP";
           type empty;
         }
       }
     }
     leaf force-version {
       description "Force protocol version";
       type enumeration {
         enum "stp" {
           description "Spanning tree protocol";
         }
       }
     }
     leaf bpdu-block-on-edge {
       description "Block BPDU on all interfaces configured as edge (BPDU Protect)";
       type empty;
     }
     leaf vpls-flush-on-topology-change {
       description "Enable VPLS MAC flush on root protected CE interface receving topology change";
       type empty;
     }
     leaf priority-hold-time {
       description "Hold time before switching to primary priority when core domain becomes up";
       units "seconds";
       type union {
         type string {
           pattern "<.*>|$.*";
         }
         type uint16 {
           range "1 .. 255";
         }
       }
     }
     list system-id {
       key name;
       ordered-by user;
       description "System ID to IP mapping";
       uses system-id-ip-map;
     }
     list interface {
       key name;
       description "Interface options";
       uses stp-interface;
     }
     list vlan {
       key name;
       description "VLAN spanning tree options";
       leaf name {
         description "VLAN id or all";
         type string;
       }
       uses apply-advanced;
       leaf bridge-priority {
         description "Priority of the bridge (in increments of 4k - 0,4k,8k,..60k)";
         type string {
           junos:posix-pattern "^(0|4k|4096|8k|8192|12k|12288|16k|16384|20k|20480|24k|24576|28k|28672|32k|32768|36k|36864|40k|40960|44k|45056|48k|49512|52k|53248|56k|57344|60k|61440)$";
           junos:pattern-message "Must be a multiple of 4096";
         }
       }
       leaf backup-bridge-priority {
         description "Priority of the bridge (in increments of 4k - 4k,8k,..60k)";
         type string {
           junos:posix-pattern "^(4k|4096|8k|8192|12k|12288|16k|16384|20k|20480|24k|24576|28k|28672|32k|32768|36k|36864|40k|40960|44k|45056|48k|49512|52k|53248|56k|57344|60k|61440)$";
           junos:pattern-message "Must be a multiple of 4096";
         }
       }
       leaf max-age {
         description "Maximum age of received protocol bpdu";
         units "seconds";
         type union {
           type string {
             pattern "<.*>|$.*";
           }
           type uint16 {
             range "6 .. 40";
           }
         }
       }
       leaf hello-time {
         description "Time interval between configuration BPDUs";
         units "seconds";
         type union {
           type string {
             pattern "<.*>|$.*";
           }
           type uint16 {
             range "1 .. 10";
           }
         }
       }
       leaf forward-delay {
         description "Time spent in listening or learning state";
         units "seconds";
         type union {
           type string {
             pattern "<.*>|$.*";
           }
           type uint16 {
             range "4 .. 30";
           }
         }
       }
       leaf system-identifier {
         description "Sytem identifier to represent this node";
         type jt:mac-unicast;
       }
       container traceoptions {
         description "Tracing options for debugging protocol operation";
         uses stp-trace-options;
       }
       list interface {
         key name;
         description "Interface options";
         uses stp-interface;
       }
     }
     container vlan-group {
       presence "enable vlan-group";
       description "Spanning tree options for group of VLANs";
       uses apply-advanced;
       list group {
         key name;
         ordered-by user;
         description "Name if VLAN group";
         leaf name {
           description "VLAN group name";
           type string {
             length "1 .. 63";
             junos:posix-pattern "^[[:alpha:]][[:alnum:]_-]+$";
             junos:pattern-message "Must be a string beginning with a letter and consisting of letters, numbers, dashes, and underscores";
           }
         }
         uses apply-advanced;
         leaf-list vlan {
           ordered-by user;
           description "VLAN ID or VLAN ID range [1..4094]";
           type string;
         }
         leaf bridge-priority {
           description "Priority of the bridge (in increments of 4k - 0,4k,8k,..60k)";
           type string {
             junos:posix-pattern "^(0|4k|4096|8k|8192|12k|12288|16k|16384|20k|20480|24k|24576|28k|28672|32k|32768|36k|36864|40k|40960|44k|45056|48k|49512|52k|53248|56k|57344|60k|61440)$";
             junos:pattern-message "Must be a multiple of 4096";
           }
         }
         leaf backup-bridge-priority {
           description "Priority of the bridge (in increments of 4k - 4k,8k,..60k)";
           type string {
             junos:posix-pattern "^(4k|4096|8k|8192|12k|12288|16k|16384|20k|20480|24k|24576|28k|28672|32k|32768|36k|36864|40k|40960|44k|45056|48k|49512|52k|53248|56k|57344|60k|61440)$";
             junos:pattern-message "Must be a multiple of 4096";
           }
         }
         leaf max-age {
           description "Maximum age of received protocol bpdu";
           units "seconds";
           type union {
             type string {
               pattern "<.*>|$.*";
             }
             type uint16 {
               range "6 .. 40";
             }
           }
         }
         leaf hello-time {
           description "Time interval between configuration BPDUs";
           units "seconds";
           type union {
             type string {
               pattern "<.*>|$.*";
             }
             type uint16 {
               range "1 .. 10";
             }
           }
         }
         leaf forward-delay {
           description "Time spent in listening or learning state";
           units "seconds";
           type union {
             type string {
               pattern "<.*>|$.*";
             }
             type uint16 {
               range "4 .. 30";
             }
           }
         }
         leaf system-identifier {
           description "Sytem identifier to represent this node";
           type jt:mac-unicast;
         }
         container traceoptions {
           description "Tracing options for debugging protocol operation";
           uses stp-trace-options;
         }
         list interface {
           key name;
           description "Interface options";
           uses stp-interface;
         }
       }
     }
   }
   grouping ldp-sync-obj {
     uses apply-advanced;
     choice enable-disable {
       case case_1 {
         leaf disable {
           description "Disable LDP synchronization";
           type empty;
         }
       }
     }
     leaf hold-time {
       description "Time during which maximum metric is advertised";
       type union {
         type string {
           pattern "<.*>|$.*";
         }
         type uint32 {
           range "1 .. 65535";
         }
       }
     }
   }
   grouping ldp_filter_obj {
     description "Filter to apply to tracing";
     leaf match-on {
       description "Argument on which to match";
       type enumeration {
         enum "fec" {
           description "Filter based on FEC associated to the traced object.";
         }
         enum "address" {
           description "Filter based on packet source and destination addresses.";
         }
       }
     }
     leaf-list policy {
       ordered-by user;
       description "Filter policy";
       type jt:policy-algebra;
     }
   }
   grouping lmp_control_channel_type {
     leaf name {
       description "Control channel interface";
       type union {
         type jt:interface-name;
         type string {
           pattern "<.*>|$.*";
         }
       }
     }
     uses apply-advanced;
     leaf remote-address {
       description "Control channel remote address";
       type jt:ipaddr;
     }
   }
   grouping lsp-set-match-type {
     uses apply-advanced;
     leaf lsp-name {
       description "LSP name that matches this string";
       junos:must "((!(\".. lsp-regex\") && (!(\".. p2mp-name\") && !(\".. p2mp-regex\"))))";
       junos:must-message "Can't configure lsp-name when lsp-regex or p2mp-name or p2mp-regex is configured";
       type string;
     }
     leaf lsp-regex {
       description "All LSPs that match this regular expression pattern";
       junos:must "((!(\".. lsp-name\") && (!(\".. p2mp-name\") && !(\".. p2mp-regex\"))))";
       junos:must-message "Can't configure lsp-regex when lsp-name or p2mp-name or p2mp-regex is configured";
       type string;
     }
     leaf p2mp-name {
       description "P2MP names that match this string";
       junos:must "((!(\".. lsp-name\") && (!(\".. lsp-regex\") && !(\".. p2mp-regex\"))))";
       junos:must-message "Can't configure p2mp-name when lsp-name or lsp-regex or p2mp-regex is configured";
       type string;
     }
     leaf p2mp-regex {
       description "P2MP names that match this regular expression pattern";
       junos:must "((!(\".. lsp-name\") && (!(\".. lsp-regex\") && !(\".. p2mp-name\"))))";
       junos:must-message "Can't configure p2mp-regex when lsp-name or lsp-regex or p2mp-name is configured";
       type string;
     }
     choice router-type {
       case case_1 {
         leaf egress {
           description "All LSPs for which this router is egress";
           type empty;
         }
       }
       case case_2 {
         leaf ingress {
           description "All LSPs for which this router is ingress";
           type empty;
         }
       }
       case case_3 {
         leaf transit {
           description "All LSPs for which this router is transit";
           type empty;
         }
       }
     }
   }
   grouping macro-data-type {
     leaf name {
       description "Keyword part of the keyword-value pair";
       type string;
     }
     leaf value {
       description "Value part of the keyword-value pair";
       type string;
     }
   }
   grouping mrp-trace-options {
     description "Trace options for MMRP Protocol";
     uses apply-advanced;
     container file {
       description "Trace file options";
       leaf filename {
         description "Name of file in which to write trace information";
         type string {
           length "1 .. 1024";
           junos:posix-pattern "![/ %]";
           junos:pattern-message "Must not contain '/', % or a space";
         }
       }
       leaf replace {
         description "Replace trace file rather than appending to it";
         status deprecated;
         type empty;
       }
       leaf size {
         description "Maximum trace file size";
         type string;
       }
       leaf files {
         description "Maximum number of trace files";
         default "10";
         type union {
           type string {
             pattern "<.*>|$.*";
           }
           type uint32 {
             range "2 .. 1000";
           }
         }
       }
       leaf no-stamp {
         description "Do not timestamp trace file";
         status deprecated;
         type empty;
       }
       choice world-readable-choice {
         leaf world-readable {
           description "Allow any user to read the log file";
           type empty;
         }
         leaf no-world-readable {
           description "Don't allow any user to read the log file";
           type empty;
         }
       }
     }
     list flag {
       key name;
       ordered-by user;
       description "Tracing parameters";
       junos:must "(\".. file\")";
       junos:must-message "Trace file name required to enable tracing";
       leaf name {
         type enumeration {
           enum "events" {
             description "Trace events to the protocol state machine";
           }
           enum "pdu" {
             description "Trace RAPS PDU reception and transmission";
           }
           enum "timers" {
             description "Trace protocol timers";
           }
           enum "state-machine" {
             description "Trace information of the state machine";
           }
           enum "socket" {
             description "Trace soccket activity";
           }
           enum "error" {
             description "Trace all failure conditions";
           }
           enum "all" {
             description "Trace all";
           }
         }
       }
       leaf disable {
         description "Disable this trace flag";
         type empty;
       }
     }
   }
   grouping mstp-interface {
     leaf name {
       type string;
     }
     uses apply-advanced;
     leaf priority {
       description "Interface priority (in increments of 16 - 0,16,..240)";
       type union {
         type string {
           pattern "<.*>|$.*";
         }
         type uint16 {
           range "0 .. 255";
         }
       }
     }
     leaf cost {
       description "Cost of the interface";
       type union {
         type string {
           pattern "<.*>|$.*";
         }
         type uint32 {
           range "1 .. 200000000";
         }
       }
     }
     leaf mode {
       description "Interface mode (P2P or shared)";
       type enumeration {
         enum "point-to-point" {
           description "Interface mode is point-to-point";
         }
         enum "shared" {
           description "Interface mode is shared";
         }
       }
     }
     leaf edge {
       description "Port is an edge port";
       type empty;
     }
     leaf access-trunk {
       description "Send/Receive untagged RSTP BPDUs on this interface";
       type empty;
     }
     container bpdu-timeout-action {
       presence "enable bpdu-timeout-action";
       description "Define action on BPDU expiry (Loop Protect)";
       uses apply-advanced;
       leaf block {
         description "Block the interface";
         type empty;
       }
       leaf alarm {
         description "Generate an alarm";
         type empty;
       }
     }
     leaf no-root-port {
       description "Do not allow the interface to become root (Root Protect)";
       type empty;
     }
     leaf disable {
       description "Disable Spanning Tree on port";
       type empty;
     }
   }
   grouping peer-group {
     leaf name {
       description "IP address for this peer";
       type jt:ipv4addr;
     }
     uses apply-advanced;
     leaf local-ip-addr {
       description "Local IP address to use for this peer alone.";
       type jt:ipv4addr;
     }
     leaf session-establishment-hold-time {
       description "Time within which connection must succeed with this peer";
       units "seconds";
       type union {
         type string {
           pattern "<.*>|$.*";
         }
         type uint32 {
           range "45 .. 600";
         }
       }
     }
     leaf-list redundancy-group-id-list {
       ordered-by user;
       description "List of redundacy groups this peer is part of";
       type union {
         type uint32;
         type string {
           pattern "<.*>|$.*";
         }
       }
       max-elements 1;
     }
     container backup-liveness-detection {
       presence "enable backup-liveness-detection";
       junos:must "(!(\".. .. .. .. .. logical-systems\"))";
       junos:must-message "backup-liveness-detection not supported with Logical Systems";
       description "Backup liveness detection";
       uses apply-advanced;
       leaf backup-peer-ip {
         description "Backup livelness detection peer's IP address";
         type jt:ipv4addr;
       }
     }
     container liveness-detection {
       presence "enable liveness-detection";
       description "Bidirectional Forwarding Detection options for the peer";
       uses apply-advanced;
       leaf version {
         description "BFD protocol version number";
         default "automatic";
         type enumeration {
           enum "0" {
             description "BFD version 0 (deprecated)";
           }
           enum "1" {
             description "BFD version 1";
           }
           enum "automatic" {
             description "Choose BFD version automatically";
           }
         }
       }
       leaf minimum-interval {
         description "Minimum transmit and receive interval";
         units "milliseconds";
         type union {
           type string {
             pattern "<.*>|$.*";
           }
           type uint32 {
             range "1 .. 255000";
           }
         }
       }
       leaf minimum-transmit-interval {
         description "Minimum transmit interval";
         status deprecated;
         units "milliseconds";
         type union {
           type string {
             pattern "<.*>|$.*";
           }
           type uint32 {
             range "1 .. 255000";
           }
         }
       }
       leaf minimum-receive-interval {
         description "Minimum receive interval";
         units "milliseconds";
         type union {
           type string {
             pattern "<.*>|$.*";
           }
           type uint32 {
             range "1 .. 255000";
           }
         }
       }
       leaf multiplier {
         description "Detection time multiplier";
         default "3";
         type union {
           type string {
             pattern "<.*>|$.*";
           }
           type uint32 {
             range "1 .. 255";
           }
         }
       }
       choice adaptation-choice {
         case case_1 {
           leaf no-adaptation {
             description "Disable adaptation";
             type empty;
           }
         }
       }
       container transmit-interval {
         description "Transmit-interval options";
         uses apply-advanced;
         leaf minimum-interval {
           description "Minimum transmit interval";
           units "milliseconds";
           type union {
             type string {
               pattern "<.*>|$.*";
             }
             type uint32 {
               range "1 .. 255000";
             }
           }
         }
         leaf threshold {
           description "High transmit interval triggering a trap";
           units "milliseconds";
           type union {
             type uint32;
             type string {
               pattern "<.*>|$.*";
             }
           }
         }
       }
       container detection-time {
         description "Detection-time options";
         uses apply-advanced;
         leaf threshold {
           description "High detection-time triggering a trap";
           units "milliseconds";
           type union {
             type uint32;
             type string {
               pattern "<.*>|$.*";
             }
           }
         }
       }
     }
     leaf authentication-key {
       description "MD5 authentication key";
       type string {
         length "1 .. 126";
       }
     }
   }
   grouping periodic_oam {
     uses apply-advanced;
     container mpls-tp-mode {
       presence "enable mpls-tp-mode";
       description "MPLS-TP Mode, Do not use IP addressing for OAM";
       uses apply-advanced;
       container lsping-channel-type {
         description "Supported Control-channel types for MPLS-TP mode....";
         uses apply-advanced;
         choice action-choice {
           case case_1 {
             leaf ipv4 {
               description "Use channel-type IPv4(0x0021), With IP-UDP encapsulation";
               type empty;
             }
           }
           case case_2 {
             leaf on-demand-cv {
               description "Use channel-type On-Demand-CV(0x0025), Without IP-UDP encapsulation";
               type empty;
             }
           }
         }
       }
     }
     container bfd-port {
       description "Egress knob to select MHOP-BFD port for MPLS BFD";
       uses apply-advanced;
       leaf-list import {
         ordered-by user;
         description "Import policy";
         type jt:policy-algebra;
       }
     }
     container bfd-liveness-detection {
       description "Bidirectional Forwarding Detection options";
       uses apply-advanced;
       leaf version {
         description "BFD protocol version number";
         default "automatic";
         type enumeration {
           enum "0" {
             description "BFD version 0 (deprecated)";
           }
           enum "1" {
             description "BFD version 1";
           }
           enum "automatic" {
             description "Choose BFD version automatically";
           }
         }
       }
       leaf minimum-interval {
         description "Minimum transmit and receive interval";
         units "milliseconds";
         type union {
           type string {
             pattern "<.*>|$.*";
           }
           type uint32 {
             range "1 .. 255000";
           }
         }
       }
       leaf minimum-transmit-interval {
         description "Minimum transmit interval";
         status deprecated;
         units "milliseconds";
         type union {
           type string {
             pattern "<.*>|$.*";
           }
           type uint32 {
             range "1 .. 255000";
           }
         }
       }
       leaf minimum-receive-interval {
         description "Minimum receive interval";
         units "milliseconds";
         type union {
           type string {
             pattern "<.*>|$.*";
           }
           type uint32 {
             range "1 .. 255000";
           }
         }
       }
       leaf multiplier {
         description "Detection time multiplier";
         default "3";
         type union {
           type string {
             pattern "<.*>|$.*";
           }
           type uint32 {
             range "1 .. 255";
           }
         }
       }
       choice adaptation-choice {
         case case_1 {
           leaf no-adaptation {
             description "Disable adaptation";
             type empty;
           }
         }
       }
       container transmit-interval {
         description "Transmit-interval options";
         uses apply-advanced;
         leaf minimum-interval {
           description "Minimum transmit interval";
           units "milliseconds";
           type union {
             type string {
               pattern "<.*>|$.*";
             }
             type uint32 {
               range "1 .. 255000";
             }
           }
         }
         leaf threshold {
           description "High transmit interval triggering a trap";
           units "milliseconds";
           type union {
             type uint32;
             type string {
               pattern "<.*>|$.*";
             }
           }
         }
       }
       container detection-time {
         description "Detection-time options";
         uses apply-advanced;
         leaf threshold {
           description "High detection-time triggering a trap";
           units "milliseconds";
           type union {
             type uint32;
             type string {
               pattern "<.*>|$.*";
             }
           }
         }
       }
       container failure-action {
         description "Action to take when BFD session goes down";
         choice action-choice {
           case case_1 {
             leaf teardown {
               description "Teardown label switched path and resignal";
               type empty;
             }
           }
           case case_2 {
             container make-before-break {
               presence "enable make-before-break";
               description "Resignal the label switched path before teardown";
               uses apply-advanced;
               leaf teardown-timeout {
                 description "Time to wait before teardown";
                 units "seconds";
                 type union {
                   type string {
                     pattern "<.*>|$.*";
                   }
                   type uint32 {
                     range "0 .. 30";
                   }
                 }
               }
             }
           }
         }
       }
       leaf no-router-alert-option {
         description "Do not set Router-Alert options in IP header for MPLS-BFD";
         type empty;
       }
       leaf use-ip-ttl-1 {
         description "Set TTL value to 1 in IP header for MPLS-BFD";
         type empty;
       }
     }
     container performance-monitoring {
       description "Performance monitoring options";
       uses apply-advanced;
       container traceoptions {
         description "Trace options for PM";
         uses apply-advanced;
         container file {
           description "Trace file options";
           leaf filename {
             description "Name of file in which to write trace information";
             type string {
               length "1 .. 1024";
               junos:posix-pattern "![/ %]";
               junos:pattern-message "Must not contain '/', % or a space";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "init" {
                 description "Trace init commnad";
               }
               enum "error" {
                 description "Trace error conditions";
               }
               enum "event" {
                 description "Trace state machine events";
               }
               enum "general" {
                 description "Trace general events";
               }
               enum "packet" {
                 description "Trace various packets ";
               }
               enum "timer" {
                 description "Trace timer processing";
               }
               enum "all" {
                 description "Trace everything";
               }
             }
           }
         }
       }
       container querier {
         junos:must "(\".. .. .. ultimate-hop-popping\")";
         junos:must-message "Performance monitoring can be configured only on ultimate-hop-popping LSPs";
         junos:must "(\".. .. .. associate-lsp\")";
         junos:must-message "Performance monitoring can be configured only for associated LSPs";
         description "Querier options";
         uses apply-advanced;
         container loss {
           description "Loss measurement options";
           uses apply-advanced;
           list traffic-class {
             key name;
             description "Traffic class specific options";
             leaf name {
               description "Traffic class value";
               type enumeration {
                 enum "tc-0" {
                   description "Traffic class 0";
                   junos:must "(\"protocols mpls statistics traffic-class-statistics\")";
                   junos:must-message "Traffic class can be configured only for traffic-class-statistics";
                 }
                 enum "tc-1" {
                   description "Traffic class 1";
                   junos:must "(\"protocols mpls statistics traffic-class-statistics\")";
                   junos:must-message "Traffic class can be configured only for traffic-class-statistics";
                 }
                 enum "tc-2" {
                   description "Traffic class 2";
                   junos:must "(\"protocols mpls statistics traffic-class-statistics\")";
                   junos:must-message "Traffic class can be configured only for traffic-class-statistics";
                 }
                 enum "tc-3" {
                   description "Traffic class 3";
                   junos:must "(\"protocols mpls statistics traffic-class-statistics\")";
                   junos:must-message "Traffic class can be configured only for traffic-class-statistics";
                 }
                 enum "tc-4" {
                   description "Traffic class 4";
                   junos:must "(\"protocols mpls statistics traffic-class-statistics\")";
                   junos:must-message "Traffic class can be configured only for traffic-class-statistics";
                 }
                 enum "tc-5" {
                   description "Traffic class 5";
                   junos:must "(\"protocols mpls statistics traffic-class-statistics\")";
                   junos:must-message "Traffic class can be configured only for traffic-class-statistics";
                 }
                 enum "tc-6" {
                   description "Traffic class 6";
                   junos:must "(\"protocols mpls statistics traffic-class-statistics\")";
                   junos:must-message "Traffic class can be configured only for traffic-class-statistics";
                 }
                 enum "tc-7" {
                   description "Traffic class 7";
                   junos:must "(\"protocols mpls statistics traffic-class-statistics\")";
                   junos:must-message "Traffic class can be configured only for traffic-class-statistics";
                 }
                 enum "all" {
                   description "All Traffic class";
                   junos:must "(\"protocols mpls statistics traffic-class-statistics\")";
                   junos:must-message "Traffic class can be configured only for traffic-class-statistics";
                 }
                 enum "none" {
                   description "No Traffic class";
                 }
               }
             }
             uses apply-advanced;
             leaf query-interval {
               description "Minimum transmit interval";
               units "milliseconds";
               type union {
                 type string {
                   pattern "<.*>|$.*";
                 }
                 type uint32 {
                   range "1000 .. 4294967295";
                 }
               }
             }
             leaf measurement-quantity {
               description "Loss measurement quantity";
               default "packets";
               type enumeration {
                 enum "bytes" {
                   description "Byte loss measurement";
                 }
                 enum "packets" {
                   description "Packet loss measurement";
                 }
               }
             }
             leaf average-sample-size {
               description "Number of samples used in average calculation";
               type union {
                 type string {
                   pattern "<.*>|$.*";
                 }
                 type uint16 {
                   range "1 .. 30";
                 }
               }
             }
             leaf loss-threshold {
               description "Loss threshold value";
               type union {
                 type string {
                   pattern "<.*>|$.*";
                 }
                 type uint32 {
                   range "1 .. 4294967295";
                 }
               }
             }
             leaf loss-threshold-window {
               description "Number of samples for loss threshold calculation";
               type union {
                 type string {
                   pattern "<.*>|$.*";
                 }
                 type uint32 {
                   range "1 .. 30";
                 }
               }
             }
           }
         }
         container delay {
           description "Delay measurement options";
           uses apply-advanced;
           list traffic-class {
             key name;
             description "Traffic class specific options";
             leaf name {
               description "Traffic class value";
               type enumeration {
                 enum "tc-0" {
                   description "Traffic class 0";
                   junos:must "(\"protocols mpls statistics traffic-class-statistics\")";
                   junos:must-message "Traffic class can be configured only for traffic-class-statistics";
                 }
                 enum "tc-1" {
                   description "Traffic class 1";
                   junos:must "(\"protocols mpls statistics traffic-class-statistics\")";
                   junos:must-message "Traffic class can be configured only for traffic-class-statistics";
                 }
                 enum "tc-2" {
                   description "Traffic class 2";
                   junos:must "(\"protocols mpls statistics traffic-class-statistics\")";
                   junos:must-message "Traffic class can be configured only for traffic-class-statistics";
                 }
                 enum "tc-3" {
                   description "Traffic class 3";
                   junos:must "(\"protocols mpls statistics traffic-class-statistics\")";
                   junos:must-message "Traffic class can be configured only for traffic-class-statistics";
                 }
                 enum "tc-4" {
                   description "Traffic class 4";
                   junos:must "(\"protocols mpls statistics traffic-class-statistics\")";
                   junos:must-message "Traffic class can be configured only for traffic-class-statistics";
                 }
                 enum "tc-5" {
                   description "Traffic class 5";
                   junos:must "(\"protocols mpls statistics traffic-class-statistics\")";
                   junos:must-message "Traffic class can be configured only for traffic-class-statistics";
                 }
                 enum "tc-6" {
                   description "Traffic class 6";
                   junos:must "(\"protocols mpls statistics traffic-class-statistics\")";
                   junos:must-message "Traffic class can be configured only for traffic-class-statistics";
                 }
                 enum "tc-7" {
                   description "Traffic class 7";
                   junos:must "(\"protocols mpls statistics traffic-class-statistics\")";
                   junos:must-message "Traffic class can be configured only for traffic-class-statistics";
                 }
                 enum "all" {
                   description "All Traffic classes";
                   junos:must "(\"protocols mpls statistics traffic-class-statistics\")";
                   junos:must-message "Traffic class can be configured only for traffic-class-statistics";
                 }
               }
             }
             uses apply-advanced;
             leaf query-interval {
               description "Minimum transmit interval";
               units "milliseconds";
               type union {
                 type string {
                   pattern "<.*>|$.*";
                 }
                 type uint32 {
                   range "1000 .. 4294967295";
                 }
               }
             }
             leaf padding-size {
               description "Size of padding";
               type union {
                 type string {
                   pattern "<.*>|$.*";
                 }
                 type uint16 {
                   range "1 .. 1500";
                 }
               }
             }
             leaf average-sample-size {
               description "Number of samples used in average calculation";
               type union {
                 type string {
                   pattern "<.*>|$.*";
                 }
                 type uint16 {
                   range "1 .. 30";
                 }
               }
             }
             leaf twcd-delay-threshold {
               description "Two way channel delay threshold value";
               units "microseconds";
               type union {
                 type string {
                   pattern "<.*>|$.*";
                 }
                 type uint32 {
                   range "1 .. 4294967295";
                 }
               }
             }
             leaf rtt-delay-threshold {
               description "Round trip delay threshold value";
               units "microseconds";
               type union {
                 type string {
                   pattern "<.*>|$.*";
                 }
                 type uint32 {
                   range "1 .. 4294967295";
                 }
               }
             }
           }
         }
         container loss-delay {
           description "Combined loss-delay measurement options";
           uses apply-advanced;
           list traffic-class {
             key name;
             description "Traffic class specific options";
             leaf name {
               description "Traffic class value";
               type enumeration {
                 enum "tc-0" {
                   description "Traffic class 0";
                   junos:must "(\"protocols mpls statistics traffic-class-statistics\")";
                   junos:must-message "Traffic class can be configured only for traffic-class-statistics";
                 }
                 enum "tc-1" {
                   description "Traffic class 1";
                   junos:must "(\"protocols mpls statistics traffic-class-statistics\")";
                   junos:must-message "Traffic class can be configured only for traffic-class-statistics";
                 }
                 enum "tc-2" {
                   description "Traffic class 2";
                   junos:must "(\"protocols mpls statistics traffic-class-statistics\")";
                   junos:must-message "Traffic class can be configured only for traffic-class-statistics";
                 }
                 enum "tc-3" {
                   description "Traffic class 3";
                   junos:must "(\"protocols mpls statistics traffic-class-statistics\")";
                   junos:must-message "Traffic class can be configured only for traffic-class-statistics";
                 }
                 enum "tc-4" {
                   description "Traffic class 4";
                   junos:must "(\"protocols mpls statistics traffic-class-statistics\")";
                   junos:must-message "Traffic class can be configured only for traffic-class-statistics";
                 }
                 enum "tc-5" {
                   description "Traffic class 5";
                   junos:must "(\"protocols mpls statistics traffic-class-statistics\")";
                   junos:must-message "Traffic class can be configured only for traffic-class-statistics";
                 }
                 enum "tc-6" {
                   description "Traffic class 6";
                   junos:must "(\"protocols mpls statistics traffic-class-statistics\")";
                   junos:must-message "Traffic class can be configured only for traffic-class-statistics";
                 }
                 enum "tc-7" {
                   description "Traffic class 7";
                   junos:must "(\"protocols mpls statistics traffic-class-statistics\")";
                   junos:must-message "Traffic class can be configured only for traffic-class-statistics";
                 }
                 enum "all" {
                   description "All Traffic classes";
                   junos:must "(\"protocols mpls statistics traffic-class-statistics\")";
                   junos:must-message "Traffic class can be configured only for traffic-class-statistics";
                 }
                 enum "none" {
                   description "No Traffic class";
                 }
               }
             }
             uses apply-advanced;
             leaf query-interval {
               description "Minimum transmit interval";
               units "milliseconds";
               type union {
                 type string {
                   pattern "<.*>|$.*";
                 }
                 type uint32 {
                   range "1000 .. 4294967295";
                 }
               }
             }
             leaf measurement-quantity {
               description "Loss measurement quantity";
               default "packets";
               type enumeration {
                 enum "bytes" {
                   description "Byte loss measurement";
                 }
                 enum "packets" {
                   description "Packet loss measurement";
                 }
               }
             }
             leaf padding-size {
               description "Size of padding";
               type union {
                 type string {
                   pattern "<.*>|$.*";
                 }
                 type uint16 {
                   range "1 .. 1500";
                 }
               }
             }
             leaf average-sample-size {
               description "Number of samples used in average calculation";
               type union {
                 type string {
                   pattern "<.*>|$.*";
                 }
                 type uint16 {
                   range "1 .. 30";
                 }
               }
             }
             leaf loss-threshold {
               description "Loss threshold value";
               type union {
                 type string {
                   pattern "<.*>|$.*";
                 }
                 type uint32 {
                   range "1 .. 4294967295";
                 }
               }
             }
             leaf loss-threshold-window {
               description "Number of samples for loss threshold calculation";
               type union {
                 type string {
                   pattern "<.*>|$.*";
                 }
                 type uint32 {
                   range "1 .. 30";
                 }
               }
             }
             leaf twcd-delay-threshold {
               description "Two way channel delay threshold value";
               units "microseconds";
               type union {
                 type string {
                   pattern "<.*>|$.*";
                 }
                 type uint32 {
                   range "1 .. 4294967295";
                 }
               }
             }
             leaf rtt-delay-threshold {
               description "Round trip delay threshold value";
               units "microseconds";
               type union {
                 type string {
                   pattern "<.*>|$.*";
                 }
                 type uint32 {
                   range "1 .. 4294967295";
                 }
               }
             }
           }
         }
       }
       container responder {
         junos:must "(\".. .. .. ultimate-hop-popping\")";
         junos:must-message "Performance monitoring can be configured only on ultimate-hop-popping LSPs";
         junos:must "(\".. .. .. associate-lsp\")";
         junos:must-message "Performance monitoring can be configured only for associated LSPs";
         description "Responder options";
         uses apply-advanced;
         container loss {
           description "Loss measurement options";
           uses apply-advanced;
           leaf min-query-interval {
             description "Minimum query interval";
             units "milliseconds";
             type union {
               type string {
                 pattern "<.*>|$.*";
               }
               type uint32 {
                 range "1000 .. 4294967295";
               }
             }
           }
         }
         container delay {
           description "Delay measurement options";
           uses apply-advanced;
           leaf min-query-interval {
             description "Minimum query interval";
             units "milliseconds";
             type union {
               type string {
                 pattern "<.*>|$.*";
               }
               type uint32 {
                 range "1000 .. 4294967295";
               }
             }
           }
         }
       }
     }
     leaf lsp-ping-interval {
       description "Time interval between LSP ping messages";
       units "seconds";
       type union {
         type string {
           pattern "<.*>|$.*";
         }
         type uint16 {
           range "30 .. 3600";
         }
       }
     }
     leaf lsp-ping-multiplier {
       description "Number of ping reply missed before declaring BFD down";
       type union {
         type string {
           pattern "<.*>|$.*";
         }
         type uint8 {
           range "1 .. 5";
         }
       }
     }
     container traceoptions {
       description "Trace options for MPLSOAM process";
       uses apply-advanced;
       leaf no-remote-trace {
         description "Disable remote tracing";
         junos:must "(\"system tracing\")";
         junos:must-message "'no-remote-trace' is valid only when [system tracing] is configured";
         type empty;
       }
       container file {
         description "Trace file information";
         leaf filename {
           description "Name of file in which to write trace information";
           type string {
             length "1 .. 1024";
             junos:posix-pattern "![/ %]";
             junos:pattern-message "Must not contain '/', % or a space";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing parameters";
         leaf name {
           type enumeration {
             enum "configuration" {
               description "Trace configuration events";
             }
             enum "pipe" {
               description "Trace pipe activity";
             }
             enum "rpc-packet-details" {
               description "Trace RPC packet details";
             }
             enum "database" {
               description "Trace database activity";
             }
             enum "network" {
               description "Trace network activity";
             }
             enum "traceroute" {
               description "Trace traceroute activity";
             }
             enum "all" {
               description "Trace everything";
             }
           }
         }
       }
     }
   }
   grouping pim_bootstrap_options_type {
     uses apply-advanced;
     leaf priority {
       description "Eligibility to be the bootstrap router";
       type union {
         type string {
           pattern "<.*>|$.*";
         }
         type uint32 {
           range "0 .. 255";
         }
       }
     }
     leaf-list import {
       ordered-by user;
       description "Bootstrap import policy";
       type jt:policy-algebra;
     }
     leaf-list export {
       ordered-by user;
       description "Bootstrap export policy";
       type jt:policy-algebra;
     }
   }
   grouping pim_filter_obj {
     description "Filter to apply to tracing";
     leaf match-on {
       description "Argument on which to match";
       type enumeration {
         enum "prefix" {
           description "Filter based on prefix";
         }
       }
     }
     leaf-list policy {
       ordered-by user;
       description "Filter policy";
       type jt:policy-algebra;
     }
   }
   grouping pim_rp_group_range_type {
     leaf name {
       type jt:ipprefix;
     }
     uses apply-advanced;
     leaf nexthop-hold-time {
       description "Nexthop hold time in milliseconds";
       units "milliseconds";
       type union {
         type string {
           pattern "<.*>|$.*";
         }
         type uint32 {
           range "1 .. 1000";
         }
       }
     }
   }
   grouping ppp-traceoptions-type {
     description "Trace options for PPP process";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Area of PPP process to enable debugging output";
       leaf name {
         type enumeration {
           enum "access" {
             description "Trace access code";
           }
           enum "address-pool" {
             description "Trace address pool code";
           }
           enum "auth" {
             description "Trace authentication code";
           }
           enum "chap" {
             description "Trace CHAP code";
           }
           enum "pap" {
             description "Trace PAP code";
           }
           enum "config" {
             description "Trace configuration code";
           }
           enum "ifdb" {
             description "Trace interface database code";
           }
           enum "lcp" {
             description "Trace LCP state machine code";
           }
           enum "memory" {
             description "Trace memory management code";
           }
           enum "message" {
             description "Trace message processing code";
           }
           enum "mlppp" {
             description "Trace MLPPP code";
           }
           enum "ncp" {
             description "Trace NCP state machine code";
           }
           enum "ppp" {
             description "Trace PPP protocol processing code";
           }
           enum "radius" {
             description "Trace RADIUS processing code";
           }
           enum "redundancy" {
             description "Trace redundancy code";
           }
           enum "rtsock" {
             description "Trace routing socket code";
           }
           enum "session" {
             description "Trace session management code";
           }
           enum "signal" {
             description "Trace signal handling code";
           }
           enum "timer" {
             description "Trace timer code";
           }
           enum "ui" {
             description "Trace user interface code";
           }
           enum "ci" {
             description "Trace ci code";
           }
           enum "all" {
             description "Trace all areas of code";
           }
         }
       }
     }
   }
   grouping pppoe-traceoptions-type {
     description "Trace options for PPPoE process";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Area of PPPoE process to enable debugging output";
       leaf name {
         type enumeration {
           enum "config" {
             description "Trace configuration code";
           }
           enum "events" {
             description "Trace event code";
           }
           enum "gres" {
             description "Trace GRES code";
           }
           enum "init" {
             description "Trace initialization code";
           }
           enum "interface-db" {
             description "Trace interface database code";
           }
           enum "memory" {
             description "Trace memory management code";
           }
           enum "protocol" {
             description "Trace PPPoE protocol processing code";
           }
           enum "rtsock" {
             description "Trace routing socket code";
           }
           enum "session-db" {
             description "Trace Session DB code";
           }
           enum "signal" {
             description "Trace signal handling code";
           }
           enum "state" {
             description "Trace state handling code";
           }
           enum "stats" {
             description "Trace Stats Handling code";
           }
           enum "timer" {
             description "Trace timer code";
           }
           enum "ui" {
             description "Trace user interface code";
           }
           enum "all" {
             description "Trace all areas of code";
           }
         }
       }
     }
     container filter {
       presence "enable filter";
       description "Trace filtering";
       uses apply-advanced;
       leaf aci {
         description "Regular expression to match ACI";
         type string {
           length "1 .. 64";
           junos:posix-pattern "^[*]*.[^*]*[*]*$";
           junos:pattern-message "Must be a non-reserved string";
         }
       }
       leaf ari {
         description "Regular expression to match ARI";
         type string {
           length "1 .. 64";
           junos:posix-pattern "^[*]*.[^*]*[*]*$";
           junos:pattern-message "Must be a non-reserved string";
         }
       }
       leaf service-name {
         description "Service name";
         type string {
           length "1 .. 64";
           junos:posix-pattern "^([[:alnum:]][[:alnum:]_-]*)|([*][[:alnum:]_-]{1,})[*]?$";
           junos:pattern-message "Must be a non-reserved string";
         }
       }
       leaf underlying-interface {
         description "Underlying interface name";
         junos:must "((\"interfaces $$-IFL encapsulation ppp-over-ether\" || (\"interfaces $$-IFL encapsulation ppp-over-ether-over-atm-llc\" || \"interfaces $$-IFL family pppoe\")))";
         junos:must-message "Underlying interface must be configured";
         type string;
       }
     }
   }
   grouping rib-inet3 {
     uses apply-advanced;
     container inet.3 {
       presence "enable inet.3";
       description "Use inet.3 to exchange labeled unicast routes";
       uses apply-advanced;
     }
   }
   grouping rib_group_inet_type {
     description "Routing table group";
     leaf ribgroup-name {
       description "Name of the routing table group";
       type string;
     }
   }
   grouping rib_group_type {
     uses apply-advanced;
     leaf inet-old-style {
       description "Name of the IPv4 routing table group";
       status deprecated;
       type string;
     }
     leaf inet {
       description "Name of the IPv4 routing table group";
       type string;
     }
     leaf inet3 {
       description "Name of the IPv4 inet.3 routing table group";
       type string;
     }
     leaf inet6 {
       description "Name of the IPv6 routing table group";
       type string;
     }
     leaf inet63 {
       description "Name of the IPv6 inet6.3 routing table group";
       type string;
     }
   }
   grouping rip_filter_obj {
     description "Filter to apply to tracing";
     leaf match-on {
       description "Argument on which to match";
       type enumeration {
         enum "prefix" {
           description "Filter based on prefix";
         }
       }
     }
     leaf-list policy {
       ordered-by user;
       description "Filter policy";
       type jt:policy-algebra;
     }
   }
   grouping stp-interface {
     leaf name {
       type string;
     }
     uses apply-advanced;
     leaf priority {
       description "Interface priority (in increments of 16 - 0,16,..240)";
       type union {
         type string {
           pattern "<.*>|$.*";
         }
         type uint16 {
           range "0 .. 255";
         }
       }
     }
     leaf cost {
       description "Cost of the interface";
       type union {
         type string {
           pattern "<.*>|$.*";
         }
         type uint32 {
           range "1 .. 200000000";
         }
       }
     }
     leaf mode {
       description "Interface mode (P2P or shared)";
       type enumeration {
         enum "point-to-point" {
           description "Interface mode is point-to-point";
         }
         enum "shared" {
           description "Interface mode is shared";
         }
       }
     }
     leaf edge {
       description "Port is an edge port";
       type empty;
     }
     leaf access-trunk {
       description "Send/Receive untagged RSTP BPDUs on this interface";
       type empty;
     }
     container bpdu-timeout-action {
       presence "enable bpdu-timeout-action";
       description "Define action on BPDU expiry (Loop Protect)";
       uses apply-advanced;
       leaf block {
         description "Block the interface";
         type empty;
       }
       leaf alarm {
         description "Generate an alarm";
         type empty;
       }
     }
     leaf no-root-port {
       description "Do not allow the interface to become root (Root Protect)";
       type empty;
     }
     leaf disable {
       description "Disable Spanning Tree on port";
       type empty;
     }
   }
   grouping stp-trace-options {
     description "Trace options for Spanning Tree Protocol";
     uses apply-advanced;
     container file {
       description "Trace file options";
       leaf filename {
         description "Name of file in which to write trace information";
         type string {
           length "1 .. 1024";
           junos:posix-pattern "![/ %]";
           junos:pattern-message "Must not contain '/', % or a space";
         }
       }
       leaf replace {
         description "Replace trace file rather than appending to it";
         status deprecated;
         type empty;
       }
       leaf size {
         description "Maximum trace file size";
         type string;
       }
       leaf files {
         description "Maximum number of trace files";
         default "10";
         type union {
           type string {
             pattern "<.*>|$.*";
           }
           type uint32 {
             range "2 .. 1000";
           }
         }
       }
       leaf no-stamp {
         description "Do not timestamp trace file";
         status deprecated;
         type empty;
       }
       choice world-readable-choice {
         leaf world-readable {
           description "Allow any user to read the log file";
           type empty;
         }
         leaf no-world-readable {
           description "Don't allow any user to read the log file";
           type empty;
         }
       }
     }
     list flag {
       key name;
       ordered-by user;
       description "Tracing parameters";
       junos:must "(\".. file\")";
       junos:must-message "Trace file name required to enable tracing";
       leaf name {
         type enumeration {
           enum "events" {
             description "Trace events to the protocol state machine";
           }
           enum "bpdu" {
             description "Trace BPDU reception and transmission";
           }
           enum "timers" {
             description "Trace protocol timers";
           }
           enum "port-information-state-machine" {
             description "Trace port information state machine";
           }
           enum "port-receive-state-machine" {
             description "Trace port receive state machine";
           }
           enum "port-role-select-state-machine" {
             description "Trace port role selection state machine";
           }
           enum "port-role-transit-state-machine" {
             description "Trace port role transit state machine";
           }
           enum "port-state-transit-state-machine" {
             description "Trace port state transit state machine";
           }
           enum "port-migration-state-machine" {
             description "Trace port migration state machine";
           }
           enum "port-transmit-state-machine" {
             description "Trace port transmit state machine";
           }
           enum "topology-change-state-machine" {
             description "Trace topology change state machine";
           }
           enum "bridge-detection-state-machine" {
             description "Trace Bridge detection state machine";
           }
           enum "state-machine-variables" {
             description "Trace when state machine variables change";
           }
           enum "ppmd" {
             description "Trace state and events for ppmd process";
           }
           enum "all-failures" {
             description "Trace all failure conditions";
           }
           enum "all" {
             description "Trace all";
           }
         }
       }
       leaf disable {
         description "Disable this trace flag";
         type empty;
       }
     }
   }
   grouping subscription-type {
     uses apply-advanced;
     leaf link-subscription {
       description "Link bandwidth percentage for RSVP reservation";
       default "100";
       type string;
     }
     leaf ct0 {
       description "Subscription percentage for traffic class 0";
       default "100";
       junos:must "(\"protocols mpls diffserv-te bandwidth-model\")";
       junos:must-message "Must have a diffserv-te bandwidth model configured when configuring subscription per traffic class";
       type string;
     }
     leaf ct1 {
       description "Subscription percentage for traffic class 1";
       default "100";
       junos:must "(\"protocols mpls diffserv-te bandwidth-model\")";
       junos:must-message "Must have a diffserv-te bandwidth model configured when configuring subscription per traffic class";
       type string;
     }
     leaf ct2 {
       description "Subscription percentage for traffic class 2";
       default "100";
       junos:must "(\"protocols mpls diffserv-te bandwidth-model\")";
       junos:must-message "Must have a diffserv-te bandwidth model configured when configuring subscription per traffic class";
       type string;
     }
     leaf ct3 {
       description "Subscription percentage for traffic class 3";
       default "100";
       junos:must "(\"protocols mpls diffserv-te bandwidth-model\")";
       junos:must-message "Must have a diffserv-te bandwidth model configured when configuring subscription per traffic class";
       type string;
     }
     list priority {
       key priority-value;
       ordered-by user;
       description "Subscription percentage for a specific priority";
       leaf priority-value {
         description "Priority for which subscription percent is being configured";
         junos:must "(!(\"protocols mpls diffserv-te\"))";
         junos:must-message "Cannot configure per-priority subscription alongside diffserv-te";
         type union {
           type string {
             pattern "<.*>|$.*";
           }
           type uint32 {
             range "0 .. 7";
           }
         }
       }
       uses apply-advanced;
       leaf percent {
         description "Subscription percent for the specific priority";
         junos:must "(!(\"protocols mpls diffserv-te\"))";
         junos:must-message "Cannot configure per-priority subscription alongside diffserv-te";
         type string;
       }
     }
   }
   grouping system-id-ip-map {
     leaf name {
       type jt:mac-unicast;
     }
     uses apply-advanced;
     leaf ip-address {
       description "Peer ID (IP Address)";
       type jt:ipv4prefix;
     }
   }
   grouping te-class-object {
     leaf traffic-class {
       description "Traffic class";
       type enumeration {
         enum "ct0" {
           description "Traffic class 0";
         }
         enum "ct1" {
           description "Traffic class 1";
         }
         enum "ct2" {
           description "Traffic class 2";
         }
         enum "ct3" {
           description "Traffic class 3";
         }
       }
     }
     leaf priority {
       description "Preemption priority for this class";
       type union {
         type string {
           pattern "<.*>|$.*";
         }
         type uint32 {
           range "0 .. 7";
         }
       }
     }
   }
   grouping ufd-group-type {
     description "Uplink failure detection group type";
     leaf name {
       description "Uplink failure detection group name";
       type string {
         length "2 .. 64";
       }
     }
     uses apply-advanced;
     list link-to-monitor {
       key name;
       ordered-by user;
       description "Uplinks to be monitored";
       leaf name {
         description "Interface to be monitored";
         junos:must "(!(\"interfaces $$ ether-options 802.3ad\"))";
         junos:must-message "link-to-monitor interface cannot be a member of Lag interface";
         junos:must "(\"interfaces $$\")";
         junos:must-message "link-to-monitor interface does not exist";
         type union {
           type jt:interface-unit;
           type string {
             pattern "<.*>|$.*";
           }
         }
       }
       uses apply-advanced;
     }
     list link-to-disable {
       key name;
       ordered-by user;
       description "Downlinks to disable";
       leaf name {
         description "Interface to disable";
         junos:must "(!(\"interfaces $$ ether-options 802.3ad\"))";
         junos:must-message "link-to-disable interface cannot be a member of Lag interface";
         junos:must "(\"interfaces $$\")";
         junos:must-message "link-to-disable interface does not exist";
         type union {
           type jt:interface-unit;
           type string {
             pattern "<.*>|$.*";
           }
         }
       }
       uses apply-advanced;
     }
     leaf debounce-interval {
       description "Delay before bring up of the link-to-disable port";
       units "seconds";
       type union {
         type string {
           pattern "<.*>|$.*";
         }
         type uint32 {
           range "5 .. 300";
         }
       }
     }
   }
 }
