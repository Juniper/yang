/*
 * Copyright (c) 2024 Juniper Networks, Inc.
 * All rights reserved.
 */
 module junos-rpc-services {
   namespace "http://yang.juniper.net/junos/rpc/services";

   prefix services;

   import junos-common-types {
     prefix jt;
     revision-date 2023-01-01;
   }

   organization "Juniper Networks, Inc.";

   contact "yang-support@juniper.net";

   description "Junos RPC YANG module for services command(s)";

   revision 2023-01-01 {
     description "Junos: 23.4R2.14-EVO";
   }

   rpc get-fwa-statistics {
     description "Show fixed wireless access statistics";
   }
   rpc get-pcef-subscribers {
     description "Show subscriber information";
     input {
       leaf address {
         description "IPv4 or IPv6 address of subscriber";
         type string;
       }
       leaf interface {
         description "Interface name, or with wildcards (e.g. fe-0/0/*, fe-0/*/*)";
         type union {
           type jt:interface-wildcard;
           type string {
             pattern "<.*>|$.*";
           }
         }
       }
       leaf physical-interface {
         description "Physical Interface name";
         type union {
           type jt:interface-wildcard;
           type string {
             pattern "<.*>|$.*";
           }
         }
       }
       leaf user-name {
         description "Username of subscriber";
         type string;
       }
       leaf logical-system {
         description "Logical system where subscriber resides";
         type string;
       }
       leaf routing-instance {
         description "Routing instance where subscriber resides";
         type string;
       }
       leaf profile-name {
         description "Profile with which subscriber has been activated";
         type string {
           length "1 .. 80";
         }
       }
       leaf agent-circuit-identifier {
         description "Display summary for specified agent circuit identifier";
         type string;
       }
       leaf aci-interface-set-name {
         description "Display summary for specified ACI interface set";
         type string;
       }
       leaf stacked-vlan-id {
         description "Stacked VLAN identifier of subscriber";
         type union {
           type string {
             pattern "<.*>|$.*";
           }
           type uint16 {
             range "0 .. 4094";
           }
         }
       }
       leaf vlan-id {
         description "VLAN identifier of subscriber";
         type union {
           type string {
             pattern "<.*>|$.*";
           }
           type uint16 {
             range "0 .. 4094";
           }
         }
       }
       leaf vpi {
         description "ATM VPI of subscriber";
         type union {
           type string {
             pattern "<.*>|$.*";
           }
           type uint16 {
             range "0 .. 255";
           }
         }
       }
       leaf vci {
         description "ATM VCI of subscriber";
         type union {
           type string {
             pattern "<.*>|$.*";
           }
           type uint16 {
             range "0 .. 65535";
           }
         }
       }
       leaf id {
         description "Identifier of subscriber";
         type string;
       }
       leaf mac-address {
         description "MAC address of subscriber";
         type jt:mac-addr;
       }
       leaf client-type {
         description "Client type of subscriber";
         type enumeration {
           enum "dhcp" {
             description "DHCP clients only";
           }
           enum "vlan" {
             description "VLAN clients only";
           }
           enum "ppp" {
             description "PPP clients only";
           }
           enum "pppoe" {
             description "PPPoE clients only";
           }
           enum "l2tp" {
             description "L2TP clients only";
           }
           enum "static" {
             description "Static clients only";
           }
           enum "vpls-pw" {
             description "VPLS-PW clients only";
           }
           enum "mlppp" {
             description "MLPPP clients only";
           }
           enum "xauth" {
             description "XAuth clients only";
           }
           enum "fwauth" {
             description "FwAuth clients only";
           }
           enum "dot1x" {
             description "Dot1x clients only";
           }
           enum "essm" {
             description "ESSM clients only";
           }
           enum "fwa" {
             description "FWA clients only";
           }
           enum "agf" {
             description "AGF clients only";
           }
         }
       }
       leaf subscriber-state {
         description "State of subscriber";
         type enumeration {
           enum "init" {
             description "INIT state only";
           }
           enum "configured" {
             description "CONFIGURED state only";
           }
           enum "active" {
             description "ACTIVE state only";
           }
           enum "terminating" {
             description "TERMINATING state only";
           }
         }
       }
       leaf display {
         default "terse";
         type enumeration {
           enum "terse" {
             description "Display terse output";
           }
           enum "detail" {
             description "Display detailed output";
           }
           enum "extensive" {
             description "Display extensive output";
           }
           enum "count" {
             description "Display number of subscribers";
           }
         }
       }
     }
   }
   rpc get-pcef-subscribers-summary {
     description "Display pcef subscriber summary";
     input {
       leaf logical-system {
         description "Display summary for specified logical system";
         type string;
       }
       leaf routing-instance {
         description "Display summary for specified routing instance";
         type string;
       }
       leaf physical-interface {
         description "Physical Interface name";
         type union {
           type jt:interface-wildcard;
           type string {
             pattern "<.*>|$.*";
           }
         }
       }
       leaf port {
         description "Display full subscriber port summary";
         type empty;
       }
       leaf pic {
         description "Display full subscriber pic summary";
         type empty;
       }
       leaf slot {
         description "Display full subscriber slot summary";
         type empty;
       }
       leaf all {
         description "Display full subscriber summary";
         type empty;
       }
     }
   }
   rpc get-pcef-pic {
     description "Show physical interface card information";
     input {
       leaf fpc-slot {
         description "FPC slot number";
         type union {
           type string {
             pattern "<.*>|$.*";
           }
           type uint32;
         }
       }
       leaf pic-slot {
         description "PIC slot number";
         type union {
           type string {
             pattern "<.*>|$.*";
           }
           type uint32;
         }
       }
       leaf display {
         default "terse";
         type enumeration {
           enum "terse" {
             description "Display terse output";
           }
         }
       }
     }
   }
   rpc get-ift-global-information {
     description "Show inband telemetry information";
     output {
       container ift-global-information {
         uses ift-global-information-block;
       }
     }
   }
   rpc get-ift-profile-information {
     description "Show inband telemetry profile details";
     input {
       leaf profile-name {
         description "Name of the profile";
         type string;
       }
     }
     output {
       container ift-profile-information {
         uses ift-profile-information-block;
       }
     }
   }
   rpc get-ift-stats-information {
     description "Show inband telemetry stats information";
     output {
       container ift-stats-information {
         uses ift-stats-information-block;
       }
     }
   }
   rpc get-services-flow-collector-information {
     description "Show flow collector service information";
     input {
       leaf display {
         default "terse";
         type enumeration {
           enum "extensive" {
             description "Display extensive output";
           }
           enum "detail" {
             description "Display detailed output";
           }
           enum "terse" {
             description "Display terse output (default)";
           }
         }
       }
       leaf interface {
         description "Interface name";
         type string;
         mandatory true;
       }
     }
   }
   rpc get-services-flow-collector-file-information {
     description "Show file status information";
     input {
       leaf interface {
         description "Interface name";
         type string;
         mandatory true;
       }
       leaf display {
         default "terse";
         type enumeration {
           enum "extensive" {
             description "Display extensive output";
           }
           enum "detail" {
             description "Display detailed output";
           }
           enum "terse" {
             description "Display terse output (default)";
           }
         }
       }
     }
   }
   rpc get-services-flow-collector-input-information {
     description "Show input status information";
     input {
       leaf interface {
         description "Interface name";
         type string;
         mandatory true;
       }
       leaf display {
         default "terse";
         type enumeration {
           enum "extensive" {
             description "Display extensive output";
           }
           enum "detail" {
             description "Display detailed output";
           }
           enum "terse" {
             description "Display terse output (default)";
           }
         }
       }
     }
   }
   rpc get-cpcd-pic-statistics {
     description "Show captive portal and content delivery statistics by PIC";
     input {
       leaf pic-name {
         type union {
           type jt:interface-name;
           type string {
             pattern "<.*>|$.*";
           }
         }
         mandatory true;
       }
     }
   }
   rpc get-cpcd-profile {
     description "Show profile database";
     input {
       leaf profile-name {
         type string;
       }
     }
   }
   rpc get-cpcd-rule {
     description "Show rule database";
     input {
       leaf rule-name {
         type string;
       }
       leaf term {
         description "Term name";
         type string;
       }
     }
   }
   rpc get-cpcd-rule-set {
     description "Show rule set database";
     input {
       leaf ruleset-name {
         type string;
       }
     }
   }
   rpc get-cpcd-pic-information {
     description "Show pic database";
     input {
       leaf pic-name {
         type union {
           type jt:interface-name;
           type string {
             pattern "<.*>|$.*";
           }
         }
       }
     }
   }
   rpc get-cpcd-service-set {
     description "Show service set database";
     input {
       leaf sset-name {
         type string;
         mandatory true;
       }
       leaf level {
         default "brief";
         type enumeration {
           enum "brief" {
             description "Display brief output (default)";
           }
           enum "detail" {
             description "Display detailed output";
           }
           enum "summary" {
             description "Display summary output";
           }
         }
       }
     }
   }
   rpc get-services-dfc-statistics-information {
     description "Show capture group statistics";
     input {
       leaf capture-group {
         description "Capture group name";
         type string;
         mandatory true;
       }
       leaf per-protocol-details {
         description "Shows ipv4 ipv6 also";
         type empty;
       }
     }
   }
   rpc get-services-dynamic-flow-capture-control-source-information {
     description "Show DFC control source information";
     input {
       leaf display {
         default "terse";
         type enumeration {
           enum "detail" {
             description "Display detailed output";
           }
           enum "terse" {
             description "Display terse output (default)";
           }
         }
       }
       leaf capture-group {
         description "Capture group name";
         type string;
         mandatory true;
       }
       leaf source-identifier {
         description "Control source identifier";
         type string;
         mandatory true;
       }
       leaf per-protocol-details {
         description "Shows ipv4 ipv6 also";
         type empty;
       }
     }
   }
   rpc get-services-dynamic-flow-capture-content-destination-information {
     description "Show DFC content destination information";
     input {
       leaf display {
         default "terse";
         type enumeration {
           enum "terse" {
             description "Display terse output (default)";
           }
         }
       }
       leaf capture-group {
         description "Capture group name";
         type string;
         mandatory true;
       }
       leaf destination-identifier {
         description "Content destination identifier";
         type string;
         mandatory true;
       }
     }
   }
   rpc get-pblq-summary-alltests {
     description "Show PBLQ summary";
     output {
       container pblq-summary-alltests {
         uses pblq-summary-alltests-block;
       }
     }
   }
   rpc get-pblq-capabilities {
     description "Show PBLQ capabilities";
     output {
       container pblq-capabilities-odl {
         uses pblq-capabilities-odl-block;
       }
     }
   }
   rpc get-test-information {
     description "Show PBLQ test info for a test Id";
     input {
       leaf verbosity_level {
         default "brief";
         type enumeration {
           enum "brief" {
             description "Display brief output (default)";
           }
           enum "detail" {
             description "Display detailed output";
           }
           enum "extensive" {
             description "Display extensive output";
           }
         }
       }
       leaf test-id {
         description "Test id";
         type union {
           type uint32;
           type string {
             pattern "<.*>|$.*";
           }
         }
       }
     }
     output {
       container pblq-test-information-odl {
         uses pblq-test-information-odl-block;
       }
     }
   }
   rpc get-rpm-history-results {
     description "Show history results";
     input {
       leaf style {
         default "brief";
         type enumeration {
           enum "brief" {
             description "Display brief output (default)";
           }
           enum "detail" {
             description "Display detailed output";
           }
         }
       }
       leaf owner {
         description "Name of owner";
         type string {
           length "1 .. 32";
         }
         mandatory true;
       }
       leaf test {
         description "Name of test";
         type string {
           length "1 .. 32";
         }
       }
       leaf since {
         description "Show history since YYYY-MM-DD.HH:MM:SS";
         type jt:time;
       }
       leaf source-address {
         description "Filter history based on test ipv4 or ipv6 source-address";
         type jt:ipaddr;
       }
       leaf target {
         description "Filter history based on configured test target";
         type string;
       }
     }
     output {
       container history-results {
         uses history-results-block;
       }
     }
   }
   rpc get-rpm-probe-results {
     description "Show probe results";
     input {
       leaf owner {
         description "Name of owner";
         type string {
           length "1 .. 32";
         }
       }
       leaf test {
         description "Name of test";
         type string {
           length "1 .. 32";
         }
       }
       leaf source-address {
         description "Filter results based on test ipv4 or ipv6 source-address";
         type jt:ipaddr;
       }
       leaf target {
         description "Filter results based on configured test target";
         type string;
       }
       leaf status {
         description "Filter based on test status PASS or FAIL";
         type enumeration {
           enum "PASS" {
             description "Dump successful tests";
           }
           enum "FAIL" {
             description "Dump failed tests";
           }
         }
       }
     }
     output {
       container probe-results {
         uses probe-results-block;
       }
     }
   }
   rpc get-twamp-history-results {
     description "Show history results";
     input {
       leaf style {
         default "brief";
         type enumeration {
           enum "brief" {
             description "Display brief output (default)";
           }
           enum "detail" {
             description "Display detailed output";
           }
         }
       }
       leaf control-connection {
         description "Name of control connection";
         type string {
           length "1 .. 32";
         }
         mandatory true;
       }
       leaf test-session {
         description "Name of test session";
         type string {
           length "1 .. 32";
         }
       }
       leaf since {
         description "Show history since YYYY-MM-DD.HH:MM:SS";
         type jt:time;
       }
       leaf source-address {
         description "Filter history based on test ipv4 or ipv6 source-address";
         type jt:ipaddr;
       }
       leaf target {
         description "Filter history based on configured test target";
         type string;
       }
     }
     output {
       container history-results {
         uses history-results-block;
       }
     }
   }
   rpc get-twamp-probe-results {
     description "Show probe results";
     input {
       leaf control-connection {
         description "Name of control connection";
         type string {
           length "1 .. 32";
         }
       }
       leaf test-session {
         description "Name of test session";
         type string {
           length "1 .. 32";
         }
       }
       leaf source-address {
         description "Filter results based on test ipv4 or ipv6 source-address";
         type jt:ipaddr;
       }
       leaf target {
         description "Filter results based on configured test target";
         type string;
       }
       leaf status {
         description "Filter based on test status PASS or FAIL";
         type enumeration {
           enum "PASS" {
             description "Dump successful tests";
           }
           enum "FAIL" {
             description "Dump failed tests";
           }
         }
       }
     }
     output {
       container probe-results {
         uses probe-results-block;
       }
     }
   }
   rpc get-twamp-client-control {
     description "Show control connection(s) status";
     input {
       leaf control-connection {
         description "Name of control connection";
         type string {
           length "1 .. 32";
         }
       }
     }
     output {
       container twamp-control-info {
         uses twamp-control-info-block;
       }
     }
   }
   rpc get-twamp-client-test {
     description "Show test session(s) status";
     input {
       leaf test-session {
         description "Name of test session";
         type string {
           length "1 .. 32";
         }
       }
       leaf control-connection {
         description "Name of control connection";
         type string {
           length "1 .. 32";
         }
       }
     }
     output {
       container twamp-test-info {
         uses twamp-test-info-block;
       }
     }
   }
   rpc get-twamp-server-control {
     description "Show control connection(s) status";
     input {
       leaf control-connection {
         description "Control connection system ID";
         type union {
           type uint32;
           type string {
             pattern "<.*>|$.*";
           }
         }
       }
     }
     output {
       container twamp-control-info {
         uses twamp-control-info-block;
       }
     }
   }
   rpc get-twamp-server-test {
     description "Show test session(s) status";
     input {
       leaf test-session {
         description "Test session system ID";
         type union {
           type uint32;
           type string {
             pattern "<.*>|$.*";
           }
         }
       }
       leaf control-connection {
         description "Control connection system ID";
         type union {
           type uint32;
           type string {
             pattern "<.*>|$.*";
           }
         }
       }
     }
     output {
       container twamp-test-info {
         uses twamp-test-info-block;
       }
     }
   }
   rpc get-rfc2544-information {
     description "Show rfc2544 information";
   }
   rpc get-test-id-information {
     description "Show rfc2544 test id";
     input {
       leaf verbosity_level {
         default "brief";
         type enumeration {
           enum "brief" {
             description "Display brief output (default)";
           }
           enum "detail" {
             description "Display detailed output";
           }
           enum "extensive" {
             description "Display extensive output";
           }
         }
       }
       leaf test-id {
         description "Test id";
         type union {
           type uint32;
           type string {
             pattern "<.*>|$.*";
           }
         }
       }
     }
     output {
       container rfc2544-test-id-information {
         uses rfc2544-test-id-information-block;
       }
     }
   }
   rpc get-active-tests-information {
     description "Show rfc2544 active tests";
     input {
       leaf verbosity_level {
         default "brief";
         type enumeration {
           enum "brief" {
             description "Display brief output (default)";
           }
           enum "detail" {
             description "Display detailed output";
           }
           enum "extensive" {
             description "Display extensive output";
           }
         }
       }
       leaf test-id {
         description "Test id";
         type union {
           type uint32;
           type string {
             pattern "<.*>|$.*";
           }
         }
       }
     }
     output {
       container rfc2544-active-tests-information {
         uses rfc2544-active-tests-information-block;
       }
     }
   }
   rpc get-terminated-tests-information {
     description "Show rfc2544 terminated tests";
     input {
       leaf verbosity_level {
         default "brief";
         type enumeration {
           enum "brief" {
             description "Display brief output (default)";
           }
           enum "detail" {
             description "Display detailed output";
           }
           enum "extensive" {
             description "Display extensive output";
           }
         }
       }
       leaf test-id {
         description "Test id";
         type union {
           type uint32;
           type string {
             pattern "<.*>|$.*";
           }
         }
       }
     }
     output {
       container rfc2544-terminated-tests-information {
         uses rfc2544-terminated-tests-information-block;
       }
     }
   }
   rpc get-completed-tests-information {
     description "Show rfc2544 completed tests";
     input {
       leaf verbosity_level {
         default "brief";
         type enumeration {
           enum "brief" {
             description "Display brief output (default)";
           }
           enum "detail" {
             description "Display detailed output";
           }
           enum "extensive" {
             description "Display extensive output";
           }
         }
       }
       leaf test-id {
         description "Test id";
         type union {
           type uint32;
           type string {
             pattern "<.*>|$.*";
           }
         }
       }
     }
   }
   rpc get-rfc2544-summary-information {
     description "Show rfc2544 summary";
     output {
       container rfc2544-summary-information {
         uses rfc2544-summary-information-block;
       }
     }
   }
   rpc get-services-security-associations-information {
     description "Show IPSec security association information";
     input {
       leaf level {
         default "brief";
         type enumeration {
           enum "brief" {
             description "Display brief output (default)";
           }
           enum "detail" {
             description "Display detailed output";
           }
           enum "extensive" {
             description "Display extensive output";
           }
         }
       }
       leaf service-set {
         description "Restrict output to one service set";
         type string {
         }
       }
       leaf hex {
         description "Display SPI in hexadecimal format";
         type empty;
       }
     }
   }
   rpc get-services-ipsec-statistics-information {
     description "Show IPSec statistics";
     input {
       leaf remote-gw {
         description "Peer address to use as filter";
         type string;
       }
       leaf display {
         default "brief";
         type enumeration {
           enum "detail" {
             description "Display all tunnels";
           }
           enum "brief" {
             description "Display accumulated statistics (default)";
           }
         }
       }
       leaf service-set {
         description "Name of service set";
         type string;
       }
     }
   }
   rpc get-ike-services-security-associations-information {
     description "Show services IKE security association information";
     input {
       leaf level {
         default "brief";
         type enumeration {
           enum "brief" {
             description "Show brief output (default)";
           }
           enum "detail" {
             description "Show detailed output";
           }
         }
       }
       leaf peer-address {
         description "Name of security association";
         type jt:ipaddr;
       }
       leaf routing-instance {
         description "Name of the local-gateway routing-instance";
         type string;
       }
     }
   }
   rpc get-ike-services-statistics {
     description "Show services IKE security association statistics";
     input {
       leaf peer-address {
         description "Name of security association";
         type jt:ipaddr;
       }
       leaf routing-instance {
         description "Name of the local-gateway routing-instance";
         type string;
       }
     }
   }
   rpc get-fips-pic-status-information {
     description "Show FIPS PIC authorization status";
   }
   rpc get-ggsn-imsi-trace {
     description "Show trace information for Identifier for International Mobile Subscriber Identity";
     input {
       leaf imsi-identifier {
         description "Identifier for IMSI";
         type string {
         }
         mandatory true;
       }
     }
   }
   rpc get-ggsn-msisdn-trace {
     description "Show trace information for Mobile Station Integrated Services Digital Network";
     input {
       leaf msisdn-identifier {
         description "Identifier for MSISDN";
         type string {
         }
         mandatory true;
       }
     }
   }
   rpc get-ggsn-trace {
     description "Show all trace information";
   }
   rpc get-ggsn-interface-information {
     description "Show GGSN operational status information";
   }
   rpc get-ggsn-statistics {
     description "Show GGSN statistics";
   }
   rpc get-ggsn-gtp-statistics-information {
     description "Show GPRS tunneling protocol statistics";
   }
   rpc get-ggsn-charging-statistics-information {
     description "Show charging statistics";
   }
   rpc get-ggsn-radius-statistics-information {
     description "Show RADIUS statistics";
   }
   rpc get-ggsn-gtp-prime-statistics-information {
     description "Show GPRS Tunneling Protocol Prime statistics";
   }
   rpc get-ggsn-imsi-user-information {
     description "Show International Mobile Subscriber Identity statistics";
     input {
       leaf imsi-identifier {
         description "Identifier for IMSI";
         type string {
         }
         mandatory true;
       }
     }
   }
   rpc get-ggsn-apn-statistics-information {
     description "Show access point name statistics";
     input {
       leaf apn-name {
         description "Name of APN";
         type string;
       }
     }
   }
   rpc get-ggsn-sgsn-statistics-information {
     description "Show statistics for client Serving GPRS Support Node";
     input {
       leaf address {
         description "IP address and optional prefix length of SGSN";
         type jt:ipv4prefix;
       }
     }
   }
   rpc get-ggsn-l2tp-tunnel-statistics-information {
     description "Show L2TP tunnel statistics";
     input {
       leaf lac-address {
         description "IP address of LAC";
         type jt:ipv4addr;
       }
     }
   }
   rpc get-pdp-diagnostics-per-apn {
     description "Show  PDP context diagnostics information";
     input {
       leaf apn {
         description "APN for which to show PDP Contexts";
         type string {
         }
         mandatory true;
       }
     }
   }
   rpc get-lrf-statistics {
     description "Show lrf statistics";
   }
   rpc get-lrf-collector-statistics {
     description "Show lrf collector statistics";
     input {
       leaf collector-name {
         description "Name of collector";
         type string;
       }
     }
   }
   rpc get-lrf-rule-statistics {
     description "Show lrf rule statistics";
     input {
       leaf rule-name {
         description "Name of rule";
         type string;
       }
     }
   }
   rpc get-lrf-template {
     description "Show lrf template";
     input {
       leaf template-type {
         description "Template type";
         type enumeration {
           enum "ipv4" {
             description "Ipv4 template type";
           }
           enum "ipv4-extended" {
             description "Ipv4 extended template type";
           }
           enum "ipv6" {
             description "Ipv6 template type";
           }
           enum "ipv6-extended" {
             description "Ipv6 extended template type";
           }
           enum "transport-layer" {
             description "Transport layer template type";
           }
           enum "flow-id" {
             description "Flow id template type";
           }
           enum "ipflow" {
             description "IPFlow type";
           }
           enum "ipflow-ts" {
             description "IPFlow TS type";
           }
           enum "ipflow-extended" {
             description "IPFlow extended type";
           }
           enum "device-data" {
             description "Device data template type";
           }
           enum "l7-app" {
             description "L7 APP template type";
           }
           enum "http" {
             description "HTTP type";
           }
           enum "mobile-subscriber" {
             description "Mobile subscriber type";
           }
           enum "subscriber-data" {
             description "Subscriber data type";
           }
           enum "ifl-subscriber" {
             description "IFL based subscriber type";
           }
           enum "wireline-subscriber" {
             description "Wireline subscriber type";
           }
           enum "ipflow-tcp-ts" {
             description "IPFLOW TCP timestamp type (IBM specific)";
           }
           enum "ipflow-tcp" {
             description "IPFLOW TCP type";
           }
           enum "video" {
             description "Video type";
           }
           enum "dns" {
             description "DNS type";
           }
           enum "status-code-distribution" {
             description "Status code distribution for HTTP and DNS";
           }
           enum "pcc" {
             description "PCC type";
           }
         }
         mandatory true;
       }
     }
   }
   rpc get-service-accounting-status-inline-jflow-information {
     description "Show service accounting inline Jflow parameters";
     input {
       leaf inline-jflow-information {
         description "FPC Slot for inline Jflow";
         type union {
           type string {
             pattern "<.*>|$.*";
           }
           type uint32;
         }
         mandatory true;
       }
     }
   }
   rpc get-service-accounting-status-inline-jflow-flow-information {
     description "Show service accounting inline Jflow flow information";
     input {
       leaf inline-jflow-flow-information {
         description "FPC Slot for inline Jflow";
         type union {
           type string {
             pattern "<.*>|$.*";
           }
           type uint32;
         }
         mandatory true;
       }
     }
   }
   rpc get-service-accounting-error-inline-jflow-information {
     description "Show service accounting inline Jflow error information";
     input {
       leaf inline-jflow-error-information {
         description "FPC Slot for inline Jflow";
         type union {
           type string {
             pattern "<.*>|$.*";
           }
           type uint32;
         }
         mandatory true;
       }
     }
   }
   rpc get-service-video-monitoring-information {
     description "Show video-monitoring information";
   }
   rpc get-service-video-monitoring-mdi-information {
     description "Show MDI flows information";
   }
   rpc get-service-video-monitoring-mdi-stats-information {
     description "Show MDI flows stats information";
     input {
       leaf fpc-slot {
         description "FPC Slot number";
         type union {
           type string {
             pattern "<.*>|$.*";
           }
           type uint32;
         }
         mandatory true;
       }
     }
   }
   rpc get-service-video-monitoring-mdi-errors-information {
     description "Show MDI flows error information";
     input {
       leaf fpc-slot {
         description "FPC Slot number";
         type union {
           type string {
             pattern "<.*>|$.*";
           }
           type uint32;
         }
         mandatory true;
       }
     }
   }
   rpc get-service-video-monitoring-mdi-flows-information {
     description "Show MDI flows information";
     input {
       leaf fpc-slot {
         description "FPC Slot number";
         type union {
           type string {
             pattern "<.*>|$.*";
           }
           type uint32;
         }
         mandatory true;
       }
       leaf flow-count {
         description "Count of flows to display";
         type union {
           type string {
             pattern "<.*>|$.*";
           }
           type uint32 {
             range "1 .. 10000";
           }
         }
       }
       leaf flow-identifier {
         description "Flow Identifier";
         type union {
           type uint32;
           type string {
             pattern "<.*>|$.*";
           }
         }
       }
       leaf source-address {
         description "Source address of flow";
         type jt:ipprefix-optional;
       }
       leaf destination-address {
         description "Destination address of flow";
         type jt:ipprefix-optional;
       }
       leaf source-port {
         description "Source port of flow";
         type union {
           type uint32;
           type string {
             pattern "<.*>|$.*";
           }
         }
       }
       leaf destination-port {
         description "Destination port of flow";
         type union {
           type uint32;
           type string {
             pattern "<.*>|$.*";
           }
         }
       }
       leaf template-name {
         description "Template name";
         type string;
       }
       leaf ifl-name {
         description "Interface name";
         type union {
           type jt:interface-name;
           type string {
             pattern "<.*>|$.*";
           }
         }
       }
       leaf flow-direction {
         description "Direction of flow";
         type enumeration {
           enum "input" {
             description "Input flows";
           }
           enum "output" {
             description "Output flows";
           }
         }
       }
       leaf flow-type {
         description "Type of flow";
         type enumeration {
           enum "udp" {
             description "UDP flows";
           }
           enum "rtp" {
             description "RTP flows";
           }
         }
       }
       leaf flow-family-type {
         description "Type of flow";
         type enumeration {
           enum "flow-over-ipv4" {
             description "Flows over IPv4";
           }
           enum "flow-over-ipv4-over-mpls" {
             description "Flows over IPv4 over MPLS";
           }
           enum "flow-over-ipv6" {
             description "Flows over IPv6";
           }
           enum "flow-over-ipv6-over-mpls" {
             description "Flows over IPv6 over MPLS";
           }
         }
       }
       leaf split-display {
         description "Display terse/details output with DF and MLR in split format";
         type enumeration {
           enum "df-mlr-split-view" {
             description "Display detailed/brief flow output with DF and MLR split";
           }
         }
       }
       leaf flow-display {
         description "Display terse/details output";
         type enumeration {
           enum "detail" {
             description "Display detailed output";
           }
           enum "brief" {
             description "Display breif output (default)";
           }
         }
       }
     }
   }
   rpc get-services-video-monitoring-mdi-alarms-information {
     description "Show Alarm information";
   }
   rpc get-services-video-monitoring-mdi-alarms-stats-information {
     description "Show MDI alarm stats information";
     input {
       leaf fpc-slot {
         description "FPC Slot number";
         type union {
           type string {
             pattern "<.*>|$.*";
           }
           type uint32;
         }
         mandatory true;
       }
     }
   }
   rpc get-service-inline-monitoring-information {
     description "Show inline-monitoring information";
     output {
       choice output_c {
         case output-tag {
           leaf output {
             type string;
           }
         }
         case multichassis-tag {
           anyxml multi-routing-engine-results;
         }
       }
     }
   }
   rpc get-service-inline-monitoring-stats-information {
     description "Show inline-monitoring statistical information";
     input {
       leaf fpc-slot {
         description "FPC Slot number";
         type union {
           type string {
             pattern "<.*>|$.*";
           }
           type uint32;
         }
         mandatory true;
       }
     }
     output {
       choice output_c {
         case output-tag {
           leaf output {
             type string;
           }
         }
         case multichassis-tag {
           anyxml multi-routing-engine-results;
         }
       }
     }
   }
   rpc get-service-inline-monitoring-flow-ctr-map {
     description "Show inline-monitoring flow counter mapping";
     input {
       leaf fpc-slot {
         description "FPC Slot number";
         type union {
           type string {
             pattern "<.*>|$.*";
           }
           type uint32;
         }
         mandatory true;
       }
     }
     output {
       choice output_c {
         case output-tag {
           leaf output {
             type string;
           }
         }
         case multichassis-tag {
           anyxml multi-routing-engine-results;
         }
       }
     }
   }
   rpc get-service-inline-monitoring-flow-feature-map {
     description "Show inline-monitoring flow feature mapping";
     input {
       leaf fpc-slot {
         description "FPC Slot number";
         type union {
           type string {
             pattern "<.*>|$.*";
           }
           type uint32;
         }
         mandatory true;
       }
     }
     output {
       choice output_c {
         case output-tag {
           leaf output {
             type string;
           }
         }
         case multichassis-tag {
           anyxml multi-routing-engine-results;
         }
       }
     }
   }
   rpc get-services-mobile-edge-peers-info {
     description "Show SAEGW peers";
   }
   rpc get-services-mobile-edge-peers-stats-info {
     description "Show SAEGW peers statistics";
   }
   rpc get-services-mobile-edge-sessions-information {
     description "Show sessions";
   }
   rpc get-services-mobile-edge-sessions-detail-info {
     description "Display session detail output";
   }
   rpc get-services-mobile-edge-sessions-detail-tran {
     description "Display session detail output for transient-state sessions";
   }
   rpc get-services-mobile-edge-sessions-detail-cpp {
     description "Display session detail output for control plane peers";
     input {
       leaf address {
         description "Display session detail output for control plane peer";
         type string;
         mandatory true;
       }
     }
   }
   rpc get-services-mobile-edge-sessions-extensive {
     description "Display session extensive output";
     input {
       leaf get-services-mobile-edge-session-extensive-lseid {
         description "Display session extensive output of local-seid";
         type string;
       }
     }
   }
   rpc get-services-mobile-edge-sessions-extensive-tran {
     description "Display sessions extensive output for transient-state sessions";
   }
   rpc get-services-mobile-edge-sessions-histogram {
     description "Display established sessions histogram";
   }
   rpc get-services-mobile-edge-session-summary {
     description "Display summary output";
   }
   rpc get-services-mobile-edge-session-summary-cpp {
     description "Display control plane peers summary output";
     input {
       leaf address {
         description "Display control plane peers <IP ADDRESS> summary output";
         type string;
       }
     }
   }
   rpc get-services-mobile-edge-session-summary-anp {
     description "Display access network peers summary output";
     input {
       leaf address {
         description "Display access network peers summary output";
         type string;
       }
     }
   }
   rpc get-services-mobile-edge-session-summary-pic {
     description "Display pic summary output";
     input {
       leaf pic-name {
         description "Display pic summary output of <pfe-x/y>";
         type string {
         }
       }
     }
   }
   rpc get-services-mobile-edge-session-summary-slot {
     description "Display slot summary output";
     input {
       leaf slot-name {
         description "Display slot summary output of <pfe-x>";
         type string {
         }
       }
     }
   }
   rpc get-services-mobile-edge-session-summary-apns {
     description "Display APN name summary output";
     input {
       leaf apn-name {
         description "Display summary output of APN <APN-NAME>";
         type string {
           length "1 .. 100";
         }
       }
     }
   }
   rpc get-services-mobile-edge-session-summary-ag {
     description "Display anchor group summary output";
     input {
       leaf apfe-name {
         description "Display summary output of anchor-group apfe<x>";
         type string {
           length "1 .. 100";
         }
       }
     }
   }
   rpc get-services-mobile-edge-session-summary-cnp {
     description "Display core network peers summary output";
     input {
       leaf address {
         description "Display core network peers summary output";
         type string;
       }
     }
   }
   rpc get-services-mobile-edge-sessions-summary-tran {
     description "Display transient-state summary output";
   }
   rpc get-services-mobile-edge-sessions-cpp-info {
     description "Display session output for control plane peers";
     input {
       leaf address {
         description "Display session output for control plane peer";
         type string;
       }
     }
   }
   rpc get-services-mobile-edge-summary-info {
     description "Show SAE gateway summary";
   }
   rpc get-services-mobile-edge-apfe-dl-cos {
     description "Show APFE CoS settings";
   }
   rpc get-services-mobile-edge-resources-cac-stats {
     description "CAC status and statistics";
   }
   rpc get-analytics-agent-information {
     description "Show analytics service agent information";
     input {
       leaf level {
         default "brief";
         type enumeration {
           enum "detail" {
             description "Display detailed data";
           }
           enum "brief" {
             description "Display brief data (default)";
           }
         }
       }
     }
   }
   rpc get-paa-status {
     description "Show status of Paragon Active Assurance test agent";
     input {
       leaf log-count {
         description "Number of lines of most recent logs to display";
         type union {
           type uint32;
           type string {
             pattern "<.*>|$.*";
           }
         }
       }
     }
     output {
       container paa-status {
         uses paa-status-block;
       }
     }
   }
   rpc get-paa-stats {
     description "Show statistics of Paragon Active Assurance test agent";
     output {
       choice output_c {
         case output-tag {
           leaf output {
             type string;
           }
         }
         case multichassis-tag {
           anyxml multi-routing-engine-results;
         }
       }
     }
   }
   rpc get-secintel-category-feed {
     description "Show category detail information";
     input {
       uses command-forwarding;
       leaf category-name {
         description "Category name";
         type string;
         mandatory true;
       }
       leaf feed-name {
         description "Feed name";
         type string;
         mandatory true;
       }
       leaf start {
         description "Start number";
         type union {
           type uint32;
           type string {
             pattern "<.*>|$.*";
           }
         }
       }
       leaf count {
         description "Total number";
         type union {
           type uint32;
           type string {
             pattern "<.*>|$.*";
           }
         }
       }
     }
   }
   rpc get-secintel-category-summary {
     description "Show category summary";
     input {
       uses command-forwarding;
       leaf category-name {
         description "Show specified category summary";
         type string;
       }
     }
   }
   rpc get-secintel-update-status {
     description "Show update status";
     input {
       uses command-forwarding;
     }
   }
   rpc get-service-set-memory-statistics {
     description "Show service interface memory utilization";
     input {
       leaf service-set {
         description "Name of service set";
         type string;
       }
       leaf interface {
         description "Name of adaptive services interface";
         type string;
       }
     }
   }
   rpc get-service-set-cpu-statistics {
     description "Show service interface CPU utilization as a percentage";
     input {
       leaf service-set {
         description "Name of service set";
         type string;
       }
       leaf interface {
         description "Name of adaptive services interface";
         type string;
       }
     }
   }
   rpc get-service-set-summary-information {
     description "Show service set summary information";
     input {
       leaf interface {
         description "Name of adaptive services interface";
         type string;
       }
     }
   }
   rpc get-service-set-packet-drop-statistics {
     description "Show service set packet drop statistics";
     input {
       leaf interface {
         description "Name of adaptive services interface";
         type string;
       }
     }
   }
   rpc get-service-set-drop-flow-statistics {
     description "Show drop flow stats";
     input {
       leaf interface {
         description "Name of adaptive services interface";
         type string;
       }
     }
   }
   rpc get-service-set-integrity-drops-statistics {
     description "Show header integrity drops";
     input {
       leaf service-set {
         description "Name of service set";
         type string;
       }
       leaf interface {
         description "Name of adaptive services interface";
         type string;
       }
     }
   }
   rpc get-service-set-tcp-tracker-statistics {
     description "Show tcp tracker statistics";
     input {
       leaf service-set {
         description "Name of service set";
         type string;
       }
       leaf interface {
         description "Name of adaptive services interface";
         type string;
       }
     }
   }
   rpc get-service-set-tcp-mss-statistics {
     description "Show service set TCP MSS statistics";
     input {
       leaf interface {
         description "Name of adaptive services interface";
         type string;
       }
     }
   }
   rpc get-service-set-syslog-statistics {
     description "Show service set syslog statistics";
     input {
       leaf host {
         description "Syslog host address";
         type string;
       }
       leaf service-set {
         description "Name of service set";
         type string;
       }
       leaf interface {
         description "Name of adaptive services interface";
         type string;
       }
       leaf display {
         default "brief";
         type enumeration {
           enum "brief" {
             description "Display brief output (default)";
           }
           enum "detail" {
             description "Display detailed output";
           }
         }
       }
     }
   }
   rpc get-service-set-jflow-log-statistics {
     description "Show service set jflow-log statistics";
     input {
       leaf service-set {
         description "Name of service set";
         type string;
       }
       leaf interface {
         description "Name of adaptive services interface";
         type string;
       }
       leaf display {
         default "brief";
         type enumeration {
           enum "brief" {
             description "Display brief output (default)";
           }
           enum "detail" {
             description "Display detailed output";
           }
         }
       }
     }
   }
   rpc get-service-set-ids-drops-statistics {
     description "Show service set IDS drops statistics";
     input {
       leaf service-set {
         description "Name of service set";
         type string;
       }
       leaf interface {
         description "Name of adaptive services interface";
         type string;
       }
     }
   }
   rpc get-ids-session-limits-counters-statistics {
     description "Show the session-limits counters";
     input {
       leaf service-set {
         description "Name of service set";
         type string;
       }
       leaf interface {
         description "Name of adaptive services interface";
         type string;
       }
     }
   }
   rpc get-service-set-plugin-summary {
     description "Show service set plugins summary";
     input {
       leaf interface {
         description "Name of extension provider interface";
         type string;
       }
     }
   }
   rpc get-services-match-policies {
     description "Show match-policy information";
     input {
       leaf service-set {
         description "Name of service set";
         type string;
       }
       leaf source-ip {
         description "Source address";
         type jt:ipprefix;
       }
       leaf source-port {
         description "Source port to use as match";
         type union {
           type uint16;
           type string {
             pattern "<.*>|$.*";
           }
         }
       }
       leaf destination-ip {
         description "Destination address";
         type jt:ipprefix;
       }
       leaf destination-port {
         description "Destination port to use as match";
         type union {
           type uint16;
           type string {
             pattern "<.*>|$.*";
           }
         }
       }
       leaf protocol {
         description "IP protocol name or number";
         type string;
       }
       leaf result-count {
         description "The number of policy matches to display";
         type union {
           type uint16;
           type string {
             pattern "<.*>|$.*";
           }
         }
       }
       leaf match-direction {
         description "Match direction";
         type enumeration {
           enum "input" {
             description "Direction input";
           }
           enum "output" {
             description "Direction output";
           }
         }
       }
     }
   }
   rpc get-service-nat-pool-information {
     description "Show NAT pools information";
     input {
       leaf pool-name {
         description "Name of pool";
         type string;
       }
       leaf display {
         default "brief";
         type enumeration {
           enum "brief" {
             description "Display brief output (default)";
           }
           enum "detail" {
             description "Display detailed output";
           }
         }
       }
     }
   }
   rpc get-service-detnat-information {
     description "Show deterministic NAT internal-host information";
     input {
       leaf nat-address {
         description "NAT address";
         type string;
         mandatory true;
       }
       leaf nat-port {
         description "NAT port";
         type string;
         mandatory true;
       }
     }
   }
   rpc get-service-detnat-pb-information {
     description "Show deterministic NAT port blocks assigned to internal-host";
     input {
       leaf internal-address {
         description "Subscriber IP address";
         type string;
         mandatory true;
       }
     }
   }
   rpc get-service-nat-ipv6-multicast-information {
     description "Show interfaces with IPv6 multicast filter";
   }
   rpc get-service-nat-mapping-address-pooling-paired {
     description "Show NAT Address Pooling Paired mapping";
     input {
       leaf private {
         description "Private IP/IPv6 prefix to use as filter";
         type string;
       }
       leaf public {
         description "Public IP/IPv6 prefix to use as filter";
         type string;
       }
     }
   }
   rpc get-service-nat-mapping-endpoint-independent {
     description "Show NAT Endpoint Independent mapping";
     input {
       leaf private {
         description "Private IP/IPv6 prefix to use as filter";
         type string;
       }
       leaf public {
         description "Public IP prefix to use as filter";
         type string;
       }
     }
   }
   rpc get-service-nat-mapping-pcp {
     description "Show NAT PCP mapping";
   }
   rpc get-service-nat-mapping-summary {
     description "Show NAT mapping entries count";
   }
   rpc get-service-nat-mapping-brief {
     description "Show NAT mapping brief";
     input {
       leaf pool-name {
         description "Name of pool";
         type string;
       }
     }
   }
   rpc get-service-nat-mapping-detail {
     description "Show NAT mapping detail";
     input {
       leaf pool-name {
         description "Name of pool";
         type string;
       }
     }
   }
   rpc get-service-nat-mapping-nptv6 {
     description "Show nptv6 translated address";
     input {
       leaf address {
         description "IPV6 Address";
         type jt:ipv6addr;
         mandatory true;
       }
       leaf direction {
         type enumeration {
           enum "internal" {
             description "Internal-address";
           }
           enum "external" {
             description "External-address";
           }
         }
         mandatory true;
       }
     }
   }
   rpc get-service-nat-statistics-information {
     description "Show NAT statistics";
     input {
       leaf interface {
         description "Name of extension provider interface";
         type string;
       }
     }
   }
   rpc get-service-cos-statistics-information {
     description "Show statistics";
     input {
       leaf display {
         default "brief";
         type enumeration {
           enum "brief" {
             description "Display brief output (default)";
           }
           enum "detail" {
             description "Display detailed output";
           }
           enum "extensive" {
             description "Display extensive output";
           }
           enum "summary" {
             description "Display summary output";
           }
         }
       }
       leaf service-set {
         description "Name of service set";
         type string;
       }
       leaf interface {
         description "Name of adaptive services interface";
         type string;
       }
     }
   }
   rpc get-service-cos-diffserv-statistics {
     description "Show Diffserv marking statistics";
     input {
       leaf display {
         default "brief";
         type enumeration {
           enum "brief" {
             description "Display brief output (default)";
           }
           enum "detail" {
             description "Display detailed output";
           }
           enum "extensive" {
             description "Display extensive output";
           }
           enum "summary" {
             description "Display summary output";
           }
         }
       }
     }
   }
   rpc get-service-cos-forwarding-class-statistics {
     description "Show forwarding Class statistics";
     input {
       leaf display {
         default "brief";
         type enumeration {
           enum "brief" {
             description "Display brief output (default)";
           }
           enum "detail" {
             description "Display detailed output";
           }
           enum "extensive" {
             description "Display extensive output";
           }
           enum "summary" {
             description "Display summary output";
           }
         }
       }
     }
   }
   rpc get-service-hcm-statistics-information {
     description "Show hcm statistics";
     input {
       leaf rule {
         description "Name of HCM tag rule";
         type string;
       }
     }
   }
   rpc get-service-hcm-pic-statistics-information {
     description "Show hcm pic statistics";
     input {
       leaf interface {
         description "Name of extension provider interface";
         type string;
       }
     }
   }
   rpc get-service-mss-sessions-information {
     description "Show mobile subscriber data sessions";
     input {
       leaf imsi {
         description "IMSI of subscriber";
         type string {
           length "5 .. 15";
         }
       }
     }
   }
   rpc get-service-hcm-sessions-stats {
     description "Show hcm session statistics";
     input {
       leaf imsi {
         description "IMSI of subscriber";
         type string {
           length "5 .. 15";
         }
         mandatory true;
       }
     }
   }
   rpc get-service-tdf-sessions-information {
     description "Show traffic-detection-function subscriber data sessions";
     input {
       leaf routing-instance {
         description "Name of routing instance";
         type string;
         mandatory true;
       }
       leaf ipv4-address {
         description "Show sessions for matching IPv4 address";
         type string;
       }
       leaf ipv6-address {
         description "Show sessions for matching IPv6 address";
         type string;
       }
       leaf subscriber-name {
         description "Show sessions for matching Subscriber name";
         type string;
       }
     }
   }
   rpc get-service-tdf-hcm-sessions-stats {
     description "Show hcm session statistics";
     input {
       leaf routing-instance {
         description "Name of routing instance";
         type string;
         mandatory true;
       }
       leaf ipv4-address {
         description "Show sessions for matching IPv4 address";
         type string;
       }
       leaf ipv6-address {
         description "Show sessions for matching IPv6 address";
         type string;
       }
       leaf subscriber-name {
         description "Show sessions for matching Subscriber name";
         type string;
       }
     }
   }
   rpc get-service-pgcp-flow-table-information {
     description "Show PGCP flow table entries";
   }
   rpc get-service-pgcp-flow-table-information-gateway {
     description "Show packet-gateway-control-protocol information for gateway";
     input {
       leaf gateway-name {
         description "Gateway name";
         type string;
         mandatory true;
       }
       leaf gate-id {
         description "Gate id";
         type union {
           type uint64;
           type string {
             pattern "<.*>|$.*";
           }
         }
       }
       leaf service-set {
         description "Name of service set";
         type string;
       }
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf source-routing-instance {
         description "Source routing-instance";
         type string;
       }
       leaf destination-routing-instance {
         description "Destination routing-instance";
         type string;
       }
       leaf protocol {
         description "IP protocol type to use as filter";
         type string;
       }
       leaf get-service-pgcp-flow-count-information {
         description "Show count of matching entries";
         type empty;
       }
       leaf level {
         default "brief";
         type enumeration {
           enum "brief" {
             description "Display brief output";
           }
           enum "extensive" {
             description "Display extensive output";
           }
         }
       }
       leaf backup-data-pic {
         description "Show flows table by querying the backup Data-PIC";
         type empty;
       }
       leaf redundancy-option {
         default "master";
         type enumeration {
           enum "master" {
             description "Query the master RE or ms-pic (default)";
           }
           enum "backup" {
             description "Query the backup ms-pic";
           }
         }
       }
     }
   }
   rpc get-service-pgcp-conversation-information {
     description "Show PGCP conversations";
   }
   rpc get-service-pgcp-conversation-information-gateway {
     description "Show PGCP conversations for gateway";
     input {
       leaf gateway-name {
         description "Gateway name";
         type string;
         mandatory true;
       }
       leaf service-set {
         description "Name of service set";
         type string;
       }
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf source-routing-instance {
         description "Source routing-instance";
         type string;
       }
       leaf destination-routing-instance {
         description "Destination routing-instance";
         type string;
       }
       leaf protocol {
         description "IP protocol type to use as filter";
         type string;
       }
       leaf level {
         default "brief";
         type enumeration {
           enum "brief" {
             description "Display brief output";
           }
           enum "extensive" {
             description "Display extensive output";
           }
         }
       }
       leaf backup-data-pic {
         description "Show conversations information by querying the backup Data-PIC";
         type empty;
       }
       leaf redundancy-option {
         default "master";
         type enumeration {
           enum "master" {
             description "Query the master RE or ms-pic (default)";
           }
           enum "backup" {
             description "Query the backup ms-pic";
           }
         }
       }
     }
   }
   rpc get-pgcpd-active-configuration {
     description "Show pgcpd active-configuration";
   }
   rpc get-service-pgcp-active-configuration-gateway {
     description "Show gateway active configuration";
     input {
       leaf gateway-name {
         description "Gateway name";
         type string;
         mandatory true;
       }
       leaf redundancy-option {
         default "master";
         type enumeration {
           enum "master" {
             description "Query the master RE or ms-pic (default)";
           }
           enum "backup" {
             description "Query the backup ms-pic";
           }
         }
       }
     }
   }
   rpc get-service-pgcp-statistics {
     description "Show pgcpd statistics";
   }
   rpc get-service-pgcp-statistics-gateway {
     description "Show gateway statistics";
     input {
       leaf gateway-name {
         description "Gateway name";
         type string;
         mandatory true;
       }
       leaf display {
         default "brief";
         type enumeration {
           enum "brief" {
             description "Display brief output (default)";
           }
           enum "extensive" {
             description "Display extensive output";
           }
         }
       }
       leaf redundancy-option {
         default "master";
         type enumeration {
           enum "master" {
             description "Query the master RE or ms-pic (default)";
           }
           enum "backup" {
             description "Query the backup ms-pic";
           }
         }
       }
     }
   }
   rpc get-service-pgcp-terminations {
     description "Show list of terminations";
   }
   rpc get-service-pgcp-terminations-gateway {
     description "Show list of terminations for gateway";
     input {
       leaf gateway-name {
         description "Gateway name";
         type string;
         mandatory true;
       }
       leaf termination-prefix {
         description "Termination-prefix to use as filter, default * (all)";
         type string;
       }
       leaf display {
         default "brief";
         type enumeration {
           enum "h248" {
             description "Display H248 output format";
           }
           enum "brief" {
             description "Display brief output (default)";
           }
           enum "count" {
             description "Show count of matching entries";
           }
         }
       }
       leaf redundancy-option {
         default "master";
         type enumeration {
           enum "master" {
             description "Query the master RE or ms-pic (default)";
           }
           enum "backup" {
             description "Query the backup ms-pic";
           }
         }
       }
     }
   }
   rpc get-service-pgcp-gates {
     description "Show list of gates";
   }
   rpc get-service-pgcp-gates-gateway {
     description "Show all gates for gateway";
     input {
       leaf gateway-name {
         description "Gateway name";
         type string;
         mandatory true;
       }
       leaf display {
         default "brief";
         type enumeration {
           enum "extensive" {
             description "Display extensive output";
           }
           enum "brief" {
             description "Display brief output (default)";
           }
           enum "count" {
             description "Show count of matching entries";
           }
         }
       }
       leaf source-routing-instance {
         description "Source routing-instance";
         type string;
       }
       leaf destination-routing-instance {
         description "Destination routing-instance";
         type string;
       }
       leaf redundancy-option {
         default "master";
         type enumeration {
           enum "master" {
             description "Query the master RE or ms-pic (default)";
           }
           enum "backup" {
             description "Query the backup ms-pic";
           }
         }
       }
     }
   }
   rpc get-service-pgcp-gate {
     description "Show gate according to gate-id";
   }
   rpc get-service-pgcp-gate-gateway {
     description "Show gate for gateway";
     input {
       leaf gateway-name {
         description "Gateway name";
         type string;
         mandatory true;
       }
       leaf gate-id {
         description "Gate id";
         type union {
           type uint64;
           type string {
             pattern "<.*>|$.*";
           }
         }
         mandatory true;
       }
       leaf display {
         default "brief";
         type enumeration {
           enum "extensive" {
             description "Display extensive output";
           }
           enum "brief" {
             description "Display brief output (default)";
           }
           enum "statistics" {
             description "Display statistics for gate";
           }
           enum "session-mirroring" {
             description "Display session mirroring for gate";
           }
         }
       }
       leaf redundancy-option {
         default "master";
         type enumeration {
           enum "master" {
             description "Query the master RE or ms-pic (default)";
           }
           enum "backup" {
             description "Query the backup ms-pic";
           }
         }
       }
     }
   }
   rpc get-services-pgcpd-root-termination {
     description "Show root termination h248 information";
   }
   rpc get-services-pgcpd-root-termination-gateway {
     description "Show root termination h248 information for gateway";
     input {
       leaf gateway-name {
         description "Gateway name";
         type string;
         mandatory true;
       }
       leaf redundancy-option {
         default "master";
         type enumeration {
           enum "master" {
             description "Query the master RE or ms-pic (default)";
           }
           enum "backup" {
             description "Query the backup ms-pic";
           }
         }
       }
     }
   }
   rpc get-service-border-signaling-gateway-statistics-calls {
     description "Show border signaling gateway calls statistics";
   }
   rpc get-service-border-signaling-gateway-statistics-calls-by-sp {
     description "Show border signaling gateway calls statistics grouped by service-point";
     input {
       leaf service-point-name {
         description "Service point name or prefix";
         type string;
       }
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
   }
   rpc get-service-border-signaling-gateway-statistics-calls-by-server {
     description "Show border signaling gateway calls statistics grouped by server";
     input {
       leaf server-name {
         description "Server name";
         type string;
       }
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
   }
   rpc get-service-border-signaling-gateway-statistics-calls-duration-by-sp {
     description "Show border signaling gateway calls duration statistics grouped by service-point";
     input {
       leaf service-point-name {
         description "Service point name or prefix";
         type string;
       }
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
   }
   rpc get-service-border-signaling-gateway-statistics-calls-duration-by-server {
     description "Show border signaling gateway calls duration statistics grouped by server";
     input {
       leaf server-name {
         description "Server name";
         type string;
       }
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
   }
   rpc get-service-border-signaling-gateway-statistics-failed-calls-by-sp {
     description "Show border signaling gateway failed calls statistics grouped by service-point";
     input {
       leaf service-point-name {
         description "Service point name or prefix";
         type string;
       }
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
   }
   rpc get-service-border-signaling-gateway-statistics-failed-calls-by-server {
     description "Show border signaling gateway failed calls statistics grouped by server";
     input {
       leaf server-name {
         description "Server name";
         type string;
       }
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
   }
   rpc get-service-bsg-denied-messages {
     description "Show information about dropped messages";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
   }
   rpc get-service-border-signaling-gateway-statistics-admission-control {
     description "Show border signaling gateway admission control profile statistics statistics";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
   }
   rpc get-service-border-signaling-gateway-information-by-request-uri {
     description "Show border signaling gateway information by request uri";
     input {
       leaf gateway {
         description "Name of border signaling gateway";
         type string;
         mandatory true;
       }
       leaf uri {
         description "URI";
         type string;
       }
       leaf display {
         default "brief";
         type enumeration {
           enum "brief" {
             description "Display brief output (default)";
           }
           enum "summary" {
             description "Display summary output";
           }
           enum "detail" {
             description "Display detailed output";
           }
         }
       }
       leaf redundancy-option {
         default "master";
         type enumeration {
           enum "master" {
             description "Query the master border signaling gateway (default)";
           }
           enum "backup" {
             description "Query the backup border signaling gateway";
           }
         }
       }
     }
   }
   rpc get-service-border-signaling-gateway-information-by-contact {
     description "Show border signaling gateway information by contact";
     input {
       leaf gateway {
         description "Name of border signaling gateway";
         type string;
         mandatory true;
       }
       leaf contact {
         description "Contact";
         type string;
       }
       leaf display {
         default "brief";
         type enumeration {
           enum "brief" {
             description "Display brief output (default)";
           }
           enum "summary" {
             description "Display summary output";
           }
           enum "detail" {
             description "Display detailed output";
           }
         }
       }
       leaf redundancy-option {
         default "master";
         type enumeration {
           enum "master" {
             description "Query the master border signaling gateway (default)";
           }
           enum "backup" {
             description "Query the backup border signaling gateway";
           }
         }
       }
     }
   }
   rpc get-service-bsg-information-by-call-context-id {
     description "Show border signaling gateway information by call context ID";
     input {
       leaf gateway {
         description "Name of border signaling gateway";
         type string;
         mandatory true;
       }
       leaf context-id {
         description "Call context ID";
         type union {
           type uint32;
           type string {
             pattern "<.*>|$.*";
           }
         }
       }
       leaf display {
         default "brief";
         type enumeration {
           enum "brief" {
             description "Display brief output (default)";
           }
           enum "detail" {
             description "Display detailed output";
           }
         }
       }
       leaf redundancy-option {
         default "master";
         type enumeration {
           enum "master" {
             description "Query the master border signaling gateway (default)";
           }
           enum "backup" {
             description "Query the backup border signaling gateway";
           }
         }
       }
     }
   }
   rpc get-service-bsg-status-information {
     description "Show border signaling gateway status information";
     input {
       leaf gateway {
         description "Name of border signaling gateway";
         type string;
         mandatory true;
       }
       leaf display {
         default "brief";
         type enumeration {
           enum "brief" {
             description "Display brief output (default)";
           }
           enum "detail" {
             description "Display detailed output";
           }
         }
       }
       leaf redundancy-option {
         default "master";
         type enumeration {
           enum "master" {
             description "Query the master border signaling gateway (default)";
           }
           enum "backup" {
             description "Query the backup border signaling gateway";
           }
         }
       }
     }
   }
   rpc get-border-signaling-gateway-name-resolution-cache-by-fqdn {
     description "Show records for the Fully Qualified Domain Name";
     input {
       leaf fqdn {
         description "Fully Qualified Domain Name";
         type string;
         mandatory true;
       }
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
   }
   rpc get-service-border-signaling-gateway-name-resolution-cache-all {
     description "Show contents of the cache";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
   }
   rpc get-service-border-signaling-gateway-routing-blacklist {
     description "Show border signaling gateway servers blacklist content";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
   }
   rpc get-service-bsg-registrations {
     description "Show border signaling gateway registrations statistics";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
   }
   rpc get-service-bsg-registrations-statistics {
     description "Show registration statistics";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
   }
   rpc get-service-bsg-registrations-realm-statistics {
     description "Realm statistics";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
       leaf realm-name {
         type string;
       }
     }
   }
   rpc get-service-border-signaling-gateway-address-of-record {
     description "Show border signaling gateway address of record";
   }
   rpc get-service-border-signaling-gateway-address-of-record-bindings {
     description "Show address of record bindings";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
       leaf address-of-record {
         description "Address of record name";
         type string;
       }
       leaf detail {
         description "Detail mode";
         type empty;
       }
     }
   }
   rpc get-service-border-signaling-gateway-charging-status {
     description "Show border signaling gateway accounting status";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
   }
   rpc get-service-border-signaling-gateway-charging-statistics {
     description "Show border signaling gateway accounting statistics";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
   }
   rpc get-service-msp-flow-table-information {
     description "Show flow table entries";
     input {
       leaf all {
         description "Display all the entries";
         type empty;
       }
       leaf limit {
         description "Maximum number of entries to display";
         type union {
           type string {
             pattern "<.*>|$.*";
           }
           type uint32 {
             range "1 .. 4294967295";
           }
         }
       }
       leaf display {
         default "brief";
         type enumeration {
           enum "extensive" {
             description "Display extensive output";
           }
           enum "brief" {
             description "Display brief output (default)";
           }
           enum "terse" {
             description "Display terse output";
           }
         }
       }
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf protocol {
         description "IP protocol type to use as filter";
         type string;
       }
       leaf service-set {
         description "Name of service set";
         type string;
       }
       leaf interface {
         description "Name of extension provider interface";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
           enum "pop3" {
             description "Post Office Protocol 3 Protocol";
           }
           enum "smtps" {
             description "Simple Mail Transfer Protocol Over TLS";
           }
           enum "imaps" {
             description "Internet Mail Access Protocol Over TLS";
           }
           enum "pop3s" {
             description "Post Office Protocol 3 Protocol Over TLS";
           }
         }
       }
       leaf get-service-sfw-flow-count-information {
         description "Show count of matching entries";
         type empty;
       }
     }
   }
   rpc get-msp-session-table {
     description "Show session table entries";
     input {
       leaf limit {
         description "Maximum number of entries to display";
         type union {
           type string {
             pattern "<.*>|$.*";
           }
           type uint32 {
             range "1 .. 4294967295";
           }
         }
       }
       leaf display {
         default "brief";
         type enumeration {
           enum "extensive" {
             description "Display extensive output";
           }
           enum "brief" {
             description "Display brief output (default)";
           }
         }
       }
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf protocol {
         description "IP protocol type to use as filter";
         type string;
       }
       leaf service-set {
         description "Name of service set";
         type string;
       }
       leaf interface {
         description "Name of extension provider interface";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
           enum "pop3" {
             description "Post Office Protocol 3 Protocol";
           }
           enum "smtps" {
             description "Simple Mail Transfer Protocol Over TLS";
           }
           enum "imaps" {
             description "Internet Mail Access Protocol Over TLS";
           }
           enum "pop3s" {
             description "Post Office Protocol 3 Protocol Over TLS";
           }
         }
       }
       leaf add-on {
         type enumeration {
           enum "nat" {
             description "Sessions with network address translation";
           }
         }
       }
       leaf source-nat-pool {
         description "Source NAT Pool name";
         type string;
       }
       leaf nat-port-overload-index {
         description "NAT port overloading index";
         type union {
           type string {
             pattern "<.*>|$.*";
           }
           type uint32 {
             range "0 .. 127";
           }
         }
       }
     }
   }
   rpc get-service-msp-sess-count-information {
     description "Show count of matching entries";
     input {
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf protocol {
         description "IP protocol type to use as filter";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
           enum "pop3" {
             description "Post Office Protocol 3 Protocol";
           }
           enum "smtps" {
             description "Simple Mail Transfer Protocol Over TLS";
           }
           enum "imaps" {
             description "Internet Mail Access Protocol Over TLS";
           }
           enum "pop3s" {
             description "Post Office Protocol 3 Protocol Over TLS";
           }
         }
       }
       leaf service-set {
         description "Name of service set";
         type string;
       }
       leaf interface {
         description "Name of extension provider interface";
         type string;
       }
       leaf add-on {
         type enumeration {
           enum "nat" {
             description "Sessions with network address translation";
           }
         }
       }
       leaf source-nat-pool {
         description "Source NAT Pool name";
         type string;
       }
       leaf nat-port-overload-index {
         description "NAT port overloading index";
         type union {
           type string {
             pattern "<.*>|$.*";
           }
           type uint32 {
             range "0 .. 127";
           }
         }
       }
     }
   }
   rpc get-service-msp-sess-softwire {
     description "Show softwire session table entries";
     input {
       leaf service-set {
         description "Name of service set";
         type string;
       }
       leaf interface {
         description "Name of adaptive services interface";
         type string;
       }
       leaf source-prefix {
         description "Source prefix to use as filter";
         type string;
       }
       leaf destination-prefix {
         description "Destination prefix to use as filter";
         type string;
       }
     }
   }
   rpc get-usf-service-softwire-table-information {
     description "Show softwire flow entries";
   }
   rpc get-service-msp-sess-softwire-count-info {
     description "Show softwire count of matching entries";
     input {
       leaf source-prefix {
         description "Source prefix to use as filter";
         type string;
       }
       leaf destination-prefix {
         description "Destination prefix to use as filter";
         type string;
       }
       leaf service-set {
         description "Name of service set";
         type string;
       }
       leaf interface {
         description "Name of extension provider interface";
         type string;
       }
     }
   }
   rpc get-service-msp-sess-softwire-dslite-info {
     description "Show ds-lite related softwire sessions";
     input {
       leaf service-set {
         description "Name of service set";
         type string;
       }
       leaf interface {
         description "Name of adaptive services interface";
         type string;
       }
       leaf source-prefix {
         description "Source prefix to use as filter";
         type string;
       }
       leaf destination-prefix {
         description "Destination prefix to use as filter";
         type string;
       }
       leaf get-service-msp-sess-softwire-dslite-count-info {
         description "Show count of matching entries";
         type empty;
       }
       leaf aftr {
         description "AFTR IPV6 Address";
         type jt:ipv6addr;
       }
       leaf b4 {
         description "B4 IPV6 Address";
         type jt:ipv6addr;
       }
     }
   }
   rpc get-service-msp-session-analysis-information {
     description "Show service sessions statistics";
     input {
       leaf interface {
         description "Name of extension provider interface";
         type string;
       }
     }
   }
   rpc get-services-sessions-utilization {
     description "Show session utilization statistics";
     input {
       leaf interface {
         description "Name of extension provider interface";
         type string;
       }
     }
   }
   rpc get-services-sessions-tcp-log {
     description "Show services sessions tcp-log";
     input {
       leaf interface {
         description "Name of extension provider interface";
         type string;
       }
     }
   }
   rpc get-service-msp-alg-conversation-information {
     description "Show alg conversations";
     input {
       leaf interface {
         description "Name of extension provider interface";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
           enum "pop3" {
             description "Post Office Protocol 3 Protocol";
           }
           enum "smtps" {
             description "Simple Mail Transfer Protocol Over TLS";
           }
           enum "imaps" {
             description "Internet Mail Access Protocol Over TLS";
           }
           enum "pop3s" {
             description "Post Office Protocol 3 Protocol Over TLS";
           }
         }
       }
       leaf display {
         default "brief";
         type enumeration {
           enum "extensive" {
             description "Display extensive output";
           }
           enum "brief" {
             description "Display brief output (default)";
           }
         }
       }
     }
   }
   rpc get-service-msp-alg-stats-information {
     description "Show ALG Statistics";
     input {
       leaf interface {
         description "Name of extension provider interface";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
           enum "pop3" {
             description "Post Office Protocol 3 Protocol";
           }
           enum "smtps" {
             description "Simple Mail Transfer Protocol Over TLS";
           }
           enum "imaps" {
             description "Internet Mail Access Protocol Over TLS";
           }
           enum "pop3s" {
             description "Post Office Protocol 3 Protocol Over TLS";
           }
         }
       }
     }
   }
   rpc get-service-msp-alg-sip-globals-information {
     description "Show SIP ALG global configurations";
     input {
       leaf interface {
         description "Name of extension provider interface";
         type string;
       }
     }
   }
   rpc get-service-ha-info {
     description "Show HA info and current status";
     input {
       leaf interface {
         description "Name of adaptive services interface";
         type string;
       }
       leaf level {
         default "brief";
         type enumeration {
           enum "brief" {
             description "Display brief output";
           }
           enum "detail" {
             description "Display detailed output";
           }
           enum "statistics" {
             description "Display statistics output";
           }
         }
       }
     }
   }
   rpc get-service-flow-analysis-information {
     description "Show flow table entries";
     input {
       leaf interface {
         description "Name of adaptive services interface";
         type string;
       }
     }
   }
   rpc get-service-subs-analysis-information {
     description "Show subscriber table entries";
     input {
       leaf interface {
         description "Name of adaptive services interface";
         type string;
       }
     }
   }
   rpc get-service-sfw-flow-table-information {
     description "Show flow table entries";
     input {
       leaf all {
         description "Display all the entries";
         type empty;
       }
       leaf limit {
         description "Maximum number of entries to display";
         type union {
           type string {
             pattern "<.*>|$.*";
           }
           type uint32 {
             range "1 .. 4294967295";
           }
         }
       }
       leaf display {
         default "brief";
         type enumeration {
           enum "extensive" {
             description "Display extensive output";
           }
           enum "brief" {
             description "Display brief output (default)";
           }
           enum "terse" {
             description "Display terse output";
           }
         }
       }
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf protocol {
         description "IP protocol type to use as filter";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
           enum "pop3" {
             description "Post Office Protocol 3 Protocol";
           }
           enum "smtps" {
             description "Simple Mail Transfer Protocol Over TLS";
           }
           enum "imaps" {
             description "Internet Mail Access Protocol Over TLS";
           }
           enum "pop3s" {
             description "Post Office Protocol 3 Protocol Over TLS";
           }
         }
       }
       leaf service-set {
         description "Name of service set";
         type string;
       }
       leaf interface {
         description "Name of adaptive services interface";
         type string;
       }
       leaf pgcp {
         description "Use pgcp flow type as filter";
         type empty;
       }
       leaf get-service-sfw-flow-count-information {
         description "Show count of matching entries";
         type empty;
       }
     }
   }
   rpc get-service-sfw-conversation-information {
     description "Show conversations";
     input {
       leaf all {
         description "Display all the entries";
         type empty;
       }
       leaf limit {
         description "Maximum number of entries to display";
         type union {
           type string {
             pattern "<.*>|$.*";
           }
           type uint32 {
             range "1 .. 4294967295";
           }
         }
       }
       leaf display {
         default "brief";
         type enumeration {
           enum "extensive" {
             description "Display extensive output";
           }
           enum "brief" {
             description "Display brief output (default)";
           }
           enum "terse" {
             description "Display terse output";
           }
         }
       }
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf protocol {
         description "IP protocol type to use as filter";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
           enum "pop3" {
             description "Post Office Protocol 3 Protocol";
           }
           enum "smtps" {
             description "Simple Mail Transfer Protocol Over TLS";
           }
           enum "imaps" {
             description "Internet Mail Access Protocol Over TLS";
           }
           enum "pop3s" {
             description "Post Office Protocol 3 Protocol Over TLS";
           }
         }
       }
       leaf service-set {
         description "Name of service set";
         type string;
       }
       leaf interface {
         description "Name of adaptive services interface";
         type string;
       }
       leaf pgcp {
         description "Use pgcp flow type as filter";
         type empty;
       }
     }
   }
   rpc get-service-sfw-sip-call-information {
     description "Show SIP call information";
     input {
       leaf all {
         description "Display all the entries";
         type empty;
       }
       leaf limit {
         description "Maximum number of entries to display";
         type union {
           type string {
             pattern "<.*>|$.*";
           }
           type uint32 {
             range "1 .. 4294967295";
           }
         }
       }
       leaf display {
         default "brief";
         type enumeration {
           enum "extensive" {
             description "Display extensive output";
           }
           enum "brief" {
             description "Display brief output (default)";
           }
           enum "terse" {
             description "Display terse output";
           }
         }
       }
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf protocol {
         description "IP protocol type to use as filter";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
           enum "pop3" {
             description "Post Office Protocol 3 Protocol";
           }
           enum "smtps" {
             description "Simple Mail Transfer Protocol Over TLS";
           }
           enum "imaps" {
             description "Internet Mail Access Protocol Over TLS";
           }
           enum "pop3s" {
             description "Post Office Protocol 3 Protocol Over TLS";
           }
         }
       }
       leaf service-set {
         description "Name of service set";
         type string;
       }
       leaf interface {
         description "Name of adaptive services interface";
         type string;
       }
       leaf get-service-sfw-sip-call-count-information {
         description "Show count of matching entries";
         type empty;
       }
     }
   }
   rpc get-service-sfw-sip-register-information {
     description "Show SIP register information";
     input {
       leaf all {
         description "Display all the entries";
         type empty;
       }
       leaf limit {
         description "Maximum number of entries to display";
         type union {
           type string {
             pattern "<.*>|$.*";
           }
           type uint32 {
             range "1 .. 4294967295";
           }
         }
       }
       leaf display {
         default "brief";
         type enumeration {
           enum "extensive" {
             description "Display extensive output";
           }
           enum "brief" {
             description "Display brief output (default)";
           }
           enum "terse" {
             description "Display terse output";
           }
         }
       }
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf protocol {
         description "IP protocol type to use as filter";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
           enum "pop3" {
             description "Post Office Protocol 3 Protocol";
           }
           enum "smtps" {
             description "Simple Mail Transfer Protocol Over TLS";
           }
           enum "imaps" {
             description "Internet Mail Access Protocol Over TLS";
           }
           enum "pop3s" {
             description "Post Office Protocol 3 Protocol Over TLS";
           }
         }
       }
       leaf service-set {
         description "Name of service set";
         type string;
       }
       leaf interface {
         description "Name of adaptive services interface";
         type string;
       }
       leaf get-service-sfw-sip-register-count-information {
         description "Show count of matching entries";
         type empty;
       }
     }
   }
   rpc get-service-sfw-statistics-information {
     description "Show statistics";
     input {
       leaf display {
         default "brief";
         type enumeration {
           enum "brief" {
             description "Display brief output (default)";
           }
           enum "detail" {
             description "Display detailed output";
           }
           enum "extensive" {
             description "Display extensive output";
           }
           enum "summary" {
             description "Display summary output";
           }
         }
       }
       leaf service-set {
         description "Name of service set";
         type string;
       }
       leaf interface {
         description "Name of adaptive services interface";
         type string;
       }
     }
   }
   rpc get-sfw-application-protocol-statistics {
     description "Application protocol type to use as filter";
     input {
       leaf protocol {
         description "Application protocol type to use as filter";
         type enumeration {
           enum "sip" {
             description "Session Initiation Protocol";
           }
         }
       }
     }
   }
   rpc get-service-sfw-redundancy-statistics {
     description "Show redundancy statistics";
     input {
       leaf backup-data-pic {
         description "Query the backup data PIC";
         type empty;
       }
       leaf display {
         default "brief";
         type enumeration {
           enum "extensive" {
             description "Display extensive output";
           }
           enum "brief" {
             description "Display brief output (default)";
           }
         }
       }
     }
   }
   rpc get-service-capture {
     description "Show Services PIC packet capture";
     input {
       leaf file {
         type string;
         mandatory true;
       }
       leaf level {
         default "brief";
         type enumeration {
           enum "brief" {
             description "Display brief output";
           }
           enum "detail" {
             description "Display detailed output";
           }
           enum "extensive" {
             description "Display extensive output";
           }
         }
       }
       leaf packet-id {
         description "Packet-id to be used as filter";
         type string;
       }
     }
   }
   rpc get-service-softwire-table-information {
     description "Show softwire information";
     input {
       leaf get-service-current-softwire-count-information {
         description "Show count of softwires created";
         type empty;
       }
     }
   }
   rpc get-service-softwire-flow-table-information {
     description "Show flow table entries";
     input {
       leaf service-set {
         description "Name of service set";
         type string;
       }
       leaf interface {
         description "Name of adaptive services interface";
         type string;
       }
       leaf get-service-softwire-count-information {
         description "Show count of matching entries";
         type empty;
       }
     }
   }
   rpc get-service-softwire-ds-lite-flow-table-information {
     description "Show ds-lite related softwire flows";
     input {
       leaf AFTR {
         description "AFTR IPV6 Address";
         type jt:ipv6addr;
       }
       leaf B4 {
         description "B4 IPV6 Address";
         type jt:ipv6addr;
       }
     }
   }
   rpc get-service-softwire-v6rd-flow-table-information {
     description "Show v6rd related softwire flows";
     input {
       leaf concentrator {
         description "Softwire concentrator IPV4 Address";
         type jt:ipv4addr;
       }
       leaf initiator {
         description "Softwire initiator IPV4 Address";
         type jt:ipv4addr;
       }
     }
   }
   rpc get-service-softwire-session-table-information {
     description "Show session table entries";
     input {
       leaf service-set {
         description "Name of service set";
         type string;
       }
       leaf interface {
         description "Name of adaptive services interface";
         type string;
       }
       leaf get-service-softwire-session-count-info {
         description "Show count of matching entries";
         type empty;
       }
     }
   }
   rpc get-service-softwire-session-dslite-table-info {
     description "Show ds-lite related softwire sessions";
     input {
       leaf service-set {
         description "Name of service set";
         type string;
       }
       leaf interface {
         description "Name of adaptive services interface";
         type string;
       }
       leaf get-service-softwire-session-count-info {
         description "Show count of matching entries";
         type empty;
       }
       leaf aftr {
         description "AFTR IPV6 Address";
         type jt:ipv6addr;
       }
       leaf b4 {
         description "B4 IPV6 Address";
         type jt:ipv6addr;
       }
     }
   }
   rpc get-service-softwire-statistics-information {
     description "Show global softwire statistics";
     input {
       leaf interface {
         description "Name of adaptive services interface";
         type string;
       }
       leaf display {
         type enumeration {
           enum "ds-lite" {
             description "Show softwire statistics for dslite";
           }
           enum "v6rd" {
             description "Show softwire statistics for v6rd";
           }
         }
       }
     }
   }
   rpc get-inline-service-sw-statistics-information {
     description "Show global inline softwire statistics";
     input {
       leaf interface {
         description "Name of adaptive services interface";
         type string;
       }
       leaf display {
         type enumeration {
           enum "v6rd" {
             description "Softwire statistics for 6rd";
           }
           enum "mape" {
             description "Softwire statistics for MAPE";
           }
           enum "mapt" {
             description "Softwire statistics for MAPT";
           }
         }
       }
     }
   }
   rpc get-inline-nat-statistics-information {
     description "Show global inline nat statistics";
     input {
       leaf interface {
         description "Name of adaptive services interface";
         type string;
       }
     }
   }
   rpc get-inline-nat-pool-information {
     description "Show NAT pools information";
     input {
       leaf pool-name {
         description "Name of pool";
         type string;
       }
     }
   }
   rpc get-inline-nat-mapping-nptv6-information {
     description "Show nptv6 translated address";
     input {
       leaf address {
         description "IPV6 Address";
         type jt:ipv6addr;
         mandatory true;
       }
       leaf direction {
         type enumeration {
           enum "internal" {
             description "Internal-address";
           }
           enum "external" {
             description "External-address";
           }
         }
         mandatory true;
       }
     }
   }
   rpc get-inline-ip-reass-statistics {
     description "Show IP Reassembly statistics";
     input {
       uses command-forwarding;
     }
   }
   rpc get-inline-ip-reass-si-statistics-information {
     description "Show inline ip-reassembly statistics on si-ifl";
     input {
       leaf interface-name {
         description "Name of adaptive services interface";
         type string;
         mandatory true;
       }
     }
   }
   rpc get-inline-ip-reass-fpc-slot-information {
     description "FPC slot number";
     input {
       uses command-forwarding;
       leaf fpc-slot {
         description "FPC slot number";
         type union {
           type string {
             pattern "<.*>|$.*";
           }
           type uint32;
         }
         mandatory true;
       }
       leaf pfe-slot {
         description "PFE slot number";
         type union {
           type string {
             pattern "<.*>|$.*";
           }
           type uint32;
         }
       }
     }
   }
   rpc get-inline-ipv6-reass-statistics {
     description "Show IPv6 Reassembly statistics";
     input {
       uses command-forwarding;
     }
   }
   rpc get-ipv6-reassembly-interface-information {
     description "Inline-service interface related statistics";
     input {
       leaf interface-name {
         description "Name of inline service interface";
         type string;
         mandatory true;
       }
     }
   }
   rpc get-inline-ipv6-reass-fpc-slot-information {
     description "FPC slot number";
     input {
       uses command-forwarding;
       leaf fpc-slot {
         description "FPC slot number";
         type union {
           type string {
             pattern "<.*>|$.*";
           }
           type uint32;
         }
         mandatory true;
       }
       leaf pfe-slot {
         description "PFE slot number";
         type union {
           type string {
             pattern "<.*>|$.*";
           }
           type uint32;
         }
       }
     }
   }
   rpc get-inline-sfw-flow-table-information {
     description "Show flow table entries";
     input {
       leaf all {
         description "Display all the entries";
         type empty;
       }
       leaf limit {
         description "Maximum number of entries to display";
         type union {
           type string {
             pattern "<.*>|$.*";
           }
           type uint32 {
             range "1 .. 4294967295";
           }
         }
       }
       leaf display {
         default "brief";
         type enumeration {
           enum "extensive" {
             description "Display extensive output";
           }
           enum "brief" {
             description "Display brief output (default)";
           }
           enum "terse" {
             description "Display terse output";
           }
         }
       }
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf protocol {
         description "IP protocol type to use as filter";
         type string;
       }
       leaf service-set {
         description "Name of service set";
         type string;
       }
       leaf interface {
         description "Name of adaptive services interface";
         type string;
       }
       leaf get-inline-sfw-flow-count-information {
         description "Show count of matching entries";
         type empty;
       }
     }
   }
   rpc get-inline-sfw-statistics-information {
     description "Show statistics";
     input {
       leaf display {
         default "brief";
         type enumeration {
           enum "brief" {
             description "Display brief output (default)";
           }
           enum "summary" {
             description "Display summary output";
           }
         }
       }
       leaf service-set {
         description "Name of service set";
         type string;
       }
       leaf interface {
         description "Name of adaptive services interface";
         type string;
       }
     }
   }
   rpc get-service-ids-source-table-information {
     description "Show attack source address table";
     input {
       leaf source-prefix {
         description "Source prefix to use as filter";
         type string;
       }
       leaf service-set {
         description "Name of service set";
         type string;
       }
       leaf interface {
         description "Name of adaptive services interface";
         type string;
       }
       leaf order {
         description "Specify table ordering criteria";
         default "anomalies";
         type enumeration {
           enum "anomalies" {
             description "Order by number of anomalies (default)";
           }
           enum "bytes" {
             description "Order by bytes received";
           }
           enum "flows" {
             description "Order by number of flows";
           }
           enum "packets" {
             description "Order by packets received";
           }
         }
       }
       leaf threshold {
         description "Minimum threshold for table entries";
         type union {
           type int32;
           type string {
             pattern "<.*>|$.*";
           }
         }
       }
       leaf limit {
         description "Maximum number of entries to display";
         type union {
           type int32;
           type string {
             pattern "<.*>|$.*";
           }
         }
       }
       leaf display {
         default "brief";
         type enumeration {
           enum "extensive" {
             description "Display extensive output";
           }
           enum "brief" {
             description "Display brief output (default)";
           }
           enum "terse" {
             description "Display terse output";
           }
         }
       }
     }
   }
   rpc get-service-ids-destination-table-information {
     description "Show attack destination address table";
     input {
       leaf destination-prefix {
         description "Destination prefix to use as filter";
         type string;
       }
       leaf service-set {
         description "Name of service set";
         type string;
       }
       leaf interface {
         description "Name of adaptive services interface";
         type string;
       }
       leaf order {
         description "Specify table ordering criteria";
         default "anomalies";
         type enumeration {
           enum "anomalies" {
             description "Order by number of anomalies (default)";
           }
           enum "bytes" {
             description "Order by bytes received";
           }
           enum "flows" {
             description "Order by number of flows";
           }
           enum "packets" {
             description "Order by packets received";
           }
         }
       }
       leaf threshold {
         description "Minimum threshold for table entries";
         type union {
           type int32;
           type string {
             pattern "<.*>|$.*";
           }
         }
       }
       leaf limit {
         description "Maximum number of entries to display";
         type union {
           type int32;
           type string {
             pattern "<.*>|$.*";
           }
         }
       }
       leaf display {
         default "brief";
         type enumeration {
           enum "extensive" {
             description "Display extensive output";
           }
           enum "brief" {
             description "Display brief output (default)";
           }
           enum "terse" {
             description "Display terse output";
           }
         }
       }
     }
   }
   rpc get-service-ids-pair-table-information {
     description "Show attack source and destination address pair table";
     input {
       leaf source-prefix {
         description "Source prefix to use as filter";
         type string;
       }
       leaf destination-prefix {
         description "Destination prefix to use as filter";
         type string;
       }
       leaf service-set {
         description "Name of service set";
         type string;
       }
       leaf interface {
         description "Name of adaptive services interface";
         type string;
       }
       leaf order {
         description "Specify table ordering criteria";
         default "anomalies";
         type enumeration {
           enum "anomalies" {
             description "Order by number of anomalies (default)";
           }
           enum "bytes" {
             description "Order by bytes received";
           }
           enum "flows" {
             description "Order by number of flows";
           }
           enum "packets" {
             description "Order by packets received";
           }
         }
       }
       leaf threshold {
         description "Minimum threshold for table entries";
         type union {
           type int32;
           type string {
             pattern "<.*>|$.*";
           }
         }
       }
       leaf limit {
         description "Maximum number of entries to display";
         type union {
           type int32;
           type string {
             pattern "<.*>|$.*";
           }
         }
       }
       leaf display {
         default "brief";
         type enumeration {
           enum "extensive" {
             description "Display extensive output";
           }
           enum "brief" {
             description "Display brief output (default)";
           }
           enum "terse" {
             description "Display terse output";
           }
         }
       }
     }
   }
   rpc get-service-identification-statistics-information {
     description "Show service identification statistics";
     input {
       leaf detail {
         description "Display detailed statistics";
         type empty;
       }
     }
   }
   rpc get-header-redirect-set-statistics-information {
     description "Show header redirect set statistics";
     input {
       leaf detail {
         description "Display detailed statistics";
         type empty;
       }
     }
   }
   rpc get-uri-redirect-set-statistics-information {
     description "Show URI redirect set statistics";
     input {
       leaf detail {
         description "Display detailed statistics";
         type empty;
       }
     }
   }
   rpc get-flow-table-statistics-information {
     description "Show flow table statistics";
     input {
       leaf detail {
         description "Show detailed statistics information";
         type empty;
       }
     }
   }
   rpc get-soft-gre-tunnel-database {
     description "Show active soft gre active tunnels";
     input {
       leaf display {
         default "brief";
         type enumeration {
           enum "extensive" {
             description "Display extensive output";
           }
           enum "brief" {
             description "Display brief output (default)";
           }
           enum "detail" {
             description "Display detailed output";
           }
           enum "statistics" {
             description "Display statistics";
           }
         }
       }
       choice filter {
         case interface {
           leaf interface {
             description "Interface name to use as filter";
             type string;
           }
         }
         case tunnel-group {
           leaf tunnel-group {
             description "Tunnel group to use as filter";
             type string;
           }
         }
         case local-ip {
           leaf local-ip {
             description "Local ip address to use as filter";
             type jt:ipv4addr;
           }
         }
         case remote-ip {
           leaf remote-ip {
             description "Remote ip address to use as filter";
             type jt:ipv4addr;
           }
         }
       }
     }
   }
   rpc get-l2tp-destination-information {
     description "Show L2TP destination information";
     input {
       leaf display {
         default "brief";
         type enumeration {
           enum "extensive" {
             description "Display extensive output";
           }
           enum "brief" {
             description "Display brief output (default)";
           }
           enum "detail" {
             description "Display detailed output";
           }
           enum "statistics" {
             description "Display statistics";
           }
         }
       }
       choice filter {
         case local-gateway {
           leaf local-gateway {
             description "Local gateway address to use as filter";
             type jt:ipv4addr;
           }
         }
         case peer-gateway {
           leaf peer-gateway {
             description "Peer gateway address to use as filter";
             type jt:ipv4addr;
           }
         }
       }
     }
   }
   rpc get-services-l2tp-destination-lockout {
     description "Display locked out destinations";
   }
   rpc get-l2tp-tunnel-information {
     description "Show active L2TP tunnel list";
     input {
       leaf display {
         default "brief";
         type enumeration {
           enum "extensive" {
             description "Display extensive output";
           }
           enum "brief" {
             description "Display brief output (default)";
           }
           enum "detail" {
             description "Display detailed output";
           }
           enum "statistics" {
             description "Display statistics";
           }
         }
       }
       choice filter {
         case tunnel-group {
           leaf tunnel-group {
             description "Tunnel group to use as filter";
             type string;
           }
         }
         case local-tunnel-id {
           leaf local-tunnel-id {
             description "Local tunnel ID to use as filter";
             type string;
           }
         }
         case local-gateway {
           leaf local-gateway {
             description "Local gateway address to use as filter";
             type jt:ipv4addr;
           }
         }
         case local-gateway-name {
           leaf local-gateway-name {
             description "Local gateway name to use as filter";
             type string;
           }
         }
         case peer-gateway {
           leaf peer-gateway {
             description "Peer gateway address to use as filter";
             type jt:ipv4addr;
           }
         }
         case peer-gateway-name {
           leaf peer-gateway-name {
             description "Peer gateway name to use as filter";
             type string;
           }
         }
         case interface {
           leaf interface {
             description "Interface name to use as filter";
             type string;
           }
         }
       }
     }
   }
   rpc get-l2tp-session-information {
     description "Show active L2TP session list";
     input {
       leaf display {
         default "brief";
         type enumeration {
           enum "extensive" {
             description "Display extensive output";
           }
           enum "brief" {
             description "Display brief output (default)";
           }
           enum "detail" {
             description "Display detailed output";
           }
           enum "statistics" {
             description "Display statistics";
           }
         }
       }
       choice filter {
         case tunnel-group {
           leaf tunnel-group {
             description "Tunnel group to use as filter";
             type string;
           }
         }
         case local-tunnel-id {
           leaf local-tunnel-id {
             description "Local tunnel ID to use as filter";
             type string;
           }
         }
         case local-gateway {
           leaf local-gateway {
             description "Local gateway address to use as filter";
             type jt:ipv4addr;
           }
         }
         case local-gateway-name {
           leaf local-gateway-name {
             description "Local gateway name to use as filter";
             type string;
           }
         }
         case peer-gateway {
           leaf peer-gateway {
             description "Peer gateway address to use as filter";
             type jt:ipv4addr;
           }
         }
         case peer-gateway-name {
           leaf peer-gateway-name {
             description "Peer gateway name to use as filter";
             type string;
           }
         }
         case local-session-id {
           leaf local-session-id {
             description "Local session ID to use as filter";
             type string;
           }
         }
         case user {
           leaf user {
             description "Username to use as filter";
             type string;
           }
         }
         case interface {
           leaf interface {
             description "Interface name to use as filter";
             type string;
           }
         }
         case routing-instance {
           leaf routing-instance {
             description "Name of routing instance";
             type string;
           }
         }
       }
     }
   }
   rpc get-l2tp-client-information {
     description "Show active L2TP clients list";
     input {
       leaf client-name {
         description "Client name";
         type string;
       }
     }
   }
   rpc get-l2tp-tunnel-group-information {
     description "Show tunnel-group list";
     input {
       leaf tunnel-group-name {
         description "Tunnel group name";
         type string;
       }
     }
   }
   rpc get-l2tp-session-limit-group-information {
     description "Show session-limit-group list";
     input {
       leaf session-limit-group-name {
         description "Session limit group name";
         type string;
       }
     }
   }
   rpc get-l2tp-tunnel-switch-information {
     description "Show table of tunnel switched sessions";
   }
   rpc get-l2tp-tunnel-switch-session-information {
     description "Show tunnel switched sessions";
     input {
       leaf display {
         default "brief";
         type enumeration {
           enum "extensive" {
             description "Display extensive output";
           }
           enum "brief" {
             description "Display brief output (default)";
           }
           enum "detail" {
             description "Display detailed output";
           }
           enum "statistics" {
             description "Display statistics";
           }
         }
       }
       choice filter {
         case tunnel-group {
           leaf tunnel-group {
             description "Tunnel group to use as filter";
             type string;
           }
         }
         case local-tunnel-id {
           leaf local-tunnel-id {
             description "Local tunnel ID to use as filter";
             type string;
           }
         }
         case local-gateway {
           leaf local-gateway {
             description "Local gateway address to use as filter";
             type jt:ipv4addr;
           }
         }
         case local-gateway-name {
           leaf local-gateway-name {
             description "Local gateway name to use as filter";
             type string;
           }
         }
         case peer-gateway {
           leaf peer-gateway {
             description "Peer gateway address to use as filter";
             type jt:ipv4addr;
           }
         }
         case peer-gateway-name {
           leaf peer-gateway-name {
             description "Peer gateway name to use as filter";
             type string;
           }
         }
         case local-session-id {
           leaf local-session-id {
             description "Local session ID to use as filter";
             type string;
           }
         }
         case user {
           leaf user {
             description "Username to use as filter";
             type string;
           }
         }
         case interface {
           leaf interface {
             description "Interface name to use as filter";
             type string;
           }
         }
         case routing-instance {
           leaf routing-instance {
             description "Name of routing instance";
             type string;
           }
         }
       }
     }
   }
   rpc get-l2tp-tunnel-switch-tunnel-information {
     description "Show switched tunnels";
     input {
       leaf display {
         default "brief";
         type enumeration {
           enum "extensive" {
             description "Display extensive output";
           }
           enum "brief" {
             description "Display brief output (default)";
           }
           enum "detail" {
             description "Display detailed output";
           }
           enum "statistics" {
             description "Display statistics";
           }
         }
       }
       choice filter {
         case tunnel-group {
           leaf tunnel-group {
             description "Tunnel group to use as filter";
             type string;
           }
         }
         case local-tunnel-id {
           leaf local-tunnel-id {
             description "Local tunnel ID to use as filter";
             type string;
           }
         }
         case local-gateway {
           leaf local-gateway {
             description "Local gateway address to use as filter";
             type jt:ipv4addr;
           }
         }
         case local-gateway-name {
           leaf local-gateway-name {
             description "Local gateway name to use as filter";
             type string;
           }
         }
         case peer-gateway {
           leaf peer-gateway {
             description "Peer gateway address to use as filter";
             type jt:ipv4addr;
           }
         }
         case peer-gateway-name {
           leaf peer-gateway-name {
             description "Peer gateway name to use as filter";
             type string;
           }
         }
         case interface {
           leaf interface {
             description "Interface name to use as filter";
             type string;
           }
         }
       }
     }
   }
   rpc get-l2tp-tunnel-switch-destination-information {
     description "Show tunnel switched destinations";
     input {
       leaf display {
         default "brief";
         type enumeration {
           enum "extensive" {
             description "Display extensive output";
           }
           enum "brief" {
             description "Display brief output (default)";
           }
           enum "detail" {
             description "Display detailed output";
           }
           enum "statistics" {
             description "Display statistics";
           }
         }
       }
       choice filter {
         case local-gateway {
           leaf local-gateway {
             description "Local gateway address to use as filter";
             type jt:ipv4addr;
           }
         }
         case peer-gateway {
           leaf peer-gateway {
             description "Peer gateway address to use as filter";
             type jt:ipv4addr;
           }
         }
       }
     }
   }
   rpc get-l2tp-disconnect-cause-summary {
     description "Show L2TP disconnect cause summary";
   }
   rpc get-l2tp-user-information {
     description "Show active L2TP user list";
     input {
       leaf display {
         default "brief";
         type enumeration {
           enum "extensive" {
             description "Display extensive output";
           }
           enum "brief" {
             description "Display brief output (default)";
           }
           enum "detail" {
             description "Display detailed output";
           }
           enum "statistics" {
             description "Display statistics";
           }
         }
       }
       choice filter {
         case user {
           leaf user {
             description "Filter by username";
             type string;
           }
         }
       }
     }
   }
   rpc get-l2tp-multilink-information {
     description "Show active L2TP multilink list";
     input {
       leaf display {
         default "brief";
         type enumeration {
           enum "extensive" {
             description "Display extensive output";
           }
           enum "brief" {
             description "Display brief output (default)";
           }
           enum "detail" {
             description "Display detailed output";
           }
           enum "statistics" {
             description "Display statistics";
           }
         }
       }
       choice filter {
         case bundle-id {
           leaf bundle-id {
             description "Filter by multilink bundle ID";
             type string;
           }
         }
       }
     }
   }
   rpc get-l2tp-summary-information {
     description "Show L2TP summary information";
     input {
       leaf display {
         default "brief";
         type enumeration {
           enum "extensive" {
             description "Display extensive output";
           }
           enum "brief" {
             description "Display brief output (default)";
           }
           enum "detail" {
             description "Display detailed output";
           }
           enum "statistics" {
             description "Display statistics";
           }
         }
       }
       leaf interface {
         description "Name of adaptive services interface";
         type string;
       }
     }
   }
   rpc get-services-l2tp-radius-authentication-accounting-servers-information {
     description "Show RADIUS authentication and accounting servers information";
   }
   rpc get-services-l2tp-radius-authentication-accounting-statistics-information {
     description "Show RADIUS authentication and accounting statistics information";
   }
   rpc get-services-l2tp-radius-authentication-servers-information {
     description "Show RADIUS authentication servers information";
   }
   rpc get-services-l2tp-radius-authentication-statistics-information {
     description "Show RADIUS authentication statistics information";
   }
   rpc get-services-l2tp-radius-accounting-servers-information {
     description "Show RADIUS accounting servers information";
   }
   rpc get-services-l2tp-radius-accounting-statistics-information {
     description "Show RADIUS accounting statistics information";
   }
   rpc get-service-crtp-params-information {
     description "Show Compressed Real-Time Protocol information";
     input {
       leaf interface {
         description "Name of link services interface";
         type string;
       }
     }
   }
   rpc get-service-crtp-extensive-information {
     description "Show CRTP extensive output";
     input {
       leaf interface {
         description "Name of link services interface";
         type string;
       }
     }
   }
   rpc get-service-crtp-flow-table-information {
     description "Show CRTP flow table entries";
     input {
       leaf interface {
         description "Name of link services interface";
         type string;
       }
     }
   }
   rpc get-link-services-cpu-usage {
     description "Show cpu usage as a percentage for the specified PIC";
     input {
       leaf interface {
         description "Name of link services interface";
         type string;
         mandatory true;
       }
       leaf level {
         default "brief";
         type enumeration {
           enum "brief" {
             description "Display brief output (1 and 5 second average)";
           }
           enum "detail" {
             description "Display detailed output (per cpu average)";
           }
         }
       }
     }
   }
   rpc get-global-pcp-statistics-information {
     description "Show global PCP statistics";
     input {
       leaf interface {
         description "Name of adaptive services interface";
         type string;
       }
       leaf level {
         type enumeration {
           enum "protocol" {
             description "Display PCP protocol statistics";
           }
         }
       }
     }
   }
   rpc get-msp-ssubscriber-table {
     description "Show subscriber table entries";
   }
   rpc get-service-subscriber-analysis-information {
     description "Show service subscribers statistics";
     input {
       leaf interface {
         description "Name of extension provider interface";
         type string;
       }
     }
   }
   rpc get-tcp-log-connection-information {
     description "Show connections related to TCP logging";
     input {
       leaf interface {
         description "Name of extension provider interface";
         type string;
       }
     }
   }
   rpc get-services-redundancy-group-information {
     description "Show services redundancy-group information";
     input {
       leaf verbose {
         default "terse";
         type enumeration {
           enum "terse" {
             description "Display terse output(default)";
           }
           enum "brief" {
             description "Display brief output";
           }
           enum "extensive" {
             description "Display detailed output";
           }
         }
       }
     }
   }
   rpc get-services-redundancy-group-id-information {
     description "Show redundancy group-id information";
     input {
       leaf verbose {
         default "terse";
         type enumeration {
           enum "terse" {
             description "Display terse output(default)";
           }
           enum "brief" {
             description "Display brief output";
           }
           enum "extensive" {
             description "Display detailed output";
           }
         }
       }
       leaf id {
         description "Show redundancy group-id information";
         type union {
           type uint32;
           type string {
             pattern "<.*>|$.*";
           }
         }
         mandatory true;
       }
     }
   }
   rpc get-traffic-load-balance-statistics {
     description "Traffic load balance statistics";
     input {
       leaf verbose {
         type enumeration {
           enum "summary" {
             description "Display summary output";
           }
           enum "extensive" {
             description "Display extensive output";
           }
         }
       }
       leaf group {
         description "Group name";
         default "all";
         type string;
       }
       leaf instance {
         description "Instance name";
         default "all";
         type string;
       }
       leaf real-service {
         description "Real service name";
         default "all";
         type string;
       }
       leaf virtual-service {
         description "Virtual service name";
         default "all";
         type string;
       }
       leaf num-instances {
         description "Number of instances to be displayed";
         default "200";
         type union {
           type uint32;
           type string {
             pattern "<.*>|$.*";
           }
         }
       }
     }
   }
   rpc get-flb-statistics {
     description "FLB  statistics";
     input {
       leaf all {
         description "All flb instances";
         type empty;
       }
     }
   }
   rpc traffic-load-balance-commit-status {
     description "Display commit status";
   }
   rpc get-url-filter-statistics {
     description "Show web filter statistics";
     input {
       leaf profile {
         description "Web filter profile specific statistics";
         type string;
         mandatory true;
       }
       leaf url-filter-template {
         description "Url filter template specific statistics";
         type string;
       }
       leaf dns-filter-template {
         description "DNS filter template specific statistics";
         type string;
       }
       leaf dns-filter-term {
         description "DNS filter term specific statistics";
         type string;
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf level {
         default "brief";
         type enumeration {
           enum "brief" {
             description "Brief Information";
           }
           enum "detail" {
             description "Detailed Information";
           }
           enum "extensive" {
             description "Extensive Information";
           }
         }
       }
     }
   }
   rpc get-web-filter-dns-feed-statistics {
     description "Show web filter dns feed statistics";
     input {
       leaf feed-name {
         description "Web filter DNS feed  specific statistics";
         type string;
         mandatory true;
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
     }
   }
   rpc get-url-filter-dns-resolution {
     description "Show url-filter dns-resolution";
     input {
       leaf profile {
         description "Url-filter profile specific DNS resolution information";
         type string;
         mandatory true;
       }
       leaf url-filter-template {
         description "Url-filter template specific DNS resolution information";
         type string;
       }
     }
   }
   rpc get-url-filter-dns-resolution-statistics {
     description "Show url-filter dns-resolution statistics";
     input {
       leaf profile {
         description "Url-filter profile specific DNS resolution information";
         type string;
         mandatory true;
       }
       leaf url-filter-template {
         description "Url-filter template specific DNS resolution information";
         type string;
         mandatory true;
       }
       leaf verbosity_level {
         type enumeration {
           enum "summary" {
             description "Display summary output";
           }
           enum "extensive" {
             description "Display extensive output";
           }
         }
         mandatory true;
       }
     }
   }
   rpc get-url-filter-secintel-policy-status {
     description "Show secintel policy status";
     input {
       leaf profile {
         description "Url-filter profile specific secintel policy status";
         type string;
         mandatory true;
       }
       leaf url-filter-template {
         description "Url-filter template specific secintel policy status";
         type string;
       }
       leaf verbosity_level {
         type enumeration {
           enum "summary" {
             description "Display summary output";
           }
           enum "extensive" {
             description "Display extensive output";
           }
         }
       }
     }
   }
   rpc get-url-filter-secintel-policy-db {
     description "Web filtering secintel policy db";
     input {
       leaf ip-prefix-information {
         description "Web filtering secintel IP prefix information";
         type string;
         mandatory true;
       }
       leaf profile {
         description "Web filtering secintel profile IP prefix information";
         type string;
         mandatory true;
       }
       leaf template {
         description "Web filtering secintel template IP prefix information";
         type string;
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping ift-global-information-block {
     container ift-global {
       leaf device-id {
         type uint32;
         description "Unique device identifier";
       }
       leaf meta-data-stack-length {
         type uint32;
         description "Maximum length of the meta-data";
       }
       leaf hop-limit {
         type uint32;
         description "Maximum hop limit";
       }
       leaf flow-type {
         type string;
         description "Traffic flow type";
       }
       leaf no-ipv6-address-match {
         type uint32;
         description "IPV6 address match allowed or not";
       }
       leaf clock-source {
         type string;
         description "Clock source for timestamping";
       }
     }
   }
   grouping ift-profile-information-block {
     list ift-profile {
       leaf profile-name {
         type string;
         description "Profile name";
       }
       leaf sample-rate {
         type uint32;
         description "Ratio of packets to be sampled (1 out of N)";
       }
       container collector-info {
         leaf source-address {
           type string;
           description "Source address";
         }
         leaf destination-address {
           type string;
           description "Destination address";
         }
         leaf destination-port {
           type int32;
           description "Destination port";
         }
         leaf maximum-clip-length {
           type int32;
           description "Clip length of data packet";
         }
         leaf mtu {
           type int32;
           description "MTU of export packets";
         }
       }
     }
   }
   grouping ift-stats-information-block {
     container ift-stats {
       leaf init-packets {
         type uint64;
         description "IFA initator statistics";
       }
       leaf transit-packets {
         type uint64;
         description "IFA transit statistics";
       }
       leaf terminate-rx-packets {
         type uint64;
         description "IFA termination rx statistics";
       }
       leaf terminate-tx-packets {
         type uint64;
         description "IFA termination tx statistics";
       }
       leaf terminate-tx-records {
         type uint64;
         description "IFA termination tx records";
       }
     }
   }
   grouping pblq-summary-alltests-block {
     leaf active-test-count {
       type uint32;
       description "Number of active tests";
     }
     leaf completed-test-count {
       type uint32;
       description "Number of completed tests";
     }
     container active-test-list {
       leaf-list active-test {
         type string;
         description "Active test";
       }
     }
     container completed-test-list {
       leaf-list completed-test {
         type string;
         description "Completed test";
       }
     }
   }
   grouping pblq-capabilities-odl-block {
     leaf ntp-sync {
       type uint32;
       description "Device is NTP synced";
     }
     leaf max-res {
       type uint32;
       description "Max result stored per interface";
     }
   }
   grouping pblq-test-information-odl-block {
     leaf test-id {
       type string;
       description "Test Id";
     }
   }
   grouping history-results-block {
     list history-sample-results {
       leaf owner-name {
         type string;
         description "Test owner name";
       }
       leaf test-name {
         type string;
         description "Name of test";
       }
       leaf sample-tx-time {
         type string;
         description "Time at which probe was sent";
       }
       leaf sample-rx-time {
         type string;
         description "Time at which probe response was received or timed out";
       }
       leaf sample-status {
         type string;
         description "Operation response status from probe";
       }
       leaf rtt {
         type uint32;
         description "Round trip time of probe";
       }
       container generic-aggregate-results {
         list generic-aggregate-measurement {
           leaf measurement-type {
             type string;
             description "Type of value observed over measurement";
           }
           leaf measurement-samples {
             type uint32;
             description "Number of measurement samples";
           }
           leaf measurement-min {
             type uint32;
             description "Minimum over measurement samples";
           }
           leaf measurement-max {
             type uint32;
             description "Maximum over measurement samples";
           }
           leaf measurement-avg {
             type uint32;
             description "Average over measurement samples";
           }
           leaf measurement-stddev {
             type uint32;
             description "Standard deviation over measurement samples";
           }
         }
         leaf aggregate-type {
           type string;
           description "Scope of aggregate results";
         }
         leaf num-samples-tx {
           type uint32;
           description "Number of probes sent";
         }
         leaf num-samples-rx {
           type uint32;
           description "Number of probes received";
         }
         leaf loss-egress {
           type uint32;
           description "Number of probes lost before reflection";
         }
         leaf loss-percentage {
           type string;
           description "Percentage of probes lost (no response)";
         }
       }
       container internal-sample-results {
         container internal-sample-software-results {
           leaf tx-utime {
             type string;
             description "Time at which probe was sent in user space";
           }
           leaf rx-utime {
             type string;
             description "Time at which probe was received in user space";
           }
           leaf rx-ktime {
             type string;
             description "Time at which probe was received by kernel";
           }
         }
         container internal-sample-protocol-results {
           leaf protocol-status {
             type string;
             description "Probe protocol embedded timestamps support";
           }
           leaf protocol-client-egress {
             type string;
             description "Protocol provided client egress time";
           }
           leaf protocol-server-ingress {
             type string;
             description "Protocol provided server ingress time";
           }
           leaf protocol-server-egress {
             type string;
             description "Protocol provided server egress time";
           }
         }
         container internal-sample-offload-results {
           leaf offload-status {
             type string;
             description "Use of offload timestamps in probes";
           }
           leaf offload-client-egress {
             type string;
             description "Offload provided client egress time";
           }
           leaf offload-server-ingress {
             type string;
             description "Offload provided server ingress time";
           }
           leaf offload-server-egress {
             type string;
             description "Offload provided server egress time";
           }
           leaf offload-client-ingress {
             type string;
             description "Offload provided client ingress time";
           }
         }
         leaf internal-tbase {
           type string;
           description "Base probe time other timstamps are offset against";
         }
         leaf internal-t1 {
           type string;
           description "Selected most accurate client egress time";
         }
         leaf internal-t2 {
           type string;
           description "Selected most accurate server ingress time";
         }
         leaf internal-t3 {
           type string;
           description "Selected most accurate server egress time";
         }
         leaf internal-t4 {
           type string;
           description "Selected most accurate client ingress time";
         }
         leaf rtt {
           type uint32;
           description "Round trip time of probe";
         }
         leaf rtt-jitter {
           type uint32;
           description "Round trip jitter of probes";
         }
         leaf egress {
           type uint32;
           description "Egress delay of probe";
         }
         leaf egress-jitter {
           type uint32;
           description "Egress delay jitter of probes";
         }
         leaf ingress {
           type uint32;
           description "Ingress delay of probe";
         }
         leaf ingress-jitter {
           type uint32;
           description "Ingress delay jitter of probes";
         }
       }
       leaf test-type {
         type string;
         description "Type of the probe";
       }
       container generic-sample-results {
         leaf sample-status {
           type string;
           description "Operation response status from probe";
         }
         leaf sample-tx-time {
           type string;
           description "Time at which probe was sent";
         }
         leaf sample-rx-time {
           type string;
           description "Time at which probe response was received or timed out";
         }
         leaf offload-status {
           type string;
           description "Use of offload timestamps in probes";
         }
         leaf rtt {
           type uint32;
           description "Round trip time of probe";
         }
         leaf rtt-jitter {
           type uint32;
           description "Round trip jitter of probes";
         }
         leaf egress-jitter {
           type uint32;
           description "Egress delay jitter of probes";
         }
         leaf ingress-jitter {
           type uint32;
           description "Ingress delay jitter of probes";
         }
       }
       leaf sample-score-status {
         type string;
         description "Scoring status from probe";
       }
     }
   }
   grouping probe-results-block {
     list probe-test-results {
       leaf owner-name {
         type string;
         description "Test owner name";
       }
       leaf test-name {
         type string;
         description "Name of test";
       }
       leaf target-address {
         type string;
         description "Target address of test";
       }
       leaf source-address {
         type string;
         description "Source address of test";
       }
       leaf test-type {
         type string;
         description "Type of the probe";
       }
       leaf test-size {
         type uint32;
         description "Number of probes in test";
       }
       container generic-sample-results {
         leaf sample-status {
           type string;
           description "Operation response status from probe";
         }
         leaf sample-tx-time {
           type string;
           description "Time at which probe was sent";
         }
         leaf sample-rx-time {
           type string;
           description "Time at which probe response was received or timed out";
         }
         leaf offload-status {
           type string;
           description "Use of offload timestamps in probes";
         }
         leaf rtt {
           type uint32;
           description "Round trip time of probe";
         }
         leaf rtt-jitter {
           type uint32;
           description "Round trip jitter of probes";
         }
         leaf egress-jitter {
           type uint32;
           description "Egress delay jitter of probes";
         }
         leaf ingress-jitter {
           type uint32;
           description "Ingress delay jitter of probes";
         }
       }
       container generic-aggregate-results {
         leaf aggregate-type {
           type string;
           description "Scope of aggregate results";
         }
         leaf num-samples-tx {
           type uint32;
           description "Number of probes sent";
         }
         leaf num-samples-rx {
           type uint32;
           description "Number of probes received";
         }
         leaf loss-egress {
           type uint32;
           description "Number of probes lost before reflection";
         }
         leaf loss-percentage {
           type string;
           description "Percentage of probes lost (no response)";
         }
         list generic-aggregate-measurement {
           leaf measurement-type {
             type string;
             description "Type of value observed over measurement";
           }
           leaf measurement-samples {
             type uint32;
             description "Number of measurement samples";
           }
           leaf measurement-min {
             type uint32;
             description "Minimum over measurement samples";
           }
           leaf measurement-max {
             type uint32;
             description "Maximum over measurement samples";
           }
           leaf measurement-avg {
             type uint32;
             description "Average over measurement samples";
           }
           leaf measurement-stddev {
             type uint32;
             description "Standard deviation over measurement samples";
           }
         }
       }
     }
   }
   grouping twamp-control-info-block {
     list twamp-control-connection {
       leaf twamp-control-name {
         type string;
         description "Control connection name";
       }
       leaf twamp-client-address {
         type string;
         description "Client IP address";
       }
       leaf twamp-client-port {
         type uint32;
         description "Client UDP/TCP port";
       }
       leaf twamp-server-address {
         type string;
         description "Server IP address";
       }
       leaf twamp-server-port {
         type uint32;
         description "Server UDP/TCP port";
       }
       leaf twamp-active-tests {
         type uint32;
         description "Active tests count";
       }
       leaf twamp-control-status {
         type string;
         description "Control connection status";
       }
       leaf twamp-authentication-mode {
         type string;
         description "Authentication mode";
       }
     }
   }
   grouping twamp-test-info-block {
     list twamp-test-session {
       leaf twamp-control-name {
         type string;
         description "Control connection name";
       }
       leaf twamp-test-name {
         type string;
         description "Test session name";
       }
       leaf twamp-client-address {
         type string;
         description "Client IP address";
       }
       leaf twamp-client-port {
         type uint32;
         description "Client UDP/TCP port";
       }
       leaf twamp-server-address {
         type string;
         description "Server IP address";
       }
       leaf twamp-server-port {
         type uint32;
         description "Server UDP/TCP port";
       }
       leaf twamp-test-status {
         type string;
         description "Test session status";
       }
     }
   }
   grouping rfc2544-test-id-information-block {
     list test-list-item {
       container test-item-header {
         leaf test-id {
           type uint32;
           description "Test id";
         }
         leaf test-name {
           type string;
           description "Test name";
         }
       }
       container test-brief-summary {
         leaf test-mode {
           type string;
           description "Test mode";
         }
         leaf test-family {
           type string;
           description "Test family";
         }
         leaf test-state {
           type string;
           description "Current state of the test";
         }
         leaf test-status {
           type string;
           description "Status";
         }
         leaf test-status-desc {
           type string;
           description "Status description";
         }
         leaf test-start-time {
           type string;
           description "Test start time";
         }
         leaf test-stop-time {
           type string;
           description "Test finish time";
         }
         leaf test-clear-counters-time {
           type string;
           description "Counters last cleared";
         }
       }
       container test-inet-config {
         leaf rtt-name {
           type string;
           description "Routing Instance Name";
         }
         leaf test-interface {
           type string;
           description "Interface ";
         }
         leaf dest-ipv4-addr {
           type string;
           description "Destination IPv4 address";
         }
         leaf dest-udp-port {
           type uint32;
           description "Destination UDP port";
         }
         leaf src-ipv4-addr {
           type string;
           description "Source IPv4 address";
         }
         leaf src-udp-port {
           type uint32;
           description "Source UDP port";
         }
         leaf disable-signature-check {
           type string;
           description "Disable signature check";
         }
       }
       container test-ccc-config {
         leaf rtt-name {
           type string;
           description "Routing Instance Name";
         }
         leaf test-interface {
           type string;
           description "Interface ";
         }
         leaf test-direction {
           type string;
           description "Test direction";
         }
         leaf test-reflect-mode {
           type string;
           description "Reflect mode";
         }
         leaf dest-mac-addr {
           type string;
           description "Destination MAC address";
         }
         leaf src-mac-addr {
           type string;
           description "Source MAC address";
         }
         leaf test-reflect-etype {
           type uint32;
           description "Reflect EType";
         }
         leaf disable-signature-check {
           type string;
           description "Disable signature check";
         }
       }
       container test-bridge-config {
         leaf rtt-name {
           type string;
           description "Routing Instance Name";
         }
         leaf test-interface {
           type string;
           description "Interface ";
         }
         leaf test-direction {
           type string;
           description "Test direction";
         }
         leaf test-service-type {
           type string;
           description "Service type";
         }
         leaf test-reflect-mode {
           type string;
           description "Reflect mode";
         }
         leaf dest-mac-addr {
           type string;
           description "Destination MAC address";
         }
         leaf src-mac-addr {
           type string;
           description "Source MAC address";
         }
         leaf test-reflect-etype {
           type uint32;
           description "Reflect EType";
         }
         leaf test-in-service {
           type string;
           description "In service";
         }
         leaf test-ip-swap {
           type string;
           description "IP address swap";
         }
         leaf test-udp-port-swap {
           type string;
           description "UDP port swap";
         }
         leaf disable-signature-check {
           type string;
           description "Disable signature check";
         }
       }
       container test-reflector-stats {
         leaf test-elapsed-time {
           type uint32;
           description "Elapsed-time in seconds";
         }
         leaf test-reflected-pkt-count {
           type uint64;
           description "Reflected packet count";
         }
         leaf test-reflected-byte-count {
           type uint64;
           description "Reflected byte count";
         }
       }
       list test-generator-profile {
         leaf generator-profile-name {
           type string;
           description "Profile name of Generator";
         }
         leaf generator-bandwidth {
           type uint32;
           description "Bandwidth to be tested with traffic generator";
         }
         leaf generator-test-type {
           type string;
           description "Generator Test type";
         }
       }
       list test-generator-config {
         leaf test-name {
           type string;
           description "Test name";
         }
         leaf test-mode {
           type string;
           description "Test mode";
         }
         leaf test-family {
           type string;
           description "Test family";
         }
         leaf iterator-duration {
           type uint32;
           description "Duration of initiating iterator";
         }
       }
       container test-generator-results {
         container generator-throughput-test-data {
           description "Throughput Generator test results";
           container generator-throughput-header {
             description "Throughput generator header";
             leaf initial-test-load {
               type string;
               description "Initial test load";
             }
             leaf iteration-mode {
               type string;
               description "Iteration mode";
             }
             leaf iteration-step {
               type string;
               description "Iteration step";
             }
             leaf bandwidth-str {
               type string;
               description "Bandwidth string";
             }
           }
           list generator-throughput-test-results {
             description "Results..";
             leaf test-pkt-size {
               type uint32;
               description "Test Packet size of stream";
             }
             list result-entry {
               description "Throughput Generator test iterator results";
               container gen-result-entry {
                 leaf iterator-num {
                   type uint32;
                   description "Test Iterator number";
                 }
                 leaf duration {
                   type uint32;
                   description "Test Iterator duration";
                 }
                 leaf it-pps {
                   type uint32;
                   description "Packets per seconds";
                 }
                 leaf tx-packets {
                   type uint32;
                   description "Transmitted packets";
                 }
                 leaf tx-bytes {
                   type uint32;
                   description "Transmitted bytes";
                 }
                 leaf rx-packets {
                   type uint32;
                   description "Received packets";
                 }
                 leaf rx-bytes {
                   type uint32;
                   description "Received bytes";
                 }
                 leaf it-measured-percent {
                   type string;
                   description "Percentage throughput achieved";
                 }
                 leaf bandwidth {
                   type uint32;
                   description "Test bandwidth";
                 }
               }
             }
           }
           container generator-tput-test-summary {
             description "Throughput Generator test result summary";
             list generator-tput-test-summary-results {
               description "Throughput Result summary..";
               list tput-summary-entry {
                 description "Throughput Generator test results summary";
                 container tput-gen-summary-entry {
                   leaf test-pkt-size {
                     type uint32;
                     description "Test Packet size of stream";
                   }
                   leaf duration {
                     type uint32;
                     description "Test Iterator duration";
                   }
                   leaf tx-packets {
                     type uint32;
                     description "Transmitted packets";
                   }
                   leaf rx-packets {
                     type uint32;
                     description "Received packets";
                   }
                   leaf it-measured-percent {
                     type string;
                     description "Percentage throughput achieved";
                   }
                   leaf bandwidth {
                     type uint32;
                     description "Test bandwidth";
                   }
                   leaf tx-bytes {
                     type uint32;
                     description "Transmitted bytes";
                   }
                   leaf rx-bytes {
                     type uint32;
                     description "Received bytes";
                   }
                 }
               }
             }
           }
         }
         container generator-latency-test-data {
           description "Latency Generator test results";
           container generator-latency-header {
             description "Latency generator header";
             leaf initial-test-load {
               type string;
               description "Initial test load";
             }
             leaf bandwidth-str {
               type string;
               description "Bandwidth string";
             }
           }
           list generator-latency-test-results {
             description "Latency Results..";
             leaf test-pkt-size {
               type uint32;
               description "Test Packet size of stream";
             }
             list latency-result-entry {
               description "Latency Generator test iterator results";
               container latency-gen-result-entry {
                 leaf iterator-num {
                   type uint32;
                   description "Test Iterator number";
                 }
                 leaf duration {
                   type uint32;
                   description "Test Iterator duration";
                 }
                 leaf it-pps {
                   type uint32;
                   description "Packets per seconds";
                 }
                 leaf tx-packets {
                   type uint32;
                   description "Transmitted packets";
                 }
                 leaf tx-bytes {
                   type uint32;
                   description "Transmitted bytes";
                 }
                 leaf rx-packets {
                   type uint32;
                   description "Received packets";
                 }
                 leaf rx-bytes {
                   type uint32;
                   description "Received bytes";
                 }
                 leaf latency {
                   type uint32;
                   description "Latency of received packet in usec ";
                 }
                 leaf bandwidth {
                   type uint32;
                   description "Test bandwidth";
                 }
               }
             }
           }
           container generator-latency-test-summary {
             description "Generator latency test summary";
             list generator-latency-test-summary-results {
               description "Result summary..";
               leaf test-pkt-size {
                 type uint32;
                 description "Test Packet size of stream";
               }
               list latency-summary-entry {
                 description "Generator latency test results summary";
                 container latency-gen-summary-entry {
                   leaf test-pkt-size {
                     type uint32;
                     description "Test Packet size of stream";
                   }
                   leaf latency {
                     type uint32;
                     description "Latency of received packet in usec ";
                   }
                   leaf bandwidth {
                     type uint32;
                     description "Test bandwidth";
                   }
                 }
               }
             }
           }
         }
         container generator-frameloss-test-data {
           description "FrameLoss Generator test results";
           container generator-frameloss-header {
             description "FrameLoss generator header";
             leaf initial-test-load {
               type string;
               description "Initial test load";
             }
             leaf iteration-mode {
               type string;
               description "Iteration mode";
             }
             leaf iteration-step {
               type string;
               description "Iteration step";
             }
             leaf bandwidth-str {
               type string;
               description "Bandwidth string";
             }
           }
           list generator-frameloss-test-results {
             description "FrameLoss Results..";
             leaf test-pkt-size {
               type uint32;
               description "Test Packet size of stream";
             }
             list frameloss-result-entry {
               description "Frameloss Generator test iterator results";
               container frameloss-gen-result-entry {
                 leaf iterator-num {
                   type uint32;
                   description "Test Iterator number";
                 }
                 leaf duration {
                   type uint32;
                   description "Test Iterator duration";
                 }
                 leaf it-pps {
                   type uint32;
                   description "Packets per seconds";
                 }
                 leaf tx-packets {
                   type uint32;
                   description "Transmitted packets";
                 }
                 leaf tx-bytes {
                   type uint32;
                   description "Transmitted bytes";
                 }
                 leaf rx-packets {
                   type uint32;
                   description "Received packets";
                 }
                 leaf rx-bytes {
                   type uint32;
                   description "Received bytes";
                 }
                 leaf frameloss {
                   type uint32;
                   description "Frameloss";
                 }
                 leaf bandwidth {
                   type uint32;
                   description "Test bandwidth";
                 }
               }
             }
           }
           container generator-frameloss-test-summary {
             description "Generator Frameloss test summary";
             list generator-frameloss-test-summary-results {
               description "Result summary..";
               leaf test-pkt-size {
                 type uint32;
                 description "Test Packet size of stream";
               }
               list frameloss-summary-entry {
                 description "Generator Frameloss test results summary";
                 container frameloss-gen-summary-entry {
                   leaf test-pkt-size {
                     type uint32;
                     description "Test Packet size of stream";
                   }
                   leaf duration {
                     type uint32;
                     description "Test Iterator duration";
                   }
                   leaf tx-packets {
                     type uint32;
                     description "Transmitted packets";
                   }
                   leaf rx-packets {
                     type uint32;
                     description "Received packets";
                   }
                   leaf frameloss {
                     type uint32;
                     description "Frameloss";
                   }
                   leaf bandwidth {
                     type uint32;
                     description "Test bandwidth";
                   }
                   leaf tx-bytes {
                     type uint32;
                     description "Transmitted bytes";
                   }
                   leaf rx-bytes {
                     type uint32;
                     description "Received bytes";
                   }
                 }
               }
             }
           }
         }
         container generator-back2back-test-data {
           description "Back To Back Frames Generator test results";
           container generator-back2back-header {
             description "Back To Back Frames generator header";
             leaf initial-test-load {
               type string;
               description "Initial test load";
             }
             leaf iteration-mode {
               type string;
               description "Iteration mode";
             }
             leaf iteration-step {
               type string;
               description "Iteration step";
             }
             leaf bandwidth-str {
               type string;
               description "Bandwidth string";
             }
           }
           list generator-back2back-test-results {
             description "Results..";
             leaf test-pkt-size {
               type uint32;
               description "Test Packet size of stream";
             }
             list back2back-result-entry {
               description "Back-to-Back Frames Generator test iterator results";
               container back2back-gen-result-entry {
                 leaf iterator-num {
                   type uint32;
                   description "Test Iterator number";
                 }
                 leaf duration {
                   type uint32;
                   description "Test Iterator duration";
                 }
                 leaf burst-length {
                   type uint32;
                   description "Burst length";
                 }
                 leaf tx-packets {
                   type uint32;
                   description "Transmitted packets";
                 }
                 leaf tx-bytes {
                   type uint32;
                   description "Transmitted bytes";
                 }
                 leaf rx-packets {
                   type uint32;
                   description "Received packets";
                 }
                 leaf rx-bytes {
                   type uint32;
                   description "Received bytes";
                 }
               }
             }
           }
           container generator-back2back-test-summary {
             description "Generator back2back test summary";
             list generator-back2back-test-summary-results {
               description "Result summary..";
               leaf test-pkt-size {
                 type uint32;
                 description "Test Packet size of stream";
               }
               list back2back-summary-entry {
                 description "Generator back2back test results summary";
                 container back2back-gen-summary-entry {
                   leaf test-pkt-size {
                     type uint32;
                     description "Test Packet size of stream";
                   }
                   leaf burst-length {
                     type uint32;
                     description "Burst length";
                   }
                   leaf duration {
                     type uint32;
                     description "Test Iterator duration";
                   }
                   leaf theoretical-bandwidth {
                     type string;
                     description "Bandwidth string";
                   }
                   leaf bandwidth {
                     type uint32;
                     description "Test bandwidth";
                   }
                 }
               }
             }
           }
         }
       }
     }
   }
   grouping rfc2544-active-tests-information-block {
     leaf test-list-header {
       type string;
     }
     list test-list-item {
       container test-item-header {
         leaf test-id {
           type uint32;
           description "Test id";
         }
         leaf test-name {
           type string;
           description "Test name";
         }
       }
       container test-brief-summary {
         leaf test-mode {
           type string;
           description "Test mode";
         }
         leaf test-family {
           type string;
           description "Test family";
         }
         leaf test-state {
           type string;
           description "Current state of the test";
         }
         leaf test-status {
           type string;
           description "Status";
         }
         leaf test-status-desc {
           type string;
           description "Status description";
         }
         leaf test-start-time {
           type string;
           description "Test start time";
         }
         leaf test-stop-time {
           type string;
           description "Test finish time";
         }
         leaf test-clear-counters-time {
           type string;
           description "Counters last cleared";
         }
       }
       container test-inet-config {
         leaf rtt-name {
           type string;
           description "Routing Instance Name";
         }
         leaf test-interface {
           type string;
           description "Interface ";
         }
         leaf dest-ipv4-addr {
           type string;
           description "Destination IPv4 address";
         }
         leaf dest-udp-port {
           type uint32;
           description "Destination UDP port";
         }
         leaf src-ipv4-addr {
           type string;
           description "Source IPv4 address";
         }
         leaf src-udp-port {
           type uint32;
           description "Source UDP port";
         }
         leaf disable-signature-check {
           type string;
           description "Disable signature check";
         }
       }
       container test-ccc-config {
         leaf rtt-name {
           type string;
           description "Routing Instance Name";
         }
         leaf test-interface {
           type string;
           description "Interface ";
         }
         leaf test-direction {
           type string;
           description "Test direction";
         }
         leaf test-reflect-mode {
           type string;
           description "Reflect mode";
         }
         leaf dest-mac-addr {
           type string;
           description "Destination MAC address";
         }
         leaf src-mac-addr {
           type string;
           description "Source MAC address";
         }
         leaf test-reflect-etype {
           type uint32;
           description "Reflect EType";
         }
         leaf disable-signature-check {
           type string;
           description "Disable signature check";
         }
       }
       container test-bridge-config {
         leaf rtt-name {
           type string;
           description "Routing Instance Name";
         }
         leaf test-interface {
           type string;
           description "Interface ";
         }
         leaf test-direction {
           type string;
           description "Test direction";
         }
         leaf test-service-type {
           type string;
           description "Service type";
         }
         leaf test-reflect-mode {
           type string;
           description "Reflect mode";
         }
         leaf dest-mac-addr {
           type string;
           description "Destination MAC address";
         }
         leaf src-mac-addr {
           type string;
           description "Source MAC address";
         }
         leaf test-reflect-etype {
           type uint32;
           description "Reflect EType";
         }
         leaf test-in-service {
           type string;
           description "In service";
         }
         leaf test-ip-swap {
           type string;
           description "IP address swap";
         }
         leaf test-udp-port-swap {
           type string;
           description "UDP port swap";
         }
         leaf disable-signature-check {
           type string;
           description "Disable signature check";
         }
       }
       container test-reflector-stats {
         leaf test-elapsed-time {
           type uint32;
           description "Elapsed-time in seconds";
         }
         leaf test-reflected-pkt-count {
           type uint64;
           description "Reflected packet count";
         }
         leaf test-reflected-byte-count {
           type uint64;
           description "Reflected byte count";
         }
       }
       list test-generator-profile {
         leaf generator-profile-name {
           type string;
           description "Profile name of Generator";
         }
         leaf generator-bandwidth {
           type uint32;
           description "Bandwidth to be tested with traffic generator";
         }
         leaf generator-test-type {
           type string;
           description "Generator Test type";
         }
       }
       list test-generator-config {
         leaf test-name {
           type string;
           description "Test name";
         }
         leaf test-mode {
           type string;
           description "Test mode";
         }
         leaf test-family {
           type string;
           description "Test family";
         }
         leaf iterator-duration {
           type uint32;
           description "Duration of initiating iterator";
         }
       }
       container test-generator-results {
         container generator-throughput-test-data {
           description "Throughput Generator test results";
           container generator-throughput-header {
             description "Throughput generator header";
             leaf initial-test-load {
               type string;
               description "Initial test load";
             }
             leaf iteration-mode {
               type string;
               description "Iteration mode";
             }
             leaf iteration-step {
               type string;
               description "Iteration step";
             }
             leaf bandwidth-str {
               type string;
               description "Bandwidth string";
             }
           }
           list generator-throughput-test-results {
             description "Results..";
             leaf test-pkt-size {
               type uint32;
               description "Test Packet size of stream";
             }
             list result-entry {
               description "Throughput Generator test iterator results";
               container gen-result-entry {
                 leaf iterator-num {
                   type uint32;
                   description "Test Iterator number";
                 }
                 leaf duration {
                   type uint32;
                   description "Test Iterator duration";
                 }
                 leaf it-pps {
                   type uint32;
                   description "Packets per seconds";
                 }
                 leaf tx-packets {
                   type uint32;
                   description "Transmitted packets";
                 }
                 leaf tx-bytes {
                   type uint32;
                   description "Transmitted bytes";
                 }
                 leaf rx-packets {
                   type uint32;
                   description "Received packets";
                 }
                 leaf rx-bytes {
                   type uint32;
                   description "Received bytes";
                 }
                 leaf it-measured-percent {
                   type string;
                   description "Percentage throughput achieved";
                 }
                 leaf bandwidth {
                   type uint32;
                   description "Test bandwidth";
                 }
               }
             }
           }
           container generator-tput-test-summary {
             description "Throughput Generator test result summary";
             list generator-tput-test-summary-results {
               description "Throughput Result summary..";
               list tput-summary-entry {
                 description "Throughput Generator test results summary";
                 container tput-gen-summary-entry {
                   leaf test-pkt-size {
                     type uint32;
                     description "Test Packet size of stream";
                   }
                   leaf duration {
                     type uint32;
                     description "Test Iterator duration";
                   }
                   leaf tx-packets {
                     type uint32;
                     description "Transmitted packets";
                   }
                   leaf rx-packets {
                     type uint32;
                     description "Received packets";
                   }
                   leaf it-measured-percent {
                     type string;
                     description "Percentage throughput achieved";
                   }
                   leaf bandwidth {
                     type uint32;
                     description "Test bandwidth";
                   }
                   leaf tx-bytes {
                     type uint32;
                     description "Transmitted bytes";
                   }
                   leaf rx-bytes {
                     type uint32;
                     description "Received bytes";
                   }
                 }
               }
             }
           }
         }
         container generator-latency-test-data {
           description "Latency Generator test results";
           container generator-latency-header {
             description "Latency generator header";
             leaf initial-test-load {
               type string;
               description "Initial test load";
             }
             leaf bandwidth-str {
               type string;
               description "Bandwidth string";
             }
           }
           list generator-latency-test-results {
             description "Latency Results..";
             leaf test-pkt-size {
               type uint32;
               description "Test Packet size of stream";
             }
             list latency-result-entry {
               description "Latency Generator test iterator results";
               container latency-gen-result-entry {
                 leaf iterator-num {
                   type uint32;
                   description "Test Iterator number";
                 }
                 leaf duration {
                   type uint32;
                   description "Test Iterator duration";
                 }
                 leaf it-pps {
                   type uint32;
                   description "Packets per seconds";
                 }
                 leaf tx-packets {
                   type uint32;
                   description "Transmitted packets";
                 }
                 leaf tx-bytes {
                   type uint32;
                   description "Transmitted bytes";
                 }
                 leaf rx-packets {
                   type uint32;
                   description "Received packets";
                 }
                 leaf rx-bytes {
                   type uint32;
                   description "Received bytes";
                 }
                 leaf latency {
                   type uint32;
                   description "Latency of received packet in usec ";
                 }
                 leaf bandwidth {
                   type uint32;
                   description "Test bandwidth";
                 }
               }
             }
           }
           container generator-latency-test-summary {
             description "Generator latency test summary";
             list generator-latency-test-summary-results {
               description "Result summary..";
               leaf test-pkt-size {
                 type uint32;
                 description "Test Packet size of stream";
               }
               list latency-summary-entry {
                 description "Generator latency test results summary";
                 container latency-gen-summary-entry {
                   leaf test-pkt-size {
                     type uint32;
                     description "Test Packet size of stream";
                   }
                   leaf latency {
                     type uint32;
                     description "Latency of received packet in usec ";
                   }
                   leaf bandwidth {
                     type uint32;
                     description "Test bandwidth";
                   }
                 }
               }
             }
           }
         }
         container generator-frameloss-test-data {
           description "FrameLoss Generator test results";
           container generator-frameloss-header {
             description "FrameLoss generator header";
             leaf initial-test-load {
               type string;
               description "Initial test load";
             }
             leaf iteration-mode {
               type string;
               description "Iteration mode";
             }
             leaf iteration-step {
               type string;
               description "Iteration step";
             }
             leaf bandwidth-str {
               type string;
               description "Bandwidth string";
             }
           }
           list generator-frameloss-test-results {
             description "FrameLoss Results..";
             leaf test-pkt-size {
               type uint32;
               description "Test Packet size of stream";
             }
             list frameloss-result-entry {
               description "Frameloss Generator test iterator results";
               container frameloss-gen-result-entry {
                 leaf iterator-num {
                   type uint32;
                   description "Test Iterator number";
                 }
                 leaf duration {
                   type uint32;
                   description "Test Iterator duration";
                 }
                 leaf it-pps {
                   type uint32;
                   description "Packets per seconds";
                 }
                 leaf tx-packets {
                   type uint32;
                   description "Transmitted packets";
                 }
                 leaf tx-bytes {
                   type uint32;
                   description "Transmitted bytes";
                 }
                 leaf rx-packets {
                   type uint32;
                   description "Received packets";
                 }
                 leaf rx-bytes {
                   type uint32;
                   description "Received bytes";
                 }
                 leaf frameloss {
                   type uint32;
                   description "Frameloss";
                 }
                 leaf bandwidth {
                   type uint32;
                   description "Test bandwidth";
                 }
               }
             }
           }
           container generator-frameloss-test-summary {
             description "Generator Frameloss test summary";
             list generator-frameloss-test-summary-results {
               description "Result summary..";
               leaf test-pkt-size {
                 type uint32;
                 description "Test Packet size of stream";
               }
               list frameloss-summary-entry {
                 description "Generator Frameloss test results summary";
                 container frameloss-gen-summary-entry {
                   leaf test-pkt-size {
                     type uint32;
                     description "Test Packet size of stream";
                   }
                   leaf duration {
                     type uint32;
                     description "Test Iterator duration";
                   }
                   leaf tx-packets {
                     type uint32;
                     description "Transmitted packets";
                   }
                   leaf rx-packets {
                     type uint32;
                     description "Received packets";
                   }
                   leaf frameloss {
                     type uint32;
                     description "Frameloss";
                   }
                   leaf bandwidth {
                     type uint32;
                     description "Test bandwidth";
                   }
                   leaf tx-bytes {
                     type uint32;
                     description "Transmitted bytes";
                   }
                   leaf rx-bytes {
                     type uint32;
                     description "Received bytes";
                   }
                 }
               }
             }
           }
         }
         container generator-back2back-test-data {
           description "Back To Back Frames Generator test results";
           container generator-back2back-header {
             description "Back To Back Frames generator header";
             leaf initial-test-load {
               type string;
               description "Initial test load";
             }
             leaf iteration-mode {
               type string;
               description "Iteration mode";
             }
             leaf iteration-step {
               type string;
               description "Iteration step";
             }
             leaf bandwidth-str {
               type string;
               description "Bandwidth string";
             }
           }
           list generator-back2back-test-results {
             description "Results..";
             leaf test-pkt-size {
               type uint32;
               description "Test Packet size of stream";
             }
             list back2back-result-entry {
               description "Back-to-Back Frames Generator test iterator results";
               container back2back-gen-result-entry {
                 leaf iterator-num {
                   type uint32;
                   description "Test Iterator number";
                 }
                 leaf duration {
                   type uint32;
                   description "Test Iterator duration";
                 }
                 leaf burst-length {
                   type uint32;
                   description "Burst length";
                 }
                 leaf tx-packets {
                   type uint32;
                   description "Transmitted packets";
                 }
                 leaf tx-bytes {
                   type uint32;
                   description "Transmitted bytes";
                 }
                 leaf rx-packets {
                   type uint32;
                   description "Received packets";
                 }
                 leaf rx-bytes {
                   type uint32;
                   description "Received bytes";
                 }
               }
             }
           }
           container generator-back2back-test-summary {
             description "Generator back2back test summary";
             list generator-back2back-test-summary-results {
               description "Result summary..";
               leaf test-pkt-size {
                 type uint32;
                 description "Test Packet size of stream";
               }
               list back2back-summary-entry {
                 description "Generator back2back test results summary";
                 container back2back-gen-summary-entry {
                   leaf test-pkt-size {
                     type uint32;
                     description "Test Packet size of stream";
                   }
                   leaf burst-length {
                     type uint32;
                     description "Burst length";
                   }
                   leaf duration {
                     type uint32;
                     description "Test Iterator duration";
                   }
                   leaf theoretical-bandwidth {
                     type string;
                     description "Bandwidth string";
                   }
                   leaf bandwidth {
                     type uint32;
                     description "Test bandwidth";
                   }
                 }
               }
             }
           }
         }
       }
     }
   }
   grouping rfc2544-terminated-tests-information-block {
     leaf test-list-header {
       type string;
     }
     list test-list-item {
       container test-item-header {
         leaf test-id {
           type uint32;
           description "Test id";
         }
         leaf test-name {
           type string;
           description "Test name";
         }
       }
       container test-brief-summary {
         leaf test-mode {
           type string;
           description "Test mode";
         }
         leaf test-family {
           type string;
           description "Test family";
         }
         leaf test-state {
           type string;
           description "Current state of the test";
         }
         leaf test-status {
           type string;
           description "Status";
         }
         leaf test-status-desc {
           type string;
           description "Status description";
         }
         leaf test-start-time {
           type string;
           description "Test start time";
         }
         leaf test-stop-time {
           type string;
           description "Test finish time";
         }
         leaf test-clear-counters-time {
           type string;
           description "Counters last cleared";
         }
       }
       container test-inet-config {
         leaf rtt-name {
           type string;
           description "Routing Instance Name";
         }
         leaf test-interface {
           type string;
           description "Interface ";
         }
         leaf dest-ipv4-addr {
           type string;
           description "Destination IPv4 address";
         }
         leaf dest-udp-port {
           type uint32;
           description "Destination UDP port";
         }
         leaf src-ipv4-addr {
           type string;
           description "Source IPv4 address";
         }
         leaf src-udp-port {
           type uint32;
           description "Source UDP port";
         }
         leaf disable-signature-check {
           type string;
           description "Disable signature check";
         }
       }
       container test-ccc-config {
         leaf rtt-name {
           type string;
           description "Routing Instance Name";
         }
         leaf test-interface {
           type string;
           description "Interface ";
         }
         leaf test-direction {
           type string;
           description "Test direction";
         }
         leaf test-reflect-mode {
           type string;
           description "Reflect mode";
         }
         leaf dest-mac-addr {
           type string;
           description "Destination MAC address";
         }
         leaf src-mac-addr {
           type string;
           description "Source MAC address";
         }
         leaf test-reflect-etype {
           type uint32;
           description "Reflect EType";
         }
         leaf disable-signature-check {
           type string;
           description "Disable signature check";
         }
       }
       container test-bridge-config {
         leaf rtt-name {
           type string;
           description "Routing Instance Name";
         }
         leaf test-interface {
           type string;
           description "Interface ";
         }
         leaf test-direction {
           type string;
           description "Test direction";
         }
         leaf test-service-type {
           type string;
           description "Service type";
         }
         leaf test-reflect-mode {
           type string;
           description "Reflect mode";
         }
         leaf dest-mac-addr {
           type string;
           description "Destination MAC address";
         }
         leaf src-mac-addr {
           type string;
           description "Source MAC address";
         }
         leaf test-reflect-etype {
           type uint32;
           description "Reflect EType";
         }
         leaf test-in-service {
           type string;
           description "In service";
         }
         leaf test-ip-swap {
           type string;
           description "IP address swap";
         }
         leaf test-udp-port-swap {
           type string;
           description "UDP port swap";
         }
         leaf disable-signature-check {
           type string;
           description "Disable signature check";
         }
       }
       container test-reflector-stats {
         leaf test-elapsed-time {
           type uint32;
           description "Elapsed-time in seconds";
         }
         leaf test-reflected-pkt-count {
           type uint64;
           description "Reflected packet count";
         }
         leaf test-reflected-byte-count {
           type uint64;
           description "Reflected byte count";
         }
       }
       list test-generator-profile {
         leaf generator-profile-name {
           type string;
           description "Profile name of Generator";
         }
         leaf generator-bandwidth {
           type uint32;
           description "Bandwidth to be tested with traffic generator";
         }
         leaf generator-test-type {
           type string;
           description "Generator Test type";
         }
       }
       list test-generator-config {
         leaf test-name {
           type string;
           description "Test name";
         }
         leaf test-mode {
           type string;
           description "Test mode";
         }
         leaf test-family {
           type string;
           description "Test family";
         }
         leaf iterator-duration {
           type uint32;
           description "Duration of initiating iterator";
         }
       }
       container test-generator-results {
         container generator-throughput-test-data {
           description "Throughput Generator test results";
           container generator-throughput-header {
             description "Throughput generator header";
             leaf initial-test-load {
               type string;
               description "Initial test load";
             }
             leaf iteration-mode {
               type string;
               description "Iteration mode";
             }
             leaf iteration-step {
               type string;
               description "Iteration step";
             }
             leaf bandwidth-str {
               type string;
               description "Bandwidth string";
             }
           }
           list generator-throughput-test-results {
             description "Results..";
             leaf test-pkt-size {
               type uint32;
               description "Test Packet size of stream";
             }
             list result-entry {
               description "Throughput Generator test iterator results";
               container gen-result-entry {
                 leaf iterator-num {
                   type uint32;
                   description "Test Iterator number";
                 }
                 leaf duration {
                   type uint32;
                   description "Test Iterator duration";
                 }
                 leaf it-pps {
                   type uint32;
                   description "Packets per seconds";
                 }
                 leaf tx-packets {
                   type uint32;
                   description "Transmitted packets";
                 }
                 leaf tx-bytes {
                   type uint32;
                   description "Transmitted bytes";
                 }
                 leaf rx-packets {
                   type uint32;
                   description "Received packets";
                 }
                 leaf rx-bytes {
                   type uint32;
                   description "Received bytes";
                 }
                 leaf it-measured-percent {
                   type string;
                   description "Percentage throughput achieved";
                 }
                 leaf bandwidth {
                   type uint32;
                   description "Test bandwidth";
                 }
               }
             }
           }
           container generator-tput-test-summary {
             description "Throughput Generator test result summary";
             list generator-tput-test-summary-results {
               description "Throughput Result summary..";
               list tput-summary-entry {
                 description "Throughput Generator test results summary";
                 container tput-gen-summary-entry {
                   leaf test-pkt-size {
                     type uint32;
                     description "Test Packet size of stream";
                   }
                   leaf duration {
                     type uint32;
                     description "Test Iterator duration";
                   }
                   leaf tx-packets {
                     type uint32;
                     description "Transmitted packets";
                   }
                   leaf rx-packets {
                     type uint32;
                     description "Received packets";
                   }
                   leaf it-measured-percent {
                     type string;
                     description "Percentage throughput achieved";
                   }
                   leaf bandwidth {
                     type uint32;
                     description "Test bandwidth";
                   }
                   leaf tx-bytes {
                     type uint32;
                     description "Transmitted bytes";
                   }
                   leaf rx-bytes {
                     type uint32;
                     description "Received bytes";
                   }
                 }
               }
             }
           }
         }
         container generator-latency-test-data {
           description "Latency Generator test results";
           container generator-latency-header {
             description "Latency generator header";
             leaf initial-test-load {
               type string;
               description "Initial test load";
             }
             leaf bandwidth-str {
               type string;
               description "Bandwidth string";
             }
           }
           list generator-latency-test-results {
             description "Latency Results..";
             leaf test-pkt-size {
               type uint32;
               description "Test Packet size of stream";
             }
             list latency-result-entry {
               description "Latency Generator test iterator results";
               container latency-gen-result-entry {
                 leaf iterator-num {
                   type uint32;
                   description "Test Iterator number";
                 }
                 leaf duration {
                   type uint32;
                   description "Test Iterator duration";
                 }
                 leaf it-pps {
                   type uint32;
                   description "Packets per seconds";
                 }
                 leaf tx-packets {
                   type uint32;
                   description "Transmitted packets";
                 }
                 leaf tx-bytes {
                   type uint32;
                   description "Transmitted bytes";
                 }
                 leaf rx-packets {
                   type uint32;
                   description "Received packets";
                 }
                 leaf rx-bytes {
                   type uint32;
                   description "Received bytes";
                 }
                 leaf latency {
                   type uint32;
                   description "Latency of received packet in usec ";
                 }
                 leaf bandwidth {
                   type uint32;
                   description "Test bandwidth";
                 }
               }
             }
           }
           container generator-latency-test-summary {
             description "Generator latency test summary";
             list generator-latency-test-summary-results {
               description "Result summary..";
               leaf test-pkt-size {
                 type uint32;
                 description "Test Packet size of stream";
               }
               list latency-summary-entry {
                 description "Generator latency test results summary";
                 container latency-gen-summary-entry {
                   leaf test-pkt-size {
                     type uint32;
                     description "Test Packet size of stream";
                   }
                   leaf latency {
                     type uint32;
                     description "Latency of received packet in usec ";
                   }
                   leaf bandwidth {
                     type uint32;
                     description "Test bandwidth";
                   }
                 }
               }
             }
           }
         }
         container generator-frameloss-test-data {
           description "FrameLoss Generator test results";
           container generator-frameloss-header {
             description "FrameLoss generator header";
             leaf initial-test-load {
               type string;
               description "Initial test load";
             }
             leaf iteration-mode {
               type string;
               description "Iteration mode";
             }
             leaf iteration-step {
               type string;
               description "Iteration step";
             }
             leaf bandwidth-str {
               type string;
               description "Bandwidth string";
             }
           }
           list generator-frameloss-test-results {
             description "FrameLoss Results..";
             leaf test-pkt-size {
               type uint32;
               description "Test Packet size of stream";
             }
             list frameloss-result-entry {
               description "Frameloss Generator test iterator results";
               container frameloss-gen-result-entry {
                 leaf iterator-num {
                   type uint32;
                   description "Test Iterator number";
                 }
                 leaf duration {
                   type uint32;
                   description "Test Iterator duration";
                 }
                 leaf it-pps {
                   type uint32;
                   description "Packets per seconds";
                 }
                 leaf tx-packets {
                   type uint32;
                   description "Transmitted packets";
                 }
                 leaf tx-bytes {
                   type uint32;
                   description "Transmitted bytes";
                 }
                 leaf rx-packets {
                   type uint32;
                   description "Received packets";
                 }
                 leaf rx-bytes {
                   type uint32;
                   description "Received bytes";
                 }
                 leaf frameloss {
                   type uint32;
                   description "Frameloss";
                 }
                 leaf bandwidth {
                   type uint32;
                   description "Test bandwidth";
                 }
               }
             }
           }
           container generator-frameloss-test-summary {
             description "Generator Frameloss test summary";
             list generator-frameloss-test-summary-results {
               description "Result summary..";
               leaf test-pkt-size {
                 type uint32;
                 description "Test Packet size of stream";
               }
               list frameloss-summary-entry {
                 description "Generator Frameloss test results summary";
                 container frameloss-gen-summary-entry {
                   leaf test-pkt-size {
                     type uint32;
                     description "Test Packet size of stream";
                   }
                   leaf duration {
                     type uint32;
                     description "Test Iterator duration";
                   }
                   leaf tx-packets {
                     type uint32;
                     description "Transmitted packets";
                   }
                   leaf rx-packets {
                     type uint32;
                     description "Received packets";
                   }
                   leaf frameloss {
                     type uint32;
                     description "Frameloss";
                   }
                   leaf bandwidth {
                     type uint32;
                     description "Test bandwidth";
                   }
                   leaf tx-bytes {
                     type uint32;
                     description "Transmitted bytes";
                   }
                   leaf rx-bytes {
                     type uint32;
                     description "Received bytes";
                   }
                 }
               }
             }
           }
         }
         container generator-back2back-test-data {
           description "Back To Back Frames Generator test results";
           container generator-back2back-header {
             description "Back To Back Frames generator header";
             leaf initial-test-load {
               type string;
               description "Initial test load";
             }
             leaf iteration-mode {
               type string;
               description "Iteration mode";
             }
             leaf iteration-step {
               type string;
               description "Iteration step";
             }
             leaf bandwidth-str {
               type string;
               description "Bandwidth string";
             }
           }
           list generator-back2back-test-results {
             description "Results..";
             leaf test-pkt-size {
               type uint32;
               description "Test Packet size of stream";
             }
             list back2back-result-entry {
               description "Back-to-Back Frames Generator test iterator results";
               container back2back-gen-result-entry {
                 leaf iterator-num {
                   type uint32;
                   description "Test Iterator number";
                 }
                 leaf duration {
                   type uint32;
                   description "Test Iterator duration";
                 }
                 leaf burst-length {
                   type uint32;
                   description "Burst length";
                 }
                 leaf tx-packets {
                   type uint32;
                   description "Transmitted packets";
                 }
                 leaf tx-bytes {
                   type uint32;
                   description "Transmitted bytes";
                 }
                 leaf rx-packets {
                   type uint32;
                   description "Received packets";
                 }
                 leaf rx-bytes {
                   type uint32;
                   description "Received bytes";
                 }
               }
             }
           }
           container generator-back2back-test-summary {
             description "Generator back2back test summary";
             list generator-back2back-test-summary-results {
               description "Result summary..";
               leaf test-pkt-size {
                 type uint32;
                 description "Test Packet size of stream";
               }
               list back2back-summary-entry {
                 description "Generator back2back test results summary";
                 container back2back-gen-summary-entry {
                   leaf test-pkt-size {
                     type uint32;
                     description "Test Packet size of stream";
                   }
                   leaf burst-length {
                     type uint32;
                     description "Burst length";
                   }
                   leaf duration {
                     type uint32;
                     description "Test Iterator duration";
                   }
                   leaf theoretical-bandwidth {
                     type string;
                     description "Bandwidth string";
                   }
                   leaf bandwidth {
                     type uint32;
                     description "Test bandwidth";
                   }
                 }
               }
             }
           }
         }
       }
     }
   }
   grouping rfc2544-summary-information-block {
     leaf active-test-cnt {
       type uint32;
       description "Number of active tests";
     }
     leaf completed-test-cnt {
       type uint32;
       description "Number of completed tests";
     }
     leaf terminated-test-cnt {
       type uint32;
       description "Number of aboirted tests";
     }
   }
   grouping paa-status-block {
     leaf paa-ta-status {
       type string;
       description "PAA Test Agent status";
     }
     leaf paa-error-message {
       type string;
       description "PAA Test Agent error code message";
     }
     leaf paa-control-center {
       type string;
       description "PAA control center";
     }
     leaf paa-ta-image {
       type string;
       description "PAA Test Agent image";
     }
     leaf paa-ta-container-status {
       type string;
       description "PAA Test Agent container status";
     }
     leaf paa-ta-running {
       type string;
       description "PAA Test Agent running";
     }
     leaf paa-ta-paused {
       type string;
       description "PAA Test Agent paused";
     }
     leaf paa-ta-restarting {
       type string;
       description "PAA Test Agent restarting";
     }
     leaf paa-ta-oomkilled {
       type string;
       description "PAA Test Agent oomkilled";
     }
     leaf paa-ta-dead {
       type string;
       description "PAA Test Agent dead";
     }
     leaf paa-ta-pid {
       type string;
       description "PAA Test Agent pid";
     }
     leaf paa-ta-exitcode {
       type string;
       description "PAA Test Agent exitcode";
     }
     leaf paa-ta-error {
       type string;
       description "PAA Test Agent error";
     }
     leaf paa-ta-startedat {
       type string;
       description "PAA Test Agent startedat";
     }
     leaf paa-ta-finishedat {
       type string;
       description "PAA Test Agent finishedat";
     }
     leaf paa-ta-vrf {
       type string;
       description "PAA Test Agent VRF";
     }
     leaf paa-ta-logs {
       type string;
       description "PAA Test Agent logs";
     }
   }
 }
