module junos-state-services {
  yang-version 1.1;
  namespace "http://yang.juniper.net/junos/state/services";
  prefix js-svc;

  import junos-base-extensions {
    prefix junos-base;
  }

  import junos-state {
    prefix js;
  }

  organization
    "Juniper Networks, Inc.";

  contact
    "Juniper Networks, Inc.

     1133 Innovation Way
     Sunnyvale, CA

     +1 888 314-5822

     E-mail: yang-support@juniper.net";

  description
    "This module contains a collection of top level nodes for JUNOS
     services state data.

     Copyright (c) 2022 Juniper Networks, Inc.
     All rights reserved.";

  revision 2021-12-03 {
    description
      "Initial revision";
    reference "0.1.0";
  }

  junos-base:version "0.1.0";

  grouping services-top {
    description
      "Top-level grouping for JUNOS services state data";

    container services {
      description
        "Encapsulating container for all JUNOS services state";
    }
  }

  augment "/js:state" {
    description
      "Adds services domain to top-level state";

    uses services-top;
  }
}
