module junos-state-anomalies {
  yang-version 1.1;
  namespace "http://yang.juniper.net/junos/state/anomalies";
  prefix js-anom;

  import junos-base-extensions {
    prefix junos-base;
  }

  import junos-state {
    prefix js;
  }

  import junos-state-system {
    prefix js-sys;
  }

  organization
    "Juniper Networks, Inc.";

  contact
    "Juniper Networks, Inc.

     1133 Innovation Way
     Sunnyvale, CA

     +1 888 314-5822

     E-mail: yang-support@juniper.net";

  description
    "This module contains a collection of top level nodes for JUNOS
     system anomaly state data.

     Copyright (c) 2022 Juniper Networks, Inc.
     All rights reserved.";

  revision 2022-02-20 {
    description
      "Initial revision";
    reference "0.1.0";
  }

  junos-base:version "0.1.0";

  grouping anomalies-top {
    description
      "Top-level grouping for system anomaly state data";

    container anomalies {
      description
        "Container for anomaly state";
    }
  }

  augment "/js:state/js-sys:system" {
    description
      "Adds anomalies domain to system state";

    uses anomalies-top;
  }
}
