/*
 * Copyright (c) 2023 Juniper Networks, Inc.
 * All rights reserved.
 */
 module junos-nfx-rpc-authentication-whitelist {
   namespace "http://yang.juniper.net/junos-nfx/rpc/authentication-whitelist";

   prefix authentication-whitelist;

   import junos-common-ddl-extensions {
     prefix junos;
     revision-date 2023-01-01;
   }

   import junos-common-types {
     prefix jt;
     revision-date 2023-01-01;
   }

   organization "Juniper Networks, Inc.";

   contact "yang-support@juniper.net";

   description "Junos RPC YANG module for authentication-whitelist command(s)";

   revision 2023-01-01 {
     description "Junos: 23.4R1.10";
   }

   rpc get-ethernet-switching-authentication-whitelist-mac {
     description "Show 802.1X White List MAC addresses";
     junos:command "show authentication-whitelist";
     output {
       container authentication-whitelist-information {
         uses authentication-whitelist-information-block;
       }
     }
   }
   rpc get-ethernet-switching-interface-mac-addresses {
     description "Show 802.1X White List MAC addresses on this interface";
     junos:command "show authentication-whitelist interface";
     input {
       leaf interface-name {
         description "Show White List MAC addresses of interface";
         junos:cli-feature "nokeyword";
         type union {
           type jt:interface-name;
           type string {
             pattern "<.*>|$.*";
           }
         }
       }
     }
     output {
       container authentication-whitelist-information {
         uses authentication-whitelist-information-block;
       }
     }
   }
   rpc get-authentication-whitelist-mac-bypassed-users {
     description "List users who have bypassed 802.1X authentication";
     junos:command "show authentication-whitelist authentication-bypassed-users";
     output {
       container authentication-whitelist-information {
         uses authentication-whitelist-information-block;
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping authentication-whitelist-information-block {
     container authentication-whitelist-mac {
       description "Information about configured white-list MAC addresses";
       leaf authentication-whitelist-mac-address {
         type jt:mac-addr;
         description "MAC address configured for bypass";
       }
       leaf authentication-whitelist-mac-prefix {
         type int32;
         description "MAC prefix configured for bypass clients";
       }
       leaf authentication-whitelist-mac-vlan-assignment {
         type string;
         description "VLAN assigned to the client with this MAC address";
       }
       leaf authentication-whitelist-mac-interface {
         type string;
         description "Interface on which client MAC was learned";
       }
     }
     container authentication-whitelist-mac-bypassed-users {
       description "List of users who bypassed authentication";
       leaf authentication-whitelist-mac-bypass {
         type jt:mac-addr;
         description "MAC address of bypassed client";
       }
       leaf authentication-whitelist-mac-bypass-interface {
         type string;
         description "Interface on which MAC address is bypassed";
       }
       leaf authentication-whitelist-mac-bypass-vlan {
         type string;
         description "VLAN of bypassed client";
       }
     }
   }
 }
