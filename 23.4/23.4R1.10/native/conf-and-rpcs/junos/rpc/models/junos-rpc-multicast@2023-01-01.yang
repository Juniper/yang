/*
 * Copyright (c) 2023 Juniper Networks, Inc.
 * All rights reserved.
 */
 module junos-rpc-multicast {
   namespace "http://yang.juniper.net/junos/rpc/multicast";

   prefix multicast;

   import junos-common-types {
     prefix jt;
     revision-date 2023-01-01;
   }

   organization "Juniper Networks, Inc.";

   contact "yang-support@juniper.net";

   description "Junos RPC YANG module for multicast command(s)";

   revision 2023-01-01 {
     description "Junos: 23.4R1.10";
   }

   rpc get-mc-fwd-cache-information {
     description "Show multicast forwarding cache statistics";
     input {
       choice daemon-select {
         case logical-system {
           leaf logical-system {
             description "Name of logical system, or 'all'";
             type string {
             }
           }
         }
       }
       leaf instance {
         description "Name of instance";
         type string;
       }
       leaf family {
         description "Address Family";
         type enumeration {
           enum "inet" {
             description "Display IPv4 information";
           }
           enum "inet6" {
             description "Display IPv6 information";
           }
         }
       }
     }
     output {
       container mc-fwd-cache-information {
         uses mc-fwd-cache-information-block;
       }
     }
   }
   rpc get-multicast-router-information {
     description "Request multicast router information";
     input {
       leaf host {
         description "Hostname or address of remote host";
         type string;
         mandatory true;
       }
     }
     output {
       choice output_c {
         case output-tag {
           leaf output {
             type string;
           }
         }
         case multichassis-tag {
           anyxml multi-routing-engine-results;
         }
       }
     }
   }
   rpc get-multicast-route-information {
     description "Show the multicast routing table";
     input {
       choice daemon-select {
         case logical-system {
           leaf logical-system {
             description "Name of logical system, or 'all'";
             type string {
             }
           }
         }
       }
       leaf instance {
         description "Name of instance";
         type string;
       }
       leaf mode {
         default "all";
         type enumeration {
           enum "all" {
             description "Display all route entries";
           }
           enum "active" {
             description "Display active route entries";
           }
           enum "inactive" {
             description "Display inactive route entries";
           }
         }
       }
       leaf verbosity_level {
         default "brief";
         type enumeration {
           enum "summary" {
             description "Display summary output";
           }
           enum "brief" {
             description "Display brief output (default)";
           }
           enum "detail" {
             description "Display detailed output";
           }
           enum "extensive" {
             description "Display extensive output";
           }
         }
       }
       leaf family {
         description "Address family";
         default "inet";
         type enumeration {
           enum "inet" {
             description "Display IPv4 information";
           }
           enum "inet6" {
             description "Display IPv6 information";
           }
         }
       }
       leaf table {
         description "Entries in a particular routing table";
         status deprecated;
         type string;
       }
       leaf group {
         description "IP address and optional prefix length of group";
         type jt:ipprefix;
       }
       leaf source-prefix {
         description "IP address and optional prefix length of source for routes";
         type jt:ipprefix;
       }
       leaf regexp {
         description "Regular expression for session to match";
         type string;
       }
       leaf display-tunnel-name {
         description "Display provider tunnel name instead of branch information";
         type empty;
       }
       leaf display-origin-protocol {
         description "Display originating protocol instead of upstream protocol";
         type empty;
       }
       leaf oif-count {
         description "Display outgoing interface count instead of list";
         type empty;
       }
     }
     output {
       container multicast-route-information {
         uses multicast-route-information-block;
       }
     }
   }
   rpc get-multicast-next-hops-information {
     description "Show the multicast next-hop table";
     input {
       choice daemon-select {
         case logical-system {
           leaf logical-system {
             description "Name of logical system, or 'all'";
             type string {
             }
           }
         }
       }
       leaf verbosity_level {
         default "brief";
         type enumeration {
           enum "terse" {
             description "Display terse output";
           }
           enum "brief" {
             description "Display brief output (default)";
           }
           enum "detail" {
             description "Display detailed output";
           }
         }
       }
       leaf identifier {
         description "ID of next hop";
         type union {
           type uint32;
           type string {
             pattern "<.*>|$.*";
           }
         }
       }
       leaf family {
         description "Address family";
         default "inet";
         type enumeration {
           enum "inet" {
             description "Display IPv4 information";
           }
           enum "inet6" {
             description "Display IPv6 information";
           }
         }
       }
     }
     output {
       container multicast-next-hops-information {
         uses multicast-next-hops-information-block;
       }
     }
   }
   rpc get-satellite-control-next-hop {
     description "Show satellite multicast unicast next-hops";
     input {
       leaf verbosity_level {
         default "brief";
         type enumeration {
           enum "brief" {
             description "Display brief output (default)";
           }
           enum "detail" {
             description "Display detailed output";
           }
         }
       }
     }
   }
   rpc get-multicast-rpf-information {
     description "Show reverse-path forwarding (RPF) source network information";
     input {
       choice daemon-select {
         case logical-system {
           leaf logical-system {
             description "Name of logical system, or 'all'";
             type string {
             }
           }
         }
       }
       leaf instance {
         description "Name of instance";
         type string;
       }
       leaf verbosity_level {
         type enumeration {
           enum "summary" {
             description "Display summary output";
           }
         }
       }
       leaf prefix {
         description "IP address and optional prefix length of host";
         type jt:ipprefix;
       }
       leaf family {
         description "Address family";
         default "inet";
         type enumeration {
           enum "inet" {
             description "Display RPF information for IPv4 ";
           }
           enum "inet6" {
             description "Display RPF information for IPv6 ";
           }
         }
       }
     }
     output {
       container multicast-rpf-information {
         uses multicast-rpf-information-block;
       }
     }
   }
   rpc get-multicast-scope-information {
     description "Show administratively scoped multicast information";
     input {
       choice daemon-select {
         case logical-system {
           leaf logical-system {
             description "Name of logical system, or 'all'";
             type string {
             }
           }
         }
       }
       leaf instance {
         description "Name of instance";
         type string;
       }
       leaf family {
         description "Address family";
         default "inet";
         type enumeration {
           enum "inet" {
             description "Display IPv4 information";
           }
           enum "inet6" {
             description "Display IPv6 information";
           }
         }
       }
     }
     output {
       container multicast-scope-information {
         uses multicast-scope-information-block;
       }
     }
   }
   rpc get-multicast-sessions-information {
     description "Show announced multicast sessions";
     input {
       choice daemon-select {
         case logical-system {
           leaf logical-system {
             description "Name of logical system, or 'all'";
             type string {
             }
           }
         }
       }
       leaf verbosity_level {
         default "brief";
         type enumeration {
           enum "brief" {
             description "Display brief output (default)";
           }
           enum "detail" {
             description "Display detailed output";
           }
           enum "extensive" {
             description "Display extensive output";
           }
         }
       }
       leaf regexp {
         description "Regular expression for sessions to match";
         type string;
       }
     }
     output {
       container multicast-sessions-information {
         uses multicast-sessions-information-block;
       }
     }
   }
   rpc get-multicast-statistics-information {
     description "Show multicast statistics";
     input {
       choice daemon-select {
         case logical-system {
           leaf logical-system {
             description "Name of logical system, or 'all'";
             type string {
             }
           }
         }
       }
       leaf instance {
         description "Name of instance";
         type string;
       }
       leaf interface {
         description "Name of interface";
         type string;
       }
       leaf family {
         description "Address family";
         default "inet";
         type enumeration {
           enum "inet" {
             description "Display statistics for IPv4 ";
           }
           enum "inet6" {
             description "Display statistics for IPv6 ";
           }
         }
       }
     }
     output {
       container multicast-statistics-information {
         uses multicast-statistics-information-block;
       }
     }
   }
   rpc get-satellite-control-statistics {
     description "Show satellite multicast statistics";
     input {
       leaf verbosity_level {
         default "detail";
         type enumeration {
           enum "brief" {
             description "Display brief output (default)";
           }
           enum "detail" {
             description "Display detailed output";
           }
         }
       }
     }
   }
   rpc get-multicast-tunnels-information {
     description "Show multicast tunnel information";
     status deprecated;
     input {
       choice daemon-select {
         case logical-system {
           leaf logical-system {
             description "Name of logical system, or 'all'";
             type string {
             }
           }
         }
       }
     }
     output {
       container multicast-tunnels-information {
         uses multicast-tunnels-information-block;
       }
     }
   }
   rpc get-multicast-usage-information {
     description "Show multicast usage information";
     input {
       choice daemon-select {
         case logical-system {
           leaf logical-system {
             description "Name of logical system, or 'all'";
             type string {
             }
           }
         }
       }
       leaf instance {
         description "Name of instance";
         type string;
       }
       leaf verbosity_level {
         default "brief";
         type enumeration {
           enum "brief" {
             description "Display brief output (default)";
           }
           enum "detail" {
             description "Display detailed output";
           }
         }
       }
       leaf family {
         description "Address family";
         default "inet";
         type enumeration {
           enum "inet" {
             description "Display IPv4 information";
           }
           enum "inet6" {
             description "Display IPv6 information";
           }
         }
       }
     }
     output {
       container multicast-usage-information {
         uses multicast-usage-information-block;
       }
     }
   }
   rpc get-multicast-flow-maps-information {
     description "Show configured flow maps";
     input {
       choice daemon-select {
         case logical-system {
           leaf logical-system {
             description "Name of logical system, or 'all'";
             type string {
             }
           }
         }
       }
       leaf instance {
         description "Name of instance";
         type string;
       }
       leaf verbosity_level {
         default "brief";
         type enumeration {
           enum "brief" {
             description "Display brief output (default)";
           }
           enum "detail" {
             description "Display detailed output";
           }
         }
       }
     }
     output {
       container multicast-flow-maps-information {
         uses multicast-flow-maps-information-block;
       }
     }
   }
   rpc get-multicast-interface-information {
     description "Show configured interfaces";
     input {
       choice daemon-select {
         case logical-system {
           leaf logical-system {
             description "Name of logical system, or 'all'";
             type string {
             }
           }
         }
       }
     }
     output {
       container multicast-interface-information {
         uses multicast-interface-information-block;
       }
     }
   }
   rpc get-multicast-pim-to-igmp-proxy-information {
     description "Show pim-to-igmp-proxy information";
     input {
       choice daemon-select {
         case logical-system {
           leaf logical-system {
             description "Name of logical system, or 'all'";
             type string {
             }
           }
         }
       }
       leaf instance {
         description "Name of instance";
         type string;
       }
     }
     output {
       container multicast-pim-to-igmp-proxy-information {
         uses multicast-pim-to-igmp-proxy-information-block;
       }
     }
   }
   rpc get-multicast-pim-to-mld-proxy-information {
     description "Show pim-to-mld-proxy information";
     input {
       choice daemon-select {
         case logical-system {
           leaf logical-system {
             description "Name of logical system, or 'all'";
             type string {
             }
           }
         }
       }
       leaf instance {
         description "Name of instance";
         type string;
       }
     }
     output {
       container multicast-pim-to-mld-proxy-information {
         uses multicast-pim-to-mld-proxy-information-block;
       }
     }
   }
   rpc get-multicast-backup-pe-groups-information {
     description "Show backup PE groups";
     input {
       choice daemon-select {
         case logical-system {
           leaf logical-system {
             description "Name of logical system, or 'all'";
             type string {
             }
           }
         }
       }
       leaf instance {
         description "Name of instance";
         type string;
       }
     }
     output {
       container multicast-backup-pe-groups-information {
         uses multicast-backup-pe-groups-information-block;
       }
     }
   }
   rpc get-multicast-backup-pe-group-information {
     description "Show information for specified group";
     input {
       choice daemon-select {
         case logical-system {
           leaf logical-system {
             description "Name of logical system, or 'all'";
             type string {
             }
           }
         }
       }
       leaf instance {
         description "Name of instance";
         type string;
       }
       leaf group_name {
         description "Name of the group";
         type string;
         mandatory true;
       }
     }
     output {
       container multicast-backup-pe-groups-information {
         uses multicast-backup-pe-groups-information-block;
       }
     }
   }
   rpc get-multicast-backup-pe-address-information {
     description "Show groups a PE address is associated with";
     input {
       choice daemon-select {
         case logical-system {
           leaf logical-system {
             description "Name of logical system, or 'all'";
             type string {
             }
           }
         }
       }
       leaf pe_address {
         description "IP address of the PE";
         type jt:ipaddr;
         mandatory true;
       }
     }
     output {
       container multicast-backup-pe-address-information {
         uses multicast-backup-pe-address-information-block;
       }
     }
   }
   rpc get-multicast-snooping-route-information {
     description "Show the multicast snooping routing table";
     input {
       leaf logical-system {
         description "Name of logical system, or 'all'";
         type string {
         }
       }
       leaf mode {
         default "data";
         type enumeration {
           enum "all" {
             description "Display all route entries";
           }
           enum "active" {
             description "Display active route entries";
           }
           enum "inactive" {
             description "Display inactive route entries";
           }
           enum "control" {
             description "Display control route entries";
           }
           enum "data" {
             description "Display data route entries";
           }
         }
       }
       leaf verbosity_level {
         default "brief";
         type enumeration {
           enum "brief" {
             description "Display brief output (default)";
           }
           enum "detail" {
             description "Display detailed output";
           }
           enum "extensive" {
             description "Display extensive output";
           }
         }
       }
       leaf family {
         description "Address family";
         type enumeration {
           enum "inet" {
             description "Display IPv4 information";
           }
           enum "inet6" {
             description "Display IPv6 information";
           }
         }
       }
       leaf vlan-id {
         description "VLAN ID for a learning domain";
         type union {
           type string {
             pattern "<.*>|$.*";
           }
           type uint32 {
             range "0 .. 4094";
           }
         }
       }
       leaf qualified-vlan {
         description "VLAN ID for a Qualified VLAN";
         type union {
           type string {
             pattern "<.*>|$.*";
           }
           type uint32 {
             range "0 .. 4094";
           }
         }
       }
       leaf mesh-group {
         description "Name of a mesh-group";
         type string;
       }
       leaf group {
         description "IP address and optional prefix length of group";
         type jt:ipprefix;
       }
       leaf source-prefix {
         description "IP address and optional prefix length of source";
         type jt:ipprefix;
       }
       leaf regexp {
         description "Regular expression for session to match";
         type string;
       }
       leaf bridge-domain {
         description "Name of bridge-domain";
         type string;
       }
       leaf vlan {
         description "Name of VLAN";
         type string;
       }
       leaf instance {
         description "Name of routing-instance";
         type string;
       }
     }
     output {
       container multicast-route-information {
         uses multicast-route-information-block;
       }
     }
   }
   rpc get-satellite-control-multicast {
     description "Show the satellite multicast snooping information";
     input {
       leaf verbosity_level {
         default "brief";
         type enumeration {
           enum "brief" {
             description "Display brief output (default)";
           }
           enum "detail" {
             description "Display detailed output";
           }
           enum "extensive" {
             description "Display extensive output";
           }
         }
       }
       leaf vswitch-name {
         description "Virtual switch name";
         type string;
       }
       leaf bridge-domain-name {
         description "Bridge domain name";
         type string;
       }
       leaf vlan-name {
         description "Vlan name";
         type string;
       }
       leaf group {
         description "Multicast Group Address";
         type jt:ipaddr;
       }
       leaf source {
         description "Source Address";
         type jt:ipaddr;
       }
     }
   }
   rpc get-multicast-snooping-next-hops-information {
     description "Show the multicast next-hop snooping table";
     input {
       leaf verbosity_level {
         default "brief";
         type enumeration {
           enum "brief" {
             description "Display brief output (default)";
           }
           enum "detail" {
             description "Display detailed output";
           }
         }
       }
       leaf identifier {
         description "ID of next hop";
         type union {
           type uint32;
           type string {
             pattern "<.*>|$.*";
           }
         }
       }
       leaf family {
         description "Address family";
         type enumeration {
           enum "inet" {
             description "Display IPv4 information";
           }
           enum "inet6" {
             description "Display IPv6 information";
           }
         }
       }
     }
     output {
       container multicast-next-hops-information {
         uses multicast-next-hops-information-block;
       }
     }
   }
   rpc get-satellite-control-indirect-next-hop {
     description "Show satellite multicast next-hops";
     input {
       leaf verbosity_level {
         default "brief";
         type enumeration {
           enum "brief" {
             description "Display brief output (default)";
           }
           enum "detail" {
             description "Display detailed output";
           }
           enum "extensive" {
             description "Display extensive output";
           }
         }
       }
       leaf nexthop-id {
         description "Next-hop ID";
         type union {
           type int32;
           type string {
             pattern "<.*>|$.*";
           }
         }
       }
     }
   }
   rpc get-satellite-control-ecid {
     description "Show the satellite multicast ECID mapping database";
     input {
       leaf verbosity_level {
         default "brief";
         type enumeration {
           enum "brief" {
             description "Display brief output (default)";
           }
           enum "detail" {
             description "Display detailed output";
           }
           enum "extensive" {
             description "Display extensive output";
           }
         }
       }
       leaf device-id {
         description "Device ID";
         type union {
           type int32;
           type string {
             pattern "<.*>|$.*";
           }
         }
       }
       leaf ecid {
         description "ECID";
         type union {
           type int32;
           type string {
             pattern "<.*>|$.*";
           }
         }
       }
       leaf reference-id {
         description "Reference ID";
         type union {
           type int32;
           type string {
             pattern "<.*>|$.*";
           }
         }
       }
     }
   }
   rpc get-satellite-control-summary {
     description "Show satellite multicast summary information";
     input {
       leaf verbosity_level {
         default "detail";
         type enumeration {
           enum "brief" {
             description "Display brief output (default)";
           }
           enum "detail" {
             description "Display detailed output";
           }
         }
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping mc-fwd-cache-information-block {
     container mc-fwd-cache-threshold {
       leaf mc-instance {
         type string;
         description "Multicast Instance";
       }
       leaf mc-fwd-cache-family {
         type string;
         description "Multicast address family";
       }
       list mc-cache-params {
         leaf mc-cache-param-name {
           type string;
           description "Multicast Fwd Cache Parameter";
         }
         leaf mc-cache-param-value {
           type uint32;
           description "Multicast Fwd Cache parameter value";
         }
       }
     }
   }
   grouping multicast-route-information-block {
     leaf multicast-route-no-group-prefix {
       type jt:ipaddr;
     }
     leaf multicast-route-no-family {
       type string;
     }
     list route-family {
       leaf multicast-instance {
         type string;
       }
       leaf address-family {
         type string;
       }
       leaf bulking-indicator {
         type string;
       }
       list multicast-route-summaries {
         container multicast-route-summary {
           leaf multicast-route-type {
             type string;
           }
           leaf multicast-route-state-type {
             type string;
           }
           leaf multicast-route-count {
             type int32;
           }
         }
       }
       list multicast-route {
         leaf multicast-route-vlan {
           type string;
         }
         leaf bandwidth-for-admission-control {
           type uint64;
           description "Bandwidth used for admission control";
         }
         list multicast-route-source {
           leaf multicast-source-address {
             type jt:ipaddr;
             description "Source address";
           }
         }
         list upstream-rpf-interface-names {
           leaf interface-name {
             type string;
             description "Name of interface";
           }
           leaf interface-nh-index {
             type uint32;
             description "Logical interface nexthop index";
           }
           leaf sub-mcnh-index {
             type uint32;
             description "Sub multicast composite nexthop index";
           }
           leaf upstream-rpf-labels {
             type string;
             description "Sender-Based RPF labels";
           }
           leaf rpf-session-id {
             type uint32;
             description "Session id";
           }
           leaf rpf-session-status {
             type string;
             description "Session Status";
           }
           leaf rpf-min-rate {
             type uint32;
             description "Min rate";
           }
           leaf rpf-weight {
             type uint32;
             description "RPF Weight";
           }
         }
         list downstream-interface-names {
           leaf interface-name {
             type string;
             description "Name of interface";
           }
           leaf interface-nh-index {
             type uint32;
             description "Logical interface nexthop index";
           }
           leaf sub-mcnh-index {
             type uint32;
             description "Sub multicast composite nexthop index";
           }
         }
         list multicast-route-summaries {
           container multicast-route-summary {
             leaf multicast-route-type {
               type string;
             }
             leaf multicast-route-state-type {
               type string;
             }
             leaf multicast-route-count {
               type int32;
             }
           }
         }
         leaf multicast-group-address {
           type jt:ipaddr;
           description "Group address";
         }
         leaf multicast-group-prefix-length {
           type uint32;
           description "Group prefix length";
         }
         leaf multicast-route-protocol {
           type string;
         }
         leaf multicast-route-packet-type {
           type string;
         }
         leaf multicast-source-address {
           type jt:ipaddr;
           description "Source address";
         }
         leaf multicast-source-prefix-length {
           type uint32;
           description "Source prefix length";
         }
         leaf multicast-route-vlan-id {
           type int32;
         }
         leaf multicast-route-bridge-domain {
           type string;
         }
         leaf multicast-route-mesh-group {
           type string;
         }
         leaf upstream-interface-name {
           type string;
           description "Upstream interface";
         }
         leaf rpf-check-disabled {
           type empty;
           description "Reverse path forwarding check is disabled";
         }
         leaf upstream-neighbor {
           type jt:ipaddr;
           description "IP Address of Upstream Neighbor";
         }
         leaf outgoing-interface-count {
           type int32;
         }
         leaf incoming-interface-list-names {
           type string;
           description "Incoming interface names";
         }
         leaf rejected-downstream-interface-names {
           type string;
           description "Downstream interfaces rejected by bandwidth admission control";
         }
         leaf for-blank-line-line {
           type empty;
         }
         leaf session-name {
           type string;
         }
         leaf forwarding-rate-kilobytes {
           type uint32;
         }
         leaf forwarding-rate-packets {
           type uint32;
         }
         leaf forwarded-packet-count {
           type uint32;
         }
         leaf multicast-statistics-timed-out {
           type empty;
         }
         leaf rpf-next-hop-id {
           type uint32;
         }
         leaf next-hop-id {
           type uint32;
         }
         leaf incoming-interface-list-id {
           type uint32;
           description "Incoming Interface list id";
         }
         leaf upstream-nbr-nh-id {
           type uint32;
           description "Upstream Neighbor Next-hop ID";
         }
         leaf upstream-protocol {
           type string;
         }
         leaf multicast-route-state {
           type string;
         }
         leaf multicast-route-forwarding-state {
           type string;
         }
         leaf multicast-route-uptime {
           type string;
         }
         leaf multicast-route-timeout {
           type string;
         }
         leaf interface-mismatch-count {
           type uint32;
         }
         leaf multicast-route-sensor {
           type uint32;
         }
       }
       list l2ng-multicast-route {
         leaf multicast-route-bridge-domain {
           type string;
         }
         leaf bandwidth-for-admission-control {
           type uint64;
           description "Bandwidth used for admission control";
         }
         list l2ng-downstream-interface-names {
           leaf interface-name {
             type string;
             description "Name of interface";
           }
           leaf interface-nh-index {
             type uint32;
             description "Logical interface nexthop index";
           }
           leaf sub-mcnh-index {
             type uint32;
             description "Sub multicast composite nexthop index";
           }
         }
         container l2ng-multicast-route-summary {
           leaf multicast-route-type {
             type string;
           }
           leaf multicast-route-state-type {
             type string;
           }
           leaf multicast-route-count {
             type int32;
           }
         }
         leaf multicast-group-address {
           type jt:ipaddr;
           description "Group address";
         }
         leaf multicast-group-prefix-length {
           type uint32;
           description "Group prefix length";
         }
         leaf multicast-route-protocol {
           type string;
         }
         leaf multicast-route-packet-type {
           type string;
         }
         leaf multicast-source-address {
           type jt:ipaddr;
           description "Source address";
         }
         leaf multicast-source-prefix-length {
           type uint32;
           description "Source prefix length";
         }
         leaf multicast-route-vlan-id {
           type int32;
         }
         leaf multicast-route-vlan {
           type string;
         }
         leaf multicast-route-mesh-group {
           type string;
         }
         leaf upstream-interface-name {
           type string;
           description "Upstream interface";
         }
         leaf rpf-check-disabled {
           type empty;
           description "Reverse path forwarding check is disabled";
         }
         leaf incoming-interface-list-names {
           type string;
           description "Incoming interface names";
         }
         leaf rejected-downstream-interface-names {
           type string;
           description "Downstream interfaces rejected by bandwidth admission control";
         }
         leaf session-name {
           type string;
         }
         leaf forwarding-rate-kilobytes {
           type uint32;
         }
         leaf forwarding-rate-packets {
           type uint32;
         }
         leaf forwarded-packet-count {
           type uint32;
         }
         leaf multicast-statistics-timed-out {
           type empty;
         }
         leaf next-hop-id {
           type uint32;
         }
         leaf incoming-interface-list-id {
           type uint32;
           description "Incoming Interface list id";
         }
         leaf upstream-protocol {
           type string;
         }
         leaf multicast-route-state {
           type string;
         }
         leaf multicast-route-forwarding-state {
           type string;
         }
         leaf multicast-route-uptime {
           type string;
         }
         leaf multicast-route-timeout {
           type string;
         }
         leaf interface-mismatch-count {
           type uint32;
         }
         leaf multicast-route-sensor {
           type uint32;
         }
       }
     }
   }
   grouping multicast-next-hops-information-block {
     list next-hops-family {
       leaf address-family {
         type string;
       }
       list iflist-next-hop {
         leaf next-hop-id {
           type uint32;
         }
         leaf next-hop-ref-count {
           type uint32;
         }
         leaf next-hop-kernel-ref-count {
           type uint32;
         }
         leaf next-hop-addr {
           type uint32;
         }
         leaf rpf-next-hop-id {
           type uint32;
         }
         list next-hop-downstream-interface {
           leaf interface-name {
             type string;
             description "Name of interface";
           }
           leaf interface-index {
             type int32;
           }
           leaf interface-nh-index {
             type uint32;
             description "Logical interface nexthop index";
           }
         }
         leaf next-hop-downstream-interface-count {
           type uint32;
         }
       }
     }
   }
   grouping multicast-rpf-information-block {
     list rpf-family {
       leaf rpf-table-name {
         type string;
       }
       leaf rpf-table-entry-count {
         type uint32;
       }
       leaf address-family {
         type string;
       }
       list rpf-route {
         leaf prefix {
           type jt:ipaddr;
         }
         leaf rpf-route-inactive {
           type empty;
         }
         leaf rpf-route-protocol {
           type string;
         }
         leaf interface-name {
           type string;
           description "Name of interface";
         }
         leaf rpf-route-neighbor {
           type jt:ipaddr;
         }
       }
     }
   }
   grouping multicast-scope-information-block {
     list multicast-scope-policy-interfaces {
       list multicast-scope-policy-interface {
         leaf interface-name {
           type string;
           description "Name of interface";
         }
         leaf scope-state {
           type string;
         }
         leaf scope-rejects {
           type uint32;
           description "Number of rejects in multicast scope";
         }
       }
       leaf instance-name {
         type string;
       }
       leaf address-family {
         type string;
       }
     }
     list multicast-scope {
       leaf scope-name {
         type string;
         description "Name of multicast scope";
       }
       leaf-list address-prefix {
         type jt:ipaddr;
       }
       leaf interface-name {
         type string;
         description "Name of interface";
       }
       leaf scope-state {
         type string;
       }
       leaf scope-rejects {
         type uint32;
         description "Number of rejects in multicast scope";
       }
     }
     leaf multicast-scope-policy {
       type string;
     }
   }
   grouping multicast-sessions-information-block {
     leaf multicast-session-count {
       type uint32;
     }
     leaf multicast-sessions-type {
       type string;
     }
     list multicast-session {
       leaf session-announcement {
         type string;
       }
       leaf session-name {
         type string;
       }
       leaf upstream-protocol {
         type string;
       }
       leaf session-version {
         type string;
       }
       leaf session-description {
         type string;
       }
       leaf session-uri {
         type string;
       }
       leaf session-email {
         type string;
       }
       leaf session-phone {
         type string;
       }
       leaf session-bandwidth {
         type string;
       }
       leaf session-start-time {
         type string;
       }
       leaf session-stop-time {
         type string;
       }
       leaf session-encryption-key {
         type string;
       }
       leaf session-attribute {
         type string;
       }
       leaf session-media {
         type string;
       }
       container session-origin {
         leaf session-originator-username {
           type string;
         }
         leaf session-originator-address {
           type string;
         }
       }
       container session-connection-data {
         leaf session-address {
           type string;
         }
         leaf session-ttl {
           type uint32;
         }
         leaf session-layers {
           type uint32;
         }
       }
     }
   }
   grouping multicast-statistics-information-block {
     list multicast-statistics {
       leaf instance-name {
         type string;
       }
       leaf address-family {
         type string;
       }
       leaf mc-resolves-no-mc-interface {
         type uint32;
         description "Number of resolve requests on non-multicast interfaces";
       }
       leaf mc-global-resolves-no-route {
         type uint32;
         description "Number of resolve requests with no route to source";
       }
       leaf mc-notifies-no-mc-interface {
         type uint32;
         description "Number of routing notifications on non-multicast interfaces";
       }
       leaf mc-notifies-no-route {
         type uint32;
         description "Number of routing notifications with no route to source";
       }
       leaf mc-mismatches-no-mc-interface {
         type uint32;
         description "Number of interface mismatches on non-multicast interfaces";
       }
       leaf mc-groups-no-mc-interface {
         type uint32;
         description "Number of group memberships on non-multicast interfaces";
       }
       list mc-stats-interface {
         leaf interface-name {
           type string;
           description "Name of interface";
         }
         leaf protocol-name {
           type string;
         }
         leaf mc-mismatch-errors {
           type uint32;
           description "Number of interface mismatch errors";
         }
         leaf mc-mismatches {
           type uint32;
           description "Number of interface mismatches";
         }
         leaf mc-mismatches-no-route {
           type uint32;
           description "Number of interface mismatches due to no route to source";
         }
         leaf mc-resolves {
           type uint32;
           description "Number of resolve requests";
         }
         leaf mc-routing-notifies {
           type uint32;
           description "Number of routing notifications";
         }
         leaf mc-resolves-no-route {
           type uint32;
           description "Number of resolve requests with no route to source";
         }
         leaf mc-resolve-errors {
           type uint32;
           description "Number of resolve errors";
         }
         leaf mc-resolves-filtered {
           type uint32;
           description "Number of resolve requests filtered by policy";
         }
         leaf mc-routing-notifies-filtered {
           type uint32;
           description "Number of routing notifications filtered by policy";
         }
         leaf mc-input-kbytes {
           type uint64;
           description "Number of input kilobytes";
         }
         leaf mc-input-packets {
           type uint64;
           description "Number of input packets";
         }
         leaf mc-output-kbytes {
           type uint64;
           description "Number of output kilobytes";
         }
         leaf mc-output-packets {
           type uint64;
           description "Number of output packets";
         }
         list mc-stats-interface-p2mp-nbr {
           leaf mc-p2mp-nbr-address {
             type jt:ipaddr;
             description "P2MP Neighbor address";
           }
           leaf mc-p2mp-mismatch-errors {
             type uint32;
             description "Number of interface mismatch errors";
           }
           leaf mc-p2mp-mismatches {
             type uint32;
             description "Number of interface mismatches";
           }
           leaf mc-p2mp-mismatches-no-route {
             type uint32;
             description "Number of interface mismatches due to no route to source";
           }
           leaf mc-p2mp-resolves {
             type uint32;
             description "Number of resolve requests";
           }
           leaf mc-p2mp-routing-notifies {
             type uint32;
             description "Number of routing notifications";
           }
           leaf mc-p2mp-resolves-no-route {
             type uint32;
             description "Number of resolve requests with no route to source";
           }
           leaf mc-p2mp-resolve-errors {
             type uint32;
             description "Number of resolve errors";
           }
           leaf mc-p2mp-resolves-filtered {
             type uint32;
             description "Number of resolve requests filtered by policy";
           }
           leaf mc-p2mp-routing-notifies-filtered {
             type uint32;
             description "Number of routing notifications filtered by policy";
           }
           leaf mc-p2mp-input-kbytes {
             type uint64;
             description "Number of input kilobytes";
           }
           leaf mc-p2mp-input-packets {
             type uint64;
             description "Number of input packets";
           }
           leaf mc-p2mp-output-kbytes {
             type uint64;
             description "Number of output kilobytes";
           }
           leaf mc-p2mp-output-packets {
             type uint64;
             description "Number of output packets";
           }
           leaf protocol-name {
             type string;
           }
         }
       }
     }
   }
   grouping multicast-tunnels-information-block {
     list multicast-tunnel {
       leaf interface-name {
         type string;
         description "Name of interface";
       }
       leaf tunnel-local-address {
         type jt:ipaddr;
       }
       leaf tunnel-remote-address {
         type jt:ipaddr;
       }
       leaf tunnel-ttl {
         type uint32;
       }
     }
   }
   grouping multicast-usage-information-block {
     leaf multicast-usage-no-group-prefix {
       type jt:ipaddr;
     }
     leaf multicast-usage-strange-family {
       type uint32;
     }
     leaf multicast-usage-timed-out {
       type empty;
     }
     list multicast-group {
       leaf multicast-group-address {
         type jt:ipaddr;
         description "Group address";
       }
       leaf multicast-source-count {
         type uint32;
       }
       leaf multicast-packet-count {
         type uint32;
       }
       leaf multicast-packet-count-not-available {
         type empty;
       }
       leaf multicast-byte-count {
         type uint32;
       }
       leaf multicast-byte-count-not-available {
         type empty;
       }
       list multicast-group-source {
         leaf multicast-source-address {
           type jt:ipaddr;
           description "Source address";
         }
         leaf multicast-source-prefix-length {
           type uint32;
           description "Source prefix length";
         }
         leaf multicast-packet-count {
           type uint32;
         }
         leaf multicast-byte-count {
           type uint32;
         }
         leaf multicast-packet-count-not-available {
           type empty;
         }
         leaf multicast-byte-count-not-available {
           type empty;
         }
       }
     }
     list multicast-source {
       leaf multicast-source-address {
         type jt:ipaddr;
         description "Source address";
       }
       leaf multicast-source-prefix-length {
         type uint32;
         description "Source prefix length";
       }
       leaf multicast-group-count {
         type uint32;
       }
       leaf multicast-packet-count {
         type uint32;
       }
       leaf multicast-packet-count-not-available {
         type empty;
       }
       leaf multicast-byte-count {
         type uint32;
       }
       leaf multicast-byte-count-not-available {
         type empty;
       }
       list multicast-source-group {
         leaf multicast-group-address {
           type jt:ipaddr;
           description "Group address";
         }
         leaf multicast-packet-count {
           type uint32;
         }
         leaf multicast-byte-count {
           type uint32;
         }
         leaf multicast-packet-count-not-available {
           type empty;
         }
         leaf multicast-byte-count-not-available {
           type empty;
         }
       }
     }
   }
   grouping multicast-flow-maps-information-block {
     container multicast-flow-maps {
       description "Information about multicast flow maps for one routing instance";
       leaf instance-name {
         type string;
       }
       list multicast-flow-map {
         description "Information about a multicast flow map";
         leaf flow-map-name {
           type string;
           description "Name of the flow map";
         }
         leaf policy-name {
           type string;
           description "Name of the policy";
         }
         leaf cache-timeout {
           type string;
           description "Delay before discarding a matched cache entry";
         }
         leaf flow-bandwidth {
           type uint64;
           description "Bandwidth for matched flows";
         }
         leaf bandwidth-type {
           type string;
           description "Bandwidth type for matched flows";
         }
         list redundant-sources {
           leaf multicast-source-address {
             type jt:ipaddr;
             description "Source address";
           }
         }
       }
     }
   }
   grouping multicast-interface-information-block {
     list multicast-interface {
       description "Information about a multicast interface";
       leaf interface-name {
         type string;
         description "Name of interface";
       }
       leaf interface-max-bandwidth {
         type uint64;
         description "Maximum bandwidth for multicast flows";
       }
       leaf interface-local-bandwidth-deduction {
         type int64;
         description "Bandwidth deduction for local multicast flows";
       }
       leaf interface-mapped-bandwidth-deduction {
         type int64;
         description "Bandwidth deduction for mapped multicast flows";
       }
       leaf interface-remaining-bandwidth {
         type int64;
         description "Remaining bandwidth for multicast flows";
       }
       leaf interface-reverse-oif-mapping {
         type string;
         description "Reverse OIF mapping is enabled";
       }
       leaf interface-reverse-oif-mapping-no-qos-adjust {
         type string;
         description "Reverse OIF mapping no QoS adjust is enabled";
       }
       leaf interface-subscriber-leave-timer {
         type uint32;
         description "Bw restore waiting time after subscriber leaves group";
       }
       leaf interface-no-qos-adjust {
         type string;
         description "Interface no QoS adjustment is enabled";
       }
     }
   }
   grouping multicast-pim-to-igmp-proxy-information-block {
     container multicast-pim-to-igmp-proxy {
       description "Pim-to-igmp-proxy state";
       leaf instance-name {
         type string;
       }
       leaf proxy-state {
         type string;
       }
     }
   }
   grouping multicast-pim-to-mld-proxy-information-block {
     container multicast-pim-to-mld-proxy {
       description "Pim-to-mld-proxy state";
       leaf instance-name {
         type string;
       }
       leaf proxy-state {
         type string;
       }
     }
   }
   grouping multicast-backup-pe-groups-information-block {
     container multicast-backup-pe-groups {
       description "Information about multicast backup PE groups for one routing instance";
       leaf instance-name {
         type string;
       }
       list multicast-backup-pe-group {
         description "Information about a multicast backup PE group";
         leaf multicast-backup-pe-group-name {
           type string;
           description "Name of the backup PE group";
         }
         leaf designated-pe {
           type jt:ipaddr;
           description "Address of the designated PE";
         }
         leaf transitions {
           type uint32;
           description "Number of times desginated PE has changed";
         }
         leaf last-transition {
           type string;
           description "Time since last designated PE transition (hours:minutes:seconds)";
         }
         leaf local-pe-address {
           type jt:ipaddr;
           description "Local address used in designated router election";
         }
         list backup-pes {
           leaf multicast-backup-pe-address {
             type jt:ipaddr;
             description "Backup PE address";
           }
         }
       }
     }
   }
   grouping multicast-backup-pe-address-information-block {
     leaf multicast-backup-pe-address {
       type jt:ipaddr;
       description "Backup PE address";
     }
     leaf pe-address-local {
       type string;
       description "Indicates if this address belongs to this local PE";
     }
     leaf lsp-to-pe-up {
       type string;
       description "Indicates if the LSP to this PE is up";
     }
     container multicast-backup-pe-group-list {
       list multicast-backup-pe-group-member {
         leaf multicast-backup-pe-group-name {
           type string;
           description "Name of the backup PE group";
         }
       }
     }
   }
 }
