/*
 * Copyright (c) 2023 Juniper Networks, Inc.
 * All rights reserved.
 */
 module junos-rpc-ancp {
   namespace "http://yang.juniper.net/junos/rpc/ancp";

   prefix ancp;

   import junos-common-ddl-extensions {
     prefix junos;
     revision-date 2023-01-01;
   }

   import junos-common-types {
     prefix jt;
     revision-date 2023-01-01;
   }

   organization "Juniper Networks, Inc.";

   contact "yang-support@juniper.net";

   description "Junos RPC YANG module for ancp command(s)";

   revision 2023-01-01 {
     description "Junos: 23.4R1.10";
   }

   rpc get-ancp-cos-information {
     description "Show ANCP class-of-service information";
     junos:command "show ancp cos";
     input {
       leaf identifier {
         description "Access loop identifier";
         type string;
       }
     }
     output {
       container ancp-cos-information {
         uses ancp-cos-information-block;
       }
     }
   }
   rpc get-ancp-cos-pending-information {
     description "Show ANCP class-of-service pending update information";
     junos:command "show ancp cos pending-update";
     output {
       container ancp-cos-information {
         uses ancp-cos-information-block;
       }
     }
   }
   rpc get-ancp-cos-last-update-information {
     description "Show ANCP class-of-service last update information";
     junos:command "show ancp cos last-update";
     output {
       container ancp-cos-information {
         uses ancp-cos-information-block;
       }
     }
   }
   rpc get-ancp-neighbor-information {
     description "Neighbor information";
     junos:command "show ancp neighbor";
     input {
       leaf verbosity_level {
         junos:cli-feature "nokeyword";
         default "brief";
         type enumeration {
           enum "brief" {
             description "Display brief output (default)";
           }
           enum "detail" {
             description "Display detailed output";
           }
         }
       }
       choice neighbor-opts {
         case ip-address {
           leaf ip-address {
             description "IP address of the neighbor";
             type jt:ipaddr;
           }
         }
         case system-name {
           leaf system-name {
             description "MAC address of the neighbor";
             type string;
           }
         }
       }
     }
     output {
       container ancp-neighbor-information {
         uses ancp-neighbor-information-block;
       }
     }
   }
   rpc get-ancp-subscriber-information {
     description "Subscriber information";
     junos:command "show ancp subscriber";
     input {
       leaf verbosity_level {
         junos:cli-feature "nokeyword";
         default "brief";
         type enumeration {
           enum "brief" {
             description "Display brief output (default)";
           }
           enum "detail" {
             description "Display detailed output";
           }
         }
       }
     }
     output {
       container ancp-subscriber-information {
         uses ancp-subscriber-information-block;
       }
     }
   }
   rpc get-ancp-subscriber-identifier-information {
     description "Access circuit identifier";
     junos:command "show ancp subscriber identifier";
     input {
       leaf identifier-name {
         description "Identifier";
         junos:cli-feature "nokeyword";
         type string;
         mandatory true;
       }
       leaf verbosity_level {
         junos:cli-feature "nokeyword";
         default "brief";
         type enumeration {
           enum "brief" {
             description "Display brief output (default)";
           }
           enum "detail" {
             description "Display detailed output";
           }
         }
       }
     }
     output {
       container ancp-subscriber-information {
         uses ancp-subscriber-information-block;
       }
     }
   }
   rpc get-ancp-subscriber-neighbor-information {
     description "IP address of the neighbor";
     junos:command "show ancp subscriber ip-address";
     input {
       leaf neighbor-ipaddress {
         description "IP address of the neighbor";
         junos:cli-feature "nokeyword";
         type jt:ipaddr;
         mandatory true;
       }
       leaf verbosity_level {
         junos:cli-feature "nokeyword";
         default "brief";
         type enumeration {
           enum "brief" {
             description "Display brief output (default)";
           }
           enum "detail" {
             description "Display detailed output";
           }
         }
       }
     }
     output {
       container ancp-subscriber-information {
         uses ancp-subscriber-information-block;
       }
     }
   }
   rpc get-ancp-subscriber-mac-information {
     description "MAC address of the neighbor";
     junos:command "show ancp subscriber system-name";
     input {
       leaf neighbor-macaddress {
         description "MAC address of the neighbor";
         junos:cli-feature "nokeyword";
         type string;
         mandatory true;
       }
       leaf verbosity_level {
         junos:cli-feature "nokeyword";
         default "brief";
         type enumeration {
           enum "brief" {
             description "Display brief output (default)";
           }
           enum "detail" {
             description "Display detailed output";
           }
         }
       }
     }
     output {
       container ancp-subscriber-information {
         uses ancp-subscriber-information-block;
       }
     }
   }
   rpc get-ancp-subscriber-access-aggregation-id {
     description "Access aggregation circuit identifier";
     junos:command "show ancp subscriber access-aggregation-circuit-id";
     input {
       leaf access-aggregation-circuit-id {
         description "Access aggregation circuit identifier";
         junos:cli-feature "nokeyword";
         type string;
         mandatory true;
       }
       leaf verbosity_level {
         junos:cli-feature "nokeyword";
         default "brief";
         type enumeration {
           enum "brief" {
             description "Display brief output (default)";
           }
           enum "detail" {
             description "Display detailed output";
           }
         }
       }
     }
     output {
       container ancp-subscriber-information {
         uses ancp-subscriber-information-block;
       }
     }
   }
   rpc get-ancp-summary-information {
     description "ANCP summary";
     junos:command "show ancp summary";
     output {
       container ancp-summary-information {
         uses ancp-summary-information-block;
       }
     }
   }
   rpc get-ancp-subscriber-summary {
     description "ANCP subscribers summary";
     junos:command "show ancp summary subscriber";
     output {
       container ancp-summary-information {
         uses ancp-summary-information-block;
       }
     }
   }
   rpc get-ancp-neighbor-summary {
     description "ANCP neighbors summary";
     junos:command "show ancp summary neighbor";
     input {
       choice neighbor-opts {
         case ip-address {
           leaf ip-address {
             description "IP address of the neighbor";
             type jt:ipaddr;
           }
         }
         case system-name {
           leaf system-name {
             description "MAC address of the neighbor";
             type string;
           }
         }
       }
     }
     output {
       container ancp-summary-information {
         uses ancp-summary-information-block;
       }
     }
   }
   rpc get-ancp-stats-information {
     description "Statistics";
     junos:command "show ancp statistics";
     input {
       choice neighbor-opts {
         case ip-address {
           leaf ip-address {
             description "IP address of the neighbor";
             type jt:ipaddr;
           }
         }
         case system-name {
           leaf system-name {
             description "MAC address of the neighbor";
             type string;
           }
         }
       }
     }
     output {
       container ancp-statistics-information {
         uses ancp-statistics-information-block;
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping ancp-cos-information-block {
     container ancp-cos-heading {
       leaf keepalive-timer {
         type int32;
         description "Keepalive timer";
       }
       leaf connect-state {
         type string;
         description "State";
       }
       leaf connect-time {
         type string;
         description "Connect time";
       }
       leaf session-time {
         type string;
         description "Session sent time";
       }
       leaf rtcreate-time {
         type string;
         description "Routing instance create time";
       }
       leaf keepalive-time {
         type string;
         description "Keepalive sent time";
       }
       leaf update-time {
         type string;
         description "Update sent time";
       }
     }
     container ancp-cos-adjust-entry {
       leaf qos-adjust {
         type string;
       }
       leaf cos-adjust-other {
         type int32;
       }
       leaf cos-adjust-other-bytes {
         type int32;
       }
       leaf cos-adjust-adsl1-bytes {
         type int32;
       }
       leaf cos-adjust-adsl2-bytes {
         type int32;
       }
       leaf cos-adjust-adsl2-plus-bytes {
         type int32;
       }
       leaf cos-adjust-vdsl {
         type int32;
       }
       leaf cos-adjust-vdsl-bytes {
         type int32;
       }
       leaf cos-adjust-vdsl2 {
         type int32;
       }
       leaf cos-adjust-vdsl2-bytes {
         type int32;
       }
       leaf cos-adjust-sdsl {
         type int32;
       }
       leaf cos-adjust-sdsl-bytes {
         type int32;
       }
       leaf cos-adjust-gfast {
         type int32;
       }
       leaf cos-adjust-gfast-bytes {
         type int32;
       }
       leaf cos-adjust-gfast-bonded {
         type int32;
       }
       leaf cos-adjust-gfast-bonded-bytes {
         type int32;
       }
       leaf cos-adjust-sdsl-bonded {
         type int32;
       }
       leaf cos-adjust-sdsl-bonded-bytes {
         type int32;
       }
       leaf cos-adjust-vdsl2-bonded {
         type int32;
       }
       leaf cos-adjust-vdsl2-bonded-bytes {
         type int32;
       }
       leaf cos-adjust-vdsl2-annex-q {
         type int32;
       }
       leaf cos-adjust-vdsl2-annex-q-bytes {
         type int32;
       }
       leaf cos-adjust-vdsl2-annex-q-bonded {
         type int32;
       }
       leaf cos-adjust-vdsl2-annex-q-bonded-bytes {
         type int32;
       }
     }
     container ancp-qos-adjust-entry {
       leaf qos-adjust-adsl {
         type int32;
         description "QoS ADSL adjustment factor";
       }
       leaf qos-adjust-adsl2 {
         type int32;
         description "QoS ADSL2 adjustment factor";
       }
       leaf qos-adjust-adsl2-plus {
         type int32;
         description "QoS ADSL2+ adjustment factor";
       }
       leaf qos-adjust-vdsl {
         type int32;
         description "QoS VDSL adjustment factor";
       }
       leaf qos-adjust-vdsl2 {
         type int32;
         description "QoS VDSL2 adjustment factor";
       }
       leaf qos-adjust-sdsl {
         type int32;
         description "QoS SDSL adjustment factor";
       }
       leaf qos-adjust-other {
         type int32;
         description "QoS OTHER adjustment factor";
       }
       leaf qos-adjust-gfast {
         type int32;
         description "QoS G.fast adjustment factor";
       }
       leaf qos-adjust-gfast-bonded {
         type int32;
         description "QoS G.fast bonded adjustment factor";
       }
       leaf qos-adjust-sdsl-bonded {
         type int32;
         description "QoS SDSL bonded adjustment factor";
       }
       leaf qos-adjust-vdsl2-bonded {
         type int32;
         description "QoS VDSL2 bonded adjustment factor";
       }
       leaf qos-adjust-vdsl2-annex-q {
         type int32;
         description "QoS VDSL2 Annex Q adjustment factor";
       }
       leaf qos-adjust-vdsl2-annex-q-bonded {
         type int32;
         description "QoS VDSL2 Annex Q bonded adjustment factor";
       }
     }
     container ancp-cos-entry {
       leaf interface-type {
         type string;
         description "Subscriber's interface type";
       }
       leaf interface-name {
         type string;
         description "Ifl/Iflset name";
       }
       leaf interface-index {
         type int32;
         description "Ifl/Iflset index";
       }
       leaf shaping-rate {
         type string;
         description "Shaping rate";
       }
       leaf last-update {
         type string;
         description "Last updated shaping rate";
       }
     }
   }
   grouping ancp-neighbor-information-block {
     list ancp-neighbor {
       leaf neighbor-stale-flag {
         type string;
         description "ANCP neighbor stale entry flag";
       }
       leaf protocol-version {
         type string;
         description "Neighbor protocol version";
       }
       leaf ip-address {
         type jt:ipaddr;
         description "Neighbor IP address";
       }
       leaf partition-identifier {
         type int32;
         description "Neighbor partition identifier";
       }
       leaf state {
         type string;
         description "Neighbor adjacency state";
       }
       leaf up-time {
         type string;
         description "Up time";
       }
       leaf neighbor-subscriber-count {
         type int32;
         description "Neighbor subscriber count";
       }
       leaf capabilities {
         type string;
         description "Neighbor capabilities";
       }
       leaf received-rcode-bad-request-msg-count {
         type uint64;
         description "Result code: bad request message count";
       }
       leaf sent-rcode-bad-request-msg-count {
         type uint64;
         description "Result code: bad request message count";
       }
       leaf received-rcode-port-down-count {
         type uint64;
         description "Result code: port(s) down count";
       }
       leaf sent-rcode-port-down-count {
         type uint64;
         description "Result code: port(s) down count";
       }
       leaf received-rcode-out-of-resources-count {
         type uint64;
         description "Result code: out of resources count";
       }
       leaf sent-rcode-out-of-resources-count {
         type uint64;
         description "Result code: out of resources count";
       }
       leaf received-rcode-request-msg-not-implemented-count {
         type uint64;
         description "Result code: message not implemented count";
       }
       leaf sent-rcode-request-msg-not-implemented-count {
         type uint64;
         description "Result code: message not implemented count";
       }
       leaf received-rcode-bad-msg-count {
         type uint64;
         description "Result code: bad message count";
       }
       leaf sent-rcode-bad-msg-count {
         type uint64;
         description "Result code: bad message count";
       }
       leaf received-rcode-tlv-missing-count {
         type uint64;
         description "Result code: TLV missing count";
       }
       leaf sent-rcode-tlv-missing-count {
         type uint64;
         description "Result code: TLV missing count";
       }
       leaf received-rcode-bad-tlv-contents-count {
         type uint64;
         description "Result code: invalid TLV contents count";
       }
       leaf sent-rcode-bad-tlv-contents-count {
         type uint64;
         description "Result code: invalid TLV contents count";
       }
       leaf received-rcode-unknown-port-count {
         type uint64;
         description "Result code: unknown port count";
       }
       leaf sent-rcode-unknown-port-count {
         type uint64;
         description "Result code: unknown port count";
       }
       leaf partition-id {
         type int32;
         description "Neighbor partition ID";
       }
       leaf mac-address {
         type jt:mac-addr;
         description "Neighbor MAC address";
       }
       leaf neighbor-autoconf-interface {
         type string;
         description "Auto-configure trigger interface";
       }
       leaf tcp-port {
         type int32;
         description "TCP port used by connection";
       }
       leaf system-instance {
         type int32;
         description "Neighbor system instance";
       }
       leaf peer-instance {
         type int32;
         description "Neighbor peer instance";
       }
       leaf adjacency-time {
         type int32;
         description "Adjacency time advertised in 100ms";
       }
       leaf peer-adjacency-time {
         type int32;
         description "Neighbor adjacency timer value in 100ms";
       }
       leaf adjacency-loss-hold-time {
         type int32;
         description "Audit duration upon adjacency loss in seconds";
       }
       leaf partition-type {
         type int32;
         description "Neighbor partition type";
       }
       leaf partition-flag {
         type int32;
         description "Neighbor partition flag";
       }
       leaf partition-adjacencies {
         type int32;
         description "Adjacencies established on partition";
       }
       leaf dead-time {
         type int32;
         description "Time left to receive an adjacency message";
       }
       leaf received-syn-count {
         type uint64;
         description "Count of SYN messages received";
       }
       leaf received-synack-count {
         type uint64;
         description "Count of SYNACK messages received";
       }
       leaf received-rstack-count {
         type uint64;
         description "Count of RSTACK messages received";
       }
       leaf received-ack-count {
         type uint64;
         description "Count of ACK messages received";
       }
       leaf received-port-up-count {
         type uint64;
         description "Count of port up messages received";
       }
       leaf received-port-down-count {
         type uint64;
         description "Count of port down messages received";
       }
       leaf received-generic-response-count {
         type uint64;
         description "Count of generic response messages received";
       }
       leaf received-adjacency-update-count {
         type uint64;
         description "Count of adjacency update messages received";
       }
       leaf received-oam-count {
         type uint64;
         description "Count of OAM messages received";
       }
       leaf received-other-count {
         type uint64;
         description "Count of other messages received";
       }
       leaf sent-syn-count {
         type uint64;
         description "Count of SYN messages sent";
       }
       leaf sent-synack-count {
         type uint64;
         description "Count of SYNACK messages sent";
       }
       leaf sent-rstack-count {
         type uint64;
         description "Count of RSTACK messages sent";
       }
       leaf sent-ack-count {
         type uint64;
         description "Count of ACK messages sent";
       }
       leaf sent-generic-response-count {
         type uint64;
         description "Count of generic response messages sent";
       }
       leaf sent-oam-count {
         type uint64;
         description "Count of OAM messages sent";
       }
       leaf max-discovery-limit-exceed-count {
         type uint64;
         description "Count of discovery table entries not created due to limit";
       }
     }
   }
   grouping ancp-subscriber-information-block {
     leaf subscriber-stale-flag {
       type string;
       description "ANCP neighbor stale entry flag";
     }
     leaf access-loop-identifier {
       type string;
       description "Subscriber circuit identifier";
     }
     leaf dsl-line-state {
       type string;
       description "DSL line state";
     }
     leaf access-tech-type {
       type string;
       description "Access Technology Type";
     }
     leaf access-type {
       type string;
       description "Access type";
     }
     leaf interface {
       type string;
       description "Subscriber's interface name";
     }
     leaf actual-net-data-downstream {
       type uint32;
       description "Actual net data downstream";
     }
     leaf neighbor-ip-address {
       type jt:ipaddr;
       description "IP address of the ANCP neighbor";
     }
     list ancp-subscriber {
       leaf subscriber-stale-flag {
         type string;
         description "ANCP neighbor stale entry flag";
       }
       leaf access-loop-identifier {
         type string;
         description "Subscriber circuit identifier";
       }
       leaf dsl-line-state {
         type string;
         description "DSL line state";
       }
       leaf access-tech-type {
         type string;
         description "Access Technology Type";
       }
       leaf access-type {
         type string;
         description "Access type";
       }
       leaf interface {
         type string;
         description "Subscriber's interface name";
       }
       leaf actual-net-data-downstream {
         type uint32;
         description "Actual net data downstream";
       }
       leaf neighbor-ip-address {
         type jt:ipaddr;
         description "IP address of the ANCP neighbor";
       }
     }
     list ancp-neighbor {
       leaf received-rcode-bad-request-msg-count {
         type uint64;
         description "Result code: bad request message count";
       }
       leaf sent-rcode-bad-request-msg-count {
         type uint64;
         description "Result code: bad request message count";
       }
       leaf received-rcode-port-down-count {
         type uint64;
         description "Result code: port(s) down count";
       }
       leaf sent-rcode-port-down-count {
         type uint64;
         description "Result code: port(s) down count";
       }
       leaf received-rcode-out-of-resources-count {
         type uint64;
         description "Result code: out of resources count";
       }
       leaf sent-rcode-out-of-resources-count {
         type uint64;
         description "Result code: out of resources count";
       }
       leaf received-rcode-request-msg-not-implemented-count {
         type uint64;
         description "Result code: message not implemented count";
       }
       leaf sent-rcode-request-msg-not-implemented-count {
         type uint64;
         description "Result code: message not implemented count";
       }
       leaf received-rcode-bad-msg-count {
         type uint64;
         description "Result code: bad message count";
       }
       leaf sent-rcode-bad-msg-count {
         type uint64;
         description "Result code: bad message count";
       }
       leaf received-rcode-tlv-missing-count {
         type uint64;
         description "Result code: TLV missing count";
       }
       leaf sent-rcode-tlv-missing-count {
         type uint64;
         description "Result code: TLV missing count";
       }
       leaf received-rcode-bad-tlv-contents-count {
         type uint64;
         description "Result code: invalid TLV contents count";
       }
       leaf sent-rcode-bad-tlv-contents-count {
         type uint64;
         description "Result code: invalid TLV contents count";
       }
       leaf received-rcode-unknown-port-count {
         type uint64;
         description "Result code: unknown port count";
       }
       leaf sent-rcode-unknown-port-count {
         type uint64;
         description "Result code: unknown port count";
       }
       leaf partition-id {
         type int32;
         description "Neighbor partition ID";
       }
     }
     leaf access-loop-remote-identifier {
       type string;
       description "Subscriber remote identifier";
     }
     leaf access-aggregate-circuit-ascii-identifier {
       type string;
       description "Aggregate circuit ASCII identifier";
     }
     leaf access-aggregate-circuit-binary-identifier {
       type string;
       description "Aggregate circuit binary identifier";
     }
     leaf access-loop-encapsulation-data-link {
       type string;
       description "Access loop encapsulation data link type";
     }
     leaf access-loop-encapsulation-encapsulation1 {
       type string;
       description "Access loop encapsulation encapsulation1";
     }
     leaf access-loop-encapsulation-encapsulation2 {
       type string;
       description "Access loop encapsulation encapsulation2";
     }
     leaf interface-type {
       type string;
       description "Subscriber's interface type";
     }
     leaf actual-net-data-upstream {
       type uint32;
       description "Actual net data upstream";
     }
     leaf minimum-net-data-upstream {
       type uint32;
       description "Minimum net data upstream";
     }
     leaf minimum-net-data-downstream {
       type uint32;
       description "Minimum net data downstream";
     }
     leaf maximum-net-data-upstream {
       type uint32;
       description "Maximum net data upstream";
     }
     leaf maximum-net-data-downstream {
       type uint32;
       description "Maximum net data downstream";
     }
     leaf attainable-net-data-upstream {
       type uint32;
       description "Attainable net data upstream";
     }
     leaf attainable-net-data-downstream {
       type uint32;
       description "Attainable net data downstream";
     }
     leaf minimum-low-power-data-upstream {
       type uint32;
       description "Minimum net low power upstream";
     }
     leaf minimum-low-power-data-downstream {
       type uint32;
       description "Minimum net low power downstream";
     }
     leaf maximum-interleave-delay-upstream {
       type uint32;
       description "Maximum interleaving delay upstream";
     }
     leaf maximum-interleave-delay-downstream {
       type uint32;
       description "Maximum interleaving delay downstream";
     }
     leaf actual-interleave-delay-upstream {
       type uint32;
       description "Actual interleaving delay upstream";
     }
     leaf actual-interleave-delay-downstream {
       type uint32;
       description "Actual interleaving delay downstream";
     }
     leaf expected-throughput-upstream {
       type uint32;
       description "Expected throughput at L2 upstream";
     }
     leaf expected-throughput-downstream {
       type uint32;
       description "Expected throughput at L2 downstream";
     }
     leaf attainable-expected-throughput-upstream {
       type uint32;
       description "Attainable expected throughput at L2 upstream";
     }
     leaf attainable-expected-throughput-downstream {
       type uint32;
       description "Attainable expected throughput at L2 downstream";
     }
     leaf gamma-data-upstream {
       type uint32;
       description "Gamma data rate upstream";
     }
     leaf gamma-data-downstream {
       type uint32;
       description "Gamma data rate downstream";
     }
     leaf attainable-gamma-data-upstream {
       type uint32;
       description "Attainable gamma data rate upstream";
     }
     leaf attainable-gamma-data-downstream {
       type uint32;
       description "Attainable gamma data rate downstream";
     }
     leaf ont-onu-average-data-downstream {
       type uint32;
       description "ONT/ONU average data rate downsteam";
     }
     leaf ont-onu-peak-data-downstream {
       type uint32;
       description "ONT/ONU peak data rate downsteam";
     }
     leaf ont-onu-max-data-upstream {
       type uint32;
       description "ONT/ONU maximum data rate upsteam";
     }
     leaf ont-onu-assured-data-upstream {
       type uint32;
       description "ONT/ONU assured data rate upsteam";
     }
     leaf pon-tree-max-data-upstream {
       type uint32;
       description "PON tree maximum data rate upsteam";
     }
     leaf pon-tree-max-data-downstream {
       type uint32;
       description "PON tree maximum data rate downsteam";
     }
     leaf downstream-rate {
       type uint32;
       description "Downstream rate";
     }
   }
   grouping ancp-summary-information-block {
     container ancp-neighbor-summary {
       leaf ancp-neighbor-status-summary {
         type string;
         description "Neighbor summary";
       }
     }
     container ancp-neighbors-summary {
       leaf ancp-configured-status-nbr-summary {
         type uint32;
         description "Configured state summary";
       }
       leaf ancp-establishing-status-nbr-summary {
         type uint32;
         description "Establishing state summary";
       }
       leaf ancp-established-status-nbr-summary {
         type uint32;
         description "Established state summary";
       }
       leaf ancp-not-established-status-nbr-summary {
         type uint32;
         description "Not established state summary";
       }
       leaf ancp-total-status-nbr-summary {
         type uint32;
         description "Total state summary";
       }
     }
     container ancp-subscribers-summary {
       leaf ancp-show-time-status-subscr-summary {
         type uint32;
         description "SYN sent state summary";
       }
       leaf ancp-idle-status-subscr-summary {
         type uint32;
         description "SYN received state summary";
       }
       leaf ancp-silent-status-subscr-summary {
         type uint32;
         description "Established state summary";
       }
       leaf ancp-unknown-status-subscr-summary {
         type uint32;
         description "Unknown state summary";
       }
       leaf ancp-total-status-subscr-summary {
         type uint32;
         description "Total state summary";
       }
     }
   }
   grouping ancp-statistics-information-block {
     leaf neighbor-count {
       type int32;
       description "Count of ANCP neighbors in the system";
     }
     leaf subscriber-count {
       type int32;
       description "Count of ANCP subscribers in the system";
     }
     leaf accept-count {
       type uint64;
       description "Count of session accepts";
     }
     leaf accept-fail-count {
       type uint64;
       description "Count of session accept failures";
     }
     leaf accept-config-deny-count {
       type uint64;
       description "Count of session accept denied because of no configuration";
     }
     leaf received-syn-count {
       type uint64;
       description "Count of SYN messages received";
     }
     leaf received-synack-count {
       type uint64;
       description "Count of SYNACK messages received";
     }
     leaf received-rstack-count {
       type uint64;
       description "Count of RSTACK messages received";
     }
     leaf received-ack-count {
       type uint64;
       description "Count of ACK messages received";
     }
     leaf received-port-up-count {
       type uint64;
       description "Count of port up messages received";
     }
     leaf received-port-down-count {
       type uint64;
       description "Count of port down messages received";
     }
     leaf received-generic-response-count {
       type uint64;
       description "Count of generic response messages received";
     }
     leaf received-adjacency-update-count {
       type uint64;
       description "Count of adjacency update messages received";
     }
     leaf received-oam-count {
       type uint64;
       description "Count of OAM messages received";
     }
     leaf received-other-count {
       type uint64;
       description "Count of other messages received";
     }
     leaf sent-syn-count {
       type uint64;
       description "Count of SYN messages sent";
     }
     leaf sent-synack-count {
       type uint64;
       description "Count of SYNACK messages sent";
     }
     leaf sent-rstack-count {
       type uint64;
       description "Count of RSTACK messages sent";
     }
     leaf sent-ack-count {
       type uint64;
       description "Count of ACK messages sent";
     }
     leaf sent-generic-response-count {
       type uint64;
       description "Count of generic response messages sent";
     }
     leaf sent-oam-count {
       type uint64;
       description "Count of OAM messages sent";
     }
     leaf received-rcode-bad-request-msg-count {
       type uint64;
       description "Result code: bad request message count";
     }
     leaf sent-rcode-bad-request-msg-count {
       type uint64;
       description "Result code: bad request message count";
     }
     leaf received-rcode-port-down-count {
       type uint64;
       description "Result code: port(s) down count";
     }
     leaf sent-rcode-port-down-count {
       type uint64;
       description "Result code: port(s) down count";
     }
     leaf received-rcode-out-of-resources-count {
       type uint64;
       description "Result code: out of resources count";
     }
     leaf sent-rcode-out-of-resources-count {
       type uint64;
       description "Result code: out of resources count";
     }
     leaf received-rcode-request-msg-not-implemented-count {
       type uint64;
       description "Result code: message not implemented count";
     }
     leaf sent-rcode-request-msg-not-implemented-count {
       type uint64;
       description "Result code: message not implemented count";
     }
     leaf received-rcode-bad-msg-count {
       type uint64;
       description "Result code: bad message count";
     }
     leaf sent-rcode-bad-msg-count {
       type uint64;
       description "Result code: bad message count";
     }
     leaf received-rcode-tlv-missing-count {
       type uint64;
       description "Result code: TLV missing count";
     }
     leaf sent-rcode-tlv-missing-count {
       type uint64;
       description "Result code: TLV missing count";
     }
     leaf received-rcode-bad-tlv-contents-count {
       type uint64;
       description "Result code: invalid TLV contents count";
     }
     leaf sent-rcode-bad-tlv-contents-count {
       type uint64;
       description "Result code: invalid TLV contents count";
     }
     leaf received-rcode-unknown-port-count {
       type uint64;
       description "Result code: unknown port count";
     }
     leaf sent-rcode-unknown-port-count {
       type uint64;
       description "Result code: unknown port count";
     }
   }
 }
