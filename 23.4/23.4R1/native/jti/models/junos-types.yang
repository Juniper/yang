module junos-types {
  yang-version 1.1;
  namespace "http://yang.juniper.net/junos/types";
  prefix jt;

  import junos-base-extensions {
    prefix junos-base;
  }

  organization
    "Juniper Networks, Inc.";

  contact
    "Juniper Networks, Inc.

     1133 Innovation Way
     Sunnyvale, CA 94089

     +1 888 314-5822

     E-mail: yang-support@juniper.net";

  description
    "This module contains a collection of common JUNOS types.

     Copyright (c) 2023 Juniper Networks, Inc.
     All rights reserved.";

  revision 2023-08-17 {
    description
      "Addition of initial distinct absolute time types. Marking
       timeticks64 as deprecated.";
    reference "0.2.0";
  }

  revision 2023-06-08 {
    description
      "Initial revision";
    reference "0.1.0";
  }

  junos-base:version "0.2.0";

  typedef timeticks64 {
    type uint64;
    status deprecated;
    description
      "The timeticks64 represents the time, modulo 2^64 between two
       epochs.  The leaf using this type must define the epochs that
       tests are relative to as well as the precision units.";
   }

  typedef absolute-time-seconds {
    type uint64;
    units "seconds";
    description
      "The absolute timestamp in seconds, modulo 2^64 expressed relative
       to the Unix Epoch (Jan 1, 1970 00:00:00 UTC).";
  }

  typedef absolute-time-milliseconds {
    type uint64;
    units "milliseconds";
    description
      "The absolute timestamp in milliseconds, modulo 2^64 expressed
       relative to the Unix Epoch (Jan 1, 1970 00:00:00 UTC).";
  }

  typedef absolute-time-microseconds {
    type uint64;
    units "microseconds";
    description
      "The absolute timestamp in microseconds, modulo 2^64 expressed
       relative to the Unix Epoch (Jan 1, 1970 00:00:00 UTC).";
  }
}
