/*
 * Copyright (c) 2023 Juniper Networks, Inc.
 * All rights reserved.
 */
 module junos-rpc-l2circuit {
   namespace "http://yang.juniper.net/junos/rpc/l2circuit";

   prefix l2circuit;

   import junos-common-ddl-extensions {
     prefix junos;
     revision-date 2023-01-01;
   }

   import junos-common-types {
     prefix jt;
     revision-date 2023-01-01;
   }

   organization "Juniper Networks, Inc.";

   contact "yang-support@juniper.net";

   description "Junos RPC YANG module for l2circuit command(s)";

   revision 2023-01-01 {
     description "Junos: 23.4R1.10";
   }

   rpc get-l2ckt-connection-information {
     description "Show the Layer 2 circuit connections";
     junos:command "show l2circuit connections";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf neighbor {
         description "IP address of neighbor";
         default "all";
         type string;
       }
       leaf interface {
         description "Name of interface";
         default "all";
         type string;
       }
       leaf state {
         junos:cli-feature "nokeyword";
         default "up-down";
         type enumeration {
           enum "down" {
             description "Display nonoperational connections";
           }
           enum "up" {
             description "Display operational connections";
           }
           enum "up-down" {
             description "Display both operational and nonoperational connections (default)";
           }
         }
       }
       leaf level {
         junos:cli-feature "nokeyword";
         default "status";
         type enumeration {
           enum "brief" {
             description "Display one-line version of output";
           }
           enum "extensive" {
             description "Display connection status and history";
           }
           enum "history" {
             description "Display connection history";
           }
           enum "instance-history" {
             description "Display instance history";
           }
           enum "status" {
             description "Display connection and interface status (default)";
           }
           enum "summary" {
             description "Display summary output";
           }
         }
       }
     }
     output {
       container l2circuit-connection-information {
         uses l2circuit-connection-information-block;
       }
     }
   }
   rpc get-l2ckt-pw-auto-sensing-information {
     description "Show the Layer 2 circuit PW auto-sensing information";
     junos:command "show l2circuit auto-sensing";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf neighbor {
         description "IP address of neighbor";
         default "all";
         type string;
       }
       leaf vc-id {
         description "VC ID";
         default "all";
         type string;
       }
     }
     output {
       container l2circuit-pw-auto-sensing-information {
         uses l2circuit-pw-auto-sensing-information-block;
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping l2circuit-connection-information-block {
     container l2circuit-neighbor {
       leaf neighbor-address {
         type jt:ipaddr;
         description "IP address of this neighbor";
       }
       leaf lsw-interface-name {
         type string;
       }
       leaf neighbor-display-error {
         type string;
       }
       list connection {
         leaf-list connection.heading {
           type string;
         }
         leaf connection-id {
           type string;
         }
         leaf connection-type {
           type string;
         }
         leaf connection-status {
           type string;
         }
         leaf last-change {
           type string;
         }
         leaf up-transitions {
           type int32;
         }
         leaf remote-pe {
           type jt:ipaddr;
         }
         leaf control-word {
           type string;
         }
         leaf control-word-type {
           type string;
         }
         leaf interface-encapsulation {
           type string;
         }
         leaf inbound-label {
           type string;
         }
         leaf outbound-label {
           type string;
         }
         leaf pw-status-tlv {
           type string;
         }
         leaf local-pw-status-code {
           type int32;
         }
         leaf remote-pw-status-code {
           type int32;
         }
         leaf connection-protection {
           type string;
         }
         leaf mesh-group-name {
           type string;
           description "Name of mesh-group";
         }
         leaf vc-flow-label-transmit {
           type string;
         }
         leaf vc-flow-label-receive {
           type string;
         }
         leaf auto-sensed {
           type empty;
           description "Auto-sensed";
         }
         container local-interface {
           leaf interface-name {
             type string;
             description "Name of interface";
           }
           leaf interface-status {
             type string;
           }
           leaf interface-encapsulation {
             type string;
           }
           leaf working-status {
             type string;
           }
           leaf profile-name {
             type string;
           }
           leaf profile-varset-name {
             type string;
           }
           leaf interface-description {
             type string;
           }
         }
         container remote-interface {
           leaf interface-name {
             type string;
             description "Name of interface";
           }
           leaf interface-status {
             type string;
           }
           leaf interface-encapsulation {
             type string;
           }
         }
         container connection-bandwidth {
           leaf connection-bandwidth.heading {
             type string;
             description "Bandwidth of a layer 2 connection";
           }
           leaf bandwidth {
             type int32;
           }
           leaf class-type {
             type int32;
           }
           leaf class-bandwidth {
             type int32;
           }
         }
         container history {
           leaf history.category-heading {
             type string;
           }
           leaf history.heading {
             type string;
           }
           container history-element {
             leaf log-time-stamp {
               type string;
             }
             leaf log-event {
               type string;
             }
             leaf changed-entity {
               type string;
             }
           }
         }
         container egress-protection-protector {
           leaf protector-state {
             type string;
           }
           leaf protector-interface {
             type string;
           }
           leaf interface-status {
             type string;
           }
           leaf protector-pe {
             type jt:ipaddr;
           }
           leaf protector-pe-status {
             type string;
           }
           leaf protection-context {
             type jt:ipaddr;
           }
           leaf context-status {
             type string;
           }
           leaf context-lsp {
             type string;
           }
         }
         container egress-protection-protected-l2ckt {
           leaf protected-l2ckt-state {
             type string;
           }
           leaf protected-l2ckt-ingress {
             type jt:ipaddr;
           }
           leaf protected-l2ckt-egress {
             type jt:ipaddr;
           }
           leaf protected-l2ckt-vcid {
             type string;
           }
         }
       }
       container connections-summary {
         leaf vc-up-count {
           type int32;
         }
         leaf vc-down-count {
           type int32;
         }
       }
     }
     container history {
       leaf history.category-heading {
         type string;
       }
       leaf history.heading {
         type string;
       }
       container history-element {
         leaf log-time-stamp {
           type string;
         }
         leaf log-event {
           type string;
         }
         leaf changed-entity {
           type string;
         }
       }
     }
   }
   grouping l2circuit-pw-auto-sensing-information-block {
     leaf auto-sensing-neighbor {
       type jt:ipaddr;
     }
     leaf vc-id {
       type int32;
     }
     leaf encapsulation {
       type string;
     }
     leaf mtu {
       type int32;
       description "MTU along an interface";
     }
     leaf control-word {
       type string;
     }
     leaf sensed {
       type string;
     }
     leaf session-id {
       type int32;
       description "Unique identifier for RSVP session";
     }
     leaf state {
       type string;
       description "HFRR profile Current state";
     }
     leaf total-count {
       type int32;
     }
   }
 }
