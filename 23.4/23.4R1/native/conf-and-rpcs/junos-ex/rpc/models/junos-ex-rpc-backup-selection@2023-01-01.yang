/*
 * Copyright (c) 2023 Juniper Networks, Inc.
 * All rights reserved.
 */
 module junos-ex-rpc-backup-selection {
   namespace "http://yang.juniper.net/junos-ex/rpc/backup-selection";

   prefix backup-selection;

   import junos-common-types {
     prefix jt;
     revision-date 2023-01-01;
   }

   organization "Juniper Networks, Inc.";

   contact "yang-support@juniper.net";

   description "Junos RPC YANG module for backup-selection command(s)";

   revision 2023-01-01 {
     description "Junos: 23.4R1.10";
   }

   rpc get-backup-selection {
     description "Show backup selection policies information";
     input {
       choice daemon-select {
         case logical-system {
           leaf logical-system {
             description "Name of logical system, or 'all'";
             type string {
             }
           }
         }
         case rib-sharding {
           leaf rib-sharding {
             description "Name of rib shard";
             type string {
             }
           }
         }
       }
       leaf prefix {
         description "IP address and optional prefix length of destination";
         type jt:ipprefix-optional;
       }
       leaf interface {
         description "Name of interface";
         type union {
           type jt:interface-wildcard;
           type string {
             pattern "<.*>|$.*";
           }
         }
       }
     }
     output {
       container juniper-backup-selection {
         uses juniper-backup-selection-block;
       }
     }
   }
   rpc get-backup-selection-instance {
     description "Show routing instances information";
     input {
       choice daemon-select {
         case logical-system {
           leaf logical-system {
             description "Name of logical system, or 'all'";
             type string {
             }
           }
         }
         case rib-sharding {
           leaf rib-sharding {
             description "Name of rib shard";
             type string {
             }
           }
         }
       }
       leaf instance-name {
         description "Instance name";
         type string;
       }
       leaf prefix {
         description "IP address and optional prefix length of destination";
         type jt:ipprefix-optional;
       }
       leaf interface {
         description "Name of interface";
         type union {
           type jt:interface-wildcard;
           type string {
             pattern "<.*>|$.*";
           }
         }
       }
     }
     output {
       container backup-selection-instance-information {
         uses backup-selection-instance-information-block;
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping juniper-backup-selection-block {
     container backup-selection-policy-dest {
       leaf-list address-prefix {
         type jt:ipaddr;
       }
       container backup-selection-policy-intf {
         leaf backup-selection-protection-type {
           type string;
         }
         leaf backup-selection-downstream-paths-only {
           type string;
         }
         leaf backup-selection-srlg-type {
           type string;
         }
         leaf backup-selection-bw-ge-primary {
           type string;
         }
         leaf backup-selection-root-metric {
           type string;
         }
         leaf backup-selection-dest-metric {
           type string;
         }
         leaf interface-name {
           type string;
           description "Name of interface";
         }
         container backup-selection-admin-group-exclude {
           leaf-list admin-group-exclude-name {
             type string;
           }
         }
         container backup-selection-admin-group-incall {
           leaf-list admin-group-incall-name {
             type string;
           }
         }
         container backup-selection-admin-group-incany {
           leaf-list admin-group-incany-name {
             type string;
           }
         }
         container backup-selection-admin-group-preference {
           leaf-list admin-group-preference-name {
             type string;
           }
         }
         container backup-selection-backup-neighbor-exclude {
           leaf-list address-prefix {
             type jt:ipaddr;
           }
         }
         container backup-selection-backup-neighbor-preference {
           leaf-list address-prefix {
             type jt:ipaddr;
           }
         }
         container backup-selection-neighbor-exclude {
           leaf-list address-prefix {
             type jt:ipaddr;
           }
         }
         container backup-selection-neighbor-preference {
           leaf-list address-prefix {
             type jt:ipaddr;
           }
         }
         container backup-selection-neighbor-tag-exclude {
           leaf-list neighbor-tag-value {
             type int32;
           }
         }
         container backup-selection-neighbor-tag-preference {
           leaf-list neighbor-tag-value {
             type int32;
           }
         }
         container backup-selection-metric-order {
           leaf-list backup-selection-metric-type {
             type string;
           }
         }
         container backup-selection-eval-order {
           leaf-list backup-selection-eval-type {
             type string;
           }
         }
       }
     }
   }
   grouping backup-selection-instance-information-block {
     container backup-selection-policy-dest {
       leaf-list address-prefix {
         type jt:ipaddr;
       }
       container backup-selection-policy-intf {
         leaf backup-selection-protection-type {
           type string;
         }
         leaf backup-selection-downstream-paths-only {
           type string;
         }
         leaf backup-selection-srlg-type {
           type string;
         }
         leaf backup-selection-bw-ge-primary {
           type string;
         }
         leaf backup-selection-root-metric {
           type string;
         }
         leaf backup-selection-dest-metric {
           type string;
         }
         leaf interface-name {
           type string;
           description "Name of interface";
         }
         container backup-selection-admin-group-exclude {
           leaf-list admin-group-exclude-name {
             type string;
           }
         }
         container backup-selection-admin-group-incall {
           leaf-list admin-group-incall-name {
             type string;
           }
         }
         container backup-selection-admin-group-incany {
           leaf-list admin-group-incany-name {
             type string;
           }
         }
         container backup-selection-admin-group-preference {
           leaf-list admin-group-preference-name {
             type string;
           }
         }
         container backup-selection-backup-neighbor-exclude {
           leaf-list address-prefix {
             type jt:ipaddr;
           }
         }
         container backup-selection-backup-neighbor-preference {
           leaf-list address-prefix {
             type jt:ipaddr;
           }
         }
         container backup-selection-neighbor-exclude {
           leaf-list address-prefix {
             type jt:ipaddr;
           }
         }
         container backup-selection-neighbor-preference {
           leaf-list address-prefix {
             type jt:ipaddr;
           }
         }
         container backup-selection-neighbor-tag-exclude {
           leaf-list neighbor-tag-value {
             type int32;
           }
         }
         container backup-selection-neighbor-tag-preference {
           leaf-list neighbor-tag-value {
             type int32;
           }
         }
         container backup-selection-metric-order {
           leaf-list backup-selection-metric-type {
             type string;
           }
         }
         container backup-selection-eval-order {
           leaf-list backup-selection-eval-type {
             type string;
           }
         }
       }
     }
   }
 }
