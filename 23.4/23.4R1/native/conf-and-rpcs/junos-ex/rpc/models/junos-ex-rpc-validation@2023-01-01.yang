/*
 * Copyright (c) 2023 Juniper Networks, Inc.
 * All rights reserved.
 */
 module junos-ex-rpc-validation {
   namespace "http://yang.juniper.net/junos-ex/rpc/validation";

   prefix validation;

   import junos-common-types {
     prefix jt;
     revision-date 2023-01-01;
   }

   organization "Juniper Networks, Inc.";

   contact "yang-support@juniper.net";

   description "Junos RPC YANG module for validation command(s)";

   revision 2023-01-01 {
     description "Junos: 23.4R1.10";
   }

   rpc get-validation-statistics-information {
     description "Show route validation statistics";
     input {
       choice daemon-select {
         case logical-system {
           leaf logical-system {
             description "Name of logical system";
             type string {
             }
           }
         }
       }
       leaf instance {
         description "Name of route validation instance";
         type string;
       }
     }
     output {
       container rv-statistics-information {
         uses rv-statistics-information-block;
       }
     }
   }
   rpc get-validation-group-information {
     description "Show route validation redundancy groups";
     input {
       choice daemon-select {
         case logical-system {
           leaf logical-system {
             description "Name of logical system";
             type string {
             }
           }
         }
       }
       leaf instance {
         description "Name of route validation instance";
         type string;
       }
     }
     output {
       container rv-group-information {
         uses rv-group-information-block;
       }
     }
   }
   rpc get-validation-session-information {
     description "Show route validation session information";
     input {
       choice daemon-select {
         case logical-system {
           leaf logical-system {
             description "Name of logical system";
             type string {
             }
           }
         }
       }
       leaf verbosity_level {
         default "brief";
         type enumeration {
           enum "brief" {
             description "Display brief output (default)";
           }
           enum "detail" {
             description "Display detailed output";
           }
         }
       }
       leaf destination {
         description "IP address of session";
         type jt:ipaddr;
       }
       leaf instance {
         description "Name of route validation instance";
         type string;
       }
     }
     output {
       container rv-session-information {
         uses rv-session-information-block;
       }
     }
   }
   rpc get-validation-database-information {
     description "Show contents of route validation database";
     input {
       choice daemon-select {
         case logical-system {
           leaf logical-system {
             description "Name of logical system";
             type string {
             }
           }
         }
       }
       leaf verbosity_level {
         default "brief";
         type enumeration {
           enum "brief" {
             description "Display brief output (default)";
           }
           enum "detail" {
             description "Display detailed output";
           }
         }
       }
       leaf record {
         description "Filter by record";
         type jt:ipprefix;
       }
       leaf origin-autonomous-system {
         description "Filter by Origin Autonomous System";
         type union {
           type uint32;
           type string {
             pattern "<.*>|$.*";
           }
         }
       }
       leaf session {
         description "Filter by Session IP Address";
         type jt:ipaddr;
       }
       leaf mismatch {
         description "Filter by mismatched Origin Autonomous System";
         type empty;
       }
       leaf database-name {
         description "Filter within a named database";
         type string;
       }
       leaf instance {
         description "Name of route validation instance";
         type string;
       }
     }
     output {
       container rv-database-information {
         uses rv-database-information-block;
       }
     }
   }
   rpc get-validation-replication-database-information {
     description "Show contents of route validation replication database";
     input {
       choice daemon-select {
         case logical-system {
           leaf logical-system {
             description "Name of logical system";
             type string {
             }
           }
         }
       }
       leaf verbosity_level {
         default "brief";
         type enumeration {
           enum "brief" {
             description "Display brief output (default)";
           }
           enum "detail" {
             description "Display detailed output";
           }
         }
       }
       leaf record {
         description "Filter by record";
         type jt:ipprefix;
       }
       leaf origin-autonomous-system {
         description "Filter by Origin Autonomous System";
         type union {
           type uint32;
           type string {
             pattern "<.*>|$.*";
           }
         }
       }
       leaf session {
         description "Filter by Session IP Address";
         type jt:ipaddr;
       }
       leaf database-name {
         description "Filter within a named database";
         type string;
       }
       leaf instance {
         description "Name of route validation instance";
         type string;
       }
     }
     output {
       container rv-replication-database-information {
         uses rv-replication-database-information-block;
       }
     }
   }
   rpc get-validation-source-file-information {
     description "Show states of route validation source-file";
     output {
       container rv-source-file-information {
         uses rv-source-file-information-block;
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping rv-statistics-information-block {
     container rv-statistics {
       leaf rv-record-count {
         type uint32;
       }
       leaf rv-replication-record-count {
         type uint32;
       }
       leaf rv-prefix-count {
         type uint32;
       }
       leaf rv-origin-as-count {
         type uint32;
       }
       leaf rv-memory-utilization {
         type string;
       }
       leaf rv-policy-origin-validation-requests {
         type uint32;
       }
       leaf rv-policy-origin-validation-results-valid {
         type uint32;
       }
       leaf rv-policy-origin-validation-results-invalid {
         type uint32;
       }
       leaf rv-policy-origin-validation-results-unknown {
         type uint32;
       }
       leaf rv-bgp-import-policy-reevaluations {
         type uint32;
       }
       leaf rv-bgp-import-policy-rib-name {
         type uint32;
       }
       leaf rv-bgp-import-policy-rib-reevaluations {
         type uint32;
       }
       leaf rv-resync-conn-flaps {
         type uint32;
       }
       leaf last-resync-started {
         type string;
       }
       leaf last-resync-complete {
         type string;
       }
       leaf last-resync-conn-down {
         type string;
       }
       leaf last-resync-conn-ready {
         type string;
       }
       container rv-vrp-information {
         description "VRP table statistics information";
         leaf count-of-records {
           type uint32;
         }
         leaf count-of-reevaluations {
           type uint32;
         }
         leaf count-of-records-added {
           type uint32;
         }
         leaf count-of-records-withdrawn {
           type uint32;
         }
       }
       container rv-database-statistics {
         leaf rv-database-name {
           type string;
         }
         leaf rv-database-record-count {
           type uint32;
         }
         leaf rv-database-origin-as-count {
           type uint32;
         }
         leaf rv-database-origin-validation-requests {
           type uint32;
         }
         leaf rv-database-origin-validation-results-valid {
           type uint32;
         }
         leaf rv-database-origin-validation-results-invalid {
           type uint32;
         }
         leaf rv-database-origin-validation-results-unknown {
           type uint32;
         }
         leaf rv-bgp-import-policy-database-reevaluations {
           type uint32;
         }
         container rv-vrp-information {
           description "VRP table statistics information";
           leaf count-of-records {
             type uint32;
           }
           leaf count-of-reevaluations {
             type uint32;
           }
           leaf count-of-records-added {
             type uint32;
           }
           leaf count-of-records-withdrawn {
             type uint32;
           }
         }
         list rv-bgp-import-policy-database-rib-statistics {
           leaf rv-bgp-import-policy-database-rib-name {
             type string;
           }
           leaf rv-bgp-import-policy-database-rib-reevaluations {
             type uint32;
           }
         }
       }
     }
   }
   grouping rv-group-information-block {
     container rv-group {
       leaf instance-name {
         type string;
       }
       leaf group-name {
         type string;
       }
       leaf maximum-sessions {
         type uint32;
       }
       leaf ip-address {
         type jt:ipaddr;
       }
       leaf session-state {
         type string;
         description "State of the session session";
       }
       leaf preference {
         type int32;
         description "Preference for the route";
       }
     }
   }
   grouping rv-session-information-block {
     container rv-session {
       leaf ip-address {
         type jt:ipaddr;
       }
       leaf session-state {
         type string;
         description "State of the session session";
       }
       leaf session-flaps {
         type uint32;
       }
       leaf session-uptime {
         type string;
       }
       leaf ip-prefix-count {
         type uint32;
       }
       leaf ip6-prefix-count {
         type uint32;
       }
       leaf session-dest-database {
         type string;
       }
       leaf last-eod-received {
         type string;
       }
       leaf last-reset-query {
         type string;
       }
       leaf last-serial-query {
         type string;
       }
       leaf last-gc-started {
         type string;
       }
       leaf last-gc-end {
         type string;
       }
       leaf last-gc-reason {
         type string;
         description "Reason for last session GC";
       }
       leaf session-index {
         type uint32;
       }
       leaf group-name {
         type string;
       }
       leaf preference {
         type int32;
         description "Preference for the route";
       }
       leaf local-ip-address {
         type jt:ipaddr;
       }
       leaf port {
         type uint32;
       }
       leaf local-cache {
         type string;
       }
       leaf refresh-time {
         type uint32;
       }
       leaf hold-time {
         type uint32;
       }
       leaf record-life-time {
         type uint32;
       }
       leaf serial-full {
         type uint32;
       }
       leaf serial-incremental {
         type uint32;
       }
       leaf connect-retry-time {
         type uint32;
       }
       leaf authentication {
         type string;
       }
       leaf last-update {
         type string;
       }
     }
   }
   grouping rv-database-information-block {
     container rv-database {
       leaf database-name {
         type string;
       }
       leaf database-id {
         type uint32;
       }
       leaf ip-prefix-count {
         type uint32;
       }
       leaf ip6-prefix-count {
         type uint32;
       }
       container rv-database-entry {
         leaf ip-prefix {
           type jt:ipprefix;
         }
         leaf maximum-length {
           type uint32;
         }
         leaf origin-as {
           type uint32;
         }
         leaf ip-address {
           type jt:ipaddr;
         }
         leaf validation-state {
           type string;
         }
         leaf validation-mismatch {
           type string;
         }
         leaf instance-name {
           type string;
         }
         leaf last-update {
           type string;
         }
         leaf last-received {
           type int32;
         }
       }
     }
   }
   grouping rv-replication-database-information-block {
     container rv-replication-database {
       leaf instance-name {
         type string;
       }
       leaf ip-prefix-count {
         type uint32;
       }
       leaf ip6-prefix-count {
         type uint32;
       }
       container rv-replication-database-entry {
         leaf ip-prefix {
           type jt:ipprefix;
         }
         leaf maximum-length {
           type uint32;
         }
         leaf origin-as {
           type uint32;
         }
         leaf ip-address {
           type jt:ipaddr;
         }
         leaf validation-state {
           type string;
         }
         leaf database-name {
           type string;
         }
         leaf instance-name {
           type string;
         }
         leaf last-update {
           type string;
         }
         leaf last-received {
           type int32;
         }
       }
     }
   }
   grouping rv-source-file-information-block {
     container rv-source-file {
       leaf rv-source-file-name {
         type string;
       }
       leaf rv-source-file-status {
         type string;
       }
       leaf rv-source-file-records {
         type uint32;
       }
       leaf rv-source-file-version {
         type string;
       }
       leaf rv-source-file-last-read {
         type string;
       }
       leaf rv-source-file-error-reason {
         type string;
       }
       leaf rv-source-file-last-synced {
         type string;
       }
       leaf rv-source-file-process-time {
         type string;
       }
       leaf rv-source-file-serial {
         type uint32;
       }
       leaf rv-source-file-size {
         type uint32;
       }
       leaf rv-source-file-reads {
         type uint32;
       }
       leaf rv-source-file-synced {
         type uint32;
       }
       leaf rv-source-file-reverts {
         type uint32;
       }
       leaf rv-source-file-errors {
         type uint32;
       }
     }
   }
 }
