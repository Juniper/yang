/*
 * Copyright (c) 2023 Juniper Networks, Inc.
 * All rights reserved.
 */
 module junos-qfx-conf-root {
   namespace "http://yang.juniper.net/junos-qfx/conf/root";

   prefix jc;

   import junos-common-types {
     prefix jt;
     revision-date 2023-01-01;
   }

   organization "Juniper Networks, Inc.";

   contact "yang-support@juniper.net";

   description "Junos YANG module for configuration hierarchies.";

   revision 2023-01-01 {
     description "Junos: 23.4R1.10";
   }

   container configuration {
     config true;
     uses juniper-config;
     list groups {
       key name;
       ordered-by user;
       description "Configuration groups";
       uses juniper-group;
     }
   }
   grouping juniper-config {
     leaf rcsid {
       description "Revision control system identifier";
       type string;
     }
     leaf version {
       description "Software version information";
       type string;
     }
     leaf-list apply-groups {
       ordered-by user;
       description "Groups from which to inherit configuration data";
       type string;
     }
     list apply-macro {
       key name;
       ordered-by user;
       description "Macro and parameters for commit script expansion";
       uses apply-macro-type;
     }
     container jsrc-partition {
       description "JSRC partition configuration";
       leaf jsrc-partition-name {
         description "JSRC partition name";
         type string {
           length "1 .. 63";
         }
       }
     }
     container jsrc {
       description "JSRC partition configuration";
       uses jsrc-options;
     }
   }
   grouping apply-macro-type {
     description "Macro data for commit-script expansion";
     leaf name {
       description "Name of the macro to be expanded";
       type string;
     }
     list data {
       key name;
       uses macro-data-type;
     }
   }
   grouping jsrc-options {
     uses apply-advanced;
     list partition {
       key name;
       ordered-by user;
       description "JSRC partition definition";
       leaf name {
         description "JSRC partition name";
         type string {
           length "1 .. 63";
         }
       }
       uses apply-advanced;
       leaf diameter-instance {
         description "JSRC diameter instance";
         type string {
           length "1 .. 63";
         }
         mandatory true;
       }
       leaf destination-realm {
         description "JSRC destination realm";
         type string {
           length "1 .. 63";
         }
         mandatory true;
       }
       leaf destination-host {
         description "JSRC destination host";
         type string {
           length "1 .. 63";
         }
         mandatory true;
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping juniper-group {
     description "Configuration groups";
     leaf name {
       description "Group name";
       type string {
         length "1 .. 254";
       }
     }
     container when {
       description "Specify additional conditions for groups";
       uses apply-advanced;
       container time {
         description "Time at which group should be effective";
         leaf start-time {
           description "Start time([yyyy-mm-dd.]hh:mm)";
           type string;
         }
         container to {
           description "End time";
           uses apply-advanced;
           leaf end-time {
             description "End time([yyyy-mm-dd.]hh:mm)";
             type string;
           }
         }
       }
       leaf-list peers {
         ordered-by user;
         description "Hosts on which this group should be effective";
         type string {
           length "1 .. 255";
         }
       }
       leaf chassis {
         description "Chassis id";
         type enumeration {
           enum "lcc0" {
             description "Chassis lcc0";
           }
           enum "lcc1" {
             description "Chassis lcc1";
           }
           enum "lcc2" {
             description "Chassis lcc2";
           }
           enum "lcc3" {
             description "Chassis lcc3";
           }
           enum "lcc4" {
             description "Chassis lcc4";
           }
           enum "lcc5" {
             description "Chassis lcc5";
           }
           enum "lcc6" {
             description "Chassis lcc6";
           }
           enum "lcc7" {
             description "Chassis lcc7";
           }
           enum "scc" {
             description "Chassis scc";
           }
           enum "sfc0" {
             description "Chassis sfc0";
           }
         }
       }
       leaf model {
         description "Model name";
         type string;
       }
       leaf routing-engine {
         description "Routing Engine";
         type enumeration {
           enum "re0" {
             description "RE0";
           }
           enum "re1" {
             description "RE1";
           }
         }
       }
       leaf member {
         description "Member of virtual chassis";
         type string;
       }
       leaf node {
         description "Node of cluster";
         type enumeration {
           enum "node0" {
             description "Node0";
           }
           enum "node1" {
             description "Node1";
           }
         }
       }
     }
     uses juniper-config;
   }
   grouping macro-data-type {
     leaf name {
       description "Keyword part of the keyword-value pair";
       type string;
     }
     leaf value {
       description "Value part of the keyword-value pair";
       type string;
     }
   }
 }
