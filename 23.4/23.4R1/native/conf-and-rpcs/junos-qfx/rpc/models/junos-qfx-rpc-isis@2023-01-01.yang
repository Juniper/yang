/*
 * Copyright (c) 2023 Juniper Networks, Inc.
 * All rights reserved.
 */
 module junos-qfx-rpc-isis {
   namespace "http://yang.juniper.net/junos-qfx/rpc/isis";

   prefix isis;

   import junos-common-types {
     prefix jt;
     revision-date 2023-01-01;
   }

   organization "Juniper Networks, Inc.";

   contact "yang-support@juniper.net";

   description "Junos RPC YANG module for isis command(s)";

   revision 2023-01-01 {
     description "Junos: 23.4R1.10";
   }

   rpc get-isis-adjacency-information {
     description "Show IS-IS adjacency database";
     input {
       choice daemon-select {
         case logical-system {
           leaf logical-system {
             description "Name of logical system, or 'all'";
             type string {
             }
           }
         }
       }
       leaf igp-instance {
         description "Name of igp-instance";
         type string;
       }
       leaf verbosity_level {
         default "brief";
         type enumeration {
           enum "brief" {
             description "Display brief output (default)";
           }
           enum "detail" {
             description "Display detailed output";
           }
           enum "extensive" {
             description "Display extensive output";
           }
         }
       }
       leaf instance {
         description "Name of IS-IS instance";
         type string;
       }
       leaf system-id {
         description "System ID of intermediate system";
         type string;
       }
     }
     output {
       container isis-adjacency-information {
         uses isis-adjacency-information-block;
       }
     }
   }
   rpc get-isis-adjacency-holddown-information {
     description "Show IS-IS adjacency-holddown status";
     input {
       choice daemon-select {
         case logical-system {
           leaf logical-system {
             description "Name of logical system, or 'all'";
             type string {
             }
           }
         }
       }
       leaf igp-instance {
         description "Name of igp-instance";
         type string;
       }
       leaf verbosity_level {
         default "brief";
         type enumeration {
           enum "brief" {
             description "Display brief output (default)";
           }
           enum "detail" {
             description "Display detailed output";
           }
           enum "extensive" {
             description "Display extensive output";
           }
         }
       }
       leaf instance {
         description "Name of IS-IS instance";
         type string;
       }
       leaf level {
         description "Number of IS-IS level";
         type union {
           type string {
             pattern "<.*>|$.*";
           }
           type uint32 {
             range "1 .. 2";
           }
         }
       }
     }
     output {
       container isis-adjacency-holddown-information {
         uses isis-adjacency-holddown-information-block;
       }
     }
   }
   rpc get-isis-authentication-information {
     description "Show IS-IS authentication information";
     input {
       choice daemon-select {
         case logical-system {
           leaf logical-system {
             description "Name of logical system, or 'all'";
             type string {
             }
           }
         }
       }
       leaf igp-instance {
         description "Name of igp-instance";
         type string;
       }
       leaf instance {
         description "Name of IS-IS instance";
         type string;
       }
     }
     output {
       container isis-authentication-information {
         uses isis-authentication-information-block;
       }
     }
   }
   rpc get-isis-bgporr-information {
     description "Show BGP optimal route reflection groups";
     input {
       choice daemon-select {
         case logical-system {
           leaf logical-system {
             description "Name of logical system, or 'all'";
             type string {
             }
           }
         }
       }
       leaf igp-instance {
         description "Name of igp-instance";
         type string;
       }
       leaf destination {
         description "IP address and optional prefix length of destination";
         type jt:ipprefix;
       }
       leaf instance {
         description "Name of IS-IS instance";
         type string;
       }
       leaf group {
         description "BGP optimal route-reflection peer group name";
         type string;
       }
     }
     output {
       container isis-bgporr-information {
         uses isis-bgporr-information-block;
       }
     }
   }
   rpc get-isis-database-information {
     description "Show IS-IS link-state database";
     input {
       choice daemon-select {
         case logical-system {
           leaf logical-system {
             description "Name of logical system, or 'all'";
             type string {
             }
           }
         }
       }
       leaf igp-instance {
         description "Name of igp-instance";
         type string;
       }
       leaf flex-algorithm-id {
         description "Flex Algorithm id";
         type union {
           type string {
             pattern "<.*>|$.*";
           }
           type uint32 {
             range "128 .. 255";
           }
         }
       }
       leaf verbosity_level {
         default "brief";
         type enumeration {
           enum "brief" {
             description "Display brief output (default)";
           }
           enum "detail" {
             description "Display detailed output";
           }
           enum "extensive" {
             description "Display extensive output";
           }
         }
       }
       leaf instance {
         description "Name of IS-IS instance";
         type string;
       }
       leaf level {
         description "Number of IS-IS level";
         type union {
           type string {
             pattern "<.*>|$.*";
           }
           type uint32 {
             range "1 .. 2";
           }
         }
       }
       leaf system-id {
         description "System ID of IS";
         type string;
       }
     }
     output {
       container isis-database-information {
         uses isis-database-information-block;
       }
     }
   }
   rpc get-isis-hostname-information {
     description "Show IS-IS hostname database";
     input {
       choice daemon-select {
         case logical-system {
           leaf logical-system {
             description "Name of logical system, or 'all'";
             type string {
             }
           }
         }
       }
     }
     output {
       container isis-hostname-information {
         uses isis-hostname-information-block;
       }
     }
   }
   rpc get-isis-interface-information {
     description "Show IS-IS interface information";
     input {
       choice daemon-select {
         case logical-system {
           leaf logical-system {
             description "Name of logical system, or 'all'";
             type string {
             }
           }
         }
       }
       leaf igp-instance {
         description "Name of igp-instance";
         type string;
       }
       leaf verbosity_level {
         default "brief";
         type enumeration {
           enum "brief" {
             description "Display brief output (default)";
           }
           enum "detail" {
             description "Display detailed output";
           }
           enum "extensive" {
             description "Display extensive output";
           }
         }
       }
       leaf instance {
         description "Name of IS-IS instance";
         type string;
       }
       leaf interface-name {
         description "Name of interface";
         type string;
       }
     }
     output {
       container isis-interface-information {
         uses isis-interface-information-block;
       }
     }
   }
   rpc get-isis-interface-group-information {
     description "Show IS-IS interface-group information";
     input {
       choice daemon-select {
         case logical-system {
           leaf logical-system {
             description "Name of logical system, or 'all'";
             type string {
             }
           }
         }
       }
       leaf igp-instance {
         description "Name of igp-instance";
         type string;
       }
       leaf instance {
         description "Name of IS-IS instance";
         type string;
       }
     }
     output {
       container isis-interface-group-information {
         uses isis-interface-group-information-block;
       }
     }
   }
   rpc get-isis-layer2-map-information {
     description "Show IS-IS ARP/ND mapping information";
     input {
       choice daemon-select {
         case logical-system {
           leaf logical-system {
             description "Name of logical system, or 'all'";
             type string {
             }
           }
         }
       }
       leaf igp-instance {
         description "Name of igp-instance";
         type string;
       }
       leaf instance {
         description "Name of IS-IS instance";
         type string;
       }
       leaf destination {
         description "IP address of mapping entry";
         type jt:ipaddr;
       }
     }
     output {
       container isis-layer2-map-information {
         uses isis-layer2-map-information-block;
       }
     }
   }
   rpc get-isis-overview-information {
     description "Show overview of IS-IS information";
     input {
       choice daemon-select {
         case logical-system {
           leaf logical-system {
             description "Name of logical system, or 'all'";
             type string {
             }
           }
         }
       }
       leaf igp-instance {
         description "Name of igp-instance";
         type string;
       }
       leaf instance {
         description "Name of IS-IS instance";
         type string;
       }
     }
     output {
       container isis-overview-information {
         uses isis-overview-information-block;
       }
     }
   }
   rpc get-isis-route-information {
     description "Show IS-IS routing table";
     input {
       choice daemon-select {
         case logical-system {
           leaf logical-system {
             description "Name of logical system, or 'all'";
             type string {
             }
           }
         }
       }
       leaf igp-instance {
         description "Name of igp-instance";
         type string;
       }
       leaf flex-algorithm-id {
         description "Flex Algorithm id";
         type union {
           type string {
             pattern "<.*>|$.*";
           }
           type uint32 {
             range "128 .. 255";
           }
         }
       }
       leaf verbosity_level {
         default "brief";
         type enumeration {
           enum "brief" {
             description "Display brief output (default)";
           }
           enum "detail" {
             description "Display detailed output";
           }
         }
       }
       leaf instance {
         description "Name of IS-IS instance";
         type string;
       }
       leaf destination {
         description "IP address and optional prefix length of destination";
         type jt:ipprefix;
       }
       leaf floodgroup {
         description "Routes belonging to a specific floodgroup";
         type string {
         }
       }
       leaf nexthop {
         description "Routes reachable through specific nexthop";
         type string;
       }
       leaf download-priority {
         description "Sorted by download priority";
         type empty;
       }
       leaf family {
         type enumeration {
           enum "inet" {
             description "Display IPv4 routes";
           }
           enum "inet6" {
             description "Display IPv6 routes";
           }
           enum "iso" {
             description "Display CLNS routes";
           }
           enum "bier" {
             description "Display bier routes";
           }
         }
       }
       leaf topology {
         description "Name of topology from which routes were learned";
         type enumeration {
           enum "unicast" {
             description "Unicast topology";
           }
           enum "ipv4-multicast" {
             description "IPv4 multicast topology";
           }
           enum "ipv6-unicast" {
             description "IPv6 unicast topology";
           }
           enum "ipv6-multicast" {
             description "IPv6 multicast topology";
           }
         }
       }
     }
     output {
       container isis-route-information {
         uses isis-route-information-block;
       }
     }
   }
   rpc get-isis-purge-log-information {
     description "Show log of PURGE runs";
     input {
       choice daemon-select {
         case logical-system {
           leaf logical-system {
             description "Name of logical system, or 'all'";
             type string {
             }
           }
         }
       }
       leaf igp-instance {
         description "Name of igp-instance";
         type string;
       }
       leaf instance {
         description "Name of IS-IS instance";
         type string;
       }
       leaf level {
         description "Number of IS-IS level";
         type union {
           type string {
             pattern "<.*>|$.*";
           }
           type uint32 {
             range "1 .. 2";
           }
         }
       }
     }
     output {
       container isis-purge-information {
         uses isis-purge-information-block;
       }
     }
   }
   rpc get-isis-spf-log-information {
     description "Show log of SPF runs";
     input {
       choice daemon-select {
         case logical-system {
           leaf logical-system {
             description "Name of logical system, or 'all'";
             type string {
             }
           }
         }
       }
       leaf igp-instance {
         description "Name of igp-instance";
         type string;
       }
       leaf flex-algorithm-id {
         description "Flex Algorithm id";
         type union {
           type string {
             pattern "<.*>|$.*";
           }
           type uint32 {
             range "128 .. 255";
           }
         }
       }
       leaf instance {
         description "Name of IS-IS instance";
         type string;
       }
       leaf level {
         description "Number of IS-IS level";
         type union {
           type string {
             pattern "<.*>|$.*";
           }
           type uint32 {
             range "1 .. 2";
           }
         }
       }
       leaf topology {
         description "Name of topology";
         type enumeration {
           enum "unicast" {
             description "Unicast topology";
           }
           enum "ipv4-multicast" {
             description "IPv4 multicast topology";
           }
           enum "ipv6-unicast" {
             description "IPv6 unicast topology";
           }
           enum "ipv6-multicast" {
             description "IPv6 multicast topology";
           }
         }
       }
     }
     output {
       container isis-spf-information {
         uses isis-spf-information-block;
       }
     }
   }
   rpc get-isis-spf-results-information {
     description "Show results from SPF runs";
     input {
       choice daemon-select {
         case logical-system {
           leaf logical-system {
             description "Name of logical system, or 'all'";
             type string {
             }
           }
         }
       }
       leaf igp-instance {
         description "Name of igp-instance";
         type string;
       }
       leaf instance {
         description "IS-IS instance";
         type string;
       }
       leaf level {
         description "Number of IS-IS level";
         type union {
           type string {
             pattern "<.*>|$.*";
           }
           type uint32 {
             range "1 .. 2";
           }
         }
       }
       leaf topology {
         description "Name of topology";
         type enumeration {
           enum "unicast" {
             description "Unicast topology";
           }
           enum "ipv4-multicast" {
             description "IPv4 multicast topology";
           }
           enum "ipv6-unicast" {
             description "IPv6 unicast topology";
           }
           enum "ipv6-multicast" {
             description "IPv6 multicast topology";
           }
         }
       }
     }
     output {
       container isis-spf-information {
         uses isis-spf-information-block;
       }
     }
   }
   rpc get-isis-spf-results-brief-information {
     description "Show brief summary of SPF results";
     input {
       choice daemon-select {
         case logical-system {
           leaf logical-system {
             description "Name of logical system, or 'all'";
             type string {
             }
           }
         }
       }
       leaf igp-instance {
         description "Name of igp-instance";
         type string;
       }
       leaf instance {
         description "Name of IS-IS instance";
         type string;
       }
       leaf level {
         description "Number of level";
         type union {
           type string {
             pattern "<.*>|$.*";
           }
           type uint32 {
             range "1 .. 2";
           }
         }
       }
       leaf topology {
         description "Name of topology";
         type enumeration {
           enum "unicast" {
             description "Unicast topology";
           }
           enum "ipv4-multicast" {
             description "IPv4 multicast topology";
           }
           enum "ipv6-unicast" {
             description "IPv6 unicast topology";
           }
           enum "ipv6-multicast" {
             description "IPv6 multicast topology";
           }
         }
       }
     }
     output {
       container isis-spf-information {
         uses isis-spf-information-block;
       }
     }
   }
   rpc get-isis-statistics-information {
     description "Show IS-IS performance statistics";
     input {
       choice daemon-select {
         case logical-system {
           leaf logical-system {
             description "Name of logical system, or 'all'";
             type string {
             }
           }
         }
       }
       leaf igp-instance {
         description "Name of igp-instance";
         type string;
       }
       leaf instance {
         description "Name of IS-IS instance";
         type string;
       }
     }
     output {
       container isis-statistics-information {
         uses isis-statistics-information-block;
       }
     }
   }
   rpc get-isis-interface-statistics-information {
     description "ISIS interface statistics information";
     input {
       choice daemon-select {
         case logical-system {
           leaf logical-system {
             description "Name of logical system, or 'all'";
             type string {
             }
           }
         }
       }
       leaf igp-instance {
         description "Name of igp-instance";
         type string;
       }
       leaf instance {
         description "Name of IS-IS instance";
         type string;
       }
       leaf interface-name {
         description "Name of interface";
         type string;
       }
     }
     output {
       container isis-interface-statistics-information {
         uses isis-interface-statistics-information-block;
       }
     }
   }
   rpc get-isis-interface-traffic-stats-information {
     description "Show aggregate SPRING traffic";
     input {
       choice daemon-select {
         case logical-system {
           leaf logical-system {
             description "Name of logical system, or 'all'";
             type string {
             }
           }
         }
       }
       leaf igp-instance {
         description "Name of igp-instance";
         type string;
       }
     }
     output {
       container isis-interface-traffic-statistics-information {
         uses isis-interface-traffic-statistics-information-block;
       }
     }
   }
   rpc get-isis-spring-flex-algorithm-information {
     description "Show SPRING flex-algorithm information";
     input {
       choice daemon-select {
         case logical-system {
           leaf logical-system {
             description "Name of logical system, or 'all'";
             type string {
             }
           }
         }
       }
       leaf flex-algorithm-id {
         description "Flex Algorithm id";
         type union {
           type string {
             pattern "<.*>|$.*";
           }
           type uint32 {
             range "128 .. 255";
           }
         }
       }
       leaf igp-instance {
         description "Name of igp-instance";
         type string;
       }
       leaf level {
         description "Number of IS-IS level";
         type union {
           type string {
             pattern "<.*>|$.*";
           }
           type uint32 {
             range "1 .. 2";
           }
         }
       }
       leaf topology {
         description "Name of topology";
         type enumeration {
           enum "unicast" {
             description "Unicast topology";
           }
           enum "ipv6-unicast" {
             description "IPv6 unicast topology";
           }
         }
       }
     }
     output {
       container isis-spring-flex-algorithm-information {
         uses isis-spring-flex-algorithm-information-block;
       }
     }
   }
   rpc get-isis-spring-sensor-information {
     description "Show SPRING sensor info";
     input {
       choice daemon-select {
         case logical-system {
           leaf logical-system {
             description "Name of logical system, or 'all'";
             type string {
             }
           }
         }
       }
       leaf igp-instance {
         description "Name of igp-instance";
         type string;
       }
     }
     output {
       container isis-spring-sensor-information {
         uses isis-spring-sensor-information-block;
       }
     }
   }
   rpc get-isis-backup-spf-results-information {
     description "Show results from backup SPF runs";
     input {
       choice daemon-select {
         case logical-system {
           leaf logical-system {
             description "Name of logical system, or 'all'";
             type string {
             }
           }
         }
       }
       leaf igp-instance {
         description "Name of igp-instance";
         type string;
       }
       leaf destination {
         description "Hostname or System-ID of remote destination";
         type string;
       }
       leaf instance {
         description "IS-IS instance";
         type string;
       }
       leaf level {
         description "Number of IS-IS level";
         type union {
           type string {
             pattern "<.*>|$.*";
           }
           type uint32 {
             range "1 .. 2";
           }
         }
       }
       leaf no-coverage {
         description "Destinations with no backup coverage";
         type empty;
       }
       leaf topology {
         description "Name of topology";
         type enumeration {
           enum "unicast" {
             description "Unicast topology";
           }
           enum "ipv4-multicast" {
             description "IPv4 multicast topology";
           }
           enum "ipv6-unicast" {
             description "IPv6 unicast topology";
           }
           enum "ipv6-multicast" {
             description "IPv6 multicast topology";
           }
         }
       }
     }
     output {
       container isis-spf-information {
         uses isis-spf-information-block;
       }
     }
   }
   rpc get-isis-backup-coverage-information {
     description "Show IS-IS backup coverage";
     input {
       choice daemon-select {
         case logical-system {
           leaf logical-system {
             description "Name of logical system, or 'all'";
             type string {
             }
           }
         }
       }
       leaf igp-instance {
         description "Name of igp-instance";
         type string;
       }
       leaf instance {
         description "Name of IS-IS instance";
         type string;
       }
     }
     output {
       container isis-backup-coverage-information {
         uses isis-backup-coverage-information-block;
       }
     }
   }
   rpc get-isis-backup-lsp-information {
     description "Show IS-IS MPLS backup LSP information";
     input {
       choice daemon-select {
         case logical-system {
           leaf logical-system {
             description "Name of logical system, or 'all'";
             type string {
             }
           }
         }
       }
       leaf igp-instance {
         description "Name of igp-instance";
         type string;
       }
     }
     output {
       container isis-backup-mplsp-information {
         uses isis-backup-mplsp-information-block;
       }
     }
   }
   rpc get-isis-context-identifier-information {
     description "Show IS-IS context-identifier information";
     input {
       choice daemon-select {
         case logical-system {
           leaf logical-system {
             description "Name of logical system, or 'all'";
             type string {
             }
           }
         }
       }
       leaf igp-instance {
         description "Name of igp-instance";
         type string;
       }
       leaf verbosity_level {
         default "brief";
         type enumeration {
           enum "brief" {
             description "Display brief output (default)";
           }
           enum "detail" {
             description "Display detailed output";
           }
         }
       }
       leaf instance {
         description "Name of IS-IS instance";
         type string;
       }
     }
     output {
       container isis-context-information {
         uses isis-context-information-block;
       }
     }
   }
   rpc get-isis-context-identifier-origin-information {
     description "Show IS-IS context-identifier information";
     input {
       choice daemon-select {
         case logical-system {
           leaf logical-system {
             description "Name of logical system, or 'all'";
             type string {
             }
           }
         }
       }
       leaf igp-instance {
         description "Name of igp-instance";
         type string;
       }
       leaf verbosity_level {
         default "brief";
         type enumeration {
           enum "brief" {
             description "Display brief output (default)";
           }
           enum "detail" {
             description "Display detailed output";
           }
         }
       }
       leaf id_addr {
         description "Context identifier address of session";
         type jt:ipprefix;
         mandatory true;
       }
       leaf instance {
         description "Name of IS-IS instance";
         type string;
       }
     }
     output {
       container isis-context-information {
         uses isis-context-information-block;
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping isis-adjacency-information-block {
     list isis-adjacency {
       leaf interface-name {
         type string;
         description "Name of interface";
       }
       leaf system-name {
         type string;
         description "Hostname for a system";
       }
       leaf not-remote-address {
         type empty;
       }
       leaf level {
         type int32;
         description "IS-IS Level";
       }
       leaf adjacency-state {
         type string;
         description "State of the adjacency";
       }
       leaf holdtime {
         type int32;
         description "Delay before timing out the adjacency (default is 180 seconds)";
       }
       leaf-list snpa {
         type string;
       }
       leaf snpa-type {
         type string;
         description "Type of SNPA";
       }
       list pfe-port-snpa {
         leaf pfe-id {
           type int32;
         }
         leaf port-id {
           type int32;
         }
       }
       list network-element-port-snpa {
         leaf port-id {
           type int32;
         }
       }
       list mstp-root-snpa {
         leaf mstp-root-id {
           type int32;
         }
       }
       list gateway-snpa {
         leaf gateway-addr {
           type jt:ipaddr;
         }
       }
       list layer2-domain-port-snpa {
         leaf port-id {
           type int32;
         }
       }
       list replication-block-snpa {
         leaf replication-block-id {
           type int32;
         }
       }
       list replication-route-snpa {
         leaf network-element-id {
           type jt:ipaddr;
         }
       }
       list layer2-multicast-port-snpa {
         leaf layer2-multicast-port-id {
           type int32;
         }
       }
       list inh-snpa {
         leaf inh-id {
           type int32;
         }
       }
       list srv6-micro-adjacency-segment-information {
         leaf srv6-micro-adjacency-segment-level {
           type int32;
           description "Micro adjacency Level";
         }
         leaf srv6-protected-micro-adjacency-segment {
           type jt:ipv6addr;
           description "SRv6 protected micro-adjacency-SID";
         }
         leaf srv6-unprotected-micro-adjacency-segment {
           type jt:ipv6addr;
           description "SRv6 unprotected micro-adjacency-SID";
         }
         leaf srv6-micro-adjacency-segment-end-point-func {
           type string;
           description "SRv6 micro-adjacency-SID Function";
         }
         leaf srv6-micro-adjacency-segment-flags {
           type string;
           description "SRv6 micro adjacency flags";
         }
         leaf srv6-micro-adjacency-segment-algorithm {
           type uint32;
           description "SRv6 micro adjacency algorithm";
         }
       }
       container isis-bfd-nlpid-stats {
         leaf isis-bfd-nlpid-stats-header {
           type string;
         }
         container isis-bfd-tlv-mtids {
           leaf isis-bfd-tlv-mtid {
             type int32;
           }
           leaf isis-bfd-mtid-v4nlpid-state {
             type string;
           }
           leaf isis-bfd-mtid-v6nlpid-state {
             type string;
           }
         }
       }
       leaf interface-priority {
         type int32;
       }
       leaf transition-count {
         type int32;
       }
       leaf last-transition-time {
         type string;
       }
       leaf circuit-type {
         type int32;
       }
       leaf adjacency-flag {
         type string;
       }
       leaf mac-address {
         type jt:mac-addr;
       }
       leaf adjacency-topologies {
         type string;
       }
       leaf adjacency-restart-capable {
         type string;
         description "Restart capability of the adjacency";
       }
       leaf adjacency-advertisement {
         type string;
         description "State of the adjacency advertisment";
       }
       leaf lan-id {
         type string;
       }
       leaf ip-address {
         type jt:ipaddr;
       }
       leaf ipv6-address {
         type jt:ipv6addr;
       }
       leaf global-ipv6-address {
         type jt:ipv6addr;
       }
       leaf flood-ref-level {
         type int32;
       }
       leaf flood-ref-node {
         type string;
         description "Flood reflector";
       }
       leaf flood-ref-cluster-id {
         type uint32;
         description "Flood reflector cluster id";
       }
       leaf adjacency-segment-level {
         type int32;
       }
       leaf ipv4-adjacency-segment-id {
         type int32;
       }
       leaf ipv6-adjacency-segment-id {
         type int32;
       }
       container adjacency-segment-information {
         leaf adjacency-segment-level {
           type int32;
         }
         leaf ipv4-protected-adjacency-segment-id {
           type int32;
         }
         leaf ipv4-unprotected-adjacency-segment-id {
           type int32;
         }
         leaf ipv6-protected-adjacency-segment-id {
           type int32;
         }
         leaf ipv6-unprotected-adjacency-segment-id {
           type int32;
         }
         leaf adjacency-segment-flags {
           type string;
         }
       }
       container srv6-adjacency-segment-information {
         leaf srv6-adjacency-segment-level {
           type int32;
           description "Adjacency Level";
         }
         leaf srv6-protected-adjacency-segment {
           type jt:ipv6addr;
           description "SRv6 Protected END-X-SID";
         }
         leaf srv6-unprotected-adjacency-segment {
           type jt:ipv6addr;
           description "SRv6 UnProtected END-X-SID";
         }
         leaf srv6-adjacency-segment-end-point-func {
           type string;
           description "SRv6 END-X-SID Function";
         }
         leaf srv6-adjacency-segment-flags {
           type string;
           description "SRv6 Adjacency Flags";
         }
         leaf srv6-adjacency-segment-algorithm {
           type uint32;
           description "SRv6 Adjacency Algorithm";
         }
       }
       container bfd-tlv-information {
         leaf bfd-tlv-info-level {
           type string;
         }
       }
       container isis-adj-bfd-state-info {
         leaf isis-bfd-v4-sess-state {
           type string;
         }
         leaf isis-bfd-v6-sess-state {
           type string;
         }
         leaf isis-bfd-req-state {
           type string;
         }
         leaf isis-bfd-adj-usable {
           type string;
         }
       }
       list isis-adjacency-log {
         leaf adjacency-when {
           type string;
           description "Time at which the transition occurred";
         }
         leaf adjacency-state {
           type string;
           description "State of the adjacency";
         }
         leaf adjacency-event {
           type string;
           description "Event which triggered the transition";
         }
         leaf adjacency-down-reason {
           type string;
           description "Reason for the down transition event";
         }
       }
     }
   }
   grouping isis-adjacency-holddown-information-block {
     list isis-adjacencyholddown {
       leaf level {
         type int32;
         description "IS-IS Level";
       }
       leaf active {
         type string;
       }
       leaf first-adj-up {
         type string;
       }
       leaf first-adj-down {
         type string;
       }
       leaf reset-complete {
         type string;
       }
       leaf last-holddown {
         type string;
       }
       leaf started {
         type string;
       }
       leaf network-stable {
         type string;
       }
       leaf time {
         type string;
         description "Time of the event";
       }
       leaf first-adj-up-time {
         type string;
       }
       leaf adj-up-count {
         type string;
       }
       leaf adjacency-holddown-when {
         type string;
       }
       leaf adjacency-holddown-state {
         type string;
       }
       leaf adjacency-holddown-event {
         type string;
       }
       leaf adjacency-holddown-reason {
         type string;
       }
     }
   }
   grouping isis-authentication-information-block {
     list isis-interface-authentication {
       leaf interface-name {
         type string;
         description "Name of interface";
       }
       list isis-interface-level-authentication {
         leaf level {
           type int32;
           description "IS-IS Level";
         }
         leaf isis-interface-level-iih-authentication {
           type string;
           description "Authentication type for IIH packets";
         }
         leaf isis-interface-level-csn-authentication {
           type string;
           description "Authentication type for CSN packets";
         }
         leaf isis-interface-level-psn-authentication {
           type string;
           description "Authentication type for PSN packets";
         }
       }
     }
     list isis-lsp-authentication {
       description "Authentication type for LSP packets";
       leaf level {
         type int32;
         description "IS-IS Level";
       }
       leaf isis-level-lsp-authentication {
         type string;
         description "Authentication type for LSP packets";
       }
     }
   }
   grouping isis-bgporr-information-block {
     container isis-bgporr {
       leaf isis-bgporr-name {
         type string;
       }
       leaf isis-bgporr-primary {
         type jt:ipaddr;
       }
       leaf isis-bgporr-primary-active-tag {
         type string;
       }
       leaf isis-bgporr-backup {
         type jt:ipaddr;
       }
       leaf isis-bgporr-backup-active-tag {
         type string;
       }
       container isis-route {
         leaf-list address-prefix {
           type jt:ipaddr;
         }
         leaf level {
           type int32;
           description "IS-IS Level";
         }
         leaf route-version {
           type int32;
         }
         leaf metric {
           type int32;
         }
         leaf metric-type {
           type string;
         }
         leaf interface-name {
           type string;
           description "Name of interface";
         }
         leaf isis-next-hop-type {
           type string;
         }
         leaf isis-next-hop {
           type string;
         }
         leaf isis-backup-score {
           type string;
         }
         leaf prefix-originator {
           type string;
         }
         leaf prefix-level {
           type int32;
         }
         leaf prefix-metric {
           type int32;
         }
         leaf prefix-preference {
           type int32;
         }
         leaf isis-route-priority {
           type string;
         }
         leaf isis-rt-congestion-protection-activate {
           type string;
         }
         leaf isis-rt-congestion-protection-activate-count {
           type uint32;
         }
         list isis-backup-next-hop-sid-info {
           leaf isis-backup-next-hop-label {
             type uint32;
           }
           leaf isis-backup-next-hop-label-type {
             type string;
           }
           leaf isis-backup-next-hop-srv6-sid {
             type jt:ipaddr;
           }
           leaf isis-backup-next-hop-srv6-sid-type {
             type string;
           }
           leaf isis-backup-next-hop-sid-info-node-id {
             type string;
           }
           leaf isis-backup-next-hop-sid-info-adj-local-node-id {
             type string;
           }
           leaf isis-backup-next-hop-sid-info-adj-remote-node-id {
             type string;
           }
           leaf isis-backup-next-hop-sid-info-adj-local-v4-addr {
             type jt:ipaddr;
           }
           leaf isis-backup-next-hop-sid-info-adj-remote-v4-addr {
             type jt:ipaddr;
           }
           leaf isis-backup-next-hop-sid-info-adj-local-v6-addr {
             type jt:ipaddr;
           }
           leaf isis-backup-next-hop-sid-info-adj-remote-v6-addr {
             type jt:ipaddr;
           }
           leaf isis-backup-next-hop-sid-info-adj-local-unnumbered-id {
             type uint32;
           }
           leaf isis-backup-next-hop-sid-info-adj-remote-unnumbered-id {
             type uint32;
           }
         }
         list snpa {
           leaf snpa-type {
             type string;
             description "Type of SNPA";
           }
           list pfe-port-snpa {
             leaf pfe-id {
               type int32;
             }
             leaf port-id {
               type int32;
             }
           }
           list network-element-port-snpa {
             leaf port-id {
               type int32;
             }
           }
           list mstp-root-snpa {
             leaf mstp-root-id {
               type int32;
             }
           }
           list gateway-snpa {
             leaf gateway-addr {
               type jt:ipaddr;
             }
           }
           list layer2-domain-port-snpa {
             leaf port-id {
               type int32;
             }
           }
           list replication-block-snpa {
             leaf replication-block-id {
               type int32;
             }
           }
           list replication-route-snpa {
             leaf network-element-id {
               type jt:ipaddr;
             }
           }
           list layer2-multicast-port-snpa {
             leaf layer2-multicast-port-id {
               type int32;
             }
           }
           list inh-snpa {
             leaf inh-id {
               type int32;
             }
           }
         }
         list isis-rt-sessid {
           leaf-list isis-rt-sessid-val {
             type uint32;
           }
           leaf-list isis-rt-sessid-ver {
             type uint32;
           }
         }
         container isis-computed-backup-paths {
           leaf isis-computed-backup-paths-type {
             type string;
           }
           leaf isis-computed-backup-paths-count {
             type uint32;
           }
           leaf isis-computed-backup-paths-valid-count {
             type uint32;
           }
           leaf isis-computed-backup-paths-rttype {
             type string;
           }
           list isis-computed-backup-path {
             leaf isis-computed-backup-path-id {
               type uint32;
             }
             leaf isis-computed-backup-path-sid-count {
               type uint32;
             }
             leaf isis-computed-backup-path-error {
               type string;
             }
           }
         }
       }
     }
   }
   grouping isis-database-information-block {
     list isis-database {
       leaf level {
         type int32;
         description "IS-IS Level";
       }
       leaf lsp-count {
         type int32;
       }
       list isis-database-entry {
         leaf lsp-id {
           type string;
         }
         leaf sequence-number {
           type int64;
           description "History event number";
         }
         leaf checksum {
           type int32;
         }
         leaf remaining-lifetime {
           type int32;
         }
         leaf lsp-attributes {
           type string;
         }
         container isis-node-segment {
           leaf isis-node-segment-ipv4-index {
             type int32;
             description "IPv4 Node Segment index for this device";
           }
           leaf isis-node-segment-ipv6-index {
             type int32;
             description "IPv6 Node Segment index for this device";
           }
           leaf isis-node-segment-block-header {
             type empty;
             description "Node Segment Blocks";
           }
           container isis-node-segment-block {
             leaf isis-node-segment-block-start-index {
               type int32;
               description "Starting Index for the specific Node Segment Block";
             }
             leaf isis-node-segment-block-size {
               type int32;
               description "Size of the specific Node Segment Block";
             }
             leaf isis-node-segment-block-first-label {
               type int32;
               description "First label allocated for the specific Node Segment Block";
             }
             leaf isis-node-segment-block-last-label {
               type int32;
               description "Last label allocated for the specific Node Segment Block";
             }
           }
         }
         list isis-neighbor {
           leaf reachability-delay {
             type empty;
           }
           leaf reachability-expense {
             type empty;
           }
           leaf reachability-error {
             type empty;
           }
           leaf isis-topology-id {
             type string;
           }
           leaf is-neighbor-id {
             type string;
           }
           leaf metric {
             type int32;
           }
           leaf two-way-lsp-id {
             type string;
           }
           leaf firstfrag-lsp-id {
             type string;
           }
           container adjacency-segment-information {
             leaf adjacency-segment-type {
               type string;
             }
             leaf ipv4-adjacency-segment-id {
               type int32;
             }
             leaf ipv6-adjacency-segment-id {
               type int32;
             }
             leaf adjacency-segment-weight {
               type int32;
             }
             leaf adjacency-segment-neighbor {
               type string;
             }
             leaf adjacency-segment-flags {
               type string;
             }
           }
         }
         list isis-prefix {
           leaf protocol-name {
             type string;
           }
           leaf isis-topology-id {
             type string;
           }
           leaf-list address-prefix {
             type jt:ipaddr;
           }
           leaf metric {
             type int32;
           }
           leaf prefix-flag {
             type string;
           }
           leaf prefix-status {
             type string;
           }
           leaf reachability-delay {
             type empty;
           }
           leaf reachability-expense {
             type empty;
           }
           leaf reachability-error {
             type empty;
           }
         }
         container isis-header {
           leaf lsp-buffer-size {
             type int32;
           }
           leaf lsp-id {
             type string;
           }
           leaf pdu-length {
             type int32;
           }
           leaf allocated-length {
             type int32;
           }
           leaf router-id {
             type jt:ipaddr;
           }
           leaf remaining-lifetime {
             type int32;
           }
           leaf level {
             type int32;
             description "IS-IS Level";
           }
           leaf interface-index {
             type int32;
           }
           leaf estimated-free-bytes {
             type int32;
           }
           leaf actual-free-bytes {
             type int32;
           }
           leaf lsdb-timer-type {
             type string;
           }
           leaf lsdb-expiration-time {
             type int32;
           }
           leaf needs-rebuild {
             type empty;
           }
           leaf-list protocol {
             type string;
           }
         }
         container isis-packet {
           leaf mtid {
             type string;
           }
           leaf lsp-id {
             type string;
           }
           leaf pdu-length {
             type int32;
           }
           leaf pdu-lifetime {
             type int32;
           }
           leaf checksum {
             type int32;
           }
           leaf sequence-number {
             type int64;
             description "History event number";
           }
           leaf lsp-attributes {
             type string;
           }
           leaf nlp-id {
             type int32;
           }
           leaf lsp-length {
             type int32;
           }
           leaf pdu-version {
             type int32;
           }
           leaf system-id-length {
             type int32;
           }
           leaf isis-packet-type {
             type int32;
           }
           leaf packet-version {
             type int32;
           }
           leaf maximum-area {
             type int32;
           }
         }
         container isis-tlv {
           leaf srv6-flags {
             type uint32;
           }
           container isis-tlv-overhead {
             leaf isis-tlv-type {
               type int32;
             }
             leaf tlv-length {
               type int32;
             }
             leaf bytes-left {
               type int32;
             }
           }
           container area-address-tlv {
             leaf address {
               type jt:ipaddr;
             }
             leaf tlv-length {
               type int32;
             }
           }
           container lsp-buffer-size-tlv {
             leaf lsp-buffer-size {
               type int32;
             }
           }
           container protocols-tlv {
             leaf-list protocol {
               type string;
             }
           }
           container mt-tlv {
             leaf mtid {
               type string;
             }
           }
           container hostname-tlv {
             leaf hostname {
               type string;
             }
           }
           container purge-originator-tlv {
             leaf purge-originator {
               type string;
             }
             leaf purge-originator-from {
               type string;
             }
           }
           container ipaddress-tlv {
             leaf address {
               type jt:ipaddr;
             }
           }
           container ipv6address-tlv {
             leaf address {
               type jt:ipaddr;
             }
           }
           container ipv6-te-router-id-tlv {
             leaf address {
               type jt:ipaddr;
             }
           }
           container router-id-tlv {
             leaf router-id {
               type jt:ipaddr;
             }
           }
           container ext-reachability-tlv {
             leaf isis-tlv-type {
               type int32;
             }
             leaf tlv-length {
               type int32;
             }
           }
           list reachability-tlv {
             leaf isis-topology-id {
               type string;
             }
             leaf-list reachability-tlv.heading {
               type string;
             }
             leaf-list address-prefix {
               type jt:ipaddr;
             }
             leaf metric-flag {
               type string;
             }
             leaf metric {
               type int32;
             }
             leaf subtlv-length {
               type int32;
             }
             leaf reachability-delay {
               type empty;
             }
             leaf reachability-expense {
               type empty;
             }
             leaf reachability-error {
               type empty;
             }
             leaf prefix-status {
               type string;
             }
             leaf address {
               type jt:ipaddr;
             }
             leaf neighbor-prefix {
               type jt:ipaddr;
             }
             leaf tlv-length {
               type int32;
             }
             list isis-reachability-subtlv {
               leaf address-prefix {
                 type jt:ipaddr;
               }
               leaf prefix-err-message {
                 type empty;
               }
               container admin-groups {
                 leaf color {
                   type int32;
                 }
                 leaf no-group-flag {
                   type empty;
                 }
                 leaf-list admin-group-name {
                   type string;
                   description "Name of the admin group";
                 }
                 leaf admin-group-number {
                   type int32;
                   description "Number of the admin group";
                 }
               }
               container link-msd-adv-sub-tlv {
                 leaf link-msd-adv-sub-tlv.heading {
                   type string;
                   description "Link Maximum SID Depth TLV";
                 }
                 leaf link-msd-adv-sub-tlv-type {
                   type uint32;
                 }
                 leaf link-msd-adv-sub-tlv-length {
                   type uint32;
                 }
                 list mpls-link-msd {
                   leaf-list mpls-link-msd.heading {
                     type string;
                   }
                   leaf mpls-link-msd-type {
                     type uint32;
                   }
                   leaf mpls-link-msd-value {
                     type uint32;
                   }
                 }
               }
               list srv6-micro-adjacency-segment-information {
                 leaf srv6-micro-adjacency-seg-type {
                   type string;
                   description "P2P or LAN micro-adjacency segment type";
                 }
                 leaf srv6-micro-adjacency-sid {
                   type jt:ipv6addr;
                   description "Micro-adjacency-SID address";
                 }
                 leaf srv6-micro-adjacency-sid-flags {
                   type string;
                   description "SRv6 micro-adjacency-SID flags";
                 }
                 leaf srv6-micro-adjacency-sid-weight {
                   type int32;
                   description "SRv6 micro-adjacency-SID weight";
                 }
                 leaf srv6-micro-adjacency-sid-algorithm {
                   type int32;
                   description "SRv6 micro-adjacency-SID algorithm";
                 }
                 leaf srv6-micro-adjacency-sid-flags-detail {
                   type string;
                   description "SRv6 micro-adjacency-SID flags with bit field";
                 }
                 leaf srv6-micro-adjacency-sid-endpoint-func {
                   type string;
                   description "SRv6 micro-adjacency-SID endpoint function";
                 }
                 leaf srv6-lan-micro-adjacency-sid-nbr-sysid {
                   type string;
                   description "LAN micro-adjacency-SID neighbor system id";
                 }
                 container isis-srv6-sid-structure-info {
                   leaf isis-srv6-locator-block-length {
                     type uint32;
                     description "Locator block length";
                   }
                   leaf isis-srv6-locator-node-length {
                     type uint32;
                     description "Locator node length";
                   }
                   leaf isis-srv6-sid-function-length {
                     type uint32;
                     description "SID function length";
                   }
                   leaf isis-srv6-sid-argument-length {
                     type uint32;
                     description "SID argument length";
                   }
                 }
               }
               container application-specific-attributes {
                 leaf application-specific-tlv-length {
                   type int32;
                 }
                 leaf standard-application-flags {
                   type string;
                   description "Legacy bit flag for SABM";
                 }
                 leaf standard-application-bitmask-length {
                   type int32;
                 }
                 leaf standard-application-bitmask {
                   type string;
                 }
                 leaf user-application-bitmask-length {
                   type int32;
                 }
                 container isis-reachability-sub-subtlv {
                   leaf max-bandwidth {
                     type int32;
                   }
                   leaf max-reserve-bandwidth {
                     type int32;
                   }
                   leaf current-bandwidth-header {
                     type empty;
                   }
                   leaf te-metric {
                     type int32;
                     description "LSP TE metric";
                   }
                   leaf uni-link-delay {
                     type int32;
                   }
                   leaf min-uni-link-delay {
                     type int32;
                   }
                   leaf max-uni-link-delay {
                     type int32;
                   }
                   leaf uni-link-delay-variation {
                     type int32;
                   }
                   leaf extended-admin-groups {
                     type string;
                   }
                   leaf isis-subtlv-type {
                     type int32;
                   }
                   container admin-groups {
                     leaf color {
                       type int32;
                     }
                     leaf no-group-flag {
                       type empty;
                     }
                     leaf-list admin-group-name {
                       type string;
                       description "Name of the admin group";
                     }
                     leaf admin-group-number {
                       type int32;
                       description "Number of the admin group";
                     }
                   }
                   list priority-reserve-bandwidth {
                     leaf bandwidth-priority {
                       type int32;
                     }
                     leaf current-reserve-bandwidth {
                       type int32;
                     }
                   }
                 }
               }
               leaf local-ifindex {
                 type uint32;
                 description "Local interface index";
               }
               leaf remote-ifindex {
                 type uint32;
                 description "Remote interface index";
               }
               leaf flood-ref-node {
                 type string;
                 description "Flood reflector";
               }
               leaf flood-ref-cluster-id {
                 type uint32;
                 description "Flood reflector cluster id";
               }
               leaf max-bandwidth {
                 type int32;
               }
               leaf max-reserve-bandwidth {
                 type int32;
               }
               leaf current-bandwidth-header {
                 type empty;
               }
               leaf address {
                 type jt:ipaddr;
               }
               leaf ipv6-address {
                 type jt:ipv6addr;
               }
               leaf neighbor-prefix {
                 type jt:ipaddr;
               }
               leaf neighbor-ipv6-address {
                 type jt:ipv6addr;
                 description "Neighbor ipv6 address";
               }
               leaf te-metric {
                 type int32;
                 description "LSP TE metric";
               }
               leaf dste-bc-header {
                 type empty;
               }
               leaf dste-bc-model {
                 type string;
                 description "DiffServ TE bandwidth constraint model";
               }
               leaf dste-bc-count {
                 type int32;
                 description "DiffServ TE bandwidth constraint count";
               }
               leaf dste-bc-bw {
                 type int32;
                 description "DiffServ TE bandwidth constraint BW";
               }
               leaf p2p-adj-sid-af {
                 type string;
                 description "Point-to-Point adjacency SID address family";
               }
               leaf p2p-adj-sid-flags {
                 type string;
                 description "Point-to-Point adjacency SID flags";
               }
               leaf p2p-adj-sid-weight {
                 type int32;
                 description "Point-to-Point adjacency SID weight";
               }
               leaf p2p-adj-sid-label {
                 type string;
                 description "Point-to-Point adjacency SID label";
               }
               leaf lan-adj-sid-af {
                 type string;
                 description "LAN adjacency SID address family";
               }
               leaf lan-adj-sid-flags {
                 type string;
                 description "LAN adjacency SID flags";
               }
               leaf lan-adj-sid-weight {
                 type int32;
                 description "LAN adjacency SID weight";
               }
               leaf lan-adj-sid-sysid {
                 type string;
                 description "LAN adjacency SID neighbor system id";
               }
               leaf lan-adj-sid-label {
                 type string;
                 description "LAN adjacency SID label";
               }
               leaf uni-link-delay {
                 type int32;
               }
               leaf min-uni-link-delay {
                 type int32;
               }
               leaf max-uni-link-delay {
                 type int32;
               }
               leaf uni-link-delay-variation {
                 type int32;
               }
               leaf extended-admin-groups {
                 type string;
               }
               leaf isis-subtlv-type {
                 type int32;
               }
               leaf subtlv-length {
                 type int32;
               }
               list priority-reserve-bandwidth {
                 leaf bandwidth-priority {
                   type int32;
                 }
                 leaf current-reserve-bandwidth {
                   type int32;
                 }
               }
               container adjacency-segment-information {
                 leaf adjacency-segment-type {
                   type string;
                 }
                 leaf ipv4-adjacency-segment-id {
                   type int32;
                 }
                 leaf ipv6-adjacency-segment-id {
                   type int32;
                 }
                 leaf adjacency-segment-weight {
                   type int32;
                 }
                 leaf adjacency-segment-neighbor {
                   type string;
                 }
                 leaf adjacency-segment-flags {
                   type string;
                 }
               }
               list srv6-end-x-segment-information {
                 leaf srv6-end-x-seg-type {
                   type string;
                   description "P2P or LAN End-X-SID segment type";
                 }
                 leaf srv6-end-x-sid {
                   type jt:ipv6addr;
                   description "END-X-SID prefix";
                 }
                 leaf srv6-end-x-sid-flags {
                   type string;
                   description "SRv6 End-X-SID flags";
                 }
                 leaf srv6-end-x-sid-weight {
                   type int32;
                   description "SRv6 End-X-SID weight";
                 }
                 leaf srv6-end-x-sid-algorithm {
                   type int32;
                   description "SRv6 End-X-SID algorithm";
                 }
                 leaf srv6-end-x-sid-flags-detail {
                   type string;
                   description "SRv6 End-X-SID flags with bit field";
                 }
                 leaf srv6-end-x-sid-endpoint-func {
                   type string;
                   description "SRv6 End-X-SID EndPoint Function";
                 }
                 leaf srv6-lan-end-x-sid-nbr-sysid {
                   type string;
                   description "LAN END-X-SID neighbor system id";
                 }
               }
             }
           }
           container isis-iso-prefix-tlv {
             leaf isis-iso-prefix-tlv.heading {
               type string;
             }
             leaf metric-flag {
               type string;
             }
             leaf metric {
               type int32;
             }
             leaf reachability-delay {
               type empty;
             }
             leaf reachability-expense {
               type empty;
             }
             leaf reachability-error {
               type empty;
             }
             leaf prefix-status {
               type string;
             }
             leaf iso-prefix {
               type string;
             }
           }
           container isis-prefix-subtlv {
             container isis-bier-info-sub-tlv {
             }
           }
           container ipv6-reachability-tlv {
             leaf isis-topology-id {
               type string;
             }
             leaf ipv6-reachability-tlv.heading {
               type string;
             }
             leaf ipv6-address {
               type jt:ipv6addr;
             }
             leaf metric {
               type int32;
             }
             leaf prefix-extern {
               type empty;
             }
             leaf prefix-downflag {
               type empty;
             }
             leaf subtlv-size {
               type int32;
             }
             container isis-prefix-subtlv {
               container isis-prefix-tag {
                 leaf isis-prefix-tag-index {
                   type int32;
                 }
                 leaf isis-prefix-tag-value {
                   type int32;
                 }
               }
               container isis-prefix-sid {
                 leaf isis-prefix-sid-type {
                   type string;
                 }
                 leaf isis-prefix-sid-flags {
                   type string;
                 }
                 leaf isis-prefix-sid-algorithm {
                   type string;
                 }
                 leaf isis-prefix-sid-value {
                   type string;
                 }
               }
               container isis-flex-algo-prefix-metric {
                 leaf isis-flex-algorithm-metric {
                   type string;
                 }
                 leaf isis-flex-algorithm-id {
                   type string;
                 }
               }
               container isis-crh-sid {
                 leaf isis-crh-sid-type {
                   type string;
                 }
                 leaf isis-crh-sid-flags {
                   type string;
                 }
                 leaf isis-crh-sid-algorithm {
                   type string;
                 }
                 leaf isis-crh-sid-value {
                   type string;
                 }
               }
               container isis-prefix-attribute-sub-tlv {
                 leaf isis-prefix-attribute-flags {
                   type string;
                 }
               }
               container isis-prefix-ipv4-source-rtrid-sub-tlv {
                 leaf isis-prefix-ipv4-source-rtrid {
                   type string;
                 }
               }
               container isis-prefix-ipv6-source-rtrid-sub-tlv {
                 leaf isis-prefix-ipv6-source-rtrid {
                   type string;
                 }
               }
               container isis-bier-info-sub-tlv {
                 leaf isis-bier-info-subdomain-id {
                   type string;
                 }
                 leaf isis-bier-info-bfr-id {
                   type string;
                 }
                 leaf isis-bier-info-bier-algo {
                   type string;
                 }
                 leaf isis-bier-info-igp-algo {
                   type string;
                 }
                 container isis-bier-mpls-encap-sub-tlv {
                   leaf isis-bier-mpls-max-si {
                     type string;
                   }
                   leaf isis-bier-mpls-bs-len {
                     type string;
                   }
                   leaf isis-bier-mpls-label {
                     type string;
                   }
                 }
               }
             }
           }
           list isis-reachability-subtlv {
             leaf local-ifindex {
               type uint32;
               description "Local interface index";
             }
             leaf remote-ifindex {
               type uint32;
               description "Remote interface index";
             }
             leaf flood-ref-node {
               type string;
               description "Flood reflector";
             }
             leaf flood-ref-cluster-id {
               type uint32;
               description "Flood reflector cluster id";
             }
             leaf max-bandwidth {
               type int32;
             }
             leaf max-reserve-bandwidth {
               type int32;
             }
             leaf current-bandwidth-header {
               type empty;
             }
             leaf address {
               type jt:ipaddr;
             }
             leaf ipv6-address {
               type jt:ipv6addr;
             }
             leaf neighbor-prefix {
               type jt:ipaddr;
             }
             leaf neighbor-ipv6-address {
               type jt:ipv6addr;
               description "Neighbor ipv6 address";
             }
             leaf te-metric {
               type int32;
               description "LSP TE metric";
             }
             leaf dste-bc-header {
               type empty;
             }
             leaf dste-bc-model {
               type string;
               description "DiffServ TE bandwidth constraint model";
             }
             leaf dste-bc-count {
               type int32;
               description "DiffServ TE bandwidth constraint count";
             }
             leaf dste-bc-bw {
               type int32;
               description "DiffServ TE bandwidth constraint BW";
             }
             leaf p2p-adj-sid-af {
               type string;
               description "Point-to-Point adjacency SID address family";
             }
             leaf p2p-adj-sid-flags {
               type string;
               description "Point-to-Point adjacency SID flags";
             }
             leaf p2p-adj-sid-weight {
               type int32;
               description "Point-to-Point adjacency SID weight";
             }
             leaf p2p-adj-sid-label {
               type string;
               description "Point-to-Point adjacency SID label";
             }
             leaf lan-adj-sid-af {
               type string;
               description "LAN adjacency SID address family";
             }
             leaf lan-adj-sid-flags {
               type string;
               description "LAN adjacency SID flags";
             }
             leaf lan-adj-sid-weight {
               type int32;
               description "LAN adjacency SID weight";
             }
             leaf lan-adj-sid-sysid {
               type string;
               description "LAN adjacency SID neighbor system id";
             }
             leaf lan-adj-sid-label {
               type string;
               description "LAN adjacency SID label";
             }
             leaf uni-link-delay {
               type int32;
             }
             leaf min-uni-link-delay {
               type int32;
             }
             leaf max-uni-link-delay {
               type int32;
             }
             leaf uni-link-delay-variation {
               type int32;
             }
             leaf extended-admin-groups {
               type string;
             }
             leaf isis-subtlv-type {
               type int32;
             }
             leaf subtlv-length {
               type int32;
             }
             leaf address-prefix {
               type jt:ipaddr;
             }
             leaf prefix-err-message {
               type empty;
             }
             container admin-groups {
               leaf color {
                 type int32;
               }
               leaf no-group-flag {
                 type empty;
               }
               leaf-list admin-group-name {
                 type string;
                 description "Name of the admin group";
               }
               leaf admin-group-number {
                 type int32;
                 description "Number of the admin group";
               }
             }
             list priority-reserve-bandwidth {
               leaf bandwidth-priority {
                 type int32;
               }
               leaf current-reserve-bandwidth {
                 type int32;
               }
             }
             container link-msd-adv-sub-tlv {
               leaf link-msd-adv-sub-tlv.heading {
                 type string;
                 description "Link Maximum SID Depth TLV";
               }
               leaf link-msd-adv-sub-tlv-type {
                 type uint32;
               }
               leaf link-msd-adv-sub-tlv-length {
                 type uint32;
               }
               list mpls-link-msd {
                 leaf-list mpls-link-msd.heading {
                   type string;
                 }
                 leaf mpls-link-msd-type {
                   type uint32;
                 }
                 leaf mpls-link-msd-value {
                   type uint32;
                 }
               }
             }
             container adjacency-segment-information {
               leaf adjacency-segment-type {
                 type string;
               }
               leaf ipv4-adjacency-segment-id {
                 type int32;
               }
               leaf ipv6-adjacency-segment-id {
                 type int32;
               }
               leaf adjacency-segment-weight {
                 type int32;
               }
               leaf adjacency-segment-neighbor {
                 type string;
               }
               leaf adjacency-segment-flags {
                 type string;
               }
             }
             list srv6-end-x-segment-information {
               leaf srv6-end-x-seg-type {
                 type string;
                 description "P2P or LAN End-X-SID segment type";
               }
               leaf srv6-end-x-sid {
                 type jt:ipv6addr;
                 description "END-X-SID prefix";
               }
               leaf srv6-end-x-sid-flags {
                 type string;
                 description "SRv6 End-X-SID flags";
               }
               leaf srv6-end-x-sid-weight {
                 type int32;
                 description "SRv6 End-X-SID weight";
               }
               leaf srv6-end-x-sid-algorithm {
                 type int32;
                 description "SRv6 End-X-SID algorithm";
               }
               leaf srv6-end-x-sid-flags-detail {
                 type string;
                 description "SRv6 End-X-SID flags with bit field";
               }
               leaf srv6-end-x-sid-endpoint-func {
                 type string;
                 description "SRv6 End-X-SID EndPoint Function";
               }
               leaf srv6-lan-end-x-sid-nbr-sysid {
                 type string;
                 description "LAN END-X-SID neighbor system id";
               }
             }
             list srv6-micro-adjacency-segment-information {
               leaf srv6-micro-adjacency-seg-type {
                 type string;
                 description "P2P or LAN micro-adjacency segment type";
               }
               leaf srv6-micro-adjacency-sid {
                 type jt:ipv6addr;
                 description "Micro-adjacency-SID address";
               }
               leaf srv6-micro-adjacency-sid-flags {
                 type string;
                 description "SRv6 micro-adjacency-SID flags";
               }
               leaf srv6-micro-adjacency-sid-weight {
                 type int32;
                 description "SRv6 micro-adjacency-SID weight";
               }
               leaf srv6-micro-adjacency-sid-algorithm {
                 type int32;
                 description "SRv6 micro-adjacency-SID algorithm";
               }
               leaf srv6-micro-adjacency-sid-flags-detail {
                 type string;
                 description "SRv6 micro-adjacency-SID flags with bit field";
               }
               leaf srv6-micro-adjacency-sid-endpoint-func {
                 type string;
                 description "SRv6 micro-adjacency-SID endpoint function";
               }
               leaf srv6-lan-micro-adjacency-sid-nbr-sysid {
                 type string;
                 description "LAN micro-adjacency-SID neighbor system id";
               }
               container isis-srv6-sid-structure-info {
                 leaf isis-srv6-locator-block-length {
                   type uint32;
                   description "Locator block length";
                 }
                 leaf isis-srv6-locator-node-length {
                   type uint32;
                   description "Locator node length";
                 }
                 leaf isis-srv6-sid-function-length {
                   type uint32;
                   description "SID function length";
                 }
                 leaf isis-srv6-sid-argument-length {
                   type uint32;
                   description "SID argument length";
                 }
               }
             }
             container application-specific-attributes {
               leaf application-specific-tlv-length {
                 type int32;
               }
               leaf standard-application-flags {
                 type string;
                 description "Legacy bit flag for SABM";
               }
               leaf standard-application-bitmask-length {
                 type int32;
               }
               leaf standard-application-bitmask {
                 type string;
               }
               leaf user-application-bitmask-length {
                 type int32;
               }
               container isis-reachability-sub-subtlv {
                 leaf max-bandwidth {
                   type int32;
                 }
                 leaf max-reserve-bandwidth {
                   type int32;
                 }
                 leaf current-bandwidth-header {
                   type empty;
                 }
                 leaf te-metric {
                   type int32;
                   description "LSP TE metric";
                 }
                 leaf uni-link-delay {
                   type int32;
                 }
                 leaf min-uni-link-delay {
                   type int32;
                 }
                 leaf max-uni-link-delay {
                   type int32;
                 }
                 leaf uni-link-delay-variation {
                   type int32;
                 }
                 leaf extended-admin-groups {
                   type string;
                 }
                 leaf isis-subtlv-type {
                   type int32;
                 }
                 container admin-groups {
                   leaf color {
                     type int32;
                   }
                   leaf no-group-flag {
                     type empty;
                   }
                   leaf-list admin-group-name {
                     type string;
                     description "Name of the admin group";
                   }
                   leaf admin-group-number {
                     type int32;
                     description "Number of the admin group";
                   }
                 }
                 list priority-reserve-bandwidth {
                   leaf bandwidth-priority {
                     type int32;
                   }
                   leaf current-reserve-bandwidth {
                     type int32;
                   }
                 }
               }
             }
           }
           container node-msd-adv-sub-tlv {
           }
           container rtr-capability-tlv {
             leaf rtr-capability-tlv.heading {
               type string;
             }
             leaf router-id {
               type jt:ipaddr;
             }
             leaf rtr-cap-flags {
               type string;
             }
             container spring-capability-sub-tlv {
               leaf spring-capability-flags {
                 type string;
               }
               leaf spring-capability-range {
                 type uint32;
               }
               leaf spring-capability-sid-label {
                 type uint32;
               }
             }
             container spring-algorithm-sub-tlv {
               leaf spring-algorithm-type {
                 type uint32;
               }
             }
             container crh-capability-sub-tlv {
               leaf crh-capability-type {
                 type uint32;
               }
             }
             container flex-algorithm-sub-tlv {
               leaf system-name {
                 type string;
                 description "Hostname for a system";
               }
               leaf flex-algorithm-id {
                 type uint32;
               }
               leaf flex-algorithm-subtlv-length {
                 type uint32;
               }
               leaf flex-algorithm-metric-str {
                 type string;
               }
               leaf flex-algorithm-calc-str {
                 type string;
               }
               leaf flex-algorithm-metric-type {
                 type uint32;
               }
               leaf flex-algorithm-calc-type {
                 type uint32;
               }
               leaf flex-algorithm-priority {
                 type uint32;
               }
               leaf flex-algorithm-flags {
                 type string;
               }
               leaf flex-algorithm-include-any {
                 type string;
               }
               leaf flex-algorithm-include-all {
                 type string;
               }
               leaf flex-algorithm-exclude {
                 type string;
               }
               leaf participation-reason {
                 type string;
               }
               leaf flex-algorithm-po-flags {
                 type uint32;
               }
               leaf flex-algorithm-po-res {
                 type uint32;
               }
               leaf flex-algorithm-po-offset {
                 type uint32;
               }
               container flex-algorithm-include-any-detail {
                 container admin-groups {
                   leaf color {
                     type int32;
                   }
                   leaf no-group-flag {
                     type empty;
                   }
                   leaf-list admin-group-name {
                     type string;
                     description "Name of the admin group";
                   }
                   leaf admin-group-number {
                     type int32;
                     description "Number of the admin group";
                   }
                 }
               }
               container flex-algorithm-include-all-detail {
                 container admin-groups {
                   leaf color {
                     type int32;
                   }
                   leaf no-group-flag {
                     type empty;
                   }
                   leaf-list admin-group-name {
                     type string;
                     description "Name of the admin group";
                   }
                   leaf admin-group-number {
                     type int32;
                     description "Number of the admin group";
                   }
                 }
               }
               container flex-algorithm-exclude-detail {
                 container admin-groups {
                   leaf color {
                     type int32;
                   }
                   leaf no-group-flag {
                     type empty;
                   }
                   leaf-list admin-group-name {
                     type string;
                     description "Name of the admin group";
                   }
                   leaf admin-group-number {
                     type int32;
                     description "Number of the admin group";
                   }
                 }
               }
             }
             container ipv6-te-router-id-sub-tlv {
               leaf ipv6-te-router-id {
                 type jt:ipv6addr;
               }
             }
             container srv6-cap-sub-tlv {
               leaf srv6-cap-flags {
                 type uint32;
               }
             }
             container node-msd-adv-sub-tlv {
               leaf node-msd-adv-sub-tlv.heading {
                 type string;
               }
               leaf msd-type {
                 type uint32;
               }
               leaf msd-length {
                 type uint32;
               }
               container srh-max-sl-sub-tlv {
                 leaf srh-max-sl-sub-tlv.heading {
                   type string;
                 }
                 leaf sl-max-type {
                   type uint32;
                 }
                 leaf sl-max-value {
                   type uint32;
                 }
               }
               container mpls-node-msd {
                 leaf mpls-node-msd.heading {
                   type string;
                 }
                 leaf mpls-node-msd-type {
                   type uint32;
                 }
                 leaf mpls-node-msd-value {
                   type uint32;
                 }
               }
             }
             container srms-preference-sub-tlv {
               leaf srms-preference {
                 type uint32;
               }
             }
           }
           container authentication-tlv {
             leaf tlv-length {
               type int32;
             }
           }
           container idrp-tlv {
             leaf tlv-length {
               type int32;
             }
           }
           list ip-prefix-tlv {
             leaf isis-topology-id {
               type string;
             }
             leaf-list ip-prefix-tlv.heading {
               type string;
             }
             leaf-list address-prefix {
               type jt:ipaddr;
             }
             leaf metric {
               type int32;
             }
             leaf prefix-status {
               type string;
             }
             leaf subtlv-size {
               type int32;
             }
             container isis-prefix-subtlv {
               container isis-prefix-tag {
                 leaf isis-prefix-tag-index {
                   type int32;
                 }
                 leaf isis-prefix-tag-value {
                   type int32;
                 }
               }
               container isis-prefix-sid {
                 leaf isis-prefix-sid-type {
                   type string;
                 }
                 leaf isis-prefix-sid-flags {
                   type string;
                 }
                 leaf isis-prefix-sid-algorithm {
                   type string;
                 }
                 leaf isis-prefix-sid-value {
                   type string;
                 }
               }
               container isis-flex-algo-prefix-metric {
                 leaf isis-flex-algorithm-metric {
                   type string;
                 }
                 leaf isis-flex-algorithm-id {
                   type string;
                 }
               }
               container isis-prefix-attribute-sub-tlv {
                 leaf isis-prefix-attribute-flags {
                   type string;
                 }
               }
               container isis-prefix-ipv4-source-rtrid-sub-tlv {
                 leaf isis-prefix-ipv4-source-rtrid {
                   type string;
                 }
               }
               container isis-prefix-ipv6-source-rtrid-sub-tlv {
                 leaf isis-prefix-ipv6-source-rtrid {
                   type string;
                 }
               }
               container isis-bier-info-sub-tlv {
                 leaf isis-bier-info-subdomain-id {
                   type string;
                 }
                 leaf isis-bier-info-bfr-id {
                   type string;
                 }
                 leaf isis-bier-info-bier-algo {
                   type string;
                 }
                 leaf isis-bier-info-igp-algo {
                   type string;
                 }
                 container isis-bier-mpls-encap-sub-tlv {
                   leaf isis-bier-mpls-max-si {
                     type string;
                   }
                   leaf isis-bier-mpls-bs-len {
                     type string;
                   }
                   leaf isis-bier-mpls-label {
                     type string;
                   }
                 }
               }
             }
           }
           container isis-srlg-tlv {
             leaf isis-srlg-tlv.heading {
               type string;
             }
             leaf-list address-prefix {
               type jt:ipaddr;
             }
             leaf srlg-flag {
               type string;
             }
             leaf srlg-address {
               type jt:ipaddr;
             }
             leaf srlg-neighbor-prefix {
               type jt:ipaddr;
             }
             leaf srlg-local-ifindex {
               type uint32;
               description "Local interface index";
             }
             leaf srlg-remote-ifindex {
               type uint32;
               description "Remote interface index";
             }
             container isis-srlg-value {
               leaf isis-srlg-value.heading {
                 type string;
               }
               leaf-list isis-srlg-name {
                 type string;
               }
             }
           }
           container unknown-sub-tlv {
             leaf isis-tlv-type {
               type int32;
             }
             leaf tlv-length {
               type int32;
             }
           }
           container label-binding-tlv {
             leaf protocol-name {
               type string;
             }
             leaf-list address-prefix {
               type jt:ipaddr;
             }
             leaf label-binding-flags {
               type string;
             }
             leaf label-binding-weight {
               type int32;
             }
             leaf label-binding-range {
               type int32;
             }
             leaf isis-label {
               type int32;
             }
             container isis-prefix-sid {
               leaf isis-prefix-sid-type {
                 type string;
               }
               leaf isis-prefix-sid-flags {
                 type string;
               }
               leaf isis-prefix-sid-algorithm {
                 type string;
               }
               leaf isis-prefix-sid-value {
                 type string;
               }
             }
           }
           container unknown-tlv {
             leaf isis-tlv-type {
               type int32;
             }
             leaf tlv-length {
               type int32;
             }
           }
           container tlv-stragglers {
             leaf bytes-left {
               type int32;
             }
           }
           container srv6-locator-micro-sid-tlv {
           }
           container isis-srv6-locator-tlv {
             leaf isis-srv6-locator-tlv.heading {
               type string;
             }
             leaf-list address-prefix {
               type jt:ipaddr;
             }
             leaf srv6-metric {
               type uint32;
             }
             leaf srv6-mtid {
               type uint32;
             }
             leaf srv6-flags {
               type uint32;
             }
             leaf srv6-algorithm {
               type uint32;
             }
             leaf sid-flags {
               type uint32;
             }
             leaf micro-sid-flags {
               type uint32;
             }
             leaf isis-prefix-attribute-flags {
               type string;
             }
             leaf isis-subtlv-type {
               type int32;
             }
             leaf subtlv-length {
               type int32;
             }
             container srv6-locator-sid-tlv {
               leaf isis-srv6-locator-sid-address {
                 type jt:ipv6addr;
               }
               leaf isis-srv6-locator-sid-func {
                 type string;
               }
             }
             container srv6-locator-micro-sid-tlv {
               leaf isis-srv6-locator-micro-sid-address {
                 type jt:ipv6addr;
               }
               leaf isis-srv6-locator-micro-sid-func {
                 type string;
               }
               container isis-srv6-sid-structure-info {
                 leaf isis-srv6-locator-block-length {
                   type uint32;
                   description "Locator block length";
                 }
                 leaf isis-srv6-locator-node-length {
                   type uint32;
                   description "Locator node length";
                 }
                 leaf isis-srv6-sid-function-length {
                   type uint32;
                   description "SID function length";
                 }
                 leaf isis-srv6-sid-argument-length {
                   type uint32;
                   description "SID argument length";
                 }
               }
             }
           }
           leaf isis-tlv.heading {
             type string;
           }
         }
         container isis-es-neighbor {
           leaf reachability-delay {
             type empty;
           }
           leaf reachability-expense {
             type empty;
           }
           leaf reachability-error {
             type empty;
           }
           leaf es-neighbor-id {
             type string;
           }
           leaf metric {
             type int32;
           }
           leaf es-neighbor-status {
             type string;
           }
         }
         container isis-label-binding {
           leaf protocol-name {
             type string;
           }
           leaf-list address-prefix {
             type jt:ipaddr;
           }
           leaf isis-label {
             type int32;
           }
           leaf binding-flags {
             type string;
           }
         }
         container isis-srv6-locator-tlv {
           container srv6-locator-micro-sid-tlv {
             leaf isis-srv6-locator-micro-sid-address {
               type jt:ipv6addr;
             }
             leaf isis-srv6-locator-micro-sid-func {
               type string;
             }
             container isis-srv6-sid-structure-info {
               leaf isis-srv6-locator-block-length {
                 type uint32;
                 description "Locator block length";
               }
               leaf isis-srv6-locator-node-length {
                 type uint32;
                 description "Locator node length";
               }
               leaf isis-srv6-sid-function-length {
                 type uint32;
                 description "SID function length";
               }
               leaf isis-srv6-sid-argument-length {
                 type uint32;
                 description "SID argument length";
               }
             }
           }
           leaf isis-srv6-locator-tlv.heading {
             type string;
           }
           leaf-list address-prefix {
             type jt:ipaddr;
           }
           leaf srv6-metric {
             type uint32;
           }
           leaf srv6-mtid {
             type uint32;
           }
           leaf srv6-flags {
             type uint32;
           }
           leaf srv6-algorithm {
             type uint32;
           }
           leaf sid-flags {
             type uint32;
           }
           leaf micro-sid-flags {
             type uint32;
           }
           leaf isis-prefix-attribute-flags {
             type string;
           }
           leaf isis-subtlv-type {
             type int32;
           }
           leaf subtlv-length {
             type int32;
           }
           container srv6-locator-sid-tlv {
             leaf isis-srv6-locator-sid-address {
               type jt:ipv6addr;
             }
             leaf isis-srv6-locator-sid-func {
               type string;
             }
           }
         }
         leaf lsp-stub {
           type empty;
         }
         container transmission-status {
           leaf transmit-count {
             type int32;
           }
           leaf message {
             type string;
           }
           leaf interface-name {
             type string;
             description "Name of interface";
           }
           leaf transmit-time {
             type string;
             description "Time at which this message is queued for transmission";
           }
         }
       }
     }
   }
   grouping isis-hostname-information-block {
     list isis-hostname {
       description "Entry in the system-ID-to-hostname mapping table";
       leaf system-id {
         type string;
         description "Six-octet ISO system ID for a system";
       }
       leaf system-name {
         type string;
         description "Hostname for a system";
       }
       leaf isis-hostname-type {
         type string;
         description "Type of system-ID-to-hostname mapping";
       }
     }
   }
   grouping isis-interface-information-block {
     container isis-interface {
       leaf interface-name {
         type string;
         description "Name of interface";
       }
       leaf circuit-type {
         type int32;
       }
       leaf circuit-id {
         type int32;
       }
       leaf isis-interface-state-one {
         type string;
       }
       leaf dr-id-one {
         type string;
       }
       leaf isis-interface-state-two {
         type string;
       }
       leaf dr-id-two {
         type string;
       }
       leaf metric-one {
         type int32;
       }
       leaf metric-two {
         type int32;
       }
       container interface-level-data {
         leaf level {
           type int32;
           description "IS-IS Level";
         }
         leaf adjacency-count {
           type int32;
         }
         leaf interface-priority {
           type int32;
         }
         leaf metric {
           type int32;
         }
         leaf passive {
           type string;
         }
         leaf hello-time {
           type int32;
         }
         leaf holdtime {
           type int32;
           description "Delay before timing out the adjacency (default is 180 seconds)";
         }
         leaf dr-id-one {
           type string;
         }
         leaf dr-id-two {
           type string;
         }
         leaf dr-flag {
           type string;
         }
         leaf te-metric {
           type int32;
           description "LSP TE metric";
         }
         leaf flex-algo-te-metric {
           type int32;
         }
         leaf tilfa-prot-link {
           type string;
         }
         leaf tilfa-prot-fate {
           type string;
         }
         leaf tilfa-prot-srlg {
           type string;
         }
         leaf tilfa-prot-node {
           type int32;
         }
         list isis-interface-level-topology {
           leaf isis-topology-id {
             type string;
           }
           leaf isis-topology-metric {
             type int32;
             description "Metric for a topology";
           }
         }
       }
       leaf isis-interface.heading {
         type string;
       }
       leaf interface-index {
         type int32;
       }
       leaf interface-state-value {
         type int32;
       }
       leaf interface-disabled-flag {
         type empty;
       }
       leaf lsp-interval {
         type int32;
       }
       leaf csnp-interval {
         type int32;
       }
       leaf system-name {
         type string;
         description "Hostname for a system";
       }
       leaf mesh-group {
         type string;
       }
       leaf adjacency-advertisement {
         type string;
         description "State of the adjacency advertisment";
       }
       leaf isis-layer2-map-enabled {
         type string;
         description "IS-IS controls kernel ARP/ND entries for its nexthops";
       }
       leaf interface-protection-type {
         type string;
       }
       leaf no-eligible-backup {
         type empty;
       }
       leaf level {
         type int32;
         description "IS-IS Level";
       }
       leaf flood-ref-node {
         type string;
         description "Flood reflector";
       }
       leaf flood-ref-cluster-id {
         type uint32;
         description "Flood reflector cluster id";
       }
       leaf hello-padding {
         type string;
       }
       leaf max-hello-size {
         type int32;
       }
       leaf flood-group-iso-address {
         type string;
         description "ISO address of an interface LSP filter";
       }
       leaf igp-ldp-sync-state {
         type string;
         description "State of synchronization between Label Distribution Protocol (LDP) and the interior gateway protocol (IGP)";
       }
       leaf igp-ldp-sync-last-change {
         type string;
         description "Time since the state of synchronization between Label Distribution Protocol (LDP) and the interior gateway protocol (IGP) last changed";
       }
       leaf igp-ldp-sync-reason {
         type string;
         description "Reason for the change in the state of synchronization between Label Distribution Protocol (LDP) and the interior gateway protocol (IGP)";
       }
       leaf igp-ldp-sync-holdtime {
         type string;
         description "Length of time during which the maximum metric is advertised for an interface that is in the hold-down state because synchronization was lost between Label Distribution Protocol (LDP) and the interior gateway protocol (IGP)";
       }
       leaf igp-ldp-sync-timeleft {
         type int32;
         description "Remaining amount of time the interface will remain in the hold-down state because synchronization was lost between Label Distribution Protocol (LDP) and the interior gateway protocol (IGP)";
       }
       leaf interface-group-holddown-delay {
         type int32;
       }
       leaf interface-group-holddown-left {
         type int32;
       }
       leaf unidirectional-link-delay {
         type uint32;
       }
       leaf min-unidirectional-link-delay {
         type uint32;
       }
       leaf max-unidirectional-link-delay {
         type uint32;
       }
       leaf unidirectional-delay-variation {
         type uint32;
       }
       container interface-strict-bfd {
         leaf interface-bfd-family {
           type string;
         }
         leaf interface-bfdv6-family {
           type string;
         }
         leaf strict-bfd {
           type string;
         }
       }
     }
   }
   grouping isis-interface-group-information-block {
     container isis-interface-group {
       description "Interface-group information for an IS-IS instance";
       leaf isis-interface-group-name {
         type string;
       }
       leaf interface-name {
         type string;
         description "Name of interface";
       }
       leaf isis-interface-bandwidth {
         type string;
       }
       leaf isis-interface-state-updown {
         type string;
       }
       leaf isis-interface-state-ignore {
         type string;
       }
       leaf isis-interface-state-degrade {
         type string;
       }
       leaf isis-interface-weight {
         type uint32;
       }
       leaf isis-interface-group-bandwidth-nominal {
         type string;
       }
       leaf isis-interface-group-bandwidth-actual {
         type string;
       }
       list isis-level-information {
         description "IS-IS Level Information";
         leaf level {
           type int32;
           description "IS-IS Level";
         }
         container isis-bbm-information {
           leaf isis-topology-id {
             type string;
           }
           leaf isis-topology-metric-default {
             type uint32;
           }
           leaf isis-topology-metric-actual {
             type uint32;
           }
           leaf isis-bbm-bandwidth {
             type uint64;
           }
           leaf isis-bbm-metric {
             type uint32;
           }
         }
         container adjacency-segment-information {
           leaf adjacency-segment-level {
             type int32;
           }
           leaf ipv4-protected-adjacency-segment-id {
             type int32;
           }
           leaf ipv4-unprotected-adjacency-segment-id {
             type int32;
           }
           leaf ipv6-protected-adjacency-segment-id {
             type int32;
           }
           leaf ipv6-unprotected-adjacency-segment-id {
             type int32;
           }
           leaf adjacency-segment-flags {
             type string;
           }
         }
         container isis-adjsid-information {
           leaf isis-adjacency-segment {
             type string;
           }
           leaf isis-adjsid-type {
             type string;
           }
           leaf isis-adjsid-value {
             type uint32;
           }
           leaf isis-adjsid-nbr {
             type string;
           }
         }
       }
     }
   }
   grouping isis-layer2-map-information-block {
     container isis-layer2-map-database {
       leaf instance-name {
         type string;
       }
       leaf ip-entry-count {
         type uint32;
       }
       leaf ip6-entry-count {
         type uint32;
       }
       container isis-layer2-map-entry {
         leaf ip-address {
           type jt:ipaddr;
         }
         leaf interface-name2 {
           type string;
         }
         leaf-list snpa {
           type string;
         }
         leaf isis-layer2-map-next-refresh {
           type uint32;
         }
         leaf-list isis-layer2-map-state {
           type string;
         }
         leaf isis-layer2-map-refcount {
           type int32;
         }
       }
     }
   }
   grouping isis-overview-information-block {
     container isis-overview {
       description "Overview information for an IS-IS instance";
       leaf instance-name {
         type string;
       }
       leaf isis-router-id {
         type jt:ipaddr;
         description "IS-IS router ID";
       }
       leaf isis-v6-router-id {
         type jt:ipv6addr;
         description "IS-IS IPv6 Router ID";
       }
       leaf isis-router-hostname {
         type string;
         description "IS-IS router hostname";
       }
       leaf isis-router-sysid {
         type string;
         description "IS-IS router sysid";
       }
       leaf isis-router-areaid {
         type string;
         description "IS-IS router areaid";
       }
       leaf isis-max-areas {
         type uint32;
         description "Maximum Number of Areas";
       }
       leaf isis-lsp-lifetime {
         type uint32;
         description "Maximum LSP lifetime";
       }
       leaf isis-lsp-lifetime-filter {
         type uint32;
         description "Low LSP life time filter";
       }
       leaf isis-reference-bandwidth {
         type uint64;
         description "Bandwidth for calculating metric defaults";
       }
       leaf isis-adjacency-holddown {
         type string;
         description "IS-IS Adjacency holddown status";
       }
       leaf isis-attached-bit-evaluation {
         type string;
         description "The IS-IS L1 attached bit evaluation";
       }
       leaf isis-layer2-map-enabled {
         type string;
         description "IS-IS controls kernel ARP/ND entries for its nexthops";
       }
       container isis-spf-information {
         description "SPF options";
         leaf isis-spf-delay {
           type string;
           description "Delay before performing SPF calculations";
         }
         leaf isis-spf-holddown {
           type string;
           description "Throttling delay between consecutive SPF calculations";
         }
         leaf isis-spf-rapid-runs {
           type uint32;
           description "Number of rapid SPF calculations before SPF holddown.";
         }
         leaf isis-uloop-avoidance {
           type string;
           description "Micro-loop avoidance status";
         }
         leaf isis-uloop-avoidance-method {
           type string;
           description "Micro-loop avoidance mechanism employed";
         }
         leaf isis-route-convergence-delay {
           type string;
           description "Delay before downloading routes to forwarding plane";
         }
         leaf isis-topo-sessid-count {
           type uint32;
           description "Number of Session IDs associated with routes in this topology";
         }
         container isis-spf {
           leaf node-count {
             type int32;
           }
           container isis-spf-results-header {
             leaf isis-topology-id {
               type string;
             }
             leaf level {
               type int32;
               description "IS-IS Level";
             }
           }
           list isis-spf-result {
             leaf node-id {
               type string;
             }
             leaf metric {
               type int32;
             }
             leaf disconnected {
               type empty;
             }
             leaf no-first-fragment {
               type empty;
             }
             leaf node-address {
               type string;
             }
             list next-hop-element {
               leaf interface-name {
                 type string;
                 description "Name of interface";
               }
               leaf isis-next-hop-type {
                 type string;
               }
               leaf isis-next-hop {
                 type string;
               }
               leaf-list snpa {
                 type string;
               }
             }
             list prefix-element {
               leaf prefix-metric {
                 type int32;
               }
               leaf external-prefix-metric {
                 type int32;
               }
               leaf-list address-prefix {
                 type jt:ipaddr;
               }
             }
             list end-system-element {
               leaf end-system-metric {
                 type int32;
               }
               leaf end-system-id {
                 type string;
                 description "Six-octet ISO system ID for a end-system";
               }
             }
           }
           container isis-spf-log-header {
             leaf isis-topology-id {
               type string;
             }
             leaf level {
               type int32;
               description "IS-IS Level";
             }
           }
           container isis-spf-log {
             leaf start-time {
               type string;
             }
             leaf elapsed-time {
               type string;
               description "Time this adjacency or session has been up or down";
             }
             leaf spf-trigger-count {
               type int32;
             }
             leaf logging-reason {
               type string;
             }
             leaf lsp-name {
               type string;
               description "Tunneled into an RSVP LSP";
             }
             leaf system-name {
               type string;
               description "Hostname for a system";
             }
             leaf interface-name {
               type string;
               description "Name of interface";
             }
           }
           container isis-backup-spf-result {
             leaf node-id {
               type string;
             }
             leaf no-first-fragment {
               type empty;
             }
             leaf backup-root {
               type string;
             }
             leaf backup-root-metric {
               type int32;
             }
             leaf metric {
               type int32;
             }
             leaf backup-root-preference {
               type int32;
             }
             leaf track-item {
               type string;
             }
             leaf track-item-isnbr {
               type string;
             }
             leaf rev-track-item {
               type string;
             }
             leaf rev-track-item-isnbr {
               type string;
             }
             leaf node-address {
               type string;
             }
             list next-hop-element {
               leaf interface-name {
                 type string;
                 description "Name of interface";
               }
               leaf isis-next-hop-type {
                 type string;
               }
               leaf isis-next-hop {
                 type string;
               }
               leaf-list snpa {
                 type string;
               }
             }
             list backup-next-hop-element {
               leaf interface-name {
                 type string;
                 description "Name of interface";
               }
               leaf isis-next-hop-type {
                 type string;
               }
               leaf isis-next-hop {
                 type string;
               }
               leaf-list snpa {
                 type string;
               }
               leaf isis-backup-prefix-refcount {
                 type uint32;
                 description "Number of prefixes that uses this nexthop as backup";
               }
               leaf isis-backup-score {
                 type string;
               }
             }
             list no-coverage-reason-element {
               leaf isis-next-hop-type {
                 type string;
               }
               leaf no-coverage-reason {
                 type string;
               }
             }
           }
         }
       }
       container isis-overload-information {
         description "Overload bit behaviour at startup";
         leaf isis-overload-enabled {
           type empty;
           description "Overload bit upon startup is set";
         }
         leaf isis-overload-high-metrics {
           type string;
           description "High metrics are used for Overload signaling";
         }
         leaf isis-overload-allow-route-leaking {
           type string;
           description "Allow route leaking when configured to be in overload";
         }
         leaf isis-overload-internal-prefixes {
           type string;
           description "Allow internal prefixes to be advertised with high metric";
         }
         leaf isis-overload-external-prefixes {
           type string;
           description "Allow external prefixes to be advertised with high metric";
         }
         leaf isis-overload-timeout {
           type int32;
           description "Clearance of the Overload bit after startup";
         }
         leaf isis-overload-remaining-time {
           type string;
           description "Time remaining on configured overload timeout";
         }
       }
       container isis-routing {
         description "List of routed IS-IS address families";
         leaf isis-routing-ipv4 {
           type empty;
           description "Routing IPv4 prefixes is enabled";
         }
         leaf isis-routing-ipv6 {
           type empty;
           description "Routing IPv6 prefixes is enabled";
         }
         leaf isis-routing-clns {
           type empty;
           description "Routing CLNS prefixes is enabled";
         }
         leaf isis-routing-spring-mpls {
           type empty;
           description "Routing CLNS prefixes is enabled";
         }
       }
       container isis-traffic-engineering {
         description "Traffic engineering";
         leaf isis-te-status {
           type string;
           description "Traffic engineering status";
         }
         leaf isis-ted-ipv6 {
           type string;
           description "Traffic Engineering v6 status";
         }
         leaf isis-te-shortcuts-ipv4 {
           type empty;
           description "IPv4 Traffic engineering shortcuts are enabled";
         }
         leaf isis-te-shortcuts-ipv6 {
           type empty;
           description "IPv6 Traffic engineering shortcuts are enabled";
         }
         leaf isis-te-shortcuts-ipv4-mpls {
           type empty;
           description "IPv4-MPLS Traffic engineering shortcuts are enabled";
         }
         leaf isis-te-shortcuts-ipv6-mpls {
           type empty;
           description "IPv6-MPLS Traffic engineering shortcuts are enabled";
         }
         leaf isis-te-shortcuts-clns {
           type empty;
           description "CLNS Traffic engineering shortcuts are enabled";
         }
         leaf isis-ipv4-multicast-rpf-routes {
           type empty;
           description "IPv4 routes for multicast RPF checks are installed into inet.2";
         }
         leaf isis-ignore-lsp-metrics {
           type empty;
           description "Label-switched path metrics when doing shortcuts are ignored";
         }
         leaf isis-ted-credibility-preference {
           type empty;
           description "Credibility follows protocol preference";
         }
       }
       container isis-restart {
         description "IS-IS restart parameters";
         leaf isis-restart-enabled {
           type string;
           description "IS-IS restart mode";
         }
         leaf isis-restart-duration {
           type uint32;
           description "Duration of IS-IS restart";
         }
         leaf isis-restart-helper-mode-enabled {
           type string;
           description "IS-IS helper mode";
         }
       }
       container isis-tilfa {
         description "IS-IS Post Convergence Backup parameters";
         leaf isis-tilfa-enabled {
           type string;
           description "Post Convergence Backup";
         }
         leaf isis-tilfa-max-labels {
           type int32;
           description "Max labels";
         }
         leaf isis-tilfa-max-srv6-sids {
           type int32;
           description "Max SRV6 SIDs";
         }
         leaf isis-tilfa-max-spf {
           type int32;
           description "Max spf";
         }
         leaf isis-tilfa-ecmp-backup {
           type int32;
           description "Post Convergence Max Ecmp Backup";
         }
       }
       container isis-spring {
         description "IS-IS SPRING parameters";
         leaf isis-spring-enabled {
           type string;
           description "Source Packet Routing";
         }
         leaf isis-srgb-allocation {
           type string;
           description "SRGB Block Allocation";
         }
         leaf isis-node-segment-enabled {
           type string;
           description "Node Segments Enabled";
         }
         leaf isis-srv6-enabled {
           type string;
           description "SRv6 Enabled";
         }
         container isis-srgb-config {
           description "SRGB block configuration related information";
           leaf isis-srgb-config-block-header {
             type string;
             description "SRGB Config Block";
           }
           leaf isis-srgb-start-label {
             type int32;
             description "Configuration of SRGB start label";
           }
           leaf isis-srgb-index-range {
             type int32;
             description "Configuration of SRGB index range";
           }
         }
         container isis-srgb-block {
           description "SRGB block related information";
           leaf isis-srgb-start-index {
             type int32;
             description "Starting Index for SRGB Block";
           }
           leaf isis-srgb-size {
             type int32;
             description "Size of the specific SRGB Block";
           }
           leaf isis-srgb-first-label {
             type int32;
             description "First label allocated for SRGB Block";
           }
           leaf isis-srgb-last-label {
             type int32;
             description "Last label allocated for SRGB Block";
           }
         }
         container isis-node-segment {
           description "Node Segments related information";
           leaf isis-node-segment-ipv4-index {
             type int32;
             description "IPv4 Node Segment index for this device";
           }
           leaf isis-node-segment-ipv6-index {
             type int32;
             description "IPv6 Node Segment index for this device";
           }
           leaf isis-node-segment-index-range {
             type int32;
             description "Range of Node Segment indices configured";
           }
           leaf isis-node-segment-block-header {
             type empty;
             description "Node Segment Blocks";
           }
           container isis-node-segment-block {
             description "Node Segment Blocks related information";
             leaf isis-node-segment-block-start-index {
               type int32;
               description "Starting Index for the specific Node Segment Block";
             }
             leaf isis-node-segment-block-size {
               type int32;
               description "Size of the specific Node Segment Block";
             }
             leaf isis-node-segment-block-first-label {
               type int32;
               description "First label allocated for the specific Node Segment Block";
             }
             leaf isis-node-segment-block-last-label {
               type int32;
               description "Last label allocated for the specific Node Segment Block";
             }
           }
         }
         list isis-srv6-locator {
           description "SRv6 Locator information";
           leaf isis-srv6-locator-name {
             type string;
             description "Locator name";
           }
           leaf isis-srv6-locator-address {
             type string;
             description "Locator prefix";
           }
           leaf isis-srv6-locator-algorithm {
             type uint32;
             description "Locator algorithm";
           }
           leaf isis-prefix-attribute-flags {
             type string;
           }
           container isis-srv6-end-sid {
             description "SRv6 end sid entry";
             leaf isis-srv6-end-sid-addr {
               type jt:ipv6addr;
               description "SRv6 End-SID prefix";
             }
             leaf-list isis-srv6-sid-flavor {
               type string;
             }
           }
           container isis-srv6-micro-node-sid {
             description "SRv6 end sid entry";
             leaf isis-srv6-micro-node-sid-addr {
               type jt:ipv6addr;
               description "SRv6 micro-node-SID address";
             }
             leaf-list isis-srv6-micro-sid-flavor {
               type string;
             }
           }
         }
       }
       list isis-level-information {
         description "IS-IS Level Information";
         leaf isis-level {
           type int32;
           description "IS-IS Level";
         }
         leaf isis-preference {
           type uint32;
           description "IS-IS internal route preference";
         }
         leaf isis-external-preference {
           type uint32;
           description "IS-IS external route preference";
         }
         leaf isis-prefix-export-limit {
           type uint32;
           description "IS-IS limit for external route export";
         }
         leaf isis-prefix-export-count {
           type uint32;
           description "Actual number of exported prefixes";
         }
         leaf isis-wide-metrics {
           type empty;
           description "Generation of wide metric TLVs is enabled";
         }
         leaf isis-narrow-metrics {
           type empty;
           description "Generation of narrow metric TLVs is enabled";
         }
         leaf isis-level-spring-enabled {
           type empty;
           description "Source Packet Routing is enabled";
         }
         leaf isis-adjacency-holddown-state {
           type string;
         }
         leaf isis-purge-originator-info {
           type string;
           description "Type of POI that gets added to purged LSPs";
         }
       }
     }
   }
   grouping isis-route-information-block {
     container isis-routing-table {
       leaf isis-topology-id {
         type string;
       }
       leaf level-one-version {
         type int32;
       }
       leaf level-two-version {
         type int32;
       }
       container isis-route {
         leaf-list address-prefix {
           type jt:ipaddr;
         }
         leaf level {
           type int32;
           description "IS-IS Level";
         }
         leaf route-version {
           type int32;
         }
         leaf metric {
           type int32;
         }
         leaf metric-type {
           type string;
         }
         leaf interface-name {
           type string;
           description "Name of interface";
         }
         leaf isis-next-hop-type {
           type string;
         }
         leaf isis-next-hop {
           type string;
         }
         leaf isis-backup-score {
           type string;
         }
         leaf prefix-originator {
           type string;
         }
         leaf prefix-level {
           type int32;
         }
         leaf prefix-metric {
           type int32;
         }
         leaf prefix-preference {
           type int32;
         }
         leaf isis-route-priority {
           type string;
         }
         leaf isis-rt-congestion-protection-activate {
           type string;
         }
         leaf isis-rt-congestion-protection-activate-count {
           type uint32;
         }
         list isis-backup-next-hop-sid-info {
           leaf isis-backup-next-hop-label {
             type uint32;
           }
           leaf isis-backup-next-hop-label-type {
             type string;
           }
           leaf isis-backup-next-hop-srv6-sid {
             type jt:ipaddr;
           }
           leaf isis-backup-next-hop-srv6-sid-type {
             type string;
           }
           leaf isis-backup-next-hop-sid-info-node-id {
             type string;
           }
           leaf isis-backup-next-hop-sid-info-adj-local-node-id {
             type string;
           }
           leaf isis-backup-next-hop-sid-info-adj-remote-node-id {
             type string;
           }
           leaf isis-backup-next-hop-sid-info-adj-local-v4-addr {
             type jt:ipaddr;
           }
           leaf isis-backup-next-hop-sid-info-adj-remote-v4-addr {
             type jt:ipaddr;
           }
           leaf isis-backup-next-hop-sid-info-adj-local-v6-addr {
             type jt:ipaddr;
           }
           leaf isis-backup-next-hop-sid-info-adj-remote-v6-addr {
             type jt:ipaddr;
           }
           leaf isis-backup-next-hop-sid-info-adj-local-unnumbered-id {
             type uint32;
           }
           leaf isis-backup-next-hop-sid-info-adj-remote-unnumbered-id {
             type uint32;
           }
         }
         list snpa {
           leaf snpa-type {
             type string;
             description "Type of SNPA";
           }
           list pfe-port-snpa {
             leaf pfe-id {
               type int32;
             }
             leaf port-id {
               type int32;
             }
           }
           list network-element-port-snpa {
             leaf port-id {
               type int32;
             }
           }
           list mstp-root-snpa {
             leaf mstp-root-id {
               type int32;
             }
           }
           list gateway-snpa {
             leaf gateway-addr {
               type jt:ipaddr;
             }
           }
           list layer2-domain-port-snpa {
             leaf port-id {
               type int32;
             }
           }
           list replication-block-snpa {
             leaf replication-block-id {
               type int32;
             }
           }
           list replication-route-snpa {
             leaf network-element-id {
               type jt:ipaddr;
             }
           }
           list layer2-multicast-port-snpa {
             leaf layer2-multicast-port-id {
               type int32;
             }
           }
           list inh-snpa {
             leaf inh-id {
               type int32;
             }
           }
         }
         list isis-rt-sessid {
           leaf-list isis-rt-sessid-val {
             type uint32;
           }
           leaf-list isis-rt-sessid-ver {
             type uint32;
           }
         }
         container isis-computed-backup-paths {
           leaf isis-computed-backup-paths-type {
             type string;
           }
           leaf isis-computed-backup-paths-count {
             type uint32;
           }
           leaf isis-computed-backup-paths-valid-count {
             type uint32;
           }
           leaf isis-computed-backup-paths-rttype {
             type string;
           }
           list isis-computed-backup-path {
             leaf isis-computed-backup-path-id {
               type uint32;
             }
             leaf isis-computed-backup-path-sid-count {
               type uint32;
             }
             leaf isis-computed-backup-path-error {
               type string;
             }
           }
         }
       }
     }
   }
   grouping isis-purge-information-block {
     container isis-purge {
       container isis-purge-log-header {
         leaf level {
           type int32;
           description "IS-IS Level";
         }
       }
       container isis-purge-log {
         leaf start-time {
           type string;
         }
         leaf lsp-name {
           type string;
           description "Tunneled into an RSVP LSP";
         }
         leaf osystem-name {
           type string;
           description "Hostname for a system";
         }
         leaf rsystem-name {
           type string;
           description "Hostname for a system";
         }
         leaf purge-trigger-count {
           type int32;
         }
       }
     }
   }
   grouping isis-spf-information-block {
     leaf isis-topo-sessid-count {
       type uint32;
       description "Number of Session IDs associated with routes in this topology";
     }
     container isis-spf {
       leaf node-count {
         type int32;
       }
       container isis-spf-results-header {
         leaf isis-topology-id {
           type string;
         }
         leaf level {
           type int32;
           description "IS-IS Level";
         }
       }
       list isis-spf-result {
         leaf node-id {
           type string;
         }
         leaf metric {
           type int32;
         }
         leaf disconnected {
           type empty;
         }
         leaf no-first-fragment {
           type empty;
         }
         leaf node-address {
           type string;
         }
         list next-hop-element {
           leaf interface-name {
             type string;
             description "Name of interface";
           }
           leaf isis-next-hop-type {
             type string;
           }
           leaf isis-next-hop {
             type string;
           }
           leaf-list snpa {
             type string;
           }
         }
         list prefix-element {
           leaf prefix-metric {
             type int32;
           }
           leaf external-prefix-metric {
             type int32;
           }
           leaf-list address-prefix {
             type jt:ipaddr;
           }
         }
         list end-system-element {
           leaf end-system-metric {
             type int32;
           }
           leaf end-system-id {
             type string;
             description "Six-octet ISO system ID for a end-system";
           }
         }
       }
       container isis-spf-log-header {
         leaf isis-topology-id {
           type string;
         }
         leaf level {
           type int32;
           description "IS-IS Level";
         }
       }
       container isis-spf-log {
         leaf start-time {
           type string;
         }
         leaf elapsed-time {
           type string;
           description "Time this adjacency or session has been up or down";
         }
         leaf spf-trigger-count {
           type int32;
         }
         leaf logging-reason {
           type string;
         }
         leaf lsp-name {
           type string;
           description "Tunneled into an RSVP LSP";
         }
         leaf system-name {
           type string;
           description "Hostname for a system";
         }
         leaf interface-name {
           type string;
           description "Name of interface";
         }
       }
       container isis-backup-spf-result {
         leaf node-id {
           type string;
         }
         leaf no-first-fragment {
           type empty;
         }
         leaf backup-root {
           type string;
         }
         leaf backup-root-metric {
           type int32;
         }
         leaf metric {
           type int32;
         }
         leaf backup-root-preference {
           type int32;
         }
         leaf track-item {
           type string;
         }
         leaf track-item-isnbr {
           type string;
         }
         leaf rev-track-item {
           type string;
         }
         leaf rev-track-item-isnbr {
           type string;
         }
         leaf node-address {
           type string;
         }
         list next-hop-element {
           leaf interface-name {
             type string;
             description "Name of interface";
           }
           leaf isis-next-hop-type {
             type string;
           }
           leaf isis-next-hop {
             type string;
           }
           leaf-list snpa {
             type string;
           }
         }
         list backup-next-hop-element {
           leaf interface-name {
             type string;
             description "Name of interface";
           }
           leaf isis-next-hop-type {
             type string;
           }
           leaf isis-next-hop {
             type string;
           }
           leaf-list snpa {
             type string;
           }
           leaf isis-backup-prefix-refcount {
             type uint32;
             description "Number of prefixes that uses this nexthop as backup";
           }
           leaf isis-backup-score {
             type string;
           }
         }
         list no-coverage-reason-element {
           leaf isis-next-hop-type {
             type string;
           }
           leaf no-coverage-reason {
             type string;
           }
         }
       }
     }
   }
   grouping isis-statistics-information-block {
     container isis-statistics {
       leaf system-name {
         type string;
         description "Hostname for a system";
       }
       leaf snp-queue-length {
         type int32;
       }
       leaf snp-queue-drops {
         type int32;
       }
       leaf lsp-queue-length {
         type int32;
       }
       leaf lsp-queue-drops {
         type int32;
       }
       leaf spf-runs {
         type int32;
       }
       leaf flex-full-spf-runs {
         type int32;
       }
       leaf flex-prc-spf-runs {
         type int32;
       }
       leaf fragments-rebuilt {
         type int32;
       }
       leaf lsps-regenerated {
         type int32;
       }
       leaf purges-initiated {
         type int32;
       }
       leaf purges-received {
         type int32;
       }
       list isis-pdu-statistics {
         leaf isis-pdu-type {
           type string;
         }
         leaf packets-received {
           type uint64;
         }
         leaf packets-processed {
           type uint64;
         }
         leaf packets-dropped {
           type uint64;
         }
         leaf packets-sent {
           type uint64;
         }
         leaf packets-retransmitted {
           type uint64;
         }
       }
       container totals-information {
         leaf packets-received {
           type uint64;
         }
         leaf packets-sent {
           type uint64;
         }
       }
     }
   }
   grouping isis-interface-statistics-information-block {
     list isis-interface-statistics {
       leaf system-name {
         type string;
         description "Hostname for a system";
       }
       container isis-interface-statistics-intf {
         leaf isis-interface-name {
           type string;
         }
       }
       container isis-interface-statistics-table {
         list isis-pdu-statistics {
           leaf isis-pdu-type {
             type string;
           }
           leaf packets-received {
             type uint64;
           }
           leaf packets-processed {
             type uint64;
           }
           leaf packets-dropped {
             type uint64;
           }
           leaf packets-sent {
             type uint64;
           }
           leaf packets-retransmitted {
             type uint64;
           }
         }
       }
       container totals-information {
         leaf packets-received {
           type uint64;
         }
         leaf packets-sent {
           type uint64;
         }
       }
       container isis-interface-statistics-lsp-queue {
         leaf lsp-queue-name {
           type string;
         }
         leaf lsp-queue-entry-count {
           type int32;
         }
         list isis-interface-statistics-lsp-queue-entry {
           leaf lsp-id {
             type string;
           }
           leaf lsp-queue-time {
             type string;
           }
           leaf lsp-queue-expiration-time {
             type string;
           }
         }
       }
     }
   }
   grouping isis-interface-traffic-statistics-information-block {
     container isis-interface-traffic-statistics {
       leaf interface-name {
         type string;
         description "Name of interface";
       }
       leaf isis-output-bytes {
         type int32;
       }
       leaf isis-output-packets {
         type int32;
       }
     }
   }
   grouping isis-spring-flex-algorithm-information-block {
     list isis-spring-flex-algorithm {
       leaf flex-algorithm-id {
         type uint32;
       }
       leaf level {
         type int32;
         description "IS-IS Level";
       }
       leaf flex-algorithm-color {
         type uint32;
       }
       leaf flex-algorithm-participation {
         type string;
       }
       leaf participation-reason {
         type string;
       }
       leaf flex-algorithm-stat {
         type uint32;
       }
       leaf isis-topology-id {
         type string;
       }
       leaf flex-full-spf-runs {
         type int32;
       }
       leaf flex-prc-spf-runs {
         type int32;
       }
       leaf flex-algorithm-topo-stat {
         type uint32;
       }
       container flex-algorithm-winner-fad {
         container flex-algorithm-sub-tlv {
           leaf system-name {
             type string;
             description "Hostname for a system";
           }
           leaf flex-algorithm-id {
             type uint32;
           }
           leaf flex-algorithm-subtlv-length {
             type uint32;
           }
           leaf flex-algorithm-metric-str {
             type string;
           }
           leaf flex-algorithm-calc-str {
             type string;
           }
           leaf flex-algorithm-metric-type {
             type uint32;
           }
           leaf flex-algorithm-calc-type {
             type uint32;
           }
           leaf flex-algorithm-priority {
             type uint32;
           }
           leaf flex-algorithm-flags {
             type string;
           }
           leaf flex-algorithm-include-any {
             type string;
           }
           leaf flex-algorithm-include-all {
             type string;
           }
           leaf flex-algorithm-exclude {
             type string;
           }
           leaf participation-reason {
             type string;
           }
           leaf flex-algorithm-po-flags {
             type uint32;
           }
           leaf flex-algorithm-po-res {
             type uint32;
           }
           leaf flex-algorithm-po-offset {
             type uint32;
           }
           container flex-algorithm-include-any-detail {
             container admin-groups {
               leaf color {
                 type int32;
               }
               leaf no-group-flag {
                 type empty;
               }
               leaf-list admin-group-name {
                 type string;
                 description "Name of the admin group";
               }
               leaf admin-group-number {
                 type int32;
                 description "Number of the admin group";
               }
             }
           }
           container flex-algorithm-include-all-detail {
             container admin-groups {
               leaf color {
                 type int32;
               }
               leaf no-group-flag {
                 type empty;
               }
               leaf-list admin-group-name {
                 type string;
                 description "Name of the admin group";
               }
               leaf admin-group-number {
                 type int32;
                 description "Number of the admin group";
               }
             }
           }
           container flex-algorithm-exclude-detail {
             container admin-groups {
               leaf color {
                 type int32;
               }
               leaf no-group-flag {
                 type empty;
               }
               leaf-list admin-group-name {
                 type string;
                 description "Name of the admin group";
               }
               leaf admin-group-number {
                 type int32;
                 description "Number of the admin group";
               }
             }
           }
         }
       }
       container flex-algorithm-loser-fad {
         container flex-algorithm-sub-tlv {
           leaf system-name {
             type string;
             description "Hostname for a system";
           }
           leaf flex-algorithm-id {
             type uint32;
           }
           leaf flex-algorithm-subtlv-length {
             type uint32;
           }
           leaf flex-algorithm-metric-str {
             type string;
           }
           leaf flex-algorithm-calc-str {
             type string;
           }
           leaf flex-algorithm-metric-type {
             type uint32;
           }
           leaf flex-algorithm-calc-type {
             type uint32;
           }
           leaf flex-algorithm-priority {
             type uint32;
           }
           leaf flex-algorithm-flags {
             type string;
           }
           leaf flex-algorithm-include-any {
             type string;
           }
           leaf flex-algorithm-include-all {
             type string;
           }
           leaf flex-algorithm-exclude {
             type string;
           }
           leaf participation-reason {
             type string;
           }
           leaf flex-algorithm-po-flags {
             type uint32;
           }
           leaf flex-algorithm-po-res {
             type uint32;
           }
           leaf flex-algorithm-po-offset {
             type uint32;
           }
           container flex-algorithm-include-any-detail {
             container admin-groups {
               leaf color {
                 type int32;
               }
               leaf no-group-flag {
                 type empty;
               }
               leaf-list admin-group-name {
                 type string;
                 description "Name of the admin group";
               }
               leaf admin-group-number {
                 type int32;
                 description "Number of the admin group";
               }
             }
           }
           container flex-algorithm-include-all-detail {
             container admin-groups {
               leaf color {
                 type int32;
               }
               leaf no-group-flag {
                 type empty;
               }
               leaf-list admin-group-name {
                 type string;
                 description "Name of the admin group";
               }
               leaf admin-group-number {
                 type int32;
                 description "Number of the admin group";
               }
             }
           }
           container flex-algorithm-exclude-detail {
             container admin-groups {
               leaf color {
                 type int32;
               }
               leaf no-group-flag {
                 type empty;
               }
               leaf-list admin-group-name {
                 type string;
                 description "Name of the admin group";
               }
               leaf admin-group-number {
                 type int32;
                 description "Number of the admin group";
               }
             }
           }
         }
       }
       container isis-flex-algo-spf-log-header {
         leaf isis-topology-id {
           type string;
         }
         leaf sr-algorithm {
           type int32;
           description "SR Algorithm";
         }
         leaf level {
           type int32;
           description "IS-IS Level";
         }
       }
       container isis-spf-log {
         leaf start-time {
           type string;
         }
         leaf elapsed-time {
           type string;
           description "Time this adjacency or session has been up or down";
         }
         leaf spf-trigger-count {
           type int32;
         }
         leaf logging-reason {
           type string;
         }
         leaf lsp-name {
           type string;
           description "Tunneled into an RSVP LSP";
         }
         leaf system-name {
           type string;
           description "Hostname for a system";
         }
         leaf interface-name {
           type string;
           description "Name of interface";
         }
       }
     }
   }
   grouping isis-spring-sensor-information-block {
     leaf isis-spring-sensor-information-attribute {
       type string;
     }
     container isis-sensor-ingress {
       description "ISIS SPRING ingress sensor information";
       list isis-sensor-ingress-entries {
         leaf ingress-sensor-name {
           type string;
         }
         leaf ingress-sensor-id {
           type int32;
         }
       }
     }
     container isis-sensor-egress {
       description "ISIS SPRING egress sensor information";
       list isis-sensor-egress-entries {
         leaf egress-sensor-name {
           type string;
         }
         leaf egress-sensor-id {
           type int32;
         }
       }
     }
     container isis-sensor-per-sid {
       description "ISIS SPRING Per Sid ingress sensor information";
       list isis-sensor-per-sid-entries {
         leaf per-sid-sensor-name {
           type string;
         }
         leaf per-sid-sensor-id {
           type int32;
         }
       }
     }
     container isis-sensor-ip-mpls {
       description "ISIS SPRING Per Sid egress sensor information";
       list isis-sensor-ip-mpls-entries {
         leaf per-sid-sensor-name {
           type string;
         }
         leaf per-sid-sensor-id {
           type int32;
         }
       }
     }
   }
   grouping isis-backup-coverage-information-block {
     container isis-backup-coverage {
       leaf isis-topology-id {
         type string;
       }
       leaf level {
         type int32;
         description "IS-IS Level";
       }
       leaf isis-node-coverage {
         type string;
       }
       leaf isis-route-coverage-ipv4 {
         type string;
       }
       leaf isis-route-coverage-ipv4-mpls {
         type string;
       }
       leaf isis-route-coverage-ipv4-mpls-sspf {
         type string;
       }
       leaf isis-route-coverage-ipv6 {
         type string;
       }
       leaf isis-route-coverage-ipv6-mpls {
         type string;
       }
       leaf isis-route-coverage-ipv6-mpls-sspf {
         type string;
       }
       leaf isis-route-coverage-clns {
         type string;
       }
     }
   }
   grouping isis-backup-mplsp-information-block {
     container isis-backup-mplsp {
       leaf lsp-name {
         type string;
         description "Tunneled into an RSVP LSP";
       }
       leaf lsp-addr {
         type jt:ipaddr;
         description "LSP destination address";
       }
       leaf lsp-status {
         type string;
         description "LSP status";
       }
       leaf lsp-last-change {
         type string;
         description "Time of last LSP change";
       }
       leaf te-metric {
         type int32;
         description "LSP TE metric";
       }
       leaf metric {
         type int32;
       }
       leaf lsp-refcount {
         type int32;
       }
     }
   }
   grouping isis-context-information-block {
     list isis-context {
       leaf isis-context-id {
         type jt:ipaddr;
         description "Context identifier is an IP address identify protected context";
       }
       leaf isis-context-level {
         type int32;
         description "Advertise level";
       }
       leaf isis-context-owner-proto {
         type string;
         description "Routing protocols owns context identifier";
       }
       leaf isis-context-role {
         type string;
         description "Context role either primary or protector";
       }
       leaf isis-context-primary {
         type string;
         description "Context role is primary or protector";
       }
       leaf isis-context-metric {
         type uint32;
         description "Metric associate with context-id";
       }
       leaf isis-context-advertiser {
         type string;
         description "Context-id advertiser name";
       }
       leaf isis-context-advertiser-router-id {
         type jt:ipaddr;
         description "Router Ids of context-id advertiser";
       }
       leaf isis-context-advertiser-metric {
         type uint32;
         description "Context-id advertiser metric";
       }
       leaf isis-context-advertiser-level {
         type uint32;
         description "Context-id advertiser level";
       }
       leaf isis-not-compatible-mode {
         type empty;
       }
       leaf isis-context-advertiser-tlv {
         type string;
         description "Context-id advertiser tlv";
       }
     }
   }
 }
