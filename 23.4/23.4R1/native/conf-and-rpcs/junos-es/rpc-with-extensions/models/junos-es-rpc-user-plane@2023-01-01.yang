/*
 * Copyright (c) 2023 Juniper Networks, Inc.
 * All rights reserved.
 */
 module junos-es-rpc-user-plane {
   namespace "http://yang.juniper.net/junos-es/rpc/user-plane";

   prefix user-plane;

   import junos-common-ddl-extensions {
     prefix junos;
     revision-date 2023-01-01;
   }

   import junos-common-types {
     prefix jt;
     revision-date 2023-01-01;
   }

   organization "Juniper Networks, Inc.";

   contact "yang-support@juniper.net";

   description "Junos RPC YANG module for user-plane command(s)";

   revision 2023-01-01 {
     description "Junos: 23.4R1.10";
   }

   rpc get-user-plane-firewall-information {
     description "Show firewall information";
     junos:command "show user-plane firewall";
     input {
       uses command-forwarding;
       leaf terse {
         description "Show filter names only";
         type empty;
       }
     }
     output {
       container firewall-information {
         uses firewall-information-block;
       }
     }
   }
   rpc get-user-plane-firewall-counter-information {
     description "Counter name";
     junos:command "show user-plane firewall counter";
     input {
       uses command-forwarding;
       leaf countername {
         description "Counter name";
         junos:cli-feature "nokeyword";
         type string;
         mandatory true;
       }
       leaf filter {
         description "Filter name";
         type string;
         mandatory true;
       }
     }
     output {
       container firewall-information {
         uses firewall-information-block;
       }
     }
   }
   rpc get-user-plane-firewall-filter-information {
     description "Filter name";
     junos:command "show user-plane firewall filter";
     input {
       uses command-forwarding;
       leaf filtername {
         description "Filter name";
         junos:cli-feature "nokeyword";
         type string;
         mandatory true;
       }
       leaf counter {
         description "Counter name";
         type string;
       }
       leaf detail {
         description "Show filter statistics with enhanced policer statistics";
         type empty;
       }
     }
     output {
       container firewall-information {
         uses firewall-information-block;
       }
     }
   }
   rpc get-user-plane-filter-version {
     description "Show filter version installed";
     junos:command "show user-plane firewall filter version";
     output {
       container firewall-information {
         uses firewall-information-block;
       }
     }
   }
   rpc get-user-plane-firewall-filter-regex-information {
     description "Show filter using regular expression";
     junos:command "show user-plane firewall filter regex";
     input {
       leaf filtername {
         description "Regular expression of filter names";
         junos:cli-feature "nokeyword";
         type jt:regular-expression;
       }
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
     output {
       container firewall-information {
         uses firewall-information-block;
       }
     }
   }
   rpc get-user-plane-firewall-log-information {
     description "Show log entries for firewall activity";
     junos:command "show user-plane firewall log";
     input {
       leaf get-user-plane-firewall-log-detailed-information {
         description "Display detailed output";
         type empty;
       }
     }
     output {
       container firewall-log-information {
         uses firewall-log-information-block;
       }
     }
   }
   rpc get-userplane-firewall-prefix-action-information {
     description "Show prefix-action statistics for a filter";
     junos:command "show user-plane firewall prefix-action-stats";
     input {
       leaf filter {
         description "Filter name";
         type string;
         mandatory true;
       }
       leaf prefix-action {
         description "Prefix-action name";
         type string;
         mandatory true;
       }
       leaf from {
         description "Starting counter or policer";
         default "0";
         type union {
           type string {
             pattern "<.*>|$.*";
           }
           type uint32 {
             range "0 .. 65535";
           }
         }
       }
       leaf to {
         description "Ending counter or policer";
         default "65535";
         type union {
           type string {
             pattern "<.*>|$.*";
           }
           type uint32 {
             range "0 .. 65535";
           }
         }
       }
     }
     output {
       container firewall-prefix-action-information {
         uses firewall-prefix-action-information-block;
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping firewall-information-block {
     list filter-information {
       description "Details of a firewall filter";
       leaf filter-name {
         type string;
         description "Name of filter";
       }
       leaf user-plane-name {
         type string;
         description "Name of the User Plane";
       }
       list counter {
         description "Counter information";
         leaf counter-name {
           type string;
           description "Counter name";
         }
         leaf byte-count {
           type uint64;
           description "Bytes counted";
         }
         leaf packet-count {
           type uint64;
           description "Packets counted";
         }
       }
       list policer {
         description "Policer information";
         leaf policer-name {
           type string;
           description "Name of this policer";
         }
         leaf byte-count {
           type uint64;
           description "Bytes counted";
         }
         leaf packet-count {
           type uint64;
           description "Packets counted";
         }
       }
       list enchanced-hierarchical-policer {
         description "Hierarchical Policer information";
         leaf policer-name {
           type string;
           description "Name of this policer";
         }
         leaf byte-count-high {
           type uint64;
           description "Bytes counted";
         }
         leaf packet-count-high {
           type uint64;
           description "Packets counted";
         }
         leaf byte-count-medium-high {
           type uint64;
           description "Bytes counted";
         }
         leaf packet-count-medium-high {
           type uint64;
           description "Packets counted";
         }
         leaf byte-count-medium-low {
           type uint64;
           description "Bytes counted";
         }
         leaf packet-count-medium-low {
           type uint64;
           description "Packets counted";
         }
         leaf byte-count-low {
           type uint64;
           description "Bytes counted";
         }
         leaf packet-count-low {
           type uint64;
           description "Packets counted";
         }
         leaf packet-count {
           type uint64;
           description "Packets counted";
         }
         leaf byte-count {
           type uint64;
           description "Bytes counted";
         }
       }
       list filter-version {
         description "Filter version information";
         leaf filter-name {
           type string;
           description "Name of filter";
         }
         leaf version {
           type uint32;
           description "Filter version";
         }
       }
     }
     list user-plane-filter-information {
       description "Details of a user-plane firewall filter";
       leaf filter-name {
         type string;
         description "Name of filter";
       }
       leaf user-plane-name {
         type string;
         description "Name of the User Plane";
       }
       list counter {
         description "Counter information";
         leaf counter-name {
           type string;
           description "Counter name";
         }
         leaf byte-count {
           type uint64;
           description "Bytes counted";
         }
         leaf packet-count {
           type uint64;
           description "Packets counted";
         }
       }
       list filter-version {
         description "Filter version information";
         leaf filter-name {
           type string;
           description "Name of filter";
         }
         leaf version {
           type uint32;
           description "Filter version";
         }
       }
     }
   }
   grouping firewall-log-information-block {
     list log-information {
       description "Details of a single firewall log entry";
       leaf time {
         type string;
         description "Time of log";
       }
       leaf filter-name {
         type string;
         description "Name of filter";
       }
       leaf action-name {
         type string;
         description "Filter action";
       }
       leaf interface-name {
         type string;
         description "Name of interface";
       }
       leaf protocol-name {
         type string;
         description "Name of protocol";
       }
       leaf source-address {
         type string;
         description "Source address";
       }
       leaf destination-address {
         type string;
         description "Destination address";
       }
       leaf packet-length {
         type int32;
         description "Packet length";
       }
       leaf icmp-type {
         type int32;
         description "ICMP type";
       }
       leaf icmp-code {
         type int32;
         description "ICMP code";
       }
       leaf hex-dump-line {
         type string;
         description "Packet in Hex format";
       }
       leaf hex-dump-line1 {
         type string;
         description "Packet in Hex format";
       }
       leaf hex-dump-line2 {
         type string;
         description "Packet in Hex format";
       }
       leaf hex-dump-line3 {
         type string;
         description "Packet in Hex format";
       }
       leaf hex-dump-line4 {
         type string;
         description "Packet in Hex format";
       }
       leaf hex-dump-line5 {
         type string;
         description "Packet in Hex format";
       }
       leaf hex-dump-line6 {
         type string;
         description "Packet in Hex format";
       }
       leaf hex-dump-line7 {
         type string;
         description "Packet in Hex format";
       }
     }
   }
   grouping firewall-prefix-action-information-block {
     leaf filter-name {
       type string;
       description "Name of filter";
     }
     list counter {
       description "Counter information";
       leaf counter-name {
         type string;
         description "Counter name";
       }
       leaf byte-count {
         type uint64;
         description "Bytes counted";
       }
       leaf packet-count {
         type uint64;
         description "Packets counted";
       }
     }
     list policer {
       description "Policer information";
       leaf policer-name {
         type string;
         description "Name of this policer";
       }
       leaf byte-count {
         type uint64;
         description "Bytes counted";
       }
       leaf packet-count {
         type uint64;
         description "Packets counted";
       }
     }
   }
 }
