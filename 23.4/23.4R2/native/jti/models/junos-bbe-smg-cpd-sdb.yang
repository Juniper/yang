module junos-bbe-smg-cpd-sdb {
  yang-version 1;
  namespace "http://juniper.net/yang/bbe-smg-cpd";
  prefix junos-bbe-smg-cpd-sdb;

  organization
    "Juniper Networks Inc.";
  contact
    "Juniper Networks, Inc.

     1133 Innovation Way
     Sunnyvale, CA

     +1 888 314-5822

     E-mail: yang-support@juniper.net";
  description
    "Juniper Networks definition of Junos native bbe-smgd yang model";

  revision 2017-01-01 {
    description
      "Initial revision";
  }

  grouping sdb-statistics-state-group {
    description
      "The set of statistics associated with sdb state";
    leaf init-state-count {
      description
        "The count of subscribers in init state";
      type uint32;
    }
    leaf configured-state-count {
      description
        "The count of subscribers in configured state";
      type uint32;
    }
    leaf active-state-count {
      description
        "The count of subscribers in active state";
      type uint32;
    }
    leaf terminating-state-count {
      description
        "The count of subscribers in terminating state";
      type uint32;
    }
    leaf terminated-state-count {
      description
        "The count of subscribers in terminated state";
      type uint32;
    }
    leaf total-state-count {
      description
        "The total state count";
      type uint32;
    }
  }

  grouping sdb-statistics-client-group {
    description
      "The set of statistics associated with sdb client";
    leaf dhcp-client-count {
      description
        "The count of DHCP clients";
      type uint32;
    }
    leaf vlan-client-count {
      description
        "The count of VLAN clients";
      type uint32;
    }
    leaf ppp-client-count {
      description
        "The count of PPP clients";
      type uint32;
    }
    leaf pppoe-client-count {
      description
        "The count of PPPoE clients";
      type uint32;
    }
    leaf l2tp-client-count {
      description
        "The count of L2TP clients";
      type uint32;
    }
    leaf static-client-count {
      description
        "The count of static clients";
      type uint32;
    }
    leaf vpls-pw-client-count {
      description
        "The count of VPLS PW clients";
      type uint32;
    }
    leaf mlppp-client-count {
      description
        "The count of MLPPP clients";
      type uint32;
    }
    leaf essm-client-count {
      description
        "The count of ESSM clients";
      type uint32;
    }
    leaf total-client-count {
      description
        "The total count of clients";
      type uint32;
    }
  }

  grouping bbe-smg-cpd-sdb-top {
    description
      "The top level grouping for bbe-smgd";
    container junos {
      description
        "Container for JunOS";
      config false;
      container system {
        description
          "Container for system";
        container subscriber-management {
          description
            "Container for subscriber management";
          container uplanes {
            description
              "Container for uplanes";
            list uplane {
              description
                "List of uplane";
              key "uplane-id";
              leaf uplane-id {
                description
                  "user plane identification number";
                type uint32;
              }
              container infra {
                description
                  "Container for infra";
                container sdb {
                  description
                    "Container for sdb";
                  container statistics {
                    description
                      "Container for sdb";
                    container state {
                      description
                        "Container for state";
                      uses sdb-statistics-state-group;
                    }
                    container client-type {
                      description
                        "Container for client type";
                      uses sdb-statistics-client-group;
                    }
                  }
                }
              }
            }
          }
        }
      }
    }
  }

  uses bbe-smg-cpd-sdb-top;
}
